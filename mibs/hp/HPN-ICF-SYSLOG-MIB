-- ==========================================================================
-- Copyright (c) 2010-2014 Hewlett-Packard Development Company, L.P.
--
-- Description: Syslog MIB
-- Reference: RFC5424
-- Version: V1.5
-- History:
--   V1.0 Initial version 2005-08-20 by wangrui
--   V1.1 added hpnicfSyslogLoghostIpaddressPort by jinyi
--   V1.2 2010-06-09 added hpnicfSyslogLogGlobalLevel by haoyan
--                   added hpnicfSyslogLoghostTAddress by jinyi
--   V1.3 2012-06-06 added hpnicfSyslogLogbufContTable, hpnicfSyslogLogbufContEntry,
--                         hpnicfLogbufContIndex, hpnicfLogbufContDescription by jixugang
--   V1.4 2013-09-13 added hpnicfSyslogState2 by duyanbing
--   V1.5 2014-03-04 repalce hpnicfSyslogLogGlobalLevel by hpnicfSyslogLogGlobalLevelRfc by chengpengxing
-- ==========================================================================
HPN-ICF-SYSLOG-MIB DEFINITIONS ::= BEGIN

IMPORTS
    hpnicfCommon
        FROM HPN-ICF-OID-MIB
    DisplayString, TruthValue, RowStatus, TAddress, TEXTUAL-CONVENTION
        FROM SNMPv2-TC
    Integer32, Counter32, Unsigned32, OBJECT-TYPE, MODULE-IDENTITY
        FROM SNMPv2-SMI
    InetAddressType, InetAddress
        FROM INET-ADDRESS-MIB;

hpnicfSyslog MODULE-IDENTITY
    LAST-UPDATED "201006091050Z"
    ORGANIZATION
        ""
    CONTACT-INFO
        ""
    DESCRIPTION
        "All the configuration of the syslog can be managed
        by syslog Mib."
    REVISION "201006091050Z"
    DESCRIPTION
        "The initial revision of this MIB module."
     ::= { hpnicfCommon 63 }

--
-- Textual conventions
--

MessageLevelType ::= TEXTUAL-CONVENTION
    STATUS current
    DESCRIPTION
        "Specify severity level of message."
    SYNTAX INTEGER
        {
            emergency(1),
            alert(2),
            critical(3),
            error(4),
            warning(5),
            notice(6),
            informational(7),
            debug(8),
            invalid(9)
        }

TimeStampType ::= TEXTUAL-CONVENTION
    STATUS current
    DESCRIPTION
        "Specify operation types on time stamp of message.
        none: no time stamp information in message.
        date: the time stamp type of message is date.
        boot: the time stamp type of message is the time from
            uptime of system.
        dateWithoutYear: the time stamp type of message is date
            without year information."
    SYNTAX INTEGER
        {
            none(1),
            date(2),
            boot(3),
            dateWithoutYear(4)
        }

FacilityType ::= TEXTUAL-CONVENTION
    STATUS current
    DESCRIPTION
        "Specify loghost facility which generates messages."
    SYNTAX INTEGER
        {
            kernel(0),
            userLevel(1),
            mailSystem(2),
            systemDaemons(3),
            securityAuthorization(4),
            internallyMessages(5),
            linePrinter(6),
            networkNews(7),
            uucp(8),
            clockDaemon(9),
            securityAuthorization2(10),
            ftpDaemon(11),
            ntp(12),
            logAudit(13),
            logAlert(14),
            clockDaemon2(15),
            local0(16),
            local1(17),
            local2(18),
            local3(19),
            local4(20),
            local5(21),
            local6(22),
            local7(23)
        }

--
-- Node definitions
--

hpnicfSyslogObjects OBJECT IDENTIFIER ::= { hpnicfSyslog 1 }

hpnicfSyslogObject OBJECT IDENTIFIER ::= { hpnicfSyslogObjects 1 }

hpnicfSyslogState OBJECT-TYPE
    SYNTAX TruthValue
    MAX-ACCESS read-write
    STATUS current
    DESCRIPTION
        "The state of syslog: true(1):enable.
                              false(2):disable."
    ::= { hpnicfSyslogObject 1 }

hpnicfSyslogMaxLoghost OBJECT-TYPE
    SYNTAX Integer32
    MAX-ACCESS read-only
    STATUS current
    DESCRIPTION
        "The object shows the maximum number of rows in
         hpnicfLoghostTable."
    ::= { hpnicfSyslogObject 2 }

hpnicfSyslogMaxChannel OBJECT-TYPE
    SYNTAX Integer32
    MAX-ACCESS read-only
    STATUS current
    DESCRIPTION
        "The object shows the maximum number of channels in
         hpnicfSyslogChannelTable."
    ::= { hpnicfSyslogObject 3 }

hpnicfSyslogMaxLogbufferSize OBJECT-TYPE
    SYNTAX Integer32
    MAX-ACCESS read-only
    STATUS current
    DESCRIPTION
        "The maximum number of messages that can be stored
         in logbuffer."
    ::= { hpnicfSyslogObject 4 }

hpnicfSyslogMaxTrapbufferSize OBJECT-TYPE
    SYNTAX Integer32
    MAX-ACCESS read-only
    STATUS current
    DESCRIPTION
        "The maximum number of messages that can be stored
         in trapbuffer."
    ::= { hpnicfSyslogObject 5 }

hpnicfSyslogState2 OBJECT-TYPE
    SYNTAX INTEGER
        {
            off(0),
            on(1)
        }
    MAX-ACCESS read-write
    STATUS current
    DESCRIPTION
        "Status of syslog, on for enabled or off for disabled.
        This node differs from hpnicfSyslogState in value."
    ::= { hpnicfSyslogObject 6 }

hpnicfSyslogConsole OBJECT IDENTIFIER ::= { hpnicfSyslogObjects 2 }

hpnicfSyslogConsoleChannel OBJECT-TYPE
    SYNTAX Integer32
    MAX-ACCESS read-write
    STATUS current
    DESCRIPTION
        "The channel number of console."
    DEFVAL { 0 }
    ::= { hpnicfSyslogConsole 1 }

hpnicfSyslogMonitor OBJECT IDENTIFIER ::= { hpnicfSyslogObjects 3 }

hpnicfSyslogMonitorChannel OBJECT-TYPE
    SYNTAX Integer32
    MAX-ACCESS read-write
    STATUS current
    DESCRIPTION
        "The channel number of monitor."
    DEFVAL { 1 }
    ::= { hpnicfSyslogMonitor 1 }

hpnicfSyslogSnmp OBJECT IDENTIFIER ::= { hpnicfSyslogObjects 4 }

hpnicfSyslogSnmpChannel OBJECT-TYPE
    SYNTAX Integer32
    MAX-ACCESS read-write
    STATUS current
    DESCRIPTION
        "The channel number of snmp."
    DEFVAL { 5 }
    ::= { hpnicfSyslogSnmp 1 }

hpnicfSyslogLogbuffer OBJECT IDENTIFIER ::= { hpnicfSyslogObjects 5 }

hpnicfSyslogLogbufferChannel OBJECT-TYPE
    SYNTAX Integer32
    MAX-ACCESS read-write
    STATUS current
    DESCRIPTION
        "The channel number of logbuffer."
    DEFVAL { 4 }
    ::= { hpnicfSyslogLogbuffer 1 }

hpnicfSyslogLogbufferSize OBJECT-TYPE
    SYNTAX Integer32
    MAX-ACCESS read-write
    STATUS current
    DESCRIPTION
        "The capacity of logbuffer which can be customized by users.
         The valid range is from 0 to hpnicfSyslogMaxLogbufferSize."
    DEFVAL { 512 }
    ::= { hpnicfSyslogLogbuffer 2 }

hpnicfSyslogLogbufferTable OBJECT-TYPE
    SYNTAX SEQUENCE OF HpnicfSyslogLogbufferEntry
    MAX-ACCESS not-accessible
    STATUS current
    DESCRIPTION
        "The table of logbuffer."
    ::= { hpnicfSyslogLogbuffer 3 }

hpnicfSyslogLogbufferEntry OBJECT-TYPE
    SYNTAX HpnicfSyslogLogbufferEntry
    MAX-ACCESS not-accessible
    STATUS current
    DESCRIPTION
        "The logbuffer entry of syslog."
    INDEX { hpnicfLogbufferIndex }
    ::= { hpnicfSyslogLogbufferTable 1 }

HpnicfSyslogLogbufferEntry ::=
    SEQUENCE {
        hpnicfLogbufferIndex                    Integer32,
        hpnicfLogbufferCurrentMessages          Unsigned32,
        hpnicfLogbufferOverwrittenMessages      Counter32,
        hpnicfLogbufferDroppedMessages          Counter32
        }

hpnicfLogbufferIndex OBJECT-TYPE
    SYNTAX Integer32
    MAX-ACCESS not-accessible
    STATUS current
    DESCRIPTION
        "The index of this table."
    ::= { hpnicfSyslogLogbufferEntry 1 }

hpnicfLogbufferCurrentMessages OBJECT-TYPE
    SYNTAX Unsigned32
    MAX-ACCESS read-only
    STATUS current
    DESCRIPTION
        "The number of log messages stored in logbuffer."
    ::= { hpnicfSyslogLogbufferEntry 2 }

hpnicfLogbufferOverwrittenMessages OBJECT-TYPE
    SYNTAX Counter32
    MAX-ACCESS read-only
    STATUS current
    DESCRIPTION
        "The number of log messages overwritten in logbuffer."
    ::= { hpnicfSyslogLogbufferEntry 3 }

hpnicfLogbufferDroppedMessages OBJECT-TYPE
    SYNTAX Counter32
    MAX-ACCESS read-only
    STATUS current
    DESCRIPTION
        "The number of log messages dropped in logbuffer."
    ::= { hpnicfSyslogLogbufferEntry 4 }

hpnicfSyslogLogbufContTable OBJECT-TYPE
    SYNTAX SEQUENCE OF HpnicfSyslogLogbufContEntry
    MAX-ACCESS not-accessible
    STATUS current
    DESCRIPTION
        "The table of logbuffer contents."
    ::= { hpnicfSyslogLogbuffer 4 }

hpnicfSyslogLogbufContEntry OBJECT-TYPE
    SYNTAX HpnicfSyslogLogbufContEntry
    MAX-ACCESS not-accessible
    STATUS current
    DESCRIPTION
        "The contens entry of logbuffer."
    INDEX { hpnicfLogbufContIndex }
    ::= { hpnicfSyslogLogbufContTable 1 }

HpnicfSyslogLogbufContEntry ::=
    SEQUENCE {
        hpnicfLogbufContIndex            Integer32,
        hpnicfLogbufContDescription      DisplayString
        }

hpnicfLogbufContIndex OBJECT-TYPE
    SYNTAX Integer32 (1..2147483647)
    MAX-ACCESS not-accessible
    STATUS current
    DESCRIPTION
        "The index of this table."
    ::= { hpnicfSyslogLogbufContEntry 1 }

hpnicfLogbufContDescription OBJECT-TYPE
    SYNTAX DisplayString (SIZE (0..1600))
    MAX-ACCESS read-only
    STATUS current
    DESCRIPTION
        "The contents of logbuffer."
    ::= { hpnicfSyslogLogbufContEntry 2 }

hpnicfSyslogTrapbuffer OBJECT IDENTIFIER ::= { hpnicfSyslogObjects 6 }

hpnicfSyslogTrapbufferChannel OBJECT-TYPE
    SYNTAX Integer32
    MAX-ACCESS read-write
    STATUS current
    DESCRIPTION
        "The channel number of trapbuffer."
    DEFVAL { 3 }
    ::= { hpnicfSyslogTrapbuffer 1 }

hpnicfSyslogTrapbufferSize OBJECT-TYPE
    SYNTAX Integer32
    MAX-ACCESS read-write
    STATUS current
    DESCRIPTION
        "The capacity of the trapbuffer which can be customized by users.
         The valid range is from 0 to hpnicfSyslogMaxTrapbufferSize."
    DEFVAL { 256 }
    ::= { hpnicfSyslogTrapbuffer 2 }

hpnicfSyslogTrapbufferTable OBJECT-TYPE
    SYNTAX SEQUENCE OF HpnicfSyslogTrapbufferEntry
    MAX-ACCESS not-accessible
    STATUS current
    DESCRIPTION
        "The table of trapbuffer."
    ::= { hpnicfSyslogTrapbuffer 3 }

hpnicfSyslogTrapbufferEntry OBJECT-TYPE
    SYNTAX HpnicfSyslogTrapbufferEntry
    MAX-ACCESS not-accessible
    STATUS current
    DESCRIPTION
        "The trapbuffer entry of syslog."
    INDEX { hpnicfTrapbufferIndex }
    ::= { hpnicfSyslogTrapbufferTable 1 }

HpnicfSyslogTrapbufferEntry ::=
    SEQUENCE {
        hpnicfTrapbufferIndex                      Integer32,
        hpnicfTrapbufferCurrentMessages            Unsigned32,
        hpnicfTrapbufferOverwrittenMessages        Counter32,
        hpnicfTrapbufferDroppedMessages            Counter32
        }

hpnicfTrapbufferIndex OBJECT-TYPE
    SYNTAX Integer32
    MAX-ACCESS not-accessible
    STATUS current
    DESCRIPTION
        "The index of this table."
    ::= { hpnicfSyslogTrapbufferEntry 1 }

hpnicfTrapbufferCurrentMessages OBJECT-TYPE
    SYNTAX Unsigned32
    MAX-ACCESS read-only
    STATUS current
    DESCRIPTION
        "The number of trap messages stored in trapbuffer."
    ::= { hpnicfSyslogTrapbufferEntry 2 }

hpnicfTrapbufferOverwrittenMessages OBJECT-TYPE
    SYNTAX Counter32
    MAX-ACCESS read-only
    STATUS current
    DESCRIPTION
        "The number of trap messages overwritten in trapbuffer."
    ::= { hpnicfSyslogTrapbufferEntry 3 }

hpnicfTrapbufferDroppedMessages OBJECT-TYPE
    SYNTAX Counter32
    MAX-ACCESS read-only
    STATUS current
    DESCRIPTION
        "The number of trap messages dropped in trapbuffer."
    ::= { hpnicfSyslogTrapbufferEntry 4 }

hpnicfSyslogLoghost OBJECT IDENTIFIER ::= { hpnicfSyslogObjects 7 }

hpnicfSyslogLoghostSourceInterface OBJECT-TYPE
    SYNTAX Integer32
    MAX-ACCESS read-write
    STATUS current
    DESCRIPTION
        "The source interface which sends message to loghost.
         All loghosts use the same source interface."
    ::= { hpnicfSyslogLoghost 1 }

hpnicfSyslogLoghostTimestampType OBJECT-TYPE
    SYNTAX TimeStampType
    MAX-ACCESS read-write
    STATUS current
    DESCRIPTION
        "Time stamp type of message sent to loghost."
    DEFVAL { date }
    ::= { hpnicfSyslogLoghost 2 }

hpnicfSyslogLoghostTable OBJECT-TYPE
    SYNTAX SEQUENCE OF HpnicfSyslogLoghostEntry
    MAX-ACCESS not-accessible
    STATUS current
    DESCRIPTION
        "The table of loghost."
    ::= { hpnicfSyslogLoghost 3 }

hpnicfSyslogLoghostEntry OBJECT-TYPE
    SYNTAX HpnicfSyslogLoghostEntry
    MAX-ACCESS not-accessible
    STATUS current
    DESCRIPTION
        "The loghost entry of syslog."
    INDEX { hpnicfSyslogLoghostIndex }
    ::= { hpnicfSyslogLoghostTable 1 }

HpnicfSyslogLoghostEntry ::=
    SEQUENCE {
        hpnicfSyslogLoghostIndex                   Integer32,
        hpnicfSyslogLoghostChannel                 Integer32,
        hpnicfSyslogLoghostIpaddressType           InetAddressType,
        hpnicfSyslogLoghostIpaddress               InetAddress,
        hpnicfSyslogLoghostFacility                FacilityType,
        hpnicfSyslogLoghostLanguage                INTEGER,
        hpnicfSyslogLoghostOperateRowStatus        RowStatus,
        hpnicfSyslogLoghostIpaddressPort           Integer32,
        hpnicfSyslogLoghostTAddress                TAddress
    }

hpnicfSyslogLoghostIndex OBJECT-TYPE
    SYNTAX Integer32(1..64)
    MAX-ACCESS not-accessible
    STATUS current
    DESCRIPTION
        "The index of this table."
    ::= { hpnicfSyslogLoghostEntry 1 }

hpnicfSyslogLoghostChannel OBJECT-TYPE
    SYNTAX Integer32
    MAX-ACCESS read-create
    STATUS current
    DESCRIPTION
        "The channel number of loghost."
    DEFVAL { 2 }
    ::= { hpnicfSyslogLoghostEntry 2 }

hpnicfSyslogLoghostIpaddressType OBJECT-TYPE
    SYNTAX InetAddressType
    MAX-ACCESS read-create
    STATUS current
    DESCRIPTION
        "The ip address type of loghost."
    DEFVAL { ipv4 }
    ::= { hpnicfSyslogLoghostEntry 3 }

hpnicfSyslogLoghostIpaddress OBJECT-TYPE
    SYNTAX InetAddress
    MAX-ACCESS read-create
    STATUS current
    DESCRIPTION
        "The ip address of loghost."
    ::= { hpnicfSyslogLoghostEntry 4 }

hpnicfSyslogLoghostFacility OBJECT-TYPE
    SYNTAX FacilityType
    MAX-ACCESS read-create
    STATUS current
    DESCRIPTION
        "The operations staff can selectively filter the messages
         with priority which consists of facility that generates
         the message and severity of the message.
         "
    DEFVAL { local7 }
    ::= { hpnicfSyslogLoghostEntry 5 }

hpnicfSyslogLoghostLanguage OBJECT-TYPE
    SYNTAX INTEGER {
        chinese(1),
        english(2)
        }
    MAX-ACCESS read-create
    STATUS current
    DESCRIPTION
        "The language of the message sent to the loghost."
    DEFVAL { english }
    ::= { hpnicfSyslogLoghostEntry 6 }

hpnicfSyslogLoghostOperateRowStatus OBJECT-TYPE
    SYNTAX RowStatus
    MAX-ACCESS read-create
    STATUS current
    DESCRIPTION
        "The status of this table entry."
    ::= { hpnicfSyslogLoghostEntry 7 }

hpnicfSyslogLoghostIpaddressPort OBJECT-TYPE
    SYNTAX Integer32(1..65535)
    MAX-ACCESS read-create
    STATUS current
    DESCRIPTION
        "The loghost server port."
    DEFVAL { 514 }
    ::= { hpnicfSyslogLoghostEntry 8 }

hpnicfSyslogLoghostTAddress OBJECT-TYPE
    SYNTAX TAddress
    MAX-ACCESS read-create
    STATUS current
    DESCRIPTION
        "The loghost server transport address."
    ::= { hpnicfSyslogLoghostEntry 9 }

hpnicfSyslogChannel OBJECT IDENTIFIER ::= { hpnicfSyslogObjects 8 }

hpnicfSyslogChannelTable OBJECT-TYPE
    SYNTAX SEQUENCE OF HpnicfSyslogChannelEntry
    MAX-ACCESS not-accessible
    STATUS current
    DESCRIPTION
        "A table of syslog channel."
    ::= { hpnicfSyslogChannel 1 }

hpnicfSyslogChannelEntry OBJECT-TYPE
    SYNTAX HpnicfSyslogChannelEntry
    MAX-ACCESS not-accessible
    STATUS current
    DESCRIPTION
        "The channel entry of syslog."
    INDEX { hpnicfSyslogChannelIndex }
    ::= { hpnicfSyslogChannelTable 1 }

HpnicfSyslogChannelEntry ::=
    SEQUENCE {
        hpnicfSyslogChannelIndex       Integer32,
        hpnicfSyslogChannelName        DisplayString
        }

hpnicfSyslogChannelIndex OBJECT-TYPE
    SYNTAX Integer32
    MAX-ACCESS not-accessible
    STATUS current
    DESCRIPTION
        "The index of this table."
    ::= { hpnicfSyslogChannelEntry 1 }

hpnicfSyslogChannelName OBJECT-TYPE
    SYNTAX DisplayString (SIZE (1..30))
    MAX-ACCESS read-write
    STATUS current
    DESCRIPTION
        "The name of channel.
         The channel name must be different from each other."
    ::= { hpnicfSyslogChannelEntry 2 }

hpnicfSyslogModule OBJECT IDENTIFIER ::= { hpnicfSyslogObjects 9 }

hpnicfSyslogModuleTable OBJECT-TYPE
    SYNTAX SEQUENCE OF HpnicfSyslogModuleEntry
    MAX-ACCESS not-accessible
    STATUS current
    DESCRIPTION
        "A table of syslog module."
    ::= { hpnicfSyslogModule 1 }

hpnicfSyslogModuleEntry OBJECT-TYPE
    SYNTAX HpnicfSyslogModuleEntry
    MAX-ACCESS not-accessible
    STATUS current
    DESCRIPTION
        "The module entry of syslog."
    INDEX { hpnicfSyslogModuleIndex }
    ::= { hpnicfSyslogModuleTable 1 }

HpnicfSyslogModuleEntry ::=
    SEQUENCE {
        hpnicfSyslogModuleIndex        Integer32,
        hpnicfSyslogModuleName         DisplayString
        }

hpnicfSyslogModuleIndex OBJECT-TYPE
    SYNTAX Integer32
    MAX-ACCESS not-accessible
    STATUS current
    DESCRIPTION
        "The index of this table."
    ::= { hpnicfSyslogModuleEntry 1 }

hpnicfSyslogModuleName OBJECT-TYPE
    SYNTAX DisplayString (SIZE (1..20))
    MAX-ACCESS read-only
    STATUS current
    DESCRIPTION
        "The name of module."
    ::= { hpnicfSyslogModuleEntry 2 }

hpnicfSyslogLog OBJECT IDENTIFIER ::= { hpnicfSyslogObjects 10 }

hpnicfSyslogLogTimestampType OBJECT-TYPE
    SYNTAX TimeStampType
    MAX-ACCESS read-write
    STATUS current
    DESCRIPTION
        "Time stamp type of log message."
    DEFVAL { date }
    ::= { hpnicfSyslogLog 1 }

hpnicfSyslogLogTable OBJECT-TYPE
    SYNTAX SEQUENCE OF HpnicfSyslogLogEntry
    MAX-ACCESS not-accessible
    STATUS current
    DESCRIPTION
        "A table of syslog module."
    ::= { hpnicfSyslogLog 2 }

hpnicfSyslogLogEntry OBJECT-TYPE
    SYNTAX HpnicfSyslogLogEntry
    MAX-ACCESS not-accessible
    STATUS current
    DESCRIPTION
        "The log entry of syslog."
    INDEX { hpnicfSyslogChannelIndex,
            hpnicfSyslogModuleIndex
          }
    ::= { hpnicfSyslogLogTable 1 }

HpnicfSyslogLogEntry ::=
    SEQUENCE {
        hpnicfSyslogLogState           TruthValue,
        hpnicfSyslogLogLevel           MessageLevelType,
        hpnicfSyslogLogRowStatus       RowStatus
        }

hpnicfSyslogLogState OBJECT-TYPE
    SYNTAX TruthValue
    MAX-ACCESS read-create
    STATUS current
    DESCRIPTION
        "The switch state of log."
    ::= { hpnicfSyslogLogEntry 1 }

hpnicfSyslogLogLevel OBJECT-TYPE
    SYNTAX MessageLevelType
    MAX-ACCESS read-create
    STATUS current
    DESCRIPTION
        "The level of log message."
    ::= { hpnicfSyslogLogEntry 2 }

hpnicfSyslogLogRowStatus OBJECT-TYPE
    SYNTAX RowStatus
    MAX-ACCESS read-create
    STATUS current
    DESCRIPTION
        "The status of this table entry."
    ::= { hpnicfSyslogLogEntry 3 }

hpnicfSyslogLogGlobalLevel OBJECT-TYPE
    SYNTAX MessageLevelType
    MAX-ACCESS read-write
    STATUS obsolete
    DESCRIPTION
        "The global level of log message.  This object is replaced by
        hpnicfSyslogLogGlobalLevelRfc because its value does not accord
        with RFC5424."
    ::= { hpnicfSyslogLog 3 }

hpnicfSyslogLogGlobalLevelRfc OBJECT-TYPE
    SYNTAX INTEGER {
        emergency(0),
        alert(1),
        critical(2),
        error(3),
        warning(4),
        notice(5),
        informational(6),
        debug(7)
        }
    MAX-ACCESS read-write
    STATUS current
    DESCRIPTION
        "The global level of log message.  This object replaces
        hpnicfSyslogLogGlobalLevel because it observes the terms of RFC5424."
    ::= { hpnicfSyslogLog 4 }

hpnicfSyslogTrap OBJECT IDENTIFIER ::= { hpnicfSyslogObjects 11 }

hpnicfSyslogTrapTimestampType OBJECT-TYPE
    SYNTAX TimeStampType
    MAX-ACCESS read-write
    STATUS current
    DESCRIPTION
        "Time stamp type of trap message."
    DEFVAL { date }
    ::= { hpnicfSyslogTrap 1 }

hpnicfSyslogTrapTable OBJECT-TYPE
    SYNTAX SEQUENCE OF HpnicfSyslogTrapEntry
    MAX-ACCESS not-accessible
    STATUS current
    DESCRIPTION
        "A table of syslog module."
    ::= { hpnicfSyslogTrap 2 }

hpnicfSyslogTrapEntry OBJECT-TYPE
    SYNTAX HpnicfSyslogTrapEntry
    MAX-ACCESS not-accessible
    STATUS current
    DESCRIPTION
        "The trap entry of syslog."
    INDEX { hpnicfSyslogChannelIndex,
            hpnicfSyslogModuleIndex
          }
    ::= { hpnicfSyslogTrapTable 1 }

HpnicfSyslogTrapEntry ::=
    SEQUENCE {
        hpnicfSyslogTrapState              TruthValue,
        hpnicfSyslogTrapLevel              MessageLevelType,
        hpnicfSyslogTrapRowStatus          RowStatus
        }

hpnicfSyslogTrapState OBJECT-TYPE
    SYNTAX TruthValue
    MAX-ACCESS read-create
    STATUS current
    DESCRIPTION
        "The switch state of trap."
    ::= { hpnicfSyslogTrapEntry 1 }

hpnicfSyslogTrapLevel OBJECT-TYPE
    SYNTAX MessageLevelType
    MAX-ACCESS read-create
    STATUS current
    DESCRIPTION
        "The level of trap message."
    ::= { hpnicfSyslogTrapEntry 2 }

hpnicfSyslogTrapRowStatus OBJECT-TYPE
    SYNTAX RowStatus
    MAX-ACCESS read-create
    STATUS current
    DESCRIPTION
        "The status of this table entry."
    ::= { hpnicfSyslogTrapEntry 3 }

hpnicfSyslogDebug OBJECT IDENTIFIER ::= { hpnicfSyslogObjects 12 }

hpnicfSyslogDebugTimestampType OBJECT-TYPE
    SYNTAX TimeStampType
    MAX-ACCESS read-write
    STATUS current
    DESCRIPTION
        "Time stamp type of debug message."
    DEFVAL { boot }
    ::= { hpnicfSyslogDebug 1 }

hpnicfSyslogDebugTable OBJECT-TYPE
    SYNTAX SEQUENCE OF HpnicfSyslogDebugEntry
    MAX-ACCESS not-accessible
    STATUS current
    DESCRIPTION
        "A table of syslog module."
    ::= { hpnicfSyslogDebug 2 }

hpnicfSyslogDebugEntry OBJECT-TYPE
    SYNTAX HpnicfSyslogDebugEntry
    MAX-ACCESS not-accessible
    STATUS current
    DESCRIPTION
        "The debug entry of syslog."
    INDEX { hpnicfSyslogChannelIndex,
            hpnicfSyslogModuleIndex
          }
    ::= { hpnicfSyslogDebugTable 1 }

HpnicfSyslogDebugEntry ::=
    SEQUENCE {
        hpnicfSyslogDebugState             TruthValue,
        hpnicfSyslogDebugLevel             MessageLevelType,
        hpnicfSyslogDebugRowStatus         RowStatus
        }

hpnicfSyslogDebugState OBJECT-TYPE
    SYNTAX TruthValue
    MAX-ACCESS read-create
    STATUS current
    DESCRIPTION
        "The switch state of debug."
    ::= { hpnicfSyslogDebugEntry 1 }

hpnicfSyslogDebugLevel OBJECT-TYPE
    SYNTAX MessageLevelType
    MAX-ACCESS read-create
    STATUS current
    DESCRIPTION
        "The level of debug message."
    ::= { hpnicfSyslogDebugEntry 2 }

hpnicfSyslogDebugRowStatus OBJECT-TYPE
    SYNTAX RowStatus
    MAX-ACCESS read-create
    STATUS current
    DESCRIPTION
        "The status of this table entry."
    ::= { hpnicfSyslogDebugEntry 3 }

END
