-- =====================================================================
-- Copyright (c) 2010-2013 Hewlett-Packard Development Company, L.P.
--
-- Description: Timerange MIB Definition
-- Reference:
-- Version: V1.1
-- History:
-- V1.0 xujunjie,2012-05-14,Initial Version.
-- V1.1 modified by MouXuanli
--     Change name "trng" to "trange".
-- =====================================================================
HPN-ICF-TRNG2-MIB DEFINITIONS ::= BEGIN
IMPORTS
    hpnicfCommon
        FROM HPN-ICF-OID-MIB
    Integer32, OBJECT-TYPE, MODULE-IDENTITY
        FROM SNMPv2-SMI
    TruthValue, DateAndTime, RowStatus
        FROM SNMPv2-TC;

hpnicfTRNG2 MODULE-IDENTITY
    LAST-UPDATED "201303080000Z"        -- Mar 8, 2013 at 00:00 GMT
    ORGANIZATION
        ""
    CONTACT-INFO
        ""
    DESCRIPTION
        "The HPN-ICF-TRNG2-MIB contains objects to
        Configure the system absolute and periodic time-range."
    REVISION "201303080000Z"        -- Mar 8, 2013 at 00:00 GMT
    DESCRIPTION
        "Modified to change node name from 'trng' to 'trange'."
    REVISION "201205140000Z"        -- May 14, 2012 at 00:00 GMT
    DESCRIPTION
        "201205140000Z, --The initial revision of this MIB module."
    ::= { hpnicfCommon 121 }

--
-- Node definitions
--

hpnicfTRNG2MibObjects OBJECT IDENTIFIER ::= { hpnicfTRNG2 1 }

-- hpnicfTrangeCreateTimerangeTable

hpnicfTrangeCreateTimerangeTable OBJECT-TYPE
    SYNTAX SEQUENCE OF HpnicfTrangeCreateTimerangeEntry
    MAX-ACCESS not-accessible
    STATUS current
    DESCRIPTION
        "Creat TimeRange."
    ::= { hpnicfTRNG2MibObjects 1 }

hpnicfTrangeCreateTimerangeEntry OBJECT-TYPE
    SYNTAX HpnicfTrangeCreateTimerangeEntry
    MAX-ACCESS not-accessible
    STATUS current
    DESCRIPTION
        "Define the entry of hpnicfTrangeCreateTimerangeTable"
    INDEX { hpnicfTrangeIndex }
    ::= { hpnicfTrangeCreateTimerangeTable 1 }

HpnicfTrangeCreateTimerangeEntry ::=
    SEQUENCE {
        hpnicfTrangeIndex
            Integer32,
        hpnicfTrangeName
            OCTET STRING,
        hpnicfTrangeValidFlag
            TruthValue,
        hpnicfTrangeCreateRowStatus
            RowStatus
     }

hpnicfTrangeIndex OBJECT-TYPE
    SYNTAX Integer32 (0..2147483647)
    MAX-ACCESS not-accessible
    STATUS current
    DESCRIPTION
        "TimeRange's index"
    ::= { hpnicfTrangeCreateTimerangeEntry 1 }

hpnicfTrangeName OBJECT-TYPE
    SYNTAX OCTET STRING (SIZE (1..32))
    MAX-ACCESS read-create
    STATUS current
    DESCRIPTION
        "TimeRange's name"
    ::= { hpnicfTrangeCreateTimerangeEntry 2 }

hpnicfTrangeValidFlag OBJECT-TYPE
    SYNTAX TruthValue
    MAX-ACCESS read-only
    STATUS current
    DESCRIPTION
        "Valid or Invalid flag"
    ::= { hpnicfTrangeCreateTimerangeEntry 3 }

hpnicfTrangeCreateRowStatus OBJECT-TYPE
    SYNTAX RowStatus
    MAX-ACCESS read-create
    STATUS current
    DESCRIPTION
        "The status of this conceptual row.Now only realize CreateAndGo and Destroy and Active."
    ::= { hpnicfTrangeCreateTimerangeEntry 4 }

-- hpnicfTrangeAbsoluteTable

hpnicfTrangeAbsoluteTable OBJECT-TYPE
    SYNTAX SEQUENCE OF HpnicfTrangeAbsoluteEntry
    MAX-ACCESS not-accessible
    STATUS current
    DESCRIPTION
        "Creat absoluteness time item of the TimeRange"
    ::= { hpnicfTRNG2MibObjects 2 }

hpnicfTrangeAbsoluteEntry OBJECT-TYPE
    SYNTAX HpnicfTrangeAbsoluteEntry
    MAX-ACCESS not-accessible
    STATUS current
    DESCRIPTION
        "Define the entry of hpnicfTrangeAbsoluteTable"
    INDEX { hpnicfTrangeAbsoluteNameIndex, hpnicfTrangeAbsoluteSubIndex }
    ::= { hpnicfTrangeAbsoluteTable 1 }

HpnicfTrangeAbsoluteEntry ::=
    SEQUENCE {
        hpnicfTrangeAbsoluteNameIndex
            Integer32,
        hpnicfTrangeAbsoluteSubIndex
            Integer32,
        hpnicfTrangeAbsoluteStartTime
            DateAndTime,
        hpnicfTrangeAbsoluteEndTime
            DateAndTime,
        hpnicfTrangeAbsolueRowStatus
            RowStatus
     }

hpnicfTrangeAbsoluteNameIndex OBJECT-TYPE
    SYNTAX Integer32 (0..2147483647)
    MAX-ACCESS not-accessible
    STATUS current
    DESCRIPTION
        "TimeRange's index"
    ::= { hpnicfTrangeAbsoluteEntry 1 }

hpnicfTrangeAbsoluteSubIndex OBJECT-TYPE
    SYNTAX Integer32 (1..12)
    MAX-ACCESS not-accessible
    STATUS current
    DESCRIPTION
        "SubItem's index"
    ::= { hpnicfTrangeAbsoluteEntry 2 }

hpnicfTrangeAbsoluteStartTime OBJECT-TYPE
    SYNTAX DateAndTime
    MAX-ACCESS read-create
    STATUS current
    DESCRIPTION
        "Start point of the timerange.The format defined like 'YYYY-MM-DD,hh:mm:0.0'."
    ::= { hpnicfTrangeAbsoluteEntry 3 }

hpnicfTrangeAbsoluteEndTime OBJECT-TYPE
    SYNTAX DateAndTime
    MAX-ACCESS read-create
    STATUS current
    DESCRIPTION
        "End point of the timerange.The format defined like 'YYYY-MM-DD,hh:mm:0.0'."
    ::= { hpnicfTrangeAbsoluteEntry 4 }

hpnicfTrangeAbsolueRowStatus OBJECT-TYPE
    SYNTAX RowStatus
    MAX-ACCESS read-create
    STATUS current
    DESCRIPTION
        "The status of this conceptual row. Now only realize CreateAndGo and Destroy and Active."
    ::= { hpnicfTrangeAbsoluteEntry 5 }

-- hpnicfTrangePeriodicTable

hpnicfTrangePeriodicTable OBJECT-TYPE
    SYNTAX SEQUENCE OF HpnicfTrangePeriodicEntry
    MAX-ACCESS not-accessible
    STATUS current
    DESCRIPTION
        "Creat periodic time item of the TimeRange"
    ::= { hpnicfTRNG2MibObjects 3 }

hpnicfTrangePeriodicEntry OBJECT-TYPE
    SYNTAX HpnicfTrangePeriodicEntry
    MAX-ACCESS not-accessible
    STATUS current
    DESCRIPTION
        "Define the index of hpnicfTrangePeriodicTable"
    INDEX { hpnicfTrangePeriodicNameIndex, hpnicfTrangePeriodicSubIndex }
    ::= { hpnicfTrangePeriodicTable 1 }

HpnicfTrangePeriodicEntry ::=
    SEQUENCE {
        hpnicfTrangePeriodicNameIndex
            Integer32,
        hpnicfTrangePeriodicSubIndex
            Integer32,
        hpnicfTrangePeriodicDayOfWeek
            BITS,
        hpnicfTrangePeriodicStartTime
            DateAndTime,
        hpnicfTrangePeriodicEndTime
            DateAndTime,
        hpnicfTrangePeriodicRowStatus
            RowStatus
     }

hpnicfTrangePeriodicNameIndex OBJECT-TYPE
    SYNTAX Integer32 (0..2147483647)
    MAX-ACCESS not-accessible
    STATUS current
    DESCRIPTION
        "TimeRange's index"
    ::= { hpnicfTrangePeriodicEntry 1 }

hpnicfTrangePeriodicSubIndex OBJECT-TYPE
    SYNTAX Integer32 (1..32)
    MAX-ACCESS not-accessible
    STATUS current
    DESCRIPTION
        "SubItem's index"
    ::= { hpnicfTrangePeriodicEntry 2 }

hpnicfTrangePeriodicDayOfWeek OBJECT-TYPE
    SYNTAX BITS {
                    sunday(0),
                    monday(1),
                    tuesday(2),
                    wednesday(3),
                    thursday(4),
                    friday(5),
                    saturday(6)
                }
    MAX-ACCESS read-create
    STATUS current
    DESCRIPTION
        "The day of week. This is a bit-map of possible conditions.
        The various bit positions are:
        |0        |sunday                 |
        |1        |monday                 |
        |2        |tuesday                |
        |3        |wednesday              |
        |4        |thursday               |
        |5        |friday                 |
        |6        |saturday               |
        "
    ::= { hpnicfTrangePeriodicEntry 3 }

hpnicfTrangePeriodicStartTime OBJECT-TYPE
    SYNTAX DateAndTime
    MAX-ACCESS read-create
    STATUS current
    DESCRIPTION
        "Start point of this timerange,The format defined like 'hh:mm:0,0'."
    ::= { hpnicfTrangePeriodicEntry 4 }

hpnicfTrangePeriodicEndTime OBJECT-TYPE
    SYNTAX DateAndTime
    MAX-ACCESS read-create
    STATUS current
    DESCRIPTION
        "End point of this timerange. The format definedlike 'hh:mm:0,0'."
    ::= { hpnicfTrangePeriodicEntry 5 }

hpnicfTrangePeriodicRowStatus OBJECT-TYPE
    SYNTAX RowStatus
    MAX-ACCESS read-create
    STATUS current
    DESCRIPTION
        "The status of this conceptual row, Now only realize CreateAndGo and Destroy and Active."
    ::= { hpnicfTrangePeriodicEntry 6 }

END
