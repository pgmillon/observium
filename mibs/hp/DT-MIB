DT-MIB DEFINITIONS ::= BEGIN
    IMPORTS
     MODULE-IDENTITY, OBJECT-TYPE, Integer32, Counter32
            FROM SNMPv2-SMI
     DisplayString, MacAddress
            FROM SNMPv2-TC
     MODULE-COMPLIANCE, OBJECT-GROUP
            FROM SNMPv2-CONF 
     hpSwitch
            FROM HP-ICF-OID
     InetAddressType, InetAddress, InetPortNumber
            FROM INET-ADDRESS-MIB;
 
     hpSwitchDt  MODULE-IDENTITY

           LAST-UPDATED "201205221800Z"  -- May 22, 2012
           ORGANIZATION "HP Networking"
           CONTACT-INFO "Hewlett Packard Company
                         8000 Foothills Blvd.
                         Roseville, CA 95747"
           
           DESCRIPTION "This MIB module contains HP proprietary
                        Distributed Trunking(DT) MIB."
	   REVISION    "201205221800Z"    -- May 22, 2012
           DESCRIPTION "Added new object hpSwitchDtSystemInfo"

           REVISION    "201108090000Z"   -- Aug 9, 2011       
           DESCRIPTION "Added hpSwitchDtConfiguration,
                        hpSwitchDtPeerKeepAliveConfig,
                        hpSwitchDtIscProtocolStats,
                        hpSwitchDtPeerKeepAliveStats."

           REVISION    "201103221800Z"
           DESCRIPTION "Added new MIB objects
                        hpSwitchDtLacpLocalIfLacpAdminKey
                        hpSwitchDtLacpLocalIfLacpOperKey."

           REVISION    "200710271800Z" 
           DESCRIPTION "Initial revision." ::= { hpSwitchConfig 27 } 

    hpSwitchISCPortIndex  OBJECT-TYPE
           SYNTAX       Integer32 (0..65535)
           MAX-ACCESS   read-write
           STATUS       current 
           DESCRIPTION 
                   "The ifIndex value of Inter Switch Connection (ISC) 
                    port. The default value is 0, which means there 
                    is no ISC port configured."
           ::= { hpSwitchDt 1}
           
    hpSwitchRemoteISCPortIndex  OBJECT-TYPE
          SYNTAX        Integer32 (0..65535) 
          MAX-ACCESS    read-only
          STATUS        current 
          DESCRIPTION
                  "The logical port value of remote switch Inter Switch 
                   Connection Port. The default value is 0, which means
                   there is no ISC port configured."
          ::= { hpSwitchDt 2}

--  Icf Switch Specific 
    hpConfig      OBJECT IDENTIFIER ::= { hpSwitch 7 }

    hpSwitchConfig   OBJECT IDENTIFIER ::= { hpConfig 1 }

    hpSwitchDtLacpStatus    OBJECT IDENTIFIER ::= { hpSwitchDt 3}

--
-- The DT LACP Local table
--

    hpSwitchDtLacpStatusLocalTable OBJECT-TYPE
          SYNTAX        SEQUENCE OF HpSwitchDtLacpStatusLocalEntry
          MAX-ACCESS    not-accessible
          STATUS        current 
          DESCRIPTION 
                  "This table holds the lacp status information of all 
                   ports that are members of trunks configured as type 
		   'dt-lacp'."
          ::= { hpSwitchDtLacpStatus 1 }
            
    hpSwitchDtLacpStatusLocalEntry  OBJECT-TYPE
          SYNTAX        HpSwitchDtLacpStatusLocalEntry
          MAX-ACCESS    not-accessible
          STATUS        current
          DESCRIPTION
                  "The lacp status information of each local port that is
                   part of a trunk configured as type 'dt-lacp'."
          INDEX { hpSwitchDtLacpLocalIfIndex }
          ::= {  hpSwitchDtLacpStatusLocalTable 1}      

    HpSwitchDtLacpStatusLocalEntry ::= 
          SEQUENCE {
          hpSwitchDtLacpLocalIfIndex            Integer32, 
          hpSwitchDtLacpLocalIfName             DisplayString,
          hpSwitchDtLacpLocalIfLacpEnable       Integer32,
          hpSwitchDtLacpLocalIfTrunkGroup       Integer32,
          hpSwitchDtLacpLocalIfLacpPortStatus   Integer32,
          hpSwitchDtLacpLocalIfLacpPartner      Integer32,
          hpSwitchDtLacpLocalIfLacpStatus       Integer32,
          hpSwitchDtLacpLocalIfLacpAdminKey     Integer32,
          hpSwitchDtLacpLocalIfLacpOperKey      Integer32

         }  
	
    hpSwitchDtLacpLocalIfIndex OBJECT-TYPE
          SYNTAX        Integer32 (0..65535)
          MAX-ACCESS    read-only 
          STATUS        current
          DESCRIPTION
                  "The ifIndex value of the local interface."
          ::= { hpSwitchDtLacpStatusLocalEntry 1 }
    
    hpSwitchDtLacpLocalIfName OBJECT-TYPE
          SYNTAX        DisplayString
          MAX-ACCESS    read-only
          STATUS        current
          DESCRIPTION
                  "The ifName value of the local interface."
          ::= { hpSwitchDtLacpStatusLocalEntry 2 }
    
    hpSwitchDtLacpLocalIfLacpEnable OBJECT-TYPE
          SYNTAX        Integer32
          MAX-ACCESS    read-only
          STATUS        current
          DESCRIPTION
                  "The lacp configuration for the local interface."
          ::= { hpSwitchDtLacpStatusLocalEntry 3 }
    
    hpSwitchDtLacpLocalIfTrunkGroup OBJECT-TYPE
          SYNTAX        Integer32
          MAX-ACCESS    read-only
          STATUS        current
          DESCRIPTION
                  "The trunk group information of the local interface."
          ::= { hpSwitchDtLacpStatusLocalEntry 4 }    
    
    hpSwitchDtLacpLocalIfLacpPortStatus OBJECT-TYPE
          SYNTAX        Integer32
          MAX-ACCESS    read-only
          STATUS        current
          DESCRIPTION
                  "The lacp port status information of the local 
                   interface."
          ::= { hpSwitchDtLacpStatusLocalEntry 5 }        
    
    hpSwitchDtLacpLocalIfLacpPartner OBJECT-TYPE
          SYNTAX        Integer32
          MAX-ACCESS    read-only
          STATUS        current
          DESCRIPTION
                  "The lacp partner information of the local 
                   interface."
          ::= { hpSwitchDtLacpStatusLocalEntry 6 }           
    
     hpSwitchDtLacpLocalIfLacpStatus OBJECT-TYPE
          SYNTAX        Integer32
          MAX-ACCESS    read-only
          STATUS        current
          DESCRIPTION
                  "The lacp status information of the local
                   interface."
          ::= { hpSwitchDtLacpStatusLocalEntry 7 }     

    hpSwitchDtLacpLocalIfLacpAdminKey OBJECT-TYPE
          SYNTAX        Integer32
          MAX-ACCESS    read-only
          STATUS        current
          DESCRIPTION
                  "The lacp admin key information of the local 
                   interface."
          ::= { hpSwitchDtLacpStatusLocalEntry 8 }

    hpSwitchDtLacpLocalIfLacpOperKey OBJECT-TYPE
          SYNTAX        Integer32
          MAX-ACCESS    read-only
          STATUS        current
          DESCRIPTION
                  "The lacp operational key information of the local
                   interface."
          ::= { hpSwitchDtLacpStatusLocalEntry 9 }

--
-- The DT LACP Peer table
--    
    
    hpSwitchDtLacpStatusPeerTable OBJECT-TYPE
          SYNTAX        SEQUENCE OF HpSwitchDtLacpStatusPeerEntry
          MAX-ACCESS    not-accessible
          STATUS        current
          DESCRIPTION 
                  "This table holds the lacp status information of 
                   all ports that are members of trunks configured
                   as type 'dt-lacp'."
          ::= { hpSwitchDtLacpStatus 2 }
    
    hpSwitchDtLacpStatusPeerEntry  OBJECT-TYPE
          SYNTAX        HpSwitchDtLacpStatusPeerEntry
          MAX-ACCESS    not-accessible
          STATUS        current
          DESCRIPTION 
                  "The lacp status information of each peer port that
                   is  part of a trunk configured as type 'dt-lacp'."
          INDEX { hpSwitchDtLacpPeerIfIndex }
          ::= {  hpSwitchDtLacpStatusPeerTable 1}      
	
    HpSwitchDtLacpStatusPeerEntry ::= SEQUENCE {
       hpSwitchDtLacpPeerIfIndex            Integer32, 
       hpSwitchDtLacpPeerIfName             DisplayString,
       hpSwitchDtLacpPeerIfLacpEnable       Integer32,
       hpSwitchDtLacpPeerIfTrunkGroup       Integer32,
       hpSwitchDtLacpPeerIfLacpPortStatus   Integer32,
       hpSwitchDtLacpPeerIfLacpPartner      Integer32,
       hpSwitchDtLacpPeerIfLacpStatus       Integer32   
    }
	
    hpSwitchDtLacpPeerIfIndex OBJECT-TYPE
          SYNTAX        Integer32 (0..65535)
          MAX-ACCESS    read-only 
          STATUS        current
          DESCRIPTION
                  "The ifIndex value of the peer interface."
          ::= { hpSwitchDtLacpStatusPeerEntry 1 }
    
    hpSwitchDtLacpPeerIfName OBJECT-TYPE
          SYNTAX        DisplayString
          MAX-ACCESS    read-only
          STATUS        current
          DESCRIPTION
                  "The ifName value of the peer interface."
          ::= { hpSwitchDtLacpStatusPeerEntry 2 }
    
    hpSwitchDtLacpPeerIfLacpEnable OBJECT-TYPE
          SYNTAX        Integer32
          MAX-ACCESS    read-only
          STATUS        current
          DESCRIPTION
                  "The lacp configuration for the peer interface."
          ::= { hpSwitchDtLacpStatusPeerEntry 3 }
    
    hpSwitchDtLacpPeerIfTrunkGroup OBJECT-TYPE
          SYNTAX        Integer32
          MAX-ACCESS    read-only
          STATUS        current
          DESCRIPTION
                  "The trunk group information of the peer interface."
          ::= { hpSwitchDtLacpStatusPeerEntry 4 }    
    
    hpSwitchDtLacpPeerIfLacpPortStatus OBJECT-TYPE
          SYNTAX        Integer32
          MAX-ACCESS    read-only
          STATUS        current
          DESCRIPTION
                  "The lacp port status information of the peer 
                   interface."
          ::= { hpSwitchDtLacpStatusPeerEntry 5 }        
    
    hpSwitchDtLacpPeerIfLacpPartner OBJECT-TYPE
          SYNTAX        Integer32
          MAX-ACCESS    read-only
          STATUS        current
          DESCRIPTION
                  "The lacp partner information of the peer 
                   interface."
          ::= { hpSwitchDtLacpStatusPeerEntry 6 }           
    
    hpSwitchDtLacpPeerIfLacpStatus OBJECT-TYPE
          SYNTAX        Integer32
          MAX-ACCESS    read-only
          STATUS        current
          DESCRIPTION
                  "The lacp status information of the peer interface."
          ::= { hpSwitchDtLacpStatusPeerEntry 7 }    
    
------------------------------------------------------------------------
-- DT peer keep-alive config
------------------------------------------------------------------------
hpSwitchDtConfig OBJECT  IDENTIFIER ::= {hpSwitchDt 4}
 
hpSwitchDtPeerKeepAliveConfig OBJECT IDENTIFIER ::= {hpSwitchDtConfig 1}

    hpSwitchDtPeerKeepAliveDestAddressType  OBJECT-TYPE
          SYNTAX        InetAddressType 
          MAX-ACCESS    read-write
          STATUS        current 
          DESCRIPTION
                  "The address type of the peer keep-alive destination
                   address. Only IPv4 type is supported."
          ::= { hpSwitchDtPeerKeepAliveConfig 1}

    hpSwitchDtPeerKeepAliveDestAddress  OBJECT-TYPE
          SYNTAX        InetAddress 
          MAX-ACCESS    read-write
          STATUS        current 
          DESCRIPTION 
                  "The destination IP address to be used by DT 
                   switches to send peer keep-alive packets to 
                   the peer DT switch."
          ::= { hpSwitchDtPeerKeepAliveConfig 2}

    hpSwitchDtPeerKeepAliveVlanId  OBJECT-TYPE
          SYNTAX        Integer32(0..4095)
          MAX-ACCESS    read-write
          STATUS        current 
          DESCRIPTION 
                  "The interface on which peer keep-alive packets 
                   are sent out. A value of zero indicates peer
                   keep-alive interface is not configured."          
          ::= { hpSwitchDtPeerKeepAliveConfig 3}

    hpSwitchDtPeerKeepAliveDestUdpPort  OBJECT-TYPE
          SYNTAX        InetPortNumber 
          MAX-ACCESS    read-write
          STATUS        current 
          DESCRIPTION
                  "The current value of the destination UDP port for 
                   transmitting peer keep-alive messages."          
          DEFVAL {1024}       
          ::= { hpSwitchDtPeerKeepAliveConfig 4}

    hpSwitchDtPeerKeepAliveInterval OBJECT-TYPE
          SYNTAX        Integer32 
          UNITS         "milliseconds"
          MAX-ACCESS    read-write
          STATUS        current 
          DESCRIPTION 
                  "The current value of peer keep-alive packet 
   	           transmission interval for DT switches in 
                   milliseconds."
          DEFVAL { 1000 }            
          ::= { hpSwitchDtPeerKeepAliveConfig 5}

    hpSwitchDtPeerKeepAliveTimeout OBJECT-TYPE
          SYNTAX        Integer32
          UNITS         "seconds"
          MAX-ACCESS    read-write
          STATUS        current 
          DESCRIPTION 
                  "The peer keep-alive timeout period for DT switches 
                   in seconds." 
          DEFVAL { 5 }                 
          ::= { hpSwitchDtPeerKeepAliveConfig 6}

    hpSwitchDtPeerKeepAliveHoldTime OBJECT-TYPE
          SYNTAX        Integer32  
          UNITS         "seconds"
          MAX-ACCESS    read-write
          STATUS        current 
          DESCRIPTION 
                  "The current value of keep-alive hold timer for DT 
                   switches in seconds."     
          DEFVAL { 3 }     
          ::= { hpSwitchDtPeerKeepAliveConfig 7}
	
	
------------------------------------------------------------------------
-- DT statistics parameters
------------------------------------------------------------------------
hpSwitchDtStats  OBJECT IDENTIFIER ::= { hpSwitchDt 5 }
hpSwitchDtIscProtocolStats  OBJECT IDENTIFIER ::= { hpSwitchDtStats 1 }
hpSwitchDtPeerKeepAliveStats OBJECT IDENTIFIER ::= { hpSwitchDtStats 2 }
 
------------------------------------------------------------------------
-- DT ISC Protocol statistics
------------------------------------------------------------------------ 
    hpSwitchDtIscHelloPktsSent   OBJECT-TYPE
          SYNTAX        Counter32
          UNITS         "Packets"
          MAX-ACCESS    read-only
          STATUS        current
          DESCRIPTION 
                  "The total number of ISC protocol hello packets sent 
                   to the peer DT switch."
          ::= { hpSwitchDtIscProtocolStats  1 }

    hpSwitchDtIscHelloPktsRecv  OBJECT-TYPE
          SYNTAX        Counter32
          UNITS         "Packets"
          MAX-ACCESS    read-only
          STATUS        current
          DESCRIPTION  
                  "The total number of ISC protocol hello packets
  	           received from the peer DT switch."
          ::= { hpSwitchDtIscProtocolStats  2 }

    hpSwitchDtIscMACLearnPktsSent  OBJECT-TYPE
          SYNTAX        Counter32
          UNITS         "Packets"
          MAX-ACCESS    read-only
          STATUS        current
          DESCRIPTION 
                  "The total number of MAC learn packets sent to the
                   peer switch."
          ::= { hpSwitchDtIscProtocolStats  3 }

    hpSwitchDtIscMACLearnPktsRecv  OBJECT-TYPE
          SYNTAX        Counter32
          UNITS         "Packets"
          MAX-ACCESS    read-only
          STATUS        current
          DESCRIPTION 
                  "The total number of MAC learn packets received from
                   the peer switch."
          ::= { hpSwitchDtIscProtocolStats  4 }

    hpSwitchDtIscMACAgedPktsSent   OBJECT-TYPE
          SYNTAX        Counter32
          UNITS         "Packets"
          MAX-ACCESS    read-only
          STATUS        current
          DESCRIPTION 
                  "The total number of MAC ageout packets sent to the 
                   peer switch."
          ::= { hpSwitchDtIscProtocolStats  5 }

    hpSwitchDtIscMACAgedPktsRecv   OBJECT-TYPE
          SYNTAX        Counter32
          UNITS         "Packets"
          MAX-ACCESS    read-only
          STATUS        current
          DESCRIPTION  
                  "The total number of MAC ageouts received from the
                   peer switch."
          ::= { hpSwitchDtIscProtocolStats  6 }

------------------------------------------------------------------------
-- DT peer keep-alive statistics
------------------------------------------------------------------------

    hpSwitchDtPeerKeepAlivePktsSent   OBJECT-TYPE
          SYNTAX        Counter32 
          UNITS         "Packets"
          MAX-ACCESS    read-only
          STATUS        current 
          DESCRIPTION 
                  "The number of peer keep-alive packets sent on the
                   keep-alive interface."  
          ::= { hpSwitchDtPeerKeepAliveStats 1 }
    hpSwitchDtPeerKeepAlivePktsRecv   OBJECT-TYPE
	  SYNTAX        Counter32 
          UNITS         "Packets"
          MAX-ACCESS    read-only
          STATUS        current 
          DESCRIPTION 
                  "The number of valid peer keep-alive packets
                   received on the keep-alive interface."
          ::= { hpSwitchDtPeerKeepAliveStats  2 }

------------------------------------------------------------------------
-- DT System Info
------------------------------------------------------------------------

hpSwitchDtSystemInfo  OBJECT IDENTIFIER ::= { hpSwitchDt 6 }

    hpSwitchDtSystemISCProtocolState OBJECT-TYPE
	  SYNTAX        INTEGER {
				unknown(1),
				inSync(2),
				outOfSync(3)
			        }
          MAX-ACCESS    read-only
	  STATUS        current
	  DESCRIPTION   "The current value of DT ISC protocol state.
			This OID will return error when DT is not configured."
	  ::= { hpSwitchDtSystemInfo 1}

   hpSwitchDtSystemDtLacpSystemID OBJECT-TYPE
	  SYNTAX        MacAddress
          MAX-ACCESS    read-only
          STATUS        current
	  DESCRIPTION	"The current value of system ID used by DT LACPDU.
			This OID will return error when DT is not configured 
			otherwise it returns the system ID."
          ::= { hpSwitchDtSystemInfo 2}
   hpSwitchDtSystemAdminRolePriority OBJECT-TYPE
          SYNTAX        Integer32(1..65535)
          MAX-ACCESS    read-write
          STATUS        current
          DESCRIPTION	"The admin value for DT role priority. 
                   	The DT switch with lower priority value will be 
			elected as DT primary when dual active scenario is detected."
	  DEFVAL { 32768 }
          ::= { hpSwitchDtSystemInfo 3}
   hpSwitchDtSystemOperRolePriority OBJECT-TYPE
          SYNTAX        Integer32(1..65535)
          MAX-ACCESS    read-only
          STATUS        current
	  DESCRIPTION	"The operational value of DT role priority which is currently
			used by the protocol."
          ::= { hpSwitchDtSystemInfo 4}
   hpSwitchDtSystemPeerOperRolePriority OBJECT-TYPE
          SYNTAX        Integer32(1..65535)
          MAX-ACCESS    read-only
          STATUS        current
	  DESCRIPTION   "The operational role priority value of the connected DT partner."
          ::= { hpSwitchDtSystemInfo 5}
   hpSwitchDtSystemRole OBJECT-TYPE
          SYNTAX        INTEGER {
				unknown(1),
				primary(2),
				secondary(3)
				}
          MAX-ACCESS    read-only
          STATUS        current
	  DESCRIPTION   "The current role of the DT switch. This is represented as primary or secondary. 
			Primary switch will keep the DT links active while 
			secondary will block its DT links when dual active is detected.When the ISC link is up role is not applicable."

          ::= { hpSwitchDtSystemInfo 6}

hpSwitchDtConformance OBJECT IDENTIFIER ::= { hpSwitchDt 256 }

hpSwitchDtCompliances OBJECT IDENTIFIER  ::= { hpSwitchDtConformance 1 }
hpSwitchDtGroups     OBJECT IDENTIFIER  ::= { hpSwitchDtConformance 2 }

-----------------------------------------------------------------------
-- compliance statement
-----------------------------------------------------------------------

hpSwitchDtCompliance MODULE-COMPLIANCE
      STATUS       deprecated
      DESCRIPTION
              "The compliance statement for the entries in 
               the Distributed Trunking MIB."
      MODULE        -- This module
      MANDATORY-GROUPS
      {
         hpSwitchDtIscGroup,
         hpSwitchDtLocalLacpGroup,
         hpSwitchDtRemoteLacpGroup,
         hpSwitchDtPeerKeepAliveGroup
      }

      GROUP        hpSwitchDtIscStatsGroup
      DESCRIPTION  "This group is optional."

      GROUP        hpSwitchDtPeerKeepAliveStatsGroup
      DESCRIPTION  "This group is optional."
	                
      ::= { hpSwitchDtCompliances 1 } 

hpSwitchDtCompliance1 MODULE-COMPLIANCE
      STATUS       current
      DESCRIPTION
              "The compliance statement for the entries in
               the Distributed Trunking MIB."
      MODULE        -- This module
      MANDATORY-GROUPS
      {
         hpSwitchDtIscGroup,
         hpSwitchDtLocalLacpGroup,
         hpSwitchDtRemoteLacpGroup,
         hpSwitchDtPeerKeepAliveGroup,
         hpSwitchDtSystemInfoGroup
      }

      GROUP        hpSwitchDtIscStatsGroup
      DESCRIPTION  "This group is optional."

      GROUP        hpSwitchDtPeerKeepAliveStatsGroup
      DESCRIPTION  "This group is optional."

      ::= { hpSwitchDtCompliances 2 }

     
-----------------------------------------------------------------------
-- units of conformance
-----------------------------------------------------------------------
hpSwitchDtIscGroup OBJECT-GROUP
      OBJECTS
      {
         hpSwitchISCPortIndex,
         hpSwitchRemoteISCPortIndex
      }
      STATUS      current
      DESCRIPTION 
              "A collection of objects providing information
               about switch-interconnect port."
      ::= { hpSwitchDtGroups 1 }

hpSwitchDtLocalLacpGroup OBJECT-GROUP
      OBJECTS
      {
         hpSwitchDtLacpLocalIfIndex,
         hpSwitchDtLacpLocalIfName,
         hpSwitchDtLacpLocalIfLacpEnable,
         hpSwitchDtLacpLocalIfTrunkGroup,
         hpSwitchDtLacpLocalIfLacpPortStatus,
         hpSwitchDtLacpLocalIfLacpPartner,
         hpSwitchDtLacpLocalIfLacpStatus,
         hpSwitchDtLacpLocalIfLacpAdminKey,
         hpSwitchDtLacpLocalIfLacpOperKey
      }
      STATUS      current
      DESCRIPTION "A collection of objects providing information
                   about local dt-lacp ports."
      ::= { hpSwitchDtGroups 2 }

hpSwitchDtRemoteLacpGroup OBJECT-GROUP
      OBJECTS
      {
         hpSwitchDtLacpPeerIfIndex,
         hpSwitchDtLacpPeerIfName,
         hpSwitchDtLacpPeerIfLacpEnable,
         hpSwitchDtLacpPeerIfTrunkGroup,
         hpSwitchDtLacpPeerIfLacpPortStatus,
         hpSwitchDtLacpPeerIfLacpPartner,
         hpSwitchDtLacpPeerIfLacpStatus
      }
      STATUS      current
      DESCRIPTION "A collection of objects providing information
                   about remote dt-lacp ports."
      ::= { hpSwitchDtGroups 3 }             

hpSwitchDtPeerKeepAliveGroup OBJECT-GROUP
      OBJECTS
      {
         hpSwitchDtPeerKeepAliveDestAddressType,
         hpSwitchDtPeerKeepAliveDestAddress,
         hpSwitchDtPeerKeepAliveVlanId,
         hpSwitchDtPeerKeepAliveDestUdpPort,
         hpSwitchDtPeerKeepAliveInterval,
         hpSwitchDtPeerKeepAliveTimeout,
         hpSwitchDtPeerKeepAliveHoldTime
      }
      STATUS      current
      DESCRIPTION "A collection of objects providing information
                   about peer keep-alive interface."
      ::= { hpSwitchDtGroups 4 }              
hpSwitchDtIscStatsGroup OBJECT-GROUP
      OBJECTS
      {
         hpSwitchDtIscHelloPktsSent,
         hpSwitchDtIscHelloPktsRecv,
         hpSwitchDtIscMACLearnPktsSent,
         hpSwitchDtIscMACLearnPktsRecv,
         hpSwitchDtIscMACAgedPktsSent,
         hpSwitchDtIscMACAgedPktsRecv
      }
      STATUS      current
      DESCRIPTION "A collection of objects providing information
                   about DT ISC protocol."
      ::= { hpSwitchDtGroups 5 }

hpSwitchDtPeerKeepAliveStatsGroup OBJECT-GROUP
      OBJECTS
      {
	 hpSwitchDtPeerKeepAlivePktsSent,
         hpSwitchDtPeerKeepAlivePktsRecv
      }
      STATUS      current
      DESCRIPTION "A collection of objects providing information
                   about peer keep-alive protocol."
      ::= { hpSwitchDtGroups 6 }             

hpSwitchDtSystemInfoGroup OBJECT-GROUP
      OBJECTS
      {
         hpSwitchDtSystemISCProtocolState,
         hpSwitchDtSystemDtLacpSystemID,
         hpSwitchDtSystemAdminRolePriority,
         hpSwitchDtSystemOperRolePriority,
         hpSwitchDtSystemPeerOperRolePriority,
         hpSwitchDtSystemRole
      }
      STATUS      current
      DESCRIPTION   "A collection of objects providing system wide information."

      ::= { hpSwitchDtGroups 7 }             
END
