-- =================================================================
-- Copyright (c) 2010-2013 Hewlett-Packard Development Company, L.P.
--
-- Description: CATV transceiver MIB
-- Reference:
-- Version: V1.0
-- History:
-- V1.0 created by xujun.
--     Initial version of the MIB
-- =================================================================
HPN-ICF-CATV-TRANSCEIVER-MIB DEFINITIONS ::= BEGIN

IMPORTS
        hpnicfCommon
    FROM HPN-ICF-OID-MIB
        Integer32, OBJECT-TYPE, MODULE-IDENTITY,
        NOTIFICATION-TYPE
    FROM SNMPv2-SMI;

hpnicfCATVTransceiver MODULE-IDENTITY
    LAST-UPDATED "200807251008Z"
    ORGANIZATION
        ""
    CONTACT-INFO
        ""
    DESCRIPTION
        "
        The objects in this MIB module are used to manage and
        display common configuration for CATV(Community Antenna
        Television) transceiver module.
        "
    ::= { hpnicfCommon 94 }

--
-- hpnicfCATVTransceiverStatus
--

hpnicfCATVTransStatus OBJECT IDENTIFIER ::= { hpnicfCATVTransceiver 1 }

hpnicfCATVTransStatusScalarObjects OBJECT IDENTIFIER ::= { hpnicfCATVTransStatus 1 }

hpnicfCATVTransState OBJECT-TYPE
    SYNTAX     INTEGER
    {
        on         (1),
        off        (2)
    }
    MAX-ACCESS read-only
    STATUS     current
    DESCRIPTION
         "
         The state of CATV transceiver.
         "
    ::= { hpnicfCATVTransStatusScalarObjects 1 }

hpnicfCATVTransInputPwr OBJECT-TYPE
    SYNTAX     Integer32
    UNITS      "dbm"
    MAX-ACCESS read-only
    STATUS     current
    DESCRIPTION
         "
         The input power of CATV transceiver.
         If transceiver is not on site,
         the value should be zero.
         "
    ::= { hpnicfCATVTransStatusScalarObjects 2 }

hpnicfCATVTransOutputLevel OBJECT-TYPE
    SYNTAX     Integer32
    UNITS      "dbuv"
    MAX-ACCESS read-only
    STATUS     current
    DESCRIPTION
         "
         The output level of CATV transceiver.
         If transceiver is not on site,
         the value should be zero.
         "
    ::= { hpnicfCATVTransStatusScalarObjects 3 }

hpnicfCATVTransTemperature OBJECT-TYPE
    SYNTAX     Integer32
    UNITS      "centigrade"
    MAX-ACCESS read-only
    STATUS     current
    DESCRIPTION
         "
         The temperature of CATV transceiver.
         If transceiver is not on site,
         the value should be zero.
         "
    ::= { hpnicfCATVTransStatusScalarObjects 4 }


--
-- hpnicfCATVTransceiverMan
--

hpnicfCATVTransceiverMan OBJECT IDENTIFIER ::= { hpnicfCATVTransceiver 2 }

hpnicfCATVTransCtrlScalarObjects OBJECT IDENTIFIER ::= { hpnicfCATVTransceiverMan 1 }

hpnicfCATVTransInputPwrLowerThr OBJECT-TYPE
    SYNTAX     Integer32
    UNITS      "dbm"
    MAX-ACCESS read-write
    STATUS     current
    DESCRIPTION
        "
        A threshold for the CATV transceiver's input power.
        When the input power of CATV transceiver is lower
        than threshold, a trap should be generated.
        "
    ::= { hpnicfCATVTransCtrlScalarObjects 1 }

hpnicfCATVTransOutputLvlLowerThr OBJECT-TYPE
    SYNTAX     Integer32
    UNITS      "dbuv"
    MAX-ACCESS read-write
    STATUS     current
    DESCRIPTION
        "
        A threshold for the CATV transceiver's output level.
        When the output level of CATV transceiver is lower
        than threshold, a trap should be generated.
        "
    ::= { hpnicfCATVTransCtrlScalarObjects 2 }

hpnicfCATVTransTempratureUpperThr OBJECT-TYPE
    SYNTAX     Integer32
    UNITS      "℃"
    MAX-ACCESS read-write
    STATUS     current
    DESCRIPTION
        "
        A threshold for the CATV transceiver's temperature.
        When the temperature of CATV transceiver is higher
        than threshold, a trap should be generated.
        "
    ::= { hpnicfCATVTransCtrlScalarObjects 3 }


--
-- hpnicfCATVTransceiver NOTIFICATION
--

hpnicfCATVTansTrap OBJECT IDENTIFIER ::= { hpnicfCATVTransceiver 3 }

hpnicfCATVTransTrapPrefix OBJECT IDENTIFIER ::= {hpnicfCATVTansTrap 0}

hpnicfCATVTransInputPwrTrap NOTIFICATION-TYPE
    OBJECTS
        {
            hpnicfCATVTransInputPwr
        }
    STATUS current
    DESCRIPTION
        "
        A hpnicfCATVTransInputPwrTrap notification is sent when the
        input power of CATV transceiver is lower than the threshold.
        "
    ::= { hpnicfCATVTransTrapPrefix 1 }

hpnicfCATVTransInputPwrReTrap NOTIFICATION-TYPE
    OBJECTS
        {
            hpnicfCATVTransInputPwr
        }
    STATUS current
    DESCRIPTION
        "
        A hpnicfCATVTransInputPwrReTrap notification is sent when the
        input power of CATV transceiver recovered from the last trap.
        "
    ::= { hpnicfCATVTransTrapPrefix 2 }

hpnicfCATVTransOutputLvlTrap NOTIFICATION-TYPE
    OBJECTS
        {
            hpnicfCATVTransOutputLevel
        }
    STATUS current
    DESCRIPTION
        "
        A hpnicfCATVTransOutputLvlTrap notification is sent when the
        output level of CATV transceiver is lower than the threshold.
        "
    ::= { hpnicfCATVTransTrapPrefix 3 }

hpnicfCATVTransOutputLvlReTrap NOTIFICATION-TYPE
    OBJECTS
        {
            hpnicfCATVTransOutputLevel
        }
    STATUS current
    DESCRIPTION
        "
        A hpnicfCATVTransOutputLvlReTrap notification is sent when the
        output level of CATV transceiver recovered from the last trap.
        "
    ::= { hpnicfCATVTransTrapPrefix 4 }

hpnicfCATVTransTemperatureTrap NOTIFICATION-TYPE
    OBJECTS
        {
            hpnicfCATVTransTemperature
        }
    STATUS current
    DESCRIPTION
        "
        A hpnicfCATVTransTemperatureTrap notification is sent when the
        temperature of CATV transceiver is higher than the threshold.
        "
    ::= { hpnicfCATVTransTrapPrefix 5 }

hpnicfCATVTransTemperatureReTrap NOTIFICATION-TYPE
    OBJECTS
        {
            hpnicfCATVTransTemperature
        }
    STATUS current
    DESCRIPTION
        "
        A hpnicfCATVTransTemperatureReTrap notification is sent when the
        temperature of CATV transceiver recovered from the last trap.
        "
    ::= { hpnicfCATVTransTrapPrefix 6 }
END
