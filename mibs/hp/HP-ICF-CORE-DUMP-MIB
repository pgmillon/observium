HP-ICF-CORE-DUMP-MIB DEFINITIONS ::= BEGIN

    IMPORTS
        MODULE-IDENTITY, OBJECT-TYPE, Integer32
            FROM SNMPv2-SMI
        MODULE-COMPLIANCE, OBJECT-GROUP
            FROM SNMPv2-CONF
        hpicfCommon
            FROM HP-ICF-OID
        InetAddressType, InetAddress
             FROM INET-ADDRESS-MIB;
        
    hpicfCoreDumpMIB MODULE-IDENTITY
         LAST-UPDATED "201006130000Z"  -- June 30, 2010
         ORGANIZATION "HP Networking"
         CONTACT-INFO "Hewlett Packard Company
                       8000 Foothills Blvd.
                       Roseville, CA 95747"
         DESCRIPTION  "This MIB module describes
                       core dump related information."

         REVISION     "201006130000Z"  -- June 30, 2010
         DESCRIPTION  "Initial version."
         
           ::= {  hpicfCommon 14 }


    hpicfCoreDumpObjects      OBJECT IDENTIFIER ::= { hpicfCoreDumpMIB 1 }
    hpicfCoreDumpConformance  OBJECT IDENTIFIER ::= { hpicfCoreDumpMIB 2 }

    hpicfCoreDumpConfig       OBJECT IDENTIFIER ::= {  hpicfCoreDumpObjects 1 }

   
   -- Core Dump Object --
       
   hpicfCoreDumpTable OBJECT-TYPE
           SYNTAX     SEQUENCE OF HpicfCoreDumpEntry
           MAX-ACCESS not-accessible
           STATUS     current
           DESCRIPTION
                   "This table gives core dump status of management module
		    and interface module."
           ::= { hpicfCoreDumpConfig 1 }

   hpicfCoreDumpEntry OBJECT-TYPE
           SYNTAX     HpicfCoreDumpEntry
           MAX-ACCESS not-accessible
           STATUS     current 
           DESCRIPTION
                   "An entry in this table contains the core dump 
                    module status of management module and interface 
                    module."                   
           INDEX      { hpicfCoreDumpModule}
           ::= { hpicfCoreDumpTable 1 }

    HpicfCoreDumpEntry ::=
           SEQUENCE {
               hpicfCoreDumpModule             Integer32,
               hpicfCoreDumpMmStatus             INTEGER,
               hpicfCoreDumpImStatus             INTEGER
           }
    hpicfCoreDumpModule  OBJECT-TYPE
           SYNTAX     Integer32 (1..65535)
           MAX-ACCESS not-accessible
           STATUS     current
           DESCRIPTION
                   "This object is the index of the table."
           ::= {  hpicfCoreDumpEntry 1}
	   
    hpicfCoreDumpMmStatus  OBJECT-TYPE
       SYNTAX         INTEGER {
                           enabled (1),
                           disabled (2)
                           }
       MAX-ACCESS   read-write 
       STATUS       current
       DESCRIPTION                  
               "This is to enable/disable core dump 
	        on the management module."
      DEFVAL  { enabled }
                 ::= { hpicfCoreDumpEntry 2 }

     hpicfCoreDumpImStatus  OBJECT-TYPE
       SYNTAX         INTEGER {
                           enabled (1),
                           disabled (2)
                           }
       MAX-ACCESS   read-write 
       STATUS       current
       DESCRIPTION
               "This is to enable/disable core dump
		on the interface module."
      DEFVAL  { enabled }
                 ::= { hpicfCoreDumpEntry 3 }
   
    hpicfCoreDumpTftpServerAddressType OBJECT-TYPE
           SYNTAX     InetAddressType
           MAX-ACCESS read-write
           STATUS     current
           DESCRIPTION
                   "The type of address in the corresponding
                    hpSwitchCoreDumpTftpServerAddress object."
           ::= { hpicfCoreDumpConfig 2 }

    hpicfCoreDumpTftpServerAddress OBJECT-TYPE
           SYNTAX     InetAddress
           MAX-ACCESS read-write
           STATUS     current
           DESCRIPTION
                    "The TFTP server address to upload the
                     core dump file."
           ::= { hpicfCoreDumpConfig 3 }

   
-- Conformance Information
 
   hpicfCoreDumpConfigGroups      OBJECT IDENTIFIER  ::= { hpicfCoreDumpConformance 1 }
   hpicfCoreDumpCompliances OBJECT IDENTIFIER  ::= { hpicfCoreDumpConformance 2 }

-- units of conformance

   hpicfCoreDumpConfigGroup OBJECT-GROUP
        OBJECTS {
                  hpicfCoreDumpMmStatus,
                  hpicfCoreDumpImStatus,
                  hpicfCoreDumpTftpServerAddress,
                  hpicfCoreDumpTftpServerAddressType
                }
        STATUS     current
        DESCRIPTION    
               "A collection of objects for enabling/disabling
                core dump on management module, interface module
                and configuring auto TFTP server address, address
                type."
       ::= { hpicfCoreDumpConfigGroups 1 }

-- compliance statements

   hpicfCoreDumpCompliance MODULE-COMPLIANCE
       STATUS  current
       DESCRIPTION
           "The compliance statement for devices support of
            HP-ICF-CORE-DUMP MIB."
       MODULE -- This Module

       MANDATORY-GROUPS { hpicfCoreDumpConfigGroup
                        }   
       ::= { hpicfCoreDumpCompliances 1 }
 END
