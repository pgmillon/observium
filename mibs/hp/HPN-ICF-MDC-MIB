-- ===========================================================================================================
-- Copyright (c) 2010-2013 Hewlett-Packard Development Company, L.P.
--
-- Description: Mdc MIB
-- Reference:
-- Version: V1.0
-- History:
-- revision 1.0 2013-03-05 created by c08124
--
-- ============================================================================================================
HPN-ICF-MDC-MIB DEFINITIONS ::= BEGIN

IMPORTS
    entPhysicalIndex
        FROM ENTITY-MIB
    hpnicfCommon
        FROM HPN-ICF-OID-MIB
    Integer32, Unsigned32, OBJECT-TYPE, MODULE-IDENTITY, NOTIFICATION-TYPE
        FROM SNMPv2-SMI
    DisplayString, RowStatus, TruthValue, TEXTUAL-CONVENTION
        FROM SNMPv2-TC;

hpnicfMDC MODULE-IDENTITY
    LAST-UPDATED "201303051448Z"
    ORGANIZATION
        ""
    CONTACT-INFO
        ""
    DESCRIPTION
        "This MIB contains objects to manage MDC (Multitenant Device Context) operations.

        Such as:
        1. Configure MDCs for a device and display MDCs and their status.
        2. Assign CPU, storage space, and memory space resources to the MDC, and display their status.
        3. Authorize the MDC to use the interface cards, and assign physical interfaces to an MDC.

        Default MDC: A device supporting MDCs is an MDC itself, and it is called the default MDC.
        From the default MDC, administrators can manage the entire physical device, create and delete non-default MDCs,
        and assign interfaces, CPU resources, storage space, and memory space to non-default MDCs.

        Non-default MDC: No MDCs can be created on a non-default MDC.
        Administrators of non-default MDCs can only manage and maintain their respective MDCs.
        A non-default MDC can use only the resources assigned to it."
    REVISION "201303051448Z"
    DESCRIPTION
        "The initial revision of this MIB module."
    ::= { hpnicfCommon 136 }


-- Scalar MIB objects, which are considered as global variables
-- Global Level Configuration
HpnicfMdcActionValue ::= TEXTUAL-CONVENTION
    STATUS current
    DESCRIPTION
        "start: start the MDC
         stop: stop the MDC"
    SYNTAX INTEGER
        {
            start(1),
            stop(2)
        }

HpnicfMdcRunStatus ::= TEXTUAL-CONVENTION
    STATUS current
    DESCRIPTION
        "Status of the MDC:
        inactive: The MDC is stopped or not started yet.
        starting: The device is executing the mdc start command to start the MDC.
        active: The MDC is operating properly.
        stopping: The device is executing the undo mdc start command to stop the MDC.
        updating: The device is executing the location command to authorize the MDC to use an interface card."
    SYNTAX INTEGER
        {
            inactive(1),
            starting(2),
            active(3),
            stopping(4),
            updating(5)
        }


-- Node definitions

hpnicfMDCScalarObjects OBJECT IDENTIFIER ::= { hpnicfMDC 1 }

hpnicfMDCMaxMDCNum OBJECT-TYPE
    SYNTAX Integer32
    MAX-ACCESS read-only
    STATUS current
    DESCRIPTION
        "The maximum number of MDCs which the system supported to create."
    ::= { hpnicfMDCScalarObjects 1 }


hpnicfMDCCurrentMDCNum OBJECT-TYPE
    SYNTAX Integer32
    MAX-ACCESS read-only
    STATUS current
    DESCRIPTION
        "The current number of MDCs which the system has created."
    ::= { hpnicfMDCScalarObjects 2 }

hpnicfMDCTables OBJECT IDENTIFIER ::= { hpnicfMDC 2 }

-- The operation and information for MDC.
hpnicfMDCControl OBJECT IDENTIFIER ::= { hpnicfMDCTables 1 }


hpnicfMDCControlTable OBJECT-TYPE
    SYNTAX SEQUENCE OF HpnicfMDCControlEntry
    MAX-ACCESS not-accessible
    STATUS current
    DESCRIPTION
        "This table is used to configure MDCs for a device and show MDC's status."
    ::= { hpnicfMDCControl 1 }


hpnicfMDCControlEntry OBJECT-TYPE
    SYNTAX HpnicfMDCControlEntry
    MAX-ACCESS not-accessible
    STATUS current
    DESCRIPTION
        "An entry of the hpnicfMDCControlTable, every entry is corresponding with an MDC."
    INDEX { hpnicfMDCIndex }
    ::= { hpnicfMDCControlTable 1 }


HpnicfMDCControlEntry ::=
    SEQUENCE
        {
            hpnicfMDCIndex
                Integer32,
            hpnicfMDCName
                DisplayString,
            hpnicfMDCAction
                HpnicfMdcActionValue,
            hpnicfMDCStatus
                HpnicfMdcRunStatus,
            hpnicfMDCRowStatus
                RowStatus
        }

hpnicfMDCIndex OBJECT-TYPE
    SYNTAX Integer32 (1..2147483647)
    MAX-ACCESS accessible-for-notify
    STATUS current
    DESCRIPTION
        "MDC ID is used as MDCIndex, the value range of MDC ID depends on the device model.
         MDCIndex cannot be modified after creation."
    ::= { hpnicfMDCControlEntry 1 }


hpnicfMDCName OBJECT-TYPE
    SYNTAX DisplayString (SIZE (1..15))
    MAX-ACCESS read-create
    STATUS current
    DESCRIPTION
        "Specifies the MDC name, a case-sensitive string of 1 to 15 characters.
        The MDC name cannot be modified after creation."
    ::= { hpnicfMDCControlEntry 2 }


hpnicfMDCAction OBJECT-TYPE
    SYNTAX HpnicfMdcActionValue
    MAX-ACCESS read-write
    STATUS current
    DESCRIPTION
        "State of MDC action: start/stop.
        After an MDC is started, administrators of the MDC can log in to
        the MDC for MDC configuration and maintenance.
        Stopping an MDC interrupts all services on the MDC and logs out
        all users of the MDC.

        Non-default MDC cannot operate."
    DEFVAL { stop }
    ::= { hpnicfMDCControlEntry 3 }


hpnicfMDCStatus OBJECT-TYPE
    SYNTAX HpnicfMdcRunStatus
    MAX-ACCESS read-only
    STATUS current
    DESCRIPTION
        "Status of MDCs."
    ::= { hpnicfMDCControlEntry 4 }


hpnicfMDCRowStatus OBJECT-TYPE
    SYNTAX RowStatus
    MAX-ACCESS read-create
    STATUS current
    DESCRIPTION
        "The status of this table entry.
        Only support active, createAndGo and destroy."
    ::= { hpnicfMDCControlEntry 5 }


hpnicfMDCResource OBJECT IDENTIFIER ::= { hpnicfMDCTables 2 }


hpnicfMDCDISKResourceTable OBJECT-TYPE
    SYNTAX SEQUENCE OF HpnicfMDCDISKResourceEntry
    MAX-ACCESS not-accessible
    STATUS current
    DESCRIPTION
        "This table is for disk resource management:
        Specify a disk space percentage for an MDC and display the disk space usage.

        Default: All MDCs share the disk space in the system,
        and an MDC can use all free disk space in the system.

        Non-default MDC can only query the disk space usage."
    ::= { hpnicfMDCResource 1 }


hpnicfMDCDISKResourceEntry OBJECT-TYPE
    SYNTAX HpnicfMDCDISKResourceEntry
    MAX-ACCESS not-accessible
    STATUS current
    DESCRIPTION
        "An entry of the hpnicfMDCDISKResourceTable, every entry is corresponding to
        disk resource of an MDC.

        Note that only entPhysicalIndex values that represent
        physical boards (i.e., associated entPhysicalClass value is
        'module(9)') are permitted to exist in this table."
    INDEX { entPhysicalIndex, hpnicfMDCIndex, hpnicfMDCDISKResourceInstance }
    ::= { hpnicfMDCDISKResourceTable 1 }


HpnicfMDCDISKResourceEntry ::=
    SEQUENCE {
        hpnicfMDCDISKResourceInstance
            Integer32,
        hpnicfMDCDISKResourceInstanceName
            DisplayString,
        hpnicfMDCDISKResourceMinLimit
            Integer32,
        hpnicfMDCDISKResourceMaxLimit
            Integer32,
        hpnicfMDCDISKResourceReserve
            Unsigned32,
        hpnicfMDCDISKResourceQuota
            Unsigned32,
        hpnicfMDCDISKResourceUsage
            Unsigned32,
        hpnicfMDCDISKResourceAvailable
            Unsigned32
     }

hpnicfMDCDISKResourceInstance OBJECT-TYPE
    SYNTAX Integer32 (1..2147483647)
    MAX-ACCESS not-accessible
    STATUS current
    DESCRIPTION
        "Instance index of disk resource.
         Different instances for disk: Flash, CF cards."
    ::= { hpnicfMDCDISKResourceEntry 1 }


hpnicfMDCDISKResourceInstanceName OBJECT-TYPE
    SYNTAX DisplayString (SIZE (1..32))
    MAX-ACCESS read-only
    STATUS current
    DESCRIPTION
        "Instance name of disk resource.

        Such as: Flash, CF cards."
    ::= { hpnicfMDCDISKResourceEntry 2 }


hpnicfMDCDISKResourceMinLimit OBJECT-TYPE
    SYNTAX Integer32 (0..100)
    UNITS       "percent"
    MAX-ACCESS read-write
    STATUS current
    DESCRIPTION
        "Limit minimum (reserve resources, must be all 0)."
    ::= { hpnicfMDCDISKResourceEntry 3 }


hpnicfMDCDISKResourceMaxLimit OBJECT-TYPE
    SYNTAX Integer32 (1..100)
    UNITS       "percent"
    MAX-ACCESS read-write
    STATUS current
    DESCRIPTION
        "Maximum of available resources of disk.
        Make sure the disk space amount assigned to an MDC is
        greater than the disk space amount the MDC is using.
        Non-default MDC cannot set"
    ::= { hpnicfMDCDISKResourceEntry 4 }

hpnicfMDCDISKResourceReserve OBJECT-TYPE
    SYNTAX Unsigned32
    UNITS       "KB"
    MAX-ACCESS read-only
    STATUS current
    DESCRIPTION
        "The reserve limit resources of disk."
    ::= { hpnicfMDCDISKResourceEntry 5 }

hpnicfMDCDISKResourceQuota OBJECT-TYPE
    SYNTAX Unsigned32
    UNITS       "KB"
    MAX-ACCESS read-only
    STATUS current
    DESCRIPTION
        "The total limit resources of disk according to hpnicfMDCDiskResourceMaxLimit."
    ::= { hpnicfMDCDISKResourceEntry 6 }


hpnicfMDCDISKResourceUsage OBJECT-TYPE
    SYNTAX Unsigned32
    UNITS       "KB"
    MAX-ACCESS read-only
    STATUS current
    DESCRIPTION
        "Current usage of disk resources."
    ::= { hpnicfMDCDISKResourceEntry 7 }


hpnicfMDCDISKResourceAvailable OBJECT-TYPE
    SYNTAX Unsigned32
    UNITS       "KB"
    MAX-ACCESS read-only
    STATUS current
    DESCRIPTION
        "Current available resources of disk."
    ::= { hpnicfMDCDISKResourceEntry 8 }

hpnicfMDCMemoryResourceTable OBJECT-TYPE
    SYNTAX SEQUENCE OF HpnicfMDCMemoryResourceEntry
    MAX-ACCESS not-accessible
    STATUS current
    DESCRIPTION
        "This table is for memory resource management:
         Specify a memory space percentage for an MDC and display the memory space usage.
         Default: All MDCs share the memory space in the system, and an MDC can use all free memory.

         Non-default MDC can only query resource message of memory."
    ::= { hpnicfMDCResource 2 }


hpnicfMDCMemoryResourceEntry OBJECT-TYPE
    SYNTAX HpnicfMDCMemoryResourceEntry
    MAX-ACCESS not-accessible
    STATUS current
    DESCRIPTION
        "An entry of the hpnicfMDCMemoryResourceTable, every entry is corresponding
        with memory resource of an MDC.

        Note that only entPhysicalIndex values that represent
        physical boards (i.e., associated entPhysicalClass value is
        'module(9)') are permitted to exist in this table."
    INDEX { entPhysicalIndex, hpnicfMDCIndex }
    ::= { hpnicfMDCMemoryResourceTable 1 }


HpnicfMDCMemoryResourceEntry ::=
    SEQUENCE {
        hpnicfMDCMemoryResourceMinLimit
            Integer32,
        hpnicfMDCMemoryResourceMaxLimit
            Integer32,
        hpnicfMDCMemoryResourceReserve
            Unsigned32,
        hpnicfMDCMemoryResourceQuota
            Unsigned32,
        hpnicfMDCMemoryResourceUsage
            Unsigned32,
        hpnicfMDCMemoryResourceAvailable
            Unsigned32
     }

hpnicfMDCMemoryResourceMinLimit OBJECT-TYPE
    SYNTAX Integer32 (0..100)
    UNITS       "percent"
    MAX-ACCESS read-write
    STATUS current
    DESCRIPTION
        "Limit minimum(reserve resources, must be all 0).

        Non-default MDC cannot set."
    ::= { hpnicfMDCMemoryResourceEntry 1 }


hpnicfMDCMemoryResourceMaxLimit OBJECT-TYPE
    SYNTAX Integer32 (1..100)
    UNITS       "percent"
    MAX-ACCESS read-write
    STATUS current
    DESCRIPTION
        "Maximum of available resources of memory,
        it specifies the ratio of the memory space that an MDC can use.
        Make sure this amount is sufficient for the MDC to operate properly.
        Non-default MDC cannot set."
    ::= { hpnicfMDCMemoryResourceEntry 2 }

hpnicfMDCMemoryResourceReserve OBJECT-TYPE
    SYNTAX Unsigned32
    UNITS       "KB"
    MAX-ACCESS read-only
    STATUS current
    DESCRIPTION
        "The reserve limit resources of memory."
    ::= { hpnicfMDCMemoryResourceEntry 3 }

hpnicfMDCMemoryResourceQuota OBJECT-TYPE
    SYNTAX Unsigned32
    UNITS       "KB"
    MAX-ACCESS read-only
    STATUS current
    DESCRIPTION
        "The total limit resources of memory."
    ::= { hpnicfMDCMemoryResourceEntry 4 }

hpnicfMDCMemoryResourceUsage OBJECT-TYPE
    SYNTAX Unsigned32
    UNITS       "KB"
    MAX-ACCESS read-only
    STATUS current
    DESCRIPTION
        "Current usage of memory resources."
    ::= { hpnicfMDCMemoryResourceEntry 5 }

hpnicfMDCMemoryResourceAvailable OBJECT-TYPE
    SYNTAX Unsigned32
    UNITS       "KB"
    MAX-ACCESS read-only
    STATUS current
    DESCRIPTION
        "Current available value of memory resources."
    ::= { hpnicfMDCMemoryResourceEntry 6 }

hpnicfMDCCPUResourceTable OBJECT-TYPE
    SYNTAX SEQUENCE OF HpnicfMDCCPUResourceEntry
    MAX-ACCESS not-accessible
    STATUS current
    DESCRIPTION
        "This table is for CPU resource management:
        Specify a CPU weight for an MDC and display the CPU usage.
        The amount of CPU resources an MDC can use depends on the CPU weight
        settings for all MDCs that share the same CPU.

        Non-default MDC can only query CPU resources."
    ::= { hpnicfMDCResource 3 }


hpnicfMDCCPUResourceEntry OBJECT-TYPE
    SYNTAX HpnicfMDCCPUResourceEntry
    MAX-ACCESS not-accessible
    STATUS current
    DESCRIPTION
        "An entry of the hpnicfMDCCPUResourceTable, every entry is corresponding
        with CPU resources of an MDC.

        Note that only entPhysicalIndex values that represent
        physical boards (i.e., associated entPhysicalClass value is
        'module(9)') are permitted to exist in this table."
    INDEX {entPhysicalIndex, hpnicfMDCIndex }
    ::= { hpnicfMDCCPUResourceTable 1 }


HpnicfMDCCPUResourceEntry ::=
    SEQUENCE {
        hpnicfMDCCPUResourceLimit
            Integer32,
        hpnicfMDCCPUResourceUsage
            Integer32
     }

hpnicfMDCCPUResourceLimit OBJECT-TYPE
    SYNTAX Integer32 (1..10)
    UNITS     "weight"
    MAX-ACCESS read-write
    STATUS current
    DESCRIPTION
        "CPU weight-maximum of available resources of CPU,
        this number specifies a CPU weight for an MDC.
        Non-default MDC cannot set."
    ::= { hpnicfMDCCPUResourceEntry 1 }


hpnicfMDCCPUResourceUsage OBJECT-TYPE
    SYNTAX Integer32 (0..100)
    UNITS    "percent"
    MAX-ACCESS read-only
    STATUS current
    DESCRIPTION
        "the CPU usage"
    ::= { hpnicfMDCCPUResourceEntry 2 }


-- The MDC location status.
hpnicfMDCLocation OBJECT IDENTIFIER ::= { hpnicfMDCTables 3 }

hpnicfMDCLocationTable OBJECT-TYPE
    SYNTAX SEQUENCE OF HpnicfMDCLocationEntry
    MAX-ACCESS not-accessible
    STATUS current
    DESCRIPTION
        "This table is for location management:
        Authorize an MDC to use an interface card and query state of location.
        To assign physical interfaces to an MDC, administrators must authorize the MDC
        to use the interface cards to which the physical interfaces belong.

        Default: All interface cards of the device belong to the default MDC,
        and a non-default MDC cannot use any interface card.
        Non-default MDC can only query location state."
    ::= { hpnicfMDCLocation 1 }


hpnicfMDCLocationEntry OBJECT-TYPE
    SYNTAX HpnicfMDCLocationEntry
    MAX-ACCESS not-accessible
    STATUS current
    DESCRIPTION
        "An entry of the hpnicfMDCLocationTable, every entry is the status
        whether an MDC has been Authorized to use the interface cards.

        Note that only entPhysicalIndex values that represent
        physical boards (i.e., associated entPhysicalClass value is
        'module(9)') are permitted to exist in this table."
    INDEX { entPhysicalIndex, hpnicfMDCIndex }
    ::= { hpnicfMDCLocationTable 1 }


HpnicfMDCLocationEntry ::=
    SEQUENCE {
        hpnicfMDCLocationStatus
            TruthValue
     }

hpnicfMDCLocationStatus OBJECT-TYPE
    SYNTAX TruthValue
    MAX-ACCESS read-write
    STATUS current
    DESCRIPTION
        "To authorize the MDC to use the interface cards, set the value
        of this object to 'true (1)'.  To cancel the authorization, set this
        value to 'false (2)'.

        Note that the return noError means the command is being executed.
        For the execution result, check hpnicfMDCLocationStatus."
    ::= { hpnicfMDCLocationEntry 1 }


-- The interfaces allocate information.
hpnicfMDCAllocate OBJECT IDENTIFIER ::= { hpnicfMDCTables 4 }

hpnicfMDCGroupIfTable OBJECT-TYPE
    SYNTAX SEQUENCE OF HpnicfMDCGroupIfEntry
    MAX-ACCESS not-accessible
    STATUS current
    DESCRIPTION
        "This table indication of relation between interfaces and groups,
        which helps to realize the allocation, together with hpnicfMDCAllocateTable.

        Non-default MDC cannot operate."
    ::= { hpnicfMDCAllocate 1 }


hpnicfMDCGroupIfEntry OBJECT-TYPE
    SYNTAX HpnicfMDCGroupIfEntry
    MAX-ACCESS not-accessible
    STATUS current
    DESCRIPTION
        "An entry of the hpnicfMDCGroupIfTable, every entry is the relationship
        between interfaces and groups.

        Due to hardware restrictions, the interfaces on some interface cards are grouped.
        The interfaces in a group must be assigned to the same MDC at the same time or
        removed from an MDC at the same time. Interface grouping depends on the device model.

        This table is used for hpnicfMDCAllocateTable to show interfae group lists.

        Note that only entPhysicalIndex values that represent
        physical ports (i.e., associated entPhysicalClass value is
        'port(10)') are permitted to exist in this table."
    INDEX { entPhysicalIndex }
    ::= { hpnicfMDCGroupIfTable 1 }


HpnicfMDCGroupIfEntry ::=
    SEQUENCE {
        hpnicfMDCGroupIdentity
            Integer32
     }

hpnicfMDCGroupIdentity OBJECT-TYPE
    SYNTAX Integer32
    MAX-ACCESS read-only
    STATUS current
    DESCRIPTION
        "The interface group ID. There are two parts for this id
         depicted as follows:

         31                  7                  0
         +++++++++++++++++++++++++++++++++++++++++
         +   entity index    +    group index    +
         +   ( bit 8..31 )       ( bit 0..7 )    +
         +++++++++++++++++++++++++++++++++++++++++

         From bit0 to bit7 (one byte), it is interfaces group index.

         From bit8 to bit31 (three bytes), it is the physical index
         the same as the entPhysicalIndex specified in ENTITY-MIB.
         Note that only entPhysicalIndex values that represent
         physical boards (i.e., associated entPhysicalClass value is
         'module(9)') are permitted to exist in this table."
    ::= { hpnicfMDCGroupIfEntry 2 }

hpnicfMDCAllocateTable OBJECT-TYPE
    SYNTAX SEQUENCE OF HpnicfMDCAllocateEntry
    MAX-ACCESS not-accessible
    STATUS current
    DESCRIPTION
        "This table is used to assigning a physical interface to an MDC.
        It is allowed that allocate interfaces to a non-default MDC from the default MDC,
        and allocate interfaces back to the default MDC from a non-default MDC.

        All physical interfaces on the device belong to the default MDC,
        and a non-default MDC has no physical interfaces to use.
        Multiple physical interfaces can be assigned to a non-default MDC.
        A physical interface must meet the following conditions to be assigned to a non-default MDC:
        1. Belongs to the default MDC.
        2. Not the console or AUX port.
        3. Not the management Ethernet interface.
        4. Not in an interface group with an interface assigned to another MDC.
        5. The default MDC uses only the physical interfaces that are not assigned to a non-default MDC.

        Non-default MDC cannot set this table."
    ::= { hpnicfMDCAllocate 2 }


hpnicfMDCAllocateEntry OBJECT-TYPE
    SYNTAX HpnicfMDCAllocateEntry
    MAX-ACCESS not-accessible
    STATUS current
    DESCRIPTION
        "An entry of the hpnicfMDCAllocateTable, every entry is the status
        whether physical interfaces have been assigned to an MDC."
    INDEX { hpnicfMDCAllocateGroupIndex }
    ::= { hpnicfMDCAllocateTable 1 }


HpnicfMDCAllocateEntry ::=
    SEQUENCE {
        hpnicfMDCAllocateGroupIndex
            Integer32,
        hpnicfMDCAllocateGroupDescription
            DisplayString,
        hpnicfMDCAllocateMDCId
            Integer32
     }

hpnicfMDCAllocateGroupIndex OBJECT-TYPE
    SYNTAX Integer32 (1..2147483647)
    MAX-ACCESS not-accessible
    STATUS current
    DESCRIPTION
        "The interface group ID, the same as hpnicfMDCGroupIdentity.
         There are two parts for this id.

         depicted as follows:
         31                  7                  0
         +++++++++++++++++++++++++++++++++++++++++
         +   entity index    +    group index    +
         +   ( bit 8..31 )       ( bit 0..7 )    +
         +++++++++++++++++++++++++++++++++++++++++

         From bit0 to bit7 (one byte), it is interfaces group index.

         From bit8 to bit31 (three bytes), it is the physical index
         the same as the entPhysicalIndex specified in ENTITY-MIB.
         Note that only entPhysicalIndex values that represent
         physical boards (i.e., associated entPhysicalClass value is
         'module(9)') are permitted to exist in this table."
    ::= { hpnicfMDCAllocateEntry 1 }

hpnicfMDCAllocateGroupDescription OBJECT-TYPE
    SYNTAX DisplayString (SIZE (1..255))
    MAX-ACCESS read-only
    STATUS current
    DESCRIPTION
        "Interfaces list
        Such as:
        GigabitEthernet4/5/0/1 to GigabitEthernet4/5/0/24,
        GigabitEthernet4/5/0/48"
    ::= { hpnicfMDCAllocateEntry 2 }


hpnicfMDCAllocateMDCId OBJECT-TYPE
    SYNTAX Integer32 (1..2147483647)
    MAX-ACCESS read-write
    STATUS current
    DESCRIPTION
        "MDC ID is used as hpnicfMDCAllocateMDCId.
        Default MDC: It is allowed that allocate interfaces to non-default MDC from
        the default MDC, and allocate interfaces back to the default MDC from
        a non-default MDC.
        Non-default MDC cannot set allocation, can only query grouping of own MDC."
    ::= { hpnicfMDCAllocateEntry 3 }


hpnicfMDCNotification OBJECT IDENTIFIER ::= { hpnicfMDC 3 }

hpnicfMDCNotificationObjects OBJECT IDENTIFIER ::= { hpnicfMDCNotification 0 }

hpnicfMDCStateChangeToActive NOTIFICATION-TYPE
    OBJECTS {hpnicfMDCIndex, hpnicfMDCName}
    STATUS current
    DESCRIPTION
        "The hpnicfMDCStateChangeToActive trap indicates that the MDC status has changed to active."
    ::= { hpnicfMDCNotificationObjects 1 }

hpnicfMDCStateChangeToInactive NOTIFICATION-TYPE
    OBJECTS {hpnicfMDCIndex, hpnicfMDCName}
    STATUS current
    DESCRIPTION
        "The hpnicfMDCStateChangeToInactive trap indicates that the MDC status has changed to inactive."
    ::= { hpnicfMDCNotificationObjects 2 }

END
