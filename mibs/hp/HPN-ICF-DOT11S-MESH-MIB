-- =============================================================================
-- Copyright (c) 2010-2014 Hewlett-Packard Development Company, L.P.
--
-- Description:
--   The file defines a MIB to provide MESH configuration information.
-- Reference:
-- Version: V1.3
-- History:
--   V1.0 2008-07-08 Initial version, created by ChangHuifeng
--   V1.1 2008-11-07 modified by liyugang
--        Add hpnicfDot11sMeshLinkStatisTable, hpnicfDot11sMeshNbrStatusTable
--        to hpnicfDot11sMeshStatusGroup
--   V1.2 2009-08-01 modified by Wang Shaojie
--        Add hpnicfDot11sMeshLinkIFName to hpnicfDot11sMeshLinkStatisTable.
--   V1.3 2013-09-14 modified by Zhang Siyu
--        Add hpnicfDot11sMeshLinkType to hpnicfDot11sMeshLinkStatusTable
-- =============================================================================
HPN-ICF-DOT11S-MESH-MIB DEFINITIONS ::= BEGIN

IMPORTS
        TruthValue,
        MacAddress,
        RowStatus
    FROM SNMPv2-TC
        MODULE-IDENTITY,
        OBJECT-TYPE,
        Integer32,
        Unsigned32,
        Counter32
    FROM SNMPv2-SMI
        hpnicfDot11, HpnicfDot11RadioElementIndex, hpnicfDot11APElementIndex
    FROM HPN-ICF-DOT11-REF-MIB;

hpnicfDot11sMesh MODULE-IDENTITY
    LAST-UPDATED "200908011000Z"        -- Nov 07, 2008 at 10:00 GMT
    ORGANIZATION
        ""
    CONTACT-INFO
        ""
    DESCRIPTION
        "The file defines a MIB to provide MESH configuration information.

        GLOSSARY

        IEEE 802.11
        Standard to encourage interoperability among
        wireless networking equipment.

        Access point (AP)
        Transmitter/receiver (transceiver) device
        that commonly connects and transports data
        between a wireless network and a wired network.

        Access control (AC)
        To control and manage multi-APs, it will bridge
        wireless and wired network.

        Fat AP
        Applied in the home, SOHO and so on, and it could
        work independently without help from AC.

        Fit AP
        Applied in the enterprise environment, it will work
        under the control and management from AC.

        BSS
        IEEE 802.11 Basic Service Set (Radio Cell).  The
        BSS of an AP comprises of the stations directly
        associating with the AP.

        Radio
        The chip set to receive and send wireless signal.

        Mesh
        A network consisting of two or more mesh points
        which communicate with each other via mesh services.

        Mesh Point (MP)
        An IEEE 802.11 entity that contains an IEEE 802.11-conformant
        medium access control (MAC) and physical layer (PHY) interface
        to the wireless medium (WM) that supports mesh services.

        Mesh Access Point (MAP)
        A mesh point that is collocated with one or more access points.

        Mesh Portal Point (MPP)
        A mesh point that is collocated with one or more portals.

        Mesh Link
        A link between two MPs."
    REVISION "200908011000Z"        -- Aug 01, 2009 at 10:00 GMT
    DESCRIPTION
        "Add new nodes."
    REVISION "200811071000Z"        -- Nov 07, 2008 at 10:00 GMT
    DESCRIPTION
        "Modified to add new nodes and a new table."
    REVISION "200807081800Z"        -- July 8, 2008 at 18:00 GMT
    DESCRIPTION
        "The initial revision of this MIB module."
    ::= { hpnicfDot11 11 }

-- *****************************************************************************
-- *  Major sections
-- *****************************************************************************

hpnicfDot11sConfigGroup OBJECT IDENTIFIER  ::= { hpnicfDot11sMesh 1 }
--  Dot11s Configuration Group has the following children:
--  hpnicfDot11sMeshGlobalPara             ::= { hpnicfDot11sConfigGroup 1 }
--  hpnicfDot11sMeshPflTable               ::= { hpnicfDot11sConfigGroup 2 }
--  hpnicfDot11sMpPlcyTable                ::= { hpnicfDot11sConfigGroup 3 }
--  hpnicfDot11sMlspCfgTable               ::= { hpnicfDot11sConfigGroup 4 }
--  hpnicfDot11sRadioCfgTable              ::= { hpnicfDot11sConfigGroup 5 }
--  hpnicfDot11sAPCfgTable                 ::= { hpnicfDot11sConfigGroup 6 }

hpnicfDot11sWDSConfigGroup OBJECT IDENTIFIER ::= { hpnicfDot11sMesh 2 }
--  Dot11s WDS Configuration Group has the following children:
--  hpnicfDot11sWDSPeerMacTable         ::= { hpnicfDot11sWDSConfigGroup 1 }

hpnicfDot11sMeshStatusGroup OBJECT IDENTIFIER ::= { hpnicfDot11sMesh 3 }
--  Dot11s Mesh Status Group has the following children:
--  hpnicfDot11sMeshLinkStatusTable    ::= { hpnicfDot11sMeshStatusGroup 1 }
--  hpnicfDot11sMeshLinkStatisTable    ::= { hpnicfDot11sMeshStatusGroup 2 }
--  hpnicfDot11sMeshNbrStatusTable     ::= { hpnicfDot11sMeshStatusGroup 3 }
-- *****************************************************************************
-- *  hpnicfDot11sMeshGlobalPara Definition
-- *****************************************************************************
hpnicfDot11sMeshGlobalPara OBJECT IDENTIFIER  ::= { hpnicfDot11sConfigGroup 1 }

hpnicfDot11sMeshMkdID OBJECT-TYPE
    SYNTAX      MacAddress
    MAX-ACCESS  read-write
    STATUS      current
    DESCRIPTION
        "This object represents the mesh key distributor identifier (MKD-ID).
        If the MKD-ID is not configured, the value is '00:00:00:00:00:00'."
    ::= { hpnicfDot11sMeshGlobalPara 1 }

-- *****************************************************************************
-- * End of hpnicfDot11sMeshGlobalPara Definition
-- *****************************************************************************
-- *****************************************************************************
-- *  hpnicfDot11sMeshPflTable Definition
-- *****************************************************************************
hpnicfDot11sMeshPflTable OBJECT-TYPE
    SYNTAX      SEQUENCE OF HpnicfDot11sMeshPflEntry
    MAX-ACCESS  not-accessible
    STATUS      current
    DESCRIPTION
        "This table is used to configure mesh profile.
        A mesh profile is created and mapped to a MP so that
        it can provide mesh services to other MPs which have the same
        mesh ID.
        When the mesh profile is enabled, all of the object in this table
        can not be modified except hpnicfDot11sMeshPflEnable.
        The mesh profile can not be deleted when it is bound with the radio."
    ::= { hpnicfDot11sConfigGroup 2 }

hpnicfDot11sMeshPflEntry OBJECT-TYPE
    SYNTAX      HpnicfDot11sMeshPflEntry
    MAX-ACCESS  not-accessible
    STATUS      current
    DESCRIPTION
        "Each entry contains information of a mesh profile."
    INDEX
        {
            hpnicfDot11sMeshPflIndex
        }
    ::= { hpnicfDot11sMeshPflTable 1 }

HpnicfDot11sMeshPflEntry ::= SEQUENCE
    {
        hpnicfDot11sMeshPflIndex         Integer32,
        hpnicfDot11sMeshPflMeshID        OCTET STRING,
        hpnicfDot11sMeshPflBindIntNum    Integer32,
        hpnicfDot11sMeshPflKeepAlive     Integer32,
        hpnicfDot11sMeshPflBackhaulRate  Integer32,
        hpnicfDot11sMeshMkdServEnable    TruthValue,
        hpnicfDot11sMeshPflEnable        TruthValue,
        hpnicfDot11sMeshPflRowStatus     RowStatus
    }

hpnicfDot11sMeshPflIndex OBJECT-TYPE
    SYNTAX      Integer32
    MAX-ACCESS  not-accessible
    STATUS      current
    DESCRIPTION
        "This object represents the index of the mesh profile."
    ::= { hpnicfDot11sMeshPflEntry 1 }

hpnicfDot11sMeshPflMeshID OBJECT-TYPE
    SYNTAX      OCTET STRING (SIZE (0..32))
    MAX-ACCESS  read-create
    STATUS      current
    DESCRIPTION
        "This object represents the mesh ID of the mesh profile.
        The string length of this object is zero when the mesh ID is not
        configured.  If the mesh ID is not configured, hpnicfDot11sMeshPflEnable
        can not be set to 'true'."
    ::= { hpnicfDot11sMeshPflEntry 2 }

hpnicfDot11sMeshPflBindIntNum OBJECT-TYPE
    SYNTAX      Integer32
    MAX-ACCESS  read-create
    STATUS      current
    DESCRIPTION
        "This object represents the specified mesh interface number
        binding to the mesh profile.
        If the value is set to -1, the binding will be removed.
        If the mesh interface is not specified, the value of
        hpnicfDot11sMeshPflEnable can not be set to 'true'."
    DEFVAL      { -1 }
    ::= { hpnicfDot11sMeshPflEntry 3 }

hpnicfDot11sMeshPflKeepAlive OBJECT-TYPE
    SYNTAX      Integer32(1..1800)
    UNITS       "second"
    MAX-ACCESS  read-create
    STATUS      current
    DESCRIPTION
        "This object represents the mesh link keep-alive interval."
    ::= { hpnicfDot11sMeshPflEntry 4 }

hpnicfDot11sMeshPflBackhaulRate OBJECT-TYPE
    SYNTAX      Integer32
    UNITS       "Kbps"
    MAX-ACCESS  read-create
    STATUS      current
    DESCRIPTION
        "This object represents the link backhaul rate."
    ::= { hpnicfDot11sMeshPflEntry 5 }

hpnicfDot11sMeshMkdServEnable OBJECT-TYPE
    SYNTAX      TruthValue
    MAX-ACCESS  read-create
    STATUS      current
    DESCRIPTION
        "This object indicates whether the mesh key distributor (MKD)
        service for the mesh profile is enabled.
        'true': The MKD service for the mesh profile is enabled.
        'false': The MKD service for the mesh profile is disabled."
    DEFVAL      { false }
    ::= { hpnicfDot11sMeshPflEntry 6 }

hpnicfDot11sMeshPflEnable OBJECT-TYPE
    SYNTAX      TruthValue
    MAX-ACCESS  read-create
    STATUS      current
    DESCRIPTION
        "This object indicates whether the mesh profile is enabled.
        'true': The mesh profile is enabled.
        'false': The mesh profile is disabled."
    DEFVAL      { false }
    ::= { hpnicfDot11sMeshPflEntry 7 }

hpnicfDot11sMeshPflRowStatus OBJECT-TYPE
    SYNTAX      RowStatus
    MAX-ACCESS  read-create
    STATUS      current
    DESCRIPTION
        "The status of this table entry."
    ::= { hpnicfDot11sMeshPflEntry 8 }

-- *****************************************************************************
-- * End of hpnicfDot11sMeshPflTable Definition
-- *****************************************************************************
-- *****************************************************************************
-- *  hpnicfDot11sMpPlcyTable Definition
-- *****************************************************************************
hpnicfDot11sMpPlcyTable OBJECT-TYPE
    SYNTAX      SEQUENCE OF HpnicfDot11sMpPlcyEntry
    MAX-ACCESS  not-accessible
    STATUS      current
    DESCRIPTION
        "This table is used to configure MP policy.
        There is 'default_mp_plcy' on system by default and its index is 1.
        The 'default_mp_plcy' can not be deleted or modified.
        The MP policy can not be deleted when it is applied to a radio.
        It can not be modified when it is applied to an enabled radio."
    ::= { hpnicfDot11sConfigGroup 3 }

hpnicfDot11sMpPlcyEntry OBJECT-TYPE
    SYNTAX      HpnicfDot11sMpPlcyEntry
    MAX-ACCESS  not-accessible
    STATUS      current
    DESCRIPTION
        "Each entry contains information of a MP policy."
    INDEX
        {
            hpnicfDot11sMpPlcyIndex
        }
    ::= { hpnicfDot11sMpPlcyTable 1 }

HpnicfDot11sMpPlcyEntry ::= SEQUENCE
    {
        hpnicfDot11sMpPlcyIndex          Integer32,
        hpnicfDot11sMpPlcyName           OCTET STRING,
        hpnicfDot11sMpPlcyInitEnable     TruthValue,
        hpnicfDot11sMlspEnable           TruthValue,
        hpnicfDot11sProbReqInterval      Integer32,
        hpnicfDot11sRoleAuthEnable       TruthValue,
        hpnicfDot11sLinkHoldRSSI         Integer32,
        hpnicfDot11sLinkHoldTime         Integer32,
        hpnicfDot11sSwitchMargin         Integer32,
        hpnicfDot11sLinkSaturationRSSI   Integer32,
        hpnicfDot11sLinkRateMode         INTEGER,
        hpnicfDot11sMaxLinkNum           Integer32,
        hpnicfDot11sMpPlcyRowStatus      RowStatus
    }

hpnicfDot11sMpPlcyIndex OBJECT-TYPE
    SYNTAX      Integer32
    MAX-ACCESS  not-accessible
    STATUS      current
    DESCRIPTION
        "This object represents the MP policy index."
    ::= { hpnicfDot11sMpPlcyEntry 1 }

hpnicfDot11sMpPlcyName OBJECT-TYPE
    SYNTAX      OCTET STRING (SIZE (1..15))
    MAX-ACCESS  read-create
    STATUS      current
    DESCRIPTION
        "This object represents the MP policy name.
        MP policy can not be created with name 'a', 'al', 'all' or
        'default_mp_plcy'.
        Modification is not supported."
    ::= { hpnicfDot11sMpPlcyEntry 2 }

hpnicfDot11sMpPlcyInitEnable OBJECT-TYPE
    SYNTAX      TruthValue
    MAX-ACCESS  read-create
    STATUS      current
    DESCRIPTION
        "This object indicates whether the link initiation for
        the MP policy is enabled.
        'true': The link initiation for the MP policy is enabled.
        'false': The link initiation for the MP policy is disabled."
    DEFVAL      { true }
    ::= { hpnicfDot11sMpPlcyEntry 3 }

hpnicfDot11sMlspEnable OBJECT-TYPE
    SYNTAX      TruthValue
    MAX-ACCESS  read-create
    STATUS      current
    DESCRIPTION
        "This object indicates whether the mesh link switch protocol (MLSP)
        is enabled.
        'true': MLSP is enabled.
        'false': MLSP is disabled."
    DEFVAL      { false }
    ::= { hpnicfDot11sMpPlcyEntry 4 }

hpnicfDot11sProbReqInterval OBJECT-TYPE
    SYNTAX      Integer32
    UNITS       "millisecond"
    MAX-ACCESS  read-create
    STATUS      current
    DESCRIPTION
        "This object represents the probe request interval."
    ::= { hpnicfDot11sMpPlcyEntry 5 }

hpnicfDot11sRoleAuthEnable OBJECT-TYPE
    SYNTAX      TruthValue
    MAX-ACCESS  read-create
    STATUS      current
    DESCRIPTION
        "This object indicates whether the device can play as the role
        of an authenticator."
    DEFVAL      { true }
    ::= { hpnicfDot11sMpPlcyEntry 6 }

hpnicfDot11sLinkHoldRSSI OBJECT-TYPE
    SYNTAX      Integer32(5..100)
    UNITS       "dBm"
    MAX-ACCESS  read-create
    STATUS      current
    DESCRIPTION
        "This object represents the link-hold
        receive signal strength indicator (RSSI)."
    ::= { hpnicfDot11sMpPlcyEntry 7 }

hpnicfDot11sLinkHoldTime OBJECT-TYPE
    SYNTAX      Integer32(1000..20000)
    UNITS       "millisecond"
    MAX-ACCESS  read-create
    STATUS      current
    DESCRIPTION
        "This object represents the link-hold time."
    ::= { hpnicfDot11sMpPlcyEntry 8 }

hpnicfDot11sSwitchMargin OBJECT-TYPE
    SYNTAX      Integer32(1..100)
    UNITS       "dBm"
    MAX-ACCESS  read-create
    STATUS      current
    DESCRIPTION
        "This object represents the link-switch margin."
    ::= { hpnicfDot11sMpPlcyEntry 9 }

hpnicfDot11sLinkSaturationRSSI OBJECT-TYPE
    SYNTAX      Integer32(30..150)
    UNITS       "dBm"
    MAX-ACCESS  read-create
    STATUS      current
    DESCRIPTION
        "This object represents the link saturation
        receive signal strength indicator (RSSI)."
    ::= { hpnicfDot11sMpPlcyEntry 10 }

hpnicfDot11sLinkRateMode OBJECT-TYPE
    SYNTAX      INTEGER
        {
            fixed(1),
            realtime(2)
        }
    MAX-ACCESS  read-create
    STATUS      current
    DESCRIPTION
        "This object represents the rate mode of the mesh link."
    DEFVAL      { fixed }
    ::= { hpnicfDot11sMpPlcyEntry 11 }

hpnicfDot11sMaxLinkNum OBJECT-TYPE
    SYNTAX      Integer32
    MAX-ACCESS  read-create
    STATUS      current
    DESCRIPTION
        "This object represents the maximum number of the mesh link."
    ::= { hpnicfDot11sMpPlcyEntry 12 }

hpnicfDot11sMpPlcyRowStatus OBJECT-TYPE
    SYNTAX      RowStatus
    MAX-ACCESS  read-create
    STATUS      current
    DESCRIPTION
        "The status of this table entry."
    ::= { hpnicfDot11sMpPlcyEntry 13 }

-- *****************************************************************************
-- * End of hpnicfDot11sMpPlcyTable Definition
-- *****************************************************************************
-- *****************************************************************************
-- *  hpnicfDot11sMlspCfgTable Definition
-- *****************************************************************************
hpnicfDot11sMlspCfgTable OBJECT-TYPE
    SYNTAX      SEQUENCE OF HpnicfDot11sMlspCfgEntry
    MAX-ACCESS  not-accessible
    STATUS      current
    DESCRIPTION
        "This table is used to configure MLSP proxy MAC address.
        Only if the specified MP policy is modifiable and the MLSP
        is enabled, the row of this table can be created and deleted.
        The row of this table can not be modified."
    ::= { hpnicfDot11sConfigGroup 4 }

hpnicfDot11sMlspCfgEntry OBJECT-TYPE
    SYNTAX      HpnicfDot11sMlspCfgEntry
    MAX-ACCESS  not-accessible
    STATUS      current
    DESCRIPTION
        "Each entry contains information of MLSP proxy MAC address."
    INDEX
        {
            hpnicfDot11sMpPlcyIndex,
            hpnicfDot11sMlspProxyIndex
        }
    ::= { hpnicfDot11sMlspCfgTable 1 }

HpnicfDot11sMlspCfgEntry ::= SEQUENCE
    {
        hpnicfDot11sMlspProxyIndex       Integer32,
        hpnicfDot11sMlspProxyMac         MacAddress,
        hpnicfDot11sMlspRowStatus        RowStatus
    }

hpnicfDot11sMlspProxyIndex OBJECT-TYPE
    SYNTAX      Integer32
    MAX-ACCESS  not-accessible
    STATUS      current
    DESCRIPTION
        "This object represents the MLSP proxy MAC address index."
    ::= { hpnicfDot11sMlspCfgEntry 1 }

hpnicfDot11sMlspProxyMac OBJECT-TYPE
    SYNTAX      MacAddress
    MAX-ACCESS  read-create
    STATUS      current
    DESCRIPTION
        "This object represents the MLSP proxy MAC address."
    ::= { hpnicfDot11sMlspCfgEntry 2 }

hpnicfDot11sMlspRowStatus OBJECT-TYPE
    SYNTAX      RowStatus
    MAX-ACCESS  read-create
    STATUS      current
    DESCRIPTION
        "The status of this table entry."
    ::= { hpnicfDot11sMlspCfgEntry 3 }

-- *****************************************************************************
-- * End of hpnicfDot11sMlspCfgTable Definition
-- *****************************************************************************
-- *****************************************************************************
-- *  hpnicfDot11sRadioCfgTable Definition
-- *****************************************************************************
hpnicfDot11sRadioCfgTable OBJECT-TYPE
    SYNTAX      SEQUENCE OF HpnicfDot11sRadioCfgEntry
    MAX-ACCESS  not-accessible
    STATUS      current
    DESCRIPTION
        "This table is used to configure mesh to the specified radio."
    ::= { hpnicfDot11sConfigGroup 5 }

hpnicfDot11sRadioCfgEntry OBJECT-TYPE
    SYNTAX      HpnicfDot11sRadioCfgEntry
    MAX-ACCESS  not-accessible
    STATUS      current
    DESCRIPTION
        "Each entry contains mesh configure information
        of the specified radio."
    INDEX
        {
            hpnicfDot11sCfgRadioIndex
        }
    ::= { hpnicfDot11sRadioCfgTable 1 }

HpnicfDot11sRadioCfgEntry ::= SEQUENCE
    {
        hpnicfDot11sCfgRadioIndex        HpnicfDot11RadioElementIndex,
        hpnicfDot11sMeshPflMap           Integer32,
        hpnicfDot11sMpPlcyMap            Integer32
    }

hpnicfDot11sCfgRadioIndex OBJECT-TYPE
    SYNTAX      HpnicfDot11RadioElementIndex
    MAX-ACCESS  not-accessible
    STATUS      current
    DESCRIPTION
        "Represents index of the radio."
    ::= { hpnicfDot11sRadioCfgEntry 1 }

hpnicfDot11sMeshPflMap OBJECT-TYPE
    SYNTAX      Integer32
    MAX-ACCESS  read-write
    STATUS      current
    DESCRIPTION
        "This object represents the number of the mesh profile mapped to
        the specified radio.  The value is zero when the radio is not
        binding mesh profile."
    DEFVAL      { 0 }
    ::= { hpnicfDot11sRadioCfgEntry 2 }

hpnicfDot11sMpPlcyMap OBJECT-TYPE
    SYNTAX      Integer32
    MAX-ACCESS  read-write
    STATUS      current
    DESCRIPTION
        "This object represents the index of the MP policy mapped to the
        specified radio.  The MP policy is 'default_mp_plcy' when the radio
        is not binding user-defined MP policy.
        The index of 'default_mp_plcy' is 1.
        This object can not be modified when the radio is enabled."
    DEFVAL      { 1 }
    ::= { hpnicfDot11sRadioCfgEntry 3 }

-- *****************************************************************************
-- * End of hpnicfDot11sRadioCfgTable Definition
-- *****************************************************************************
-- *****************************************************************************
-- *  hpnicfDot11sAPCfgTable Definition
-- *****************************************************************************
hpnicfDot11sAPCfgTable OBJECT-TYPE
    SYNTAX      SEQUENCE OF HpnicfDot11sAPCfgEntry
    MAX-ACCESS  not-accessible
    STATUS      current
    DESCRIPTION
        "This table is used to configure mesh to the specified AP."
    ::= { hpnicfDot11sConfigGroup 6 }

hpnicfDot11sAPCfgEntry OBJECT-TYPE
    SYNTAX      HpnicfDot11sAPCfgEntry
    MAX-ACCESS  not-accessible
    STATUS      current
    DESCRIPTION
        "Each entry contains mesh configure information
        of the specified AP."
    INDEX
        {
            hpnicfDot11APElementIndex
        }
    ::= { hpnicfDot11sAPCfgTable 1 }

HpnicfDot11sAPCfgEntry ::= SEQUENCE
    {
        hpnicfDot11sPortalEnable         TruthValue
    }

hpnicfDot11sPortalEnable OBJECT-TYPE
    SYNTAX      TruthValue
    MAX-ACCESS  read-write
    STATUS      current
    DESCRIPTION
        "This object indicates whether the portal service is enabled.
        'true': The portal service is enabled.
        'false': The portal service is disabled."
    DEFVAL      { false }
    ::= { hpnicfDot11sAPCfgEntry 1 }

-- *****************************************************************************
-- * End of hpnicfDot11sAPCfgTable Definition
-- *****************************************************************************
-- *****************************************************************************
-- *  hpnicfDot11sWDSPeerMacTable Definition
-- *****************************************************************************
hpnicfDot11sWDSPeerMacTable OBJECT-TYPE
    SYNTAX      SEQUENCE OF HpnicfDot11sWDSPeerMacEntry
    MAX-ACCESS  not-accessible
    STATUS      current
    DESCRIPTION
        "This table is used to configure wireless distribution system (WDS).
        The row of this table can not be modified."
    ::= { hpnicfDot11sWDSConfigGroup 1 }

hpnicfDot11sWDSPeerMacEntry OBJECT-TYPE
    SYNTAX      HpnicfDot11sWDSPeerMacEntry
    MAX-ACCESS  not-accessible
    STATUS      current
    DESCRIPTION
        "Each entry contains information of WDS."
    INDEX
        {
            hpnicfDot11sCfgRadioIndex,
            hpnicfDot11sWDSPeerMacIndex
        }
    ::= { hpnicfDot11sWDSPeerMacTable 1 }

HpnicfDot11sWDSPeerMacEntry ::= SEQUENCE
    {
        hpnicfDot11sWDSPeerMacIndex      Integer32,
        hpnicfDot11sWDSPeerMacAddrss     MacAddress,
        hpnicfDot11sWDSPeerMacRowStatus  RowStatus
    }

hpnicfDot11sWDSPeerMacIndex OBJECT-TYPE
    SYNTAX      Integer32
    MAX-ACCESS  not-accessible
    STATUS      current
    DESCRIPTION
        "This object represents the peer MAC address index."
    ::= { hpnicfDot11sWDSPeerMacEntry 1 }

hpnicfDot11sWDSPeerMacAddrss OBJECT-TYPE
    SYNTAX      MacAddress
    MAX-ACCESS  read-create
    STATUS      current
    DESCRIPTION
        "This object represents the peer MAC address."
    ::= { hpnicfDot11sWDSPeerMacEntry 2 }

hpnicfDot11sWDSPeerMacRowStatus OBJECT-TYPE
    SYNTAX      RowStatus
    MAX-ACCESS  read-create
    STATUS      current
    DESCRIPTION
        "The status of this table entry."
    ::= { hpnicfDot11sWDSPeerMacEntry 3 }

-- *****************************************************************************
-- * End of hpnicfDot11sWDSPeerMacTable Definition
-- *****************************************************************************
-- *****************************************************************************
-- *  hpnicfDot11sMeshLinkStatusTable Definition
-- *****************************************************************************
hpnicfDot11sMeshLinkStatusTable OBJECT-TYPE
    SYNTAX      SEQUENCE OF HpnicfDot11sMeshLinkStatusEntry
    MAX-ACCESS  not-accessible
    STATUS      current
    DESCRIPTION
        "This table is used to represent the status of mesh link."
    ::= { hpnicfDot11sMeshStatusGroup 1 }

hpnicfDot11sMeshLinkStatusEntry OBJECT-TYPE
    SYNTAX      HpnicfDot11sMeshLinkStatusEntry
    MAX-ACCESS  not-accessible
    STATUS      current
    DESCRIPTION
        "Each entry contains status information of mesh link."
    INDEX
        {
            hpnicfDot11sMeshLinkIfIndex
        }
    ::= { hpnicfDot11sMeshLinkStatusTable 1 }

HpnicfDot11sMeshLinkStatusEntry ::= SEQUENCE
    {
        hpnicfDot11sMeshLinkIfIndex        Unsigned32,
        hpnicfDot11sMeshLinkName           OCTET STRING,
        hpnicfDot11sMeshLinkBSSID          MacAddress,
        hpnicfDot11sMeshLinkPeerMac        MacAddress,
        hpnicfDot11sMeshLinkExistDuration  Integer32,
        hpnicfDot11sMeshLinkType           INTEGER
    }

hpnicfDot11sMeshLinkIfIndex OBJECT-TYPE
    SYNTAX      Unsigned32
    MAX-ACCESS  not-accessible
    STATUS      current
    DESCRIPTION
        "This object represents the interface index of the mesh link."
    ::= { hpnicfDot11sMeshLinkStatusEntry 1 }

hpnicfDot11sMeshLinkName OBJECT-TYPE
    SYNTAX      OCTET STRING
    MAX-ACCESS  read-only
    STATUS      current
    DESCRIPTION
        "This object represents the name of the mesh link."
    ::= { hpnicfDot11sMeshLinkStatusEntry 2 }

hpnicfDot11sMeshLinkBSSID OBJECT-TYPE
    SYNTAX      MacAddress
    MAX-ACCESS  read-only
    STATUS      current
    DESCRIPTION
        "This object represents the BSS ID of the mesh link."
    ::= { hpnicfDot11sMeshLinkStatusEntry 3 }

hpnicfDot11sMeshLinkPeerMac OBJECT-TYPE
    SYNTAX      MacAddress
    MAX-ACCESS  read-only
    STATUS      current
    DESCRIPTION
        "This object represents the peer MAC address of the mesh link."
    ::= { hpnicfDot11sMeshLinkStatusEntry 4 }

hpnicfDot11sMeshLinkExistDuration OBJECT-TYPE
    SYNTAX      Integer32
    UNITS       "second"
    MAX-ACCESS  read-only
    STATUS      current
    DESCRIPTION
        "This object represents the time for which the link has been up."
    ::= { hpnicfDot11sMeshLinkStatusEntry 5 }

hpnicfDot11sMeshLinkType OBJECT-TYPE
    SYNTAX      INTEGER
        {
            active(1),
            dormant(2)
        }
    MAX-ACCESS  read-only
    STATUS      current
    DESCRIPTION
        "This object represents the type for the link."
    ::= { hpnicfDot11sMeshLinkStatusEntry 6 }
-- *****************************************************************************
-- * End of hpnicfDot11sMeshLinkStatusTable Definition
-- *****************************************************************************

-- *****************************************************************************
-- *  hpnicfDot11sMeshLinkStatisTable Definition
-- *****************************************************************************
hpnicfDot11sMeshLinkStatisTable OBJECT-TYPE
    SYNTAX      SEQUENCE OF HpnicfDot11sMeshLinkStatisEntry
    MAX-ACCESS  not-accessible
    STATUS      current
    DESCRIPTION
        "This table is used to represent the statistical information of
         mesh link."
    ::= { hpnicfDot11sMeshStatusGroup 2 }

hpnicfDot11sMeshLinkStatisEntry OBJECT-TYPE
    SYNTAX      HpnicfDot11sMeshLinkStatisEntry
    MAX-ACCESS  not-accessible
    STATUS      current
    DESCRIPTION
        "Each entry contains statistical information of mesh link."
    INDEX
        {
            hpnicfDot11APElementIndex,
            hpnicfDot11sMeshLinkStatIfIndex
        }
    ::= { hpnicfDot11sMeshLinkStatisTable 1 }

HpnicfDot11sMeshLinkStatisEntry ::= SEQUENCE
    {
        hpnicfDot11sMeshLinkStatIfIndex    Unsigned32,
        hpnicfDot11sMeshLinkNbrIndex       Unsigned32,
        hpnicfDot11sMeshLinkRxTotByte      Counter32,
        hpnicfDot11sMeshLinkRxTotPkt       Counter32,
        hpnicfDot11sMeshLinkRxUniPkt       Counter32,
        hpnicfDot11sMeshLinkRxBrocPkt      Counter32,
        hpnicfDot11sMeshLinkRxMuticPkt     Counter32,
        hpnicfDot11sMeshLinkRxDiscPkt      Counter32,
        hpnicfDot11sMeshLinkTxTotByte      Counter32,
        hpnicfDot11sMeshLinkTxTotPkt       Counter32,
        hpnicfDot11sMeshLinkTxUniPkt       Counter32,
        hpnicfDot11sMeshLinkTxBrocPkt      Counter32,
        hpnicfDot11sMeshLinkTxMuticPkt     Counter32,
        hpnicfDot11sMeshLinkTxDiscPkt      Counter32,
        hpnicfDot11sMeshLinkIFName         OCTET STRING
    }

hpnicfDot11sMeshLinkStatIfIndex OBJECT-TYPE
    SYNTAX      Unsigned32
    MAX-ACCESS  not-accessible
    STATUS      current
    DESCRIPTION
        "This object represents the interface index of the mesh link."
    ::= { hpnicfDot11sMeshLinkStatisEntry 1 }

hpnicfDot11sMeshLinkNbrIndex OBJECT-TYPE
    SYNTAX      Unsigned32
    MAX-ACCESS  read-only
    STATUS      current
    DESCRIPTION
        "Represents the neighbor index of the mesh link."
    ::= { hpnicfDot11sMeshLinkStatisEntry 2 }

hpnicfDot11sMeshLinkRxTotByte OBJECT-TYPE
    SYNTAX      Counter32
    MAX-ACCESS  read-only
    STATUS      current
    DESCRIPTION
        "Represents the amount of bytes that the mesh link received."
    ::= { hpnicfDot11sMeshLinkStatisEntry 3 }

hpnicfDot11sMeshLinkRxTotPkt OBJECT-TYPE
    SYNTAX      Counter32
    MAX-ACCESS  read-only
    STATUS      current
    DESCRIPTION
        "Represents the amount of packets that the mesh link received."
    ::= { hpnicfDot11sMeshLinkStatisEntry 4 }

hpnicfDot11sMeshLinkRxUniPkt OBJECT-TYPE
    SYNTAX      Counter32
    MAX-ACCESS  read-only
    STATUS      current
    DESCRIPTION
        "Represents the amount of unicast packets that the mesh link received."
    ::= { hpnicfDot11sMeshLinkStatisEntry 5 }

hpnicfDot11sMeshLinkRxBrocPkt OBJECT-TYPE
    SYNTAX      Counter32
    MAX-ACCESS  read-only
    STATUS      current
    DESCRIPTION
        "Represents the amount of broadcast packets that the mesh link
         received."
    ::= { hpnicfDot11sMeshLinkStatisEntry 6 }

hpnicfDot11sMeshLinkRxMuticPkt OBJECT-TYPE
    SYNTAX      Counter32
    MAX-ACCESS  read-only
    STATUS      current
    DESCRIPTION
        "Represents the amount of multicast packets that the mesh link
         received."
    ::= { hpnicfDot11sMeshLinkStatisEntry 7 }

hpnicfDot11sMeshLinkRxDiscPkt OBJECT-TYPE
    SYNTAX      Counter32
    MAX-ACCESS  read-only
    STATUS      current
    DESCRIPTION
        "Represents the amount of packets that the mesh link discarded."
    ::= { hpnicfDot11sMeshLinkStatisEntry 8 }

hpnicfDot11sMeshLinkTxTotByte OBJECT-TYPE
    SYNTAX      Counter32
    MAX-ACCESS  read-only
    STATUS      current
    DESCRIPTION
        "Represents the total amount of bytes that the mesh link transmitted."
    ::= { hpnicfDot11sMeshLinkStatisEntry 9 }

hpnicfDot11sMeshLinkTxTotPkt OBJECT-TYPE
    SYNTAX      Counter32
    MAX-ACCESS  read-only
    STATUS      current
    DESCRIPTION
        "Represents the total amount of packets that the mesh link transmitted."
    ::= { hpnicfDot11sMeshLinkStatisEntry 10 }

hpnicfDot11sMeshLinkTxUniPkt OBJECT-TYPE
    SYNTAX      Counter32
    MAX-ACCESS  read-only
    STATUS      current
    DESCRIPTION
        "Represents the amount of unicast packets that the mesh link
         transmitted."
    ::= { hpnicfDot11sMeshLinkStatisEntry 11 }

hpnicfDot11sMeshLinkTxBrocPkt OBJECT-TYPE
    SYNTAX      Counter32
    MAX-ACCESS  read-only
    STATUS      current
    DESCRIPTION
        "Represents the amount of broadcast packets that the mesh link
         transmitted."
    ::= { hpnicfDot11sMeshLinkStatisEntry 12 }

hpnicfDot11sMeshLinkTxMuticPkt OBJECT-TYPE
    SYNTAX      Counter32
    MAX-ACCESS  read-only
    STATUS      current
    DESCRIPTION
        "Represents the amount of multicast packets that the mesh link
         transmitted."
    ::= { hpnicfDot11sMeshLinkStatisEntry 13 }

hpnicfDot11sMeshLinkTxDiscPkt OBJECT-TYPE
    SYNTAX      Counter32
    MAX-ACCESS  read-only
    STATUS      current
    DESCRIPTION
        "Represents the amount of discarded packets that the mesh link
         transmitted."
    ::= { hpnicfDot11sMeshLinkStatisEntry 14 }

hpnicfDot11sMeshLinkIFName    OBJECT-TYPE
    SYNTAX      OCTET STRING
    MAX-ACCESS  read-only
    STATUS      current
    DESCRIPTION
        "Represents the name of mesh link interface."
    ::= { hpnicfDot11sMeshLinkStatisEntry 15 }

-- *****************************************************************************
-- * End of hpnicfDot11sMeshLinkStatisTable Definition
-- *****************************************************************************

-- *****************************************************************************
-- *  hpnicfDot11sMeshNbrStatusTable Definition
-- *****************************************************************************
hpnicfDot11sMeshNbrStatusTable OBJECT-TYPE
    SYNTAX      SEQUENCE OF HpnicfDot11sMeshNbrStatusEntry
    MAX-ACCESS  not-accessible
    STATUS      current
    DESCRIPTION
        "This table represents the status information for the neighbors of MP."
    ::= { hpnicfDot11sMeshStatusGroup 3 }

hpnicfDot11sMeshNbrStatusEntry OBJECT-TYPE
    SYNTAX      HpnicfDot11sMeshNbrStatusEntry
    MAX-ACCESS  not-accessible
    STATUS      current
    DESCRIPTION
        "Each entry of the table will provide status information for the
         neighbors of MP."
    INDEX
        {
            hpnicfDot11APElementIndex,
            hpnicfDot11sMeshNbrIndex
        }
    ::= { hpnicfDot11sMeshNbrStatusTable 1 }

HpnicfDot11sMeshNbrStatusEntry ::= SEQUENCE
    {
        hpnicfDot11sMeshNbrIndex          Unsigned32,
        hpnicfDot11sMeshNbrRadioID        Unsigned32,
        hpnicfDot11sMeshLocalMeshID       OCTET STRING,
        hpnicfDot11sMeshNbrMeshID         OCTET STRING,
        hpnicfDot11sMeshNbrBSSID          MacAddress,
        hpnicfDot11sMeshNbrPeerMac        MacAddress,
        hpnicfDot11sMeshLinkInMp          Unsigned32,
        hpnicfDot11sMeshMPLinkStatus      INTEGER,
        hpnicfDot11sMeshNbrChannel        Unsigned32,
        hpnicfDot11sMeshNbrLinkDuration   Integer32,
        hpnicfDot11sMeshNbrRSSI           Integer32,
        hpnicfDot11sMeshNbrSNR            Integer32
    }

hpnicfDot11sMeshNbrIndex OBJECT-TYPE
    SYNTAX      Unsigned32
    MAX-ACCESS  not-accessible
    STATUS      current
    DESCRIPTION
        "Represents the index for the neighbor."
    ::= { hpnicfDot11sMeshNbrStatusEntry 1 }

hpnicfDot11sMeshNbrRadioID OBJECT-TYPE
    SYNTAX      Unsigned32
    MAX-ACCESS  read-only
    STATUS      current
    DESCRIPTION
        "Represents the radio ID of the neighbor."
    ::= { hpnicfDot11sMeshNbrStatusEntry 2 }

hpnicfDot11sMeshLocalMeshID OBJECT-TYPE
    SYNTAX      OCTET STRING(SIZE(0..32))
    MAX-ACCESS  read-only
    STATUS      current
    DESCRIPTION
        "Represents the local mesh ID."
    ::= { hpnicfDot11sMeshNbrStatusEntry 3 }

hpnicfDot11sMeshNbrMeshID OBJECT-TYPE
    SYNTAX      OCTET STRING(SIZE(0..32))
    MAX-ACCESS  read-only
    STATUS      current
    DESCRIPTION
        "Represents the mesh ID of the neighbor."
    ::= { hpnicfDot11sMeshNbrStatusEntry 4 }

hpnicfDot11sMeshNbrBSSID OBJECT-TYPE
    SYNTAX      MacAddress
    MAX-ACCESS  read-only
    STATUS      current
    DESCRIPTION
        "Represents the BSS ID of the neighbor."
    ::= { hpnicfDot11sMeshNbrStatusEntry 5 }

hpnicfDot11sMeshNbrPeerMac OBJECT-TYPE
    SYNTAX      MacAddress
    MAX-ACCESS  read-only
    STATUS      current
    DESCRIPTION
        "Represents the MAC address of the peer neighbor."
    ::= { hpnicfDot11sMeshNbrStatusEntry 6 }

hpnicfDot11sMeshLinkInMp OBJECT-TYPE
    SYNTAX      Unsigned32
    MAX-ACCESS  read-only
    STATUS      current
    DESCRIPTION
        "Represents the interface index of mesh link that used to connect with
         this neighbor."
    ::= { hpnicfDot11sMeshNbrStatusEntry 7 }

hpnicfDot11sMeshMPLinkStatus OBJECT-TYPE
    SYNTAX      INTEGER
        {
            processing(1),
            up(2),
            down(3)
        }
    MAX-ACCESS  read-only
    STATUS      current
    DESCRIPTION
        "Represents the status of mesh link that used to connect with this
         neighbor."
    ::= { hpnicfDot11sMeshNbrStatusEntry 8 }

hpnicfDot11sMeshNbrChannel OBJECT-TYPE
    SYNTAX      Unsigned32
    MAX-ACCESS  read-only
    STATUS      current
    DESCRIPTION
        "Represents the channel number used by this neighbor."
    ::= { hpnicfDot11sMeshNbrStatusEntry 9 }

hpnicfDot11sMeshNbrLinkDuration OBJECT-TYPE
    SYNTAX      Integer32
    UNITS       "second"
    MAX-ACCESS  read-only
    STATUS      current
    DESCRIPTION
        "Represents the duration of mesh link that used to connect with this
         neighbor."
    ::= { hpnicfDot11sMeshNbrStatusEntry 10 }

hpnicfDot11sMeshNbrRSSI OBJECT-TYPE
    SYNTAX      Integer32
    MAX-ACCESS  read-only
    STATUS      current
    DESCRIPTION
        "Represents the RSSI of mesh link that used to connect with this
         neighbor."
    ::= { hpnicfDot11sMeshNbrStatusEntry 11 }

hpnicfDot11sMeshNbrSNR OBJECT-TYPE
    SYNTAX      Integer32
    UNITS       "percent"
    MAX-ACCESS  read-only
    STATUS      current
    DESCRIPTION
        "Represents the SNR of mesh link that used to connect with this
         neighbor."
    ::= { hpnicfDot11sMeshNbrStatusEntry 12 }

-- *****************************************************************************
-- *  End of hpnicfDot11sMeshNbrStatusTable Definition
-- *****************************************************************************
END
