-- =========================================================================
-- Copyright (c) 2010-2013 Hewlett-Packard Development Company, L.P.
--
-- Description: This file describes various common MIB objects implemented 
-- by both Routers and Switches.
-- Reference: VRRP-MIB
-- Version: V1.0
-- History:
--      V1.0 2004-12-09
--        Initial version
-- =========================================================================
HPN-ICF-VRRP-EXT-MIB DEFINITIONS ::= BEGIN

 IMPORTS
     MODULE-IDENTITY, OBJECT-TYPE, Integer32                         
         FROM SNMPv2-SMI

     RowStatus       
         FROM SNMPv2-TC

     ifIndex               
         FROM IF-MIB  

     vrrpOperVrId                        
         FROM VRRP-MIB     

     hpnicfCommon                          
         FROM HPN-ICF-OID-MIB;


 hpnicfVrrpExt MODULE-IDENTITY
     LAST-UPDATED 
         "200412090000Z"
     ORGANIZATION
         ""
     CONTACT-INFO
         ""
     DESCRIPTION
         "This MIB describes objects used for managing Virtual Router
         Redundancy Protocol (VRRP) routers."
     ::= { hpnicfCommon 24 }


-- ===================================================================
--  Start of MIB objects
-- ===================================================================

 hpnicfVrrpExtMibObject      OBJECT IDENTIFIER ::= { hpnicfVrrpExt 1 }        

-- ===================================================================
--  VRRP EXT Table
-- ===================================================================

 hpnicfVrrpExtTable OBJECT-TYPE
     SYNTAX       SEQUENCE OF HpnicfVrrpExtEntry
     MAX-ACCESS   not-accessible
     STATUS       current
     DESCRIPTION
         "Table extends for a VRRP router which consists of a
         sequence (i.e., one or more conceptual rows) of
         hpnicfVrrpExtEntry items."
     ::= { hpnicfVrrpExtMibObject 1 }

 hpnicfVrrpExtEntry OBJECT-TYPE
     SYNTAX       HpnicfVrrpExtEntry
     MAX-ACCESS   not-accessible
     STATUS       current
     DESCRIPTION
         "An entry in the hpnicfVrrpExtTable containing the status
         values of a virtual router."
     INDEX    { ifIndex, vrrpOperVrId, hpnicfVrrpExtTrackInterface }
     ::= { hpnicfVrrpExtTable 1 }

 HpnicfVrrpExtEntry ::=
     SEQUENCE {
         hpnicfVrrpExtTrackInterface
             INTEGER,
         hpnicfVrrpExtPriorityReduce
             Integer32,
         hpnicfVrrpExtRowStatus
             RowStatus
 }

 hpnicfVrrpExtTrackInterface OBJECT-TYPE
     SYNTAX INTEGER (0..2147483647)
     MAX-ACCESS not-accessible
     STATUS current
     DESCRIPTION
         "This value is the ifIndex that identifies which interface 
         the virtual router tracked."
     ::= { hpnicfVrrpExtEntry 1 }

 hpnicfVrrpExtPriorityReduce  OBJECT-TYPE
     SYNTAX       Integer32 (1..255)
     MAX-ACCESS   read-create
     STATUS       current
     DESCRIPTION
         "This value identifies how much priority of a virtual router
         will be reduced/increased when the interface tracked is down/up."
     DEFVAL { 10 }
     ::= { hpnicfVrrpExtEntry 2 }

 hpnicfVrrpExtRowStatus OBJECT-TYPE
     SYNTAX       RowStatus
     MAX-ACCESS   read-create
     STATUS       current
     DESCRIPTION   
         "The row status variable, used according to installation
         and removal conventions for conceptual rows. Setting this
         object to active(1) or createAndGo(4) results in the
         addition of the ifIndex tracked by a virtual router.
         Destroying the entry removes the tracked ifIndex from the 
         virtual router. Other values is not supported now."
     ::= { hpnicfVrrpExtEntry 3 }

END
