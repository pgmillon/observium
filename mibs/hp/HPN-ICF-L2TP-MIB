-- ============================================================================
-- Copyright (c) 2010-2013 Hewlett-Packard Development Company, L.P.
-- Description:  This MIB file is used for configuration of L2TP(Layer 2
--               Tunneling Protocol).
--               include :1.L2TP statistics information
-- Reference:
-- Version: V1.0
-- History:
-- V1.0 2013/7/5 created by yanbotao
-- ============================================================================
HPN-ICF-L2TP-MIB DEFINITIONS ::= BEGIN
IMPORTS
    hpnicfCommon
        FROM HPN-ICF-OID-MIB
    Integer32, Counter32, OBJECT-TYPE, MODULE-IDENTITY
        FROM SNMPv2-SMI;

hpnicfL2tp MODULE-IDENTITY
    LAST-UPDATED "201307051518Z"            -- July 05, 2013 at 15:18 GMT
    ORGANIZATION
        ""
    CONTACT-INFO
        ""
    DESCRIPTION
        "This MIB contains objects to manage configuration of L2TP.
        There are no constraints on this MIB."
        REVISION "201307051518Z"                -- July 05, 2013 at 15:18 GMT
    DESCRIPTION
        "The initial revision of this MIB module."
    ::= { hpnicfCommon 139 }

--
-- Node definitions
--
--
-- Definitions of significant branches
--
hpnicfL2tpObjects         OBJECT IDENTIFIER  ::= { hpnicfL2tp 1 }
hpnicfL2tpScalar          OBJECT IDENTIFIER  ::= { hpnicfL2tpObjects 1 }
hpnicfL2tpStats           OBJECT IDENTIFIER  ::= { hpnicfL2tpScalar 1 }

--
-- The L2TP Scalar Status and Statistics Group
--

hpnicfL2tpStatsTotalTunnels OBJECT-TYPE
    SYNTAX          Counter32
    MAX-ACCESS      read-only
    STATUS          current
    DESCRIPTION
        "The total number of tunnels at the time of querying."
    ::= { hpnicfL2tpStats 1 }

hpnicfL2tpStatsTotalSessions OBJECT-TYPE
    SYNTAX        Counter32
    MAX-ACCESS    read-only
    STATUS        current
    DESCRIPTION
        "The total number of sessions at the time of querying."
    ::= { hpnicfL2tpStats 2 }

hpnicfL2tpSessionRate  OBJECT-TYPE
    SYNTAX        Integer32
    MAX-ACCESS    read-only
    STATUS        current
    DESCRIPTION
        "The number of sessions that were created in the previous second."
    ::= { hpnicfL2tpStats 3 }

END
