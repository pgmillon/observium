-- =====================================================================
-- Copyright (c) 2010-2013 Hewlett-Packard Development Company, L.P.
-- Description: Service loopback group MIB.
-- Reference:
-- Version: V1.0
-- History:
-- V1.0 Initial version
-- =====================================================================
HPN-ICF-SLBG-MIB DEFINITIONS ::= BEGIN

IMPORTS
    Unsigned32, OBJECT-TYPE, MODULE-IDENTITY
        FROM SNMPv2-SMI
    RowStatus
        FROM SNMPv2-TC
    InterfaceIndex
        FROM IF-MIB
    hpnicfCommon
        FROM HPN-ICF-OID-MIB;

hpnicfSlbg MODULE-IDENTITY
    LAST-UPDATED "201210160000Z"
    ORGANIZATION
        ""
    CONTACT-INFO
        ""
    DESCRIPTION
        "H3C service loopback group MIB."
    REVISION "201210160000Z"
    DESCRIPTION
        "The initial revision of this MIB module."
    ::= { hpnicfCommon 130 }

---------------------------------------------------------------
-- Node definitions
---------------------------------------------------------------

hpnicfSlbgMibTable OBJECT IDENTIFIER ::= { hpnicfSlbg 1 }

hpnicfSlbgGroupTable OBJECT-TYPE
    SYNTAX SEQUENCE OF HpnicfSlbgGroupEntry
    MAX-ACCESS not-accessible
    STATUS current
    DESCRIPTION
        "A table of service loopback group objects."
    ::= { hpnicfSlbgMibTable 1 }

hpnicfSlbgGroupEntry OBJECT-TYPE
    SYNTAX HpnicfSlbgGroupEntry
    MAX-ACCESS not-accessible
    STATUS current
    DESCRIPTION
        "The service loopback group entry."
    INDEX { hpnicfSlbgGroupNumber }
    ::= { hpnicfSlbgGroupTable 1 }

HpnicfSlbgGroupEntry ::=
    SEQUENCE {
        hpnicfSlbgGroupNumber
            Unsigned32,
        hpnicfSlbgGroupSrvType
            BITS,
        hpnicfSlbgGroupRowStatus
            RowStatus
     }

hpnicfSlbgGroupNumber OBJECT-TYPE
    SYNTAX Unsigned32
    MAX-ACCESS not-accessible
    STATUS current
    DESCRIPTION
        "Serial number of the service loopback group."
    ::= { hpnicfSlbgGroupEntry 1 }

hpnicfSlbgGroupSrvType OBJECT-TYPE
    SYNTAX BITS
        {
            ipv6(0),
            ipv6mc(1),
            tunnel(2),
            multicastTunnel(3),
            mpls(4)
        }
    MAX-ACCESS read-create
    STATUS current
    DESCRIPTION
        "Service type of the service loopback group.
         ipv6: IPv6 unicast service type.
         ipv6mc: IPv6 multicast service type.
         tunnel: Unicast tunnel service type.
         multicastTunnel: Multicast tunnel service type.
         mpls: MPLS service type."
    ::= { hpnicfSlbgGroupEntry 2 }

hpnicfSlbgGroupRowStatus OBJECT-TYPE
    SYNTAX      RowStatus
    MAX-ACCESS  read-create
    STATUS      current
    DESCRIPTION
        "This object is used to create, modify, or delete rows.
         hpnicfSlbgGroupNumber and hpnicfSlbgGroupSrvType must have a valid value before a row can be activated."
    ::= { hpnicfSlbgGroupEntry 3 }

hpnicfSlbgPortTable OBJECT-TYPE
    SYNTAX SEQUENCE OF HpnicfSlbgPortEntry
    MAX-ACCESS not-accessible
    STATUS current
    DESCRIPTION
        "A table of port objects."
    ::= { hpnicfSlbgMibTable 2 }

hpnicfSlbgPortEntry OBJECT-TYPE
    SYNTAX HpnicfSlbgPortEntry
    MAX-ACCESS not-accessible
    STATUS current
    DESCRIPTION
        "The service loopback group port entry."
    INDEX { hpnicfSlbgPortIndex }
    ::= { hpnicfSlbgPortTable 1 }

HpnicfSlbgPortEntry ::=
    SEQUENCE {
        hpnicfSlbgPortIndex
            InterfaceIndex,
        hpnicfSlbgPortAttachedGroupNumber
            Unsigned32,
        hpnicfSlbgPortSelectedGroupNumber
            Unsigned32
    }

hpnicfSlbgPortIndex OBJECT-TYPE
    SYNTAX InterfaceIndex
    MAX-ACCESS not-accessible
    STATUS current
    DESCRIPTION
        "Interface index of the port, which is defined in RFC1213 (MIB-II)."
    ::= { hpnicfSlbgPortEntry 1 }

hpnicfSlbgPortAttachedGroupNumber OBJECT-TYPE
    SYNTAX Unsigned32
    MAX-ACCESS read-write
    STATUS current
    DESCRIPTION
        "The value of the service group number to which this port is assigned.
         The value is zero if the port is not assigned to any service loopback group."
    ::= { hpnicfSlbgPortEntry 2 }

hpnicfSlbgPortSelectedGroupNumber OBJECT-TYPE
    SYNTAX Unsigned32
    MAX-ACCESS read-only
    STATUS current
    DESCRIPTION
        "The value of the service group number to which this selected port is assigned.
         The value is zero if the port is not selected or not assigned to any service loopback group."
    ::= { hpnicfSlbgPortEntry 3 }

END
