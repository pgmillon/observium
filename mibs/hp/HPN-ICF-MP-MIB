-- =================================================================
-- Copyright (c) 2010-2013 Hewlett-Packard Development Company, L.P.
-- 
-- Description: This MIB file is used for inquiring for MP (Multilink PPP)
--              link status information.
-- Reference:
-- Version: V1.0
-- History:
--   V1.0 tianli,2004.5.18,publish 
-- =================================================================

HPN-ICF-MP-MIB DEFINITIONS ::= BEGIN

        IMPORTS
            ifIndex			
                FROM RFC1213-MIB
            hpnicfRhw
                FROM HPN-ICF-OID-MIB                                                     
            OBJECT-GROUP, MODULE-COMPLIANCE                 
                FROM SNMPv2-CONF                        
            Integer32, Counter32, OBJECT-TYPE, MODULE-IDENTITY                   
                FROM SNMPv2-SMI
            TEXTUAL-CONVENTION, DisplayString
                FROM SNMPv2-TC;        

        hpnicfMultilinkPPP MODULE-IDENTITY 
                LAST-UPDATED "200405180000Z"            -- May 18, 2004 at 00:00 GMT
                ORGANIZATION
                    ""
                CONTACT-INFO
                    ""
                DESCRIPTION 
                        "The HPN-ICF-MP-MIB provides read access to MP(Multilink PPP) link
                        status information. The information available through this MIB includes:
                        the father channel, the bundled son channel, the slot on which MP bundled, 
                        the number of son channels, the bundle name,
                        the statistic of lost fragments, reordered packets, unassigned packets, 
                        interleaved packets, and the received/sent sequence, etc.
                        "
                ::= { hpnicfRhw 33 }

--
-- Node definitions
--        
        
        hpnicfMpObjects OBJECT IDENTIFIER ::= { hpnicfMultilinkPPP  1 }
        
        hpnicfMpMultilinkTable OBJECT-TYPE
                SYNTAX SEQUENCE OF HpnicfMpMultilinkEntry
                MAX-ACCESS not-accessible
                STATUS current
                DESCRIPTION
                        "This table describes the information of MP link. 
                        The index of this table is the interface index of MP group or 
                        VT(Virtual Template)."
                ::= { hpnicfMpObjects 1 }

        hpnicfMpMultilinkEntry OBJECT-TYPE
                SYNTAX HpnicfMpMultilinkEntry
                MAX-ACCESS not-accessible
                STATUS current
                DESCRIPTION
                        "Each entry in this table describes the information of MP link.
                        The available information includes: 
                        the father channel, the slot on which MP bundled, 
                        the number of bundled son channels, 
                        the statistics of lost fragments, reordered packets, 
                        unassigned packets, interleaved packets, 
                        and received/sent sequence.                         
                        "
                INDEX { ifIndex }
                ::= { hpnicfMpMultilinkTable 1 }
        
        HpnicfMpMultilinkEntry ::=
                SEQUENCE {
                        hpnicfMpMultilinkDescr
                                DisplayString,   
                        hpnicfMpBundleName
                                DisplayString,                                               
                        hpnicfMpBundledSlot
                                Integer32,
                        hpnicfMpBundledMemberCnt
                                Integer32,
			hpnicfMpLostFragments
				Counter32,
			hpnicfMpReorderedPkts
				Counter32,
			hpnicfMpUnassignedPkts
				Counter32,
			hpnicfMpInterleavedPkts
				Counter32,
			hpnicfMpRcvdSequence
				Integer32,
			hpnicfMpSentSequence
				Integer32																														
                 } 
                                         
        hpnicfMpMultilinkDescr OBJECT-TYPE
                SYNTAX DisplayString
                MAX-ACCESS read-only
                STATUS current
                DESCRIPTION
                        "The interface name of the father interface on which MP bundled. 
                        It is the name of a Virtual Temblate or a MP group."
                ::= { hpnicfMpMultilinkEntry 1 } 
                
        hpnicfMpBundleName OBJECT-TYPE
                SYNTAX DisplayString
                MAX-ACCESS read-only
                STATUS current
                DESCRIPTION
                        "The bundle name of the multilink. 
                        when authentication is configured, the bundle name is the authenticated
                        user name; when authentication not configured, the bundle name is
                        multilink.
                        "
                ::= { hpnicfMpMultilinkEntry 2 }                 
                
        hpnicfMpBundledSlot OBJECT-TYPE
                SYNTAX Integer32
                MAX-ACCESS read-only
                STATUS current
                DESCRIPTION
                        "The slot on which MP bundled. 
                        "
                ::= { hpnicfMpMultilinkEntry 3 }
        
        hpnicfMpBundledMemberCnt OBJECT-TYPE
                SYNTAX Integer32
                MAX-ACCESS read-only
                STATUS current
                DESCRIPTION
                        "The number of the bundled son channel of the MP link. "
                ::= { hpnicfMpMultilinkEntry 4 }

        hpnicfMpLostFragments OBJECT-TYPE
                SYNTAX Counter32
                MAX-ACCESS read-only
                STATUS current
                DESCRIPTION
                        "The number of fragments of the MP link discarded because 
                        bad fragments received, or assembling packet failed, etc."
                ::= { hpnicfMpMultilinkEntry 5 }

         hpnicfMpReorderedPkts OBJECT-TYPE
                SYNTAX Counter32
                MAX-ACCESS read-only
                STATUS current
                DESCRIPTION
                        "The number of received packets of the MP link reordered.
                        "
                ::= { hpnicfMpMultilinkEntry 6 }                       

         hpnicfMpUnassignedPkts OBJECT-TYPE
                SYNTAX Counter32
                MAX-ACCESS read-only
                STATUS current
                DESCRIPTION
                        "The number of received packets of the MP link waiting for reordering.
                        "
                ::= { hpnicfMpMultilinkEntry 7 }      
                
         hpnicfMpInterleavedPkts OBJECT-TYPE
                SYNTAX Counter32
                MAX-ACCESS read-only
                STATUS current
                DESCRIPTION
                        "The number of received packets of the MP link interleaved by the 
                        packets queued in RTPQ(Real-time Transport Protocol Queue) or 
                        LLQ(Low Latency Queue).
                        "
                ::= { hpnicfMpMultilinkEntry 8 }  
                
         hpnicfMpRcvdSequence OBJECT-TYPE
                SYNTAX Integer32
                MAX-ACCESS read-only
                STATUS current
                DESCRIPTION
                        "The current sequence number of the MP link for receiving.
                        "
                ::= { hpnicfMpMultilinkEntry 9 }   

         hpnicfMpSentSequence OBJECT-TYPE
                SYNTAX Integer32
                MAX-ACCESS read-only
                STATUS current
                DESCRIPTION
                        "The current sequence number of the MP link for sending.
                        "
                ::= { hpnicfMpMultilinkEntry 10 }


        hpnicfMpMemberlinkTable OBJECT-TYPE
                SYNTAX SEQUENCE OF HpnicfMpMemberlinkEntry
                MAX-ACCESS not-accessible
                STATUS current
                DESCRIPTION
                        "This table describes the information of son channels of the MP link.
                        The index of this table is the interface index of MP group or
                        VT(Virtual Template). 
                        "
                ::= { hpnicfMpObjects 2 }

        hpnicfMpMemberlinkEntry OBJECT-TYPE
                SYNTAX HpnicfMpMemberlinkEntry
                MAX-ACCESS not-accessible
                STATUS current
                DESCRIPTION
                        "Each entry in this table describes the information of the bundled
                        son channels of MP link. The available information includes: 
                        the interface index of the son channel, 
                        the interface name of the son channel.
                        "
                INDEX { ifIndex, hpnicfMpMemberlinkSeqNumber }
                ::= { hpnicfMpMemberlinkTable 1 }
        
        HpnicfMpMemberlinkEntry ::=
                SEQUENCE {
                        hpnicfMpMemberlinkSeqNumber
                                Integer32,
                        hpnicfMpMemberlinkIfIndex
                                Integer32,
                        hpnicfMpMemberlinkDescr
                                DisplayString,
                        hpnicfMpMemberlinkMpStatus
                                Integer32																													
                 } 

        hpnicfMpMemberlinkSeqNumber OBJECT-TYPE
                SYNTAX Integer32
                MAX-ACCESS read-only
                STATUS current
                DESCRIPTION
                        "The bundled sequence number of the son channels of the MP link.
                        This object is one of the index of the table.
                        "
                ::= { hpnicfMpMemberlinkEntry 1 }  

        hpnicfMpMemberlinkIfIndex OBJECT-TYPE
                SYNTAX Integer32
                MAX-ACCESS read-only
                STATUS current
                DESCRIPTION
                        "The interface index of the son channels of the MP link.
                        "
                ::= { hpnicfMpMemberlinkEntry 2 } 
                
        hpnicfMpMemberlinkDescr OBJECT-TYPE
                SYNTAX DisplayString
                MAX-ACCESS read-only
                STATUS current
                DESCRIPTION
                        "The interface name of the son channels of the MP link.
                        "
                ::= { hpnicfMpMemberlinkEntry 3 } 
                
        hpnicfMpMemberlinkMpStatus OBJECT-TYPE
                SYNTAX Integer32
                MAX-ACCESS read-only
                STATUS current
                DESCRIPTION
                        "The MP status of the son channels of the MP link.
                        "
                ::= { hpnicfMpMemberlinkEntry 4 } 
                                
         hpnicfMpNotifications OBJECT IDENTIFIER ::= { hpnicfMultilinkPPP 2 }

         
         hpnicfMpConformance OBJECT IDENTIFIER ::= { hpnicfMultilinkPPP 3 }

         
         hpnicfMpCompliances OBJECT IDENTIFIER ::= { hpnicfMpConformance 1 }

         
         hpnicfMpCompliance MODULE-COMPLIANCE
                 STATUS current
                 DESCRIPTION 
                         "The compliance statement for entities which 
                         implement the Multilink PPP MIB."
                 MODULE -- this module
                         MANDATORY-GROUPS { hpnicfMpMandatoryGroup }
                 ::= { hpnicfMpCompliances 1 }

         
         hpnicfMpGroups OBJECT IDENTIFIER ::= { hpnicfMpConformance 2 }

         
         hpnicfMpMandatoryGroup OBJECT-GROUP
                 OBJECTS { hpnicfMpBundledMemberCnt, hpnicfMpMemberlinkSeqNumber, hpnicfMpMemberlinkIfIndex }
                 STATUS current
                 DESCRIPTION 
                         "A collection of objects providing mandatory MP information."
                 ::= { hpnicfMpGroups 1 }
         
         hpnicfMpInfoGroup OBJECT-GROUP
                 OBJECTS { hpnicfMpMultilinkDescr, hpnicfMpBundleName, 
                         hpnicfMpBundledSlot, hpnicfMpBundledMemberCnt,
                         hpnicfMpLostFragments, hpnicfMpReorderedPkts, 
                         hpnicfMpUnassignedPkts, hpnicfMpInterleavedPkts, 
                         hpnicfMpRcvdSequence, hpnicfMpSentSequence,
                         hpnicfMpMemberlinkDescr,hpnicfMpMemberlinkMpStatus }
                 STATUS current
                 DESCRIPTION 
                         "All running information of MP feature."
                 ::= { hpnicfMpGroups 2 }                                                                                        
                                                                                                                                                                                    
   END
