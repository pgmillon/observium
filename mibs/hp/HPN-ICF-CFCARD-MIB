-- =============================================================
-- Copyright (c) 2010-2013 Hewlett-Packard Development Company, L.P.
--
-- Description:  provide the info about CF Card.
-- Version: V1.0
-- History:
--   V1.0 Initial Version created by lizhiyong
-- =============================================================
HPN-ICF-CFCARD-MIB DEFINITIONS ::= BEGIN

        IMPORTS
            hpnicfCfCard
                FROM HPN-ICF-OID-MIB
            OBJECT-GROUP, MODULE-COMPLIANCE, NOTIFICATION-GROUP
                FROM SNMPv2-CONF
            Unsigned32, OBJECT-TYPE, MODULE-IDENTITY, OBJECT-IDENTITY, NOTIFICATION-TYPE
                FROM SNMPv2-SMI;


--  December 24, 2004 at 15:41 GMT
        hpnicfCfCardMIB MODULE-IDENTITY
            LAST-UPDATED "200412240000Z"
            ORGANIZATION
                ""
            CONTACT-INFO
                ""
            DESCRIPTION
                "This MIB provides the information about CF Card."
            ::= { hpnicfCfCard 1 }




        hpnicfCfCardMIBObjects OBJECT-IDENTITY
            STATUS current
            DESCRIPTION
                "Objects used for CF Card management."
            ::= { hpnicfCfCardMIB 1 }


        hpnicfCfCardScalarObjects OBJECT-IDENTITY
            STATUS current
            DESCRIPTION
                "The scalar objects for the CF Card(s)."
            ::= { hpnicfCfCardMIBObjects 1 }


        hpnicfCfCardNumber OBJECT-TYPE
            SYNTAX INTEGER (0..255)
            MAX-ACCESS read-only
            STATUS current
            DESCRIPTION
                "The total number of the CF Card(s) at present."
            ::= { hpnicfCfCardScalarObjects 1 }


        hpnicfCfCardInfoObjects OBJECT-IDENTITY
            STATUS current
            DESCRIPTION
                "The basic information about CF Card(s)."
            ::= { hpnicfCfCardMIBObjects 2 }


        hpnicfCfCardInfoTable OBJECT-TYPE
            SYNTAX SEQUENCE OF HPN-ICFCfCardInfoEntry
            MAX-ACCESS not-accessible
            STATUS current
            DESCRIPTION
                "This table contains the basic information about CF Card(s)."
            ::= { hpnicfCfCardInfoObjects 2 }


        hpnicfCfCardInfoEntry OBJECT-TYPE
            SYNTAX HPN-ICFCfCardInfoEntry
            MAX-ACCESS not-accessible
            STATUS current
            DESCRIPTION
                "This list contains the basic information about CF Card."
            INDEX { hpnicfCfCardIndex }
            ::= { hpnicfCfCardInfoTable 1 }


        HPN-ICFCfCardInfoEntry ::=
            SEQUENCE {
                hpnicfCfCardIndex
                    INTEGER,
                hpnicfCfCardIsPresent
                    INTEGER,
                hpnicfCfCardContainedIn
                    INTEGER,
                hpnicfCfCardParentRelPos
                    INTEGER,
                hpnicfCfCardDescription
                    OCTET STRING,
                hpnicfCfCardSerialNumber
                    OCTET STRING,
                hpnicfCfCardFirewareVersion
                    OCTET STRING,
                hpnicfCfCardModelNumber
                    OCTET STRING,
                hpnicfCfCardState
                    INTEGER,
                hpnicfCfCardSize
                    Unsigned32,
                hpnicfCfCardUsedSize
                    Unsigned32,
                hpnicfCfCardFreeSize
                    Unsigned32
             }

        hpnicfCfCardIndex OBJECT-TYPE
            SYNTAX INTEGER (1..255)
            MAX-ACCESS read-only
            STATUS current
            DESCRIPTION
                "The index of the table."
            ::= { hpnicfCfCardInfoEntry 1 }


        hpnicfCfCardIsPresent OBJECT-TYPE
            SYNTAX INTEGER
                {
                yes(1),
                no(2)
                }
            MAX-ACCESS read-only
            STATUS current
            DESCRIPTION
                "The value indicates whether the CF Card is present or not."
            ::= { hpnicfCfCardInfoEntry 2 }


        hpnicfCfCardContainedIn OBJECT-TYPE
            SYNTAX INTEGER (0..255)
            MAX-ACCESS read-only
            STATUS current
            DESCRIPTION
                "The number of the slot which containes this CF Card "
            ::= { hpnicfCfCardInfoEntry 3 }


        hpnicfCfCardParentRelPos OBJECT-TYPE
            SYNTAX INTEGER (0..255)
            MAX-ACCESS read-only
            STATUS current
            DESCRIPTION
                "An indication of the relative position of this CF Card
                among all the CF Card contained in the same slot."
            ::= { hpnicfCfCardInfoEntry 4 }


        hpnicfCfCardDescription OBJECT-TYPE
            SYNTAX OCTET STRING (SIZE (0..255))
            MAX-ACCESS read-only
            STATUS current
            DESCRIPTION
                "The Description of CF Card."
            ::= { hpnicfCfCardInfoEntry 5 }


        hpnicfCfCardSerialNumber OBJECT-TYPE
            SYNTAX OCTET STRING (SIZE (0..255))
            MAX-ACCESS read-only
            STATUS current
            DESCRIPTION
                "The serial number of CF Card."
            ::= { hpnicfCfCardInfoEntry 6 }


        hpnicfCfCardFirewareVersion OBJECT-TYPE
            SYNTAX OCTET STRING (SIZE (0..255))
            MAX-ACCESS read-only
            STATUS current
            DESCRIPTION
                "The firmware revision of CF Card."
            ::= { hpnicfCfCardInfoEntry 7 }


        hpnicfCfCardModelNumber OBJECT-TYPE
            SYNTAX OCTET STRING (SIZE (0..255))
            MAX-ACCESS read-only
            STATUS current
            DESCRIPTION
                "The model number containing infomation of manufacturer."
            ::= { hpnicfCfCardInfoEntry 8 }


        hpnicfCfCardState OBJECT-TYPE
            SYNTAX INTEGER
                {
                sNoError(1),          -- No error
                sFormatError(2),      -- Format error
                sSectorBufferError(3),-- Sector Buffer error
                sECCError(4),         -- ECC circuitry error
                sCMPError(5),         -- Controlling microprocessor error
                sSlaveError(128),     -- Slave error in True IDE Mode
                sIOError(240),        -- I/O error
                sOther(255)           -- Unknown status
                }
            MAX-ACCESS read-only
            STATUS current
            DESCRIPTION
                "The state of CF Card."
            ::= { hpnicfCfCardInfoEntry 9 }


        hpnicfCfCardSize OBJECT-TYPE
            SYNTAX Unsigned32
            UNITS "byte"
            MAX-ACCESS read-only
            STATUS current
            DESCRIPTION
                "The size of CF Card."
            ::= { hpnicfCfCardInfoEntry 10 }


        hpnicfCfCardUsedSize OBJECT-TYPE
            SYNTAX Unsigned32
            UNITS "byte"
            MAX-ACCESS read-only
            STATUS current
            DESCRIPTION
                "The used size of CF Card."
            ::= { hpnicfCfCardInfoEntry 11 }


        hpnicfCfCardFreeSize OBJECT-TYPE
            SYNTAX Unsigned32
            UNITS "byte"
            MAX-ACCESS read-only
            STATUS current
            DESCRIPTION
                "The free size of CF Card."
            ::= { hpnicfCfCardInfoEntry 12 }


        hpnicfCfCardNotifications OBJECT-IDENTITY
            STATUS current
            DESCRIPTION
                "Notification about the CF Card."
            ::= { hpnicfCfCardMIB 2 }


        hpnicfCfCardNotificationsV2 OBJECT-IDENTITY
            STATUS current
            DESCRIPTION
                "Root node for the Notification."
            ::= { hpnicfCfCardNotifications 0 }


        hpnicfCfCardHotSwapOn NOTIFICATION-TYPE
            OBJECTS { hpnicfCfCardContainedIn, hpnicfCfCardParentRelPos, hpnicfCfCardDescription }
            STATUS current
            DESCRIPTION
                "This notification is sent when a CF Card is hot swapped in."
            ::= { hpnicfCfCardNotificationsV2 1 }


        hpnicfCfCardHotSwapOff NOTIFICATION-TYPE
            OBJECTS { hpnicfCfCardContainedIn, hpnicfCfCardParentRelPos, hpnicfCfCardDescription }
            STATUS current
            DESCRIPTION
                "This notification is sent when a CF Card is hot swapped out."
            ::= { hpnicfCfCardNotificationsV2 2 }


        hpnicfCfCardMIBConformance OBJECT IDENTIFIER ::= { hpnicfCfCardMIB 4 }


        hpnicfCfCardMIBGroups OBJECT IDENTIFIER ::= { hpnicfCfCardMIBConformance 1 }


        hpnicfcurrentObjectGroup OBJECT-GROUP
            OBJECTS { hpnicfCfCardNumber, hpnicfCfCardIndex, hpnicfCfCardIsPresent,
                    hpnicfCfCardContainedIn, hpnicfCfCardParentRelPos, hpnicfCfCardDescription,
                    hpnicfCfCardSerialNumber, hpnicfCfCardFirewareVersion, hpnicfCfCardModelNumber,
                    hpnicfCfCardState, hpnicfCfCardSize, hpnicfCfCardUsedSize, hpnicfCfCardFreeSize
                    }
            STATUS current
            DESCRIPTION
                "A collection of objects."
            ::= { hpnicfCfCardMIBGroups 1 }


        hpnicfcurrentNotificationGroup NOTIFICATION-GROUP
            NOTIFICATIONS { hpnicfCfCardHotSwapOn, hpnicfCfCardHotSwapOff }
            STATUS current
            DESCRIPTION
                "Notification group."
            ::= { hpnicfCfCardMIBGroups 2 }


        hpnicfCfCardMIBCompliances OBJECT IDENTIFIER ::= { hpnicfCfCardMIBConformance 2 }



        hpnicfbasicCompliance MODULE-COMPLIANCE
            STATUS current
            DESCRIPTION
                "The compliance statement."
            MODULE -- this module
                MANDATORY-GROUPS { hpnicfcurrentObjectGroup, hpnicfcurrentNotificationGroup }
            ::= { hpnicfCfCardMIBCompliances 1 }



    END
