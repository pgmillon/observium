-- =================================================================
-- Copyright (c) 2010-2013 Hewlett-Packard Development Company, L.P.
--
-- Description: RPR private MIB. Description of entity extend properties for
-- IEEE-802DOT17-RPR-MIB
-- Reference: IEEE-802DOT17-RPR-MIB
-- Version: V1.1
-- History:
--  V1.0 created by qinxia
--  V1.1 modified by hexuefei,Add the RPR packet drop counters table.
-- =================================================================
HPN-ICF-RPR-MIB DEFINITIONS ::= BEGIN

    IMPORTS
        hpnicfCommon
            FROM HPN-ICF-OID-MIB
        rprTopoImageEntry, rprTopoImageMacAddress, rprTopoImageInetAddress
            FROM IEEE-802DOT17-RPR-MIB
        InterfaceIndex
            FROM IF-MIB
        SnmpAdminString
            FROM SNMP-FRAMEWORK-MIB
        RowStatus, TruthValue
            FROM SNMPv2-TC;

        hpnicfRpr MODULE-IDENTITY
            LAST-UPDATED "200503161000Z"  -- March 16, 2005 at 10:18:41 GMT
            ORGANIZATION
                ""
            CONTACT-INFO
                ""
            DESCRIPTION
                "This MIB manages RPR(Resilient Packet Ring)interfaces by
                 providing an operational table which controls parameters
                 of each RPR interface and reports alarm conditions.

                 A RPR ring is composed of two fiber rings: Outer and Inner."
            REVISION "200503161000Z"      -- March 16, 2005 at 10:18:41 GMT
            DESCRIPTION
                "First published version."
            ::= { hpnicfCommon 60 }

--
-- Textual conventions
--

    HpnicfRprRingletID ::= TEXTUAL-CONVENTION
        STATUS current
        DESCRIPTION
            "Indicates the path on which data flow is selected.
             The valid value is ringlet0 and ringlet1. They indicate
             two RPR fiber rings. Ringlet0 refers to outer ring and
             ringlet1 refers to inner ring."
        REFERENCE
            "IEEE 802.17 V3.3 Subclause 11.2.1.1 Span and
             ringlet parameterization."
        SYNTAX INTEGER
            {
             ringlet0(1),
             ringlet1(2)
        }

    HpnicfRprServiceClass ::= TEXTUAL-CONVENTION
        STATUS current
        DESCRIPTION
            "Indicates the service class of RPR.
             The valid value is ClassC, ClassB, ClassA1 and ClassA0."
        REFERENCE
                "IEEE 802.17 V3.3 Subclause 7.3 Service class."
        SYNTAX INTEGER
            {
             classC(1),
             classB(2),
             classA1(3),
             classA0(4)
        }

    hpnicfRprObjects OBJECT IDENTIFIER ::= { hpnicfRpr 1 }

-- RPR maximum define table

    hpnicfRprMaxmumDefine OBJECT IDENTIFIER ::= { hpnicfRprObjects 1 }

    hpnicfRprMaxmumDefineTable OBJECT-TYPE
        SYNTAX SEQUENCE OF HpnicfRprMaxmumDefineEntry
        MAX-ACCESS not-accessible
        STATUS current
        DESCRIPTION
            "This table contains the specs of RPR ring."
      ::= { hpnicfRprMaxmumDefine 1 }

    hpnicfRprMaxmumDefineEntry OBJECT-TYPE
        SYNTAX HpnicfRprMaxmumDefineEntry
        MAX-ACCESS not-accessible
        STATUS current
        DESCRIPTION
            "The entry of RPR Maximum Table."
        INDEX { hpnicfRprMaxMumIfIndex }
        ::= { hpnicfRprMaxmumDefineTable 1 }

    HpnicfRprMaxmumDefineEntry ::=
        SEQUENCE {
            hpnicfRprMaxMumIfIndex
                InterfaceIndex,
            hpnicfRprMaxStationNumDefine
                INTEGER,
            hpnicfRprMaxReservedRateDefine
                Gauge32
        }

    hpnicfRprMaxMumIfIndex OBJECT-TYPE
        SYNTAX InterfaceIndex
        MAX-ACCESS not-accessible
        STATUS current
        DESCRIPTION
            "The ifIndex of this RPR interface."
        ::= { hpnicfRprMaxmumDefineEntry 1 }

    hpnicfRprMaxStationNumDefine OBJECT-TYPE
        SYNTAX INTEGER
        MAX-ACCESS read-only
        STATUS current
        DESCRIPTION
            "Max station number supported by RPR ring."
        ::= { hpnicfRprMaxmumDefineEntry 2 }


    hpnicfRprMaxReservedRateDefine OBJECT-TYPE
        SYNTAX Gauge32
        MAX-ACCESS read-only
        STATUS current
        DESCRIPTION
            "Max reserved rate supported by each RPR ringlet.
             An estimate of the interface's current bandwidth in
             units of 1,000,000 bits per second.  If this object
             reports a value of 'n' then the speed of the interface
             is somewhere in the range of 'n-500,000' to
             'n+499,999'.  For interfaces which do not vary in
             bandwidth or for those where no accurate estimation
             can be made, this object should contain the nominal
             bandwidth.  For a sub-layer which has no concept of
             bandwidth, this object should be zero."
        ::= { hpnicfRprMaxmumDefineEntry 3 }

    hpnicfRprTopoImage OBJECT IDENTIFIER ::= { hpnicfRprObjects 2 }

-- extension to the RPR topology table

    hpnicfRprTopoImageXTable OBJECT-TYPE
        SYNTAX SEQUENCE OF HpnicfRprTopoImageXEntry
        MAX-ACCESS not-accessible
        STATUS current
        DESCRIPTION
            "This table contains additional objects
             for the rprTopoImageTable in IEEE-802DOT17-RPR-MIB."
        REFERENCE
            "rprTopoImageTable in IEEE-802DOT17-RPR-MIB."
        ::= { hpnicfRprTopoImage 1 }

    hpnicfRprTopoImageXEntry OBJECT-TYPE
        SYNTAX HpnicfRprTopoImageXEntry
        MAX-ACCESS not-accessible
        STATUS current
        DESCRIPTION
            "Each entry contains information specific to a particular
             station on the ring. The table has at least one entry for
             the station itself, this entry indicates zero hops on each
             ringlet."
         AUGMENTS { rprTopoImageEntry }
         ::= { hpnicfRprTopoImageXTable 1 }

    HpnicfRprTopoImageXEntry ::=
        SEQUENCE {
            hpnicfRprTopoImageXWestEdgeStatus
                TruthValue,
            hpnicfRprTopoImageXEastEdgeStatus
                TruthValue,
            hpnicfRprTopoImageXStationName
                SnmpAdminString
        }

    hpnicfRprTopoImageXWestEdgeStatus OBJECT-TYPE
        SYNTAX TruthValue
        MAX-ACCESS read-only
        STATUS current
        DESCRIPTION
            "The current edge status of the west span.
             If an edge exists,the hpnicfRprTopoImageXWestEdgeStatus is true.
             Otherwise, the hpnicfRprTopoImageXWestEdgeStatus is false."
        REFERENCE
            "IEEE 802.17  V3.3 Subclause 11.1.1.5, Edges"
        ::= { hpnicfRprTopoImageXEntry 3 }

    hpnicfRprTopoImageXEastEdgeStatus OBJECT-TYPE
        SYNTAX TruthValue
        MAX-ACCESS read-only
        STATUS current
        DESCRIPTION
            "The current edge status of the east span.
             If an edge exists, the hpnicfRprTopoImageXEastEdgeStatus is true.
             Otherwise, the hpnicfRprTopoImageXEastEdgeStatus is false."
        REFERENCE
             "IEEE 802.17  V3.3 Subclause 11.1.1.5, Edges"
        ::= { hpnicfRprTopoImageXEntry 4 }

    hpnicfRprTopoImageXStationName OBJECT-TYPE
        SYNTAX SnmpAdminString
        MAX-ACCESS read-write
        STATUS current
        DESCRIPTION
            "The operator assigned station name. The operator can assigned it
             by hpnicfRprTopoImageXStationName."
        REFERENCE
            "IEEE 802.17 V3.3 Subclause 11.2.6, stationName."
        ::= { hpnicfRprTopoImageXEntry 5 }

    hpnicfRprSpanCounters OBJECT IDENTIFIER ::= { hpnicfRprObjects 3 }

-- RPR source mac counters table

    hpnicfRprSrcMacCountTable OBJECT-TYPE
        SYNTAX SEQUENCE OF HpnicfRprSrcMacCountEntry
        MAX-ACCESS not-accessible
        STATUS current
        DESCRIPTION
            "The RPR Source Mac Count Table contains the cumulative sum
             of frames and octects from the particular source station."
        ::= { hpnicfRprSpanCounters 1 }

    hpnicfRprSrcMacCountEntry OBJECT-TYPE
        SYNTAX HpnicfRprSrcMacCountEntry
        MAX-ACCESS not-accessible
        STATUS current
        DESCRIPTION
            "An entry in the RPR Source Mac Count Table."
        INDEX { hpnicfRprSrcMacCountIfIndex, hpnicfRprSrcMacCountBySrcAddress }
        ::= { hpnicfRprSrcMacCountTable 1 }

    HpnicfRprSrcMacCountEntry ::=
        SEQUENCE {
            hpnicfRprSrcMacCountIfIndex
                InterfaceIndex,
            hpnicfRprSrcMacCountBySrcAddress
                MacAddress,
          hpnicfRprSrcMacCountReceivedFrames
                Counter64,
            hpnicfRprSrcMacCountReceivedOctets
                Counter64
        }

    hpnicfRprSrcMacCountIfIndex OBJECT-TYPE
        SYNTAX InterfaceIndex
        MAX-ACCESS not-accessible
        STATUS current
        DESCRIPTION
            "The ifIndex of this RPR interface."
        REFERENCE
            "RFC 2863, ifIndex."
        ::= { hpnicfRprSrcMacCountEntry 1 }

    hpnicfRprSrcMacCountBySrcAddress OBJECT-TYPE
        SYNTAX MacAddress
        MAX-ACCESS not-accessible
        STATUS current
        DESCRIPTION
            "MAC address of the source station where the frames come from."
        ::= { hpnicfRprSrcMacCountEntry 2 }

    hpnicfRprSrcMacCountReceivedFrames OBJECT-TYPE
        SYNTAX Counter64
        MAX-ACCESS read-only
        STATUS current
        DESCRIPTION
            "Frames received from a particular MAC address of source station."
        ::= { hpnicfRprSrcMacCountEntry 3 }

    hpnicfRprSrcMacCountReceivedOctets OBJECT-TYPE
        SYNTAX Counter64
        MAX-ACCESS read-only
        STATUS current
        DESCRIPTION
            "Octets received from a particular MAC address of source station."
        ::= { hpnicfRprSrcMacCountEntry 4 }

-- RPR destination mac counters table

    hpnicfRprDestMacCountTable OBJECT-TYPE
        SYNTAX SEQUENCE OF HpnicfRprDestMacCountEntry
        MAX-ACCESS not-accessible
        STATUS current
        DESCRIPTION
            "The RPR Destination MAC Count Table contains the cumulative sum
             of  frames and octects to the particular destination station."
        ::= { hpnicfRprSpanCounters 2 }

    hpnicfRprDestMacCountEntry OBJECT-TYPE
        SYNTAX HpnicfRprDestMacCountEntry
        MAX-ACCESS not-accessible
        STATUS current
        DESCRIPTION
            "An entry in the RPR MAC Destination Count Table."
        INDEX { hpnicfRprDestMacCountIfIndex, hpnicfRprDestMacCountByDestAddress }
        ::= { hpnicfRprDestMacCountTable 1 }

    HpnicfRprDestMacCountEntry ::=
        SEQUENCE {
            hpnicfRprDestMacCountIfIndex
                InterfaceIndex,
            hpnicfRprDestMacCountByDestAddress
                MacAddress,
            hpnicfRprDestMacCountReceivedFrames
                Counter64,
            hpnicfRprDestMacCountReceivedOctets
                Counter64
        }

    hpnicfRprDestMacCountIfIndex OBJECT-TYPE
        SYNTAX InterfaceIndex
        MAX-ACCESS not-accessible
        STATUS current
        DESCRIPTION
            "The ifIndex of RPR interface."
        REFERENCE
            "RFC 2863, ifIndex"
        ::= { hpnicfRprDestMacCountEntry 1 }

    hpnicfRprDestMacCountByDestAddress OBJECT-TYPE
        SYNTAX MacAddress
        MAX-ACCESS not-accessible
        STATUS current
        DESCRIPTION
            "MAC address of the destination station where the frames are sent
             to."
        ::= { hpnicfRprDestMacCountEntry 2 }

    hpnicfRprDestMacCountReceivedFrames OBJECT-TYPE
        SYNTAX Counter64
        MAX-ACCESS read-only
        STATUS current
        DESCRIPTION
            "Frames sent to a particular MAC address of destination station."
        ::= { hpnicfRprDestMacCountEntry 3 }

    hpnicfRprDestMacCountReceivedOctets OBJECT-TYPE
        SYNTAX Counter64
        MAX-ACCESS read-only
        STATUS current
        DESCRIPTION
            "Octets sent to a particular MAC address of destination station."
        ::= { hpnicfRprDestMacCountEntry 4 }

-- RPR packet drop counters table

     hpnicfRprPktDropCountTable OBJECT-TYPE
        SYNTAX SEQUENCE OF HpnicfRprPktDropCountEntry
        MAX-ACCESS not-accessible
        STATUS current
        DESCRIPTION
            "The RPR Packet Drop Count Table contains the cumulative sum
             of packets dropped for congestion."
        ::= { hpnicfRprSpanCounters 3 }

     hpnicfRprPktDropCountEntry OBJECT-TYPE
        SYNTAX HpnicfRprPktDropCountEntry
        MAX-ACCESS not-accessible
        STATUS current
        DESCRIPTION
            "An entry in the RPR Packet Drop Count Table."
        INDEX { hpnicfRprPktDropCntIfIndex, hpnicfRprPktDropCntRingletID }
        ::= { hpnicfRprPktDropCountTable 1 }

     HpnicfRprPktDropCountEntry ::=
        SEQUENCE {
                hpnicfRprPktDropCntIfIndex
                    InterfaceIndex,
                hpnicfRprPktDropCntRingletID
                    HpnicfRprRingletID,
                hpnicfRprDownFlowClassAPktDrops
                    Counter64,
                hpnicfRprUpFlowClassAPktDrops
                    Counter64,
                hpnicfRprDownFlowClassBPktDrops
                    Counter64,
                hpnicfRprUpFlowClassBPktDrops
                    Counter64,
                hpnicfRprDownFlowClassCPktDrops
                    Counter64,
                hpnicfRprUpFlowClassCPktDrops
                    Counter64
        }

     hpnicfRprPktDropCntIfIndex OBJECT-TYPE
        SYNTAX InterfaceIndex
        MAX-ACCESS not-accessible
        STATUS current
        DESCRIPTION
            "The ifIndex of this RPR interface."
        REFERENCE
             "RFC 2863, ifIndex."
        ::= { hpnicfRprPktDropCountEntry 1 }

     hpnicfRprPktDropCntRingletID OBJECT-TYPE
        SYNTAX HpnicfRprRingletID
        MAX-ACCESS not-accessible
        STATUS current
        DESCRIPTION
            "The RPR Ringlet of the station through which the packets transmit."
        ::= { hpnicfRprPktDropCountEntry 2 }

     hpnicfRprDownFlowClassAPktDrops OBJECT-TYPE
        SYNTAX Counter64
        MAX-ACCESS read-only
        STATUS current
        DESCRIPTION
            "The total dropped number of Class A packets which transmit
             down from the host."
        ::= { hpnicfRprPktDropCountEntry 3 }

     hpnicfRprUpFlowClassAPktDrops OBJECT-TYPE
        SYNTAX Counter64
        MAX-ACCESS read-only
        STATUS current
        DESCRIPTION
            "The total dropped number of Class A packets which transmit
             up to the host."
        ::= { hpnicfRprPktDropCountEntry 4 }

     hpnicfRprDownFlowClassBPktDrops OBJECT-TYPE
        SYNTAX Counter64
        MAX-ACCESS read-only
        STATUS current
        DESCRIPTION
            "The total dropped number of Class B packets which transmit
             down from the host."
        ::= { hpnicfRprPktDropCountEntry 5 }

     hpnicfRprUpFlowClassBPktDrops OBJECT-TYPE
         SYNTAX Counter64
         MAX-ACCESS read-only
         STATUS current
         DESCRIPTION
            "The total dropped number of Class B packets which transmit
             up to the host."
         ::= { hpnicfRprPktDropCountEntry 6 }

     hpnicfRprDownFlowClassCPktDrops OBJECT-TYPE
         SYNTAX Counter64
         MAX-ACCESS read-only
         STATUS current
         DESCRIPTION
             "The total dropped number of Class C packets which transmit
              down from the host."
         ::= { hpnicfRprPktDropCountEntry 7 }

     hpnicfRprUpFlowClassCPktDrops OBJECT-TYPE
         SYNTAX Counter64
         MAX-ACCESS read-only
         STATUS current
         DESCRIPTION
             "The total dropped number of Class C packets which transmit
              up to the host."
         ::= { hpnicfRprPktDropCountEntry 8 }

    hpnicfRprRS OBJECT IDENTIFIER ::= { hpnicfRprObjects 4 }

-- The RPR static ring selection table

    hpnicfRprStaticRSTable OBJECT-TYPE
        SYNTAX SEQUENCE OF HpnicfRprStaticRSEntry
        MAX-ACCESS not-accessible
        STATUS current
        DESCRIPTION
            "The RPR Static Ring Selection table contains the static
             ring selection information by the way of configuration."
        ::= { hpnicfRprRS 1 }

    hpnicfRprStaticRSEntry OBJECT-TYPE
        SYNTAX HpnicfRprStaticRSEntry
        MAX-ACCESS not-accessible
        STATUS current
        DESCRIPTION
            "An entry in the RPR Static Ring Selection table."
        INDEX { hpnicfRprStaticRSIfIndex, hpnicfRprStaticRSMacAddress }
        ::= { hpnicfRprStaticRSTable 1 }

    HpnicfRprStaticRSEntry ::=
        SEQUENCE {
            hpnicfRprStaticRSIfIndex
                InterfaceIndex,
            hpnicfRprStaticRSMacAddress
                MacAddress,
            hpnicfRprStaticRSRingletID
                HpnicfRprRingletID,
            hpnicfRprStaticRSTtl
                INTEGER,
            hpnicfRprStaticRSValid
                TruthValue,
            hpnicfRprStaticRSRowStatus
                RowStatus
        }

    hpnicfRprStaticRSIfIndex OBJECT-TYPE
        SYNTAX InterfaceIndex
        MAX-ACCESS not-accessible
        STATUS current
        DESCRIPTION
            "The ifIndex of RPR interface."
        REFERENCE
            "RFC 2863, ifIndex"
        ::= { hpnicfRprStaticRSEntry 1 }

    hpnicfRprStaticRSMacAddress OBJECT-TYPE
        SYNTAX MacAddress
        MAX-ACCESS not-accessible
        STATUS current
        DESCRIPTION
            "The MAC address of the station on the ring."
        ::= { hpnicfRprStaticRSEntry 2 }

    hpnicfRprStaticRSRingletID OBJECT-TYPE
        SYNTAX HpnicfRprRingletID
        MAX-ACCESS read-create
        STATUS current
        DESCRIPTION
            "The identifier of the ring which frames are sent
             from one station to another. Ringlet0 refers to outer ring,
             while ringlet1 does inner."
        ::= { hpnicfRprStaticRSEntry 3 }

    hpnicfRprStaticRSTtl  OBJECT-TYPE
        SYNTAX INTEGER
        MAX-ACCESS read-only
        STATUS current
        DESCRIPTION
            "The hops from source station to destination station by the
             selected ringlet."
        ::= { hpnicfRprStaticRSEntry 4 }

    hpnicfRprStaticRSValid OBJECT-TYPE
        SYNTAX TruthValue
        MAX-ACCESS read-only
        STATUS current
        DESCRIPTION
            "The flag identify whether the configed ringlet is valid.
             If it is true, the configed ringlet is valid, otherwise
             it's invalid."
        ::= { hpnicfRprStaticRSEntry 5 }

    hpnicfRprStaticRSRowStatus OBJECT-TYPE
        SYNTAX RowStatus
        MAX-ACCESS read-create
        STATUS current
        DESCRIPTION
            "The status of this table entry.
             The status includes createAndGo, active and destroy."
        ::= { hpnicfRprStaticRSEntry 6 }

-- The RPR Ipv4 dynamic ring selection table

    hpnicfRprIpv4DynamicRSTable OBJECT-TYPE
        SYNTAX SEQUENCE OF HpnicfRprIpv4DynamicRSEntry
        MAX-ACCESS not-accessible
        STATUS current
        DESCRIPTION
            "The RPR Ipv4Dynamic Ring Selection Table that contains the
             dynamic ring selection information by shortest path."
        ::= { hpnicfRprRS 2 }

    hpnicfRprIpv4DynamicRSEntry OBJECT-TYPE
        SYNTAX HpnicfRprIpv4DynamicRSEntry
        MAX-ACCESS not-accessible
        STATUS current
        DESCRIPTION
            "An entry in the RPR Ipv4Dynamic Ring Selection Table."
        INDEX { hpnicfRprIpv4DynamicRSIfIndex, hpnicfRprIpv4DynamicRSMacAddress }
        ::= { hpnicfRprIpv4DynamicRSTable 1 }

    HpnicfRprIpv4DynamicRSEntry ::=
        SEQUENCE {
            hpnicfRprIpv4DynamicRSIfIndex
                InterfaceIndex,
            hpnicfRprIpv4DynamicRSMacAddress
                MacAddress,
            hpnicfRprIpv4DynamicRSRingletID
                HpnicfRprRingletID,
            hpnicfRprIpv4DynamicRSTtl
                INTEGER
        }

    hpnicfRprIpv4DynamicRSIfIndex OBJECT-TYPE
        SYNTAX InterfaceIndex
        MAX-ACCESS not-accessible
        STATUS current
        DESCRIPTION
            "The ifIndex of RPR interface."
        REFERENCE
            "RFC 2863, ifIndex"
        ::= { hpnicfRprIpv4DynamicRSEntry 1 }

    hpnicfRprIpv4DynamicRSMacAddress OBJECT-TYPE
        SYNTAX MacAddress
        MAX-ACCESS not-accessible
        STATUS current
        DESCRIPTION
            "The Ipv4 MAC address of destination station on the ring."
        ::= { hpnicfRprIpv4DynamicRSEntry 2 }

    hpnicfRprIpv4DynamicRSRingletID OBJECT-TYPE
        SYNTAX HpnicfRprRingletID
        MAX-ACCESS read-only
        STATUS current
        DESCRIPTION
            "The identifier of the ring which frames are sent
             from the source station to the destination station."
        ::= { hpnicfRprIpv4DynamicRSEntry 3 }

    hpnicfRprIpv4DynamicRSTtl OBJECT-TYPE
        SYNTAX INTEGER
        MAX-ACCESS read-only
        STATUS current
        DESCRIPTION
            "The hops from source station to destination station by the
             selected ringlet."
        ::= { hpnicfRprIpv4DynamicRSEntry 4 }

-- The RPR Ipv6 dynamic ring selection table

    hpnicfRprIpv6DynamicRSTable OBJECT-TYPE
        SYNTAX SEQUENCE OF HpnicfRprIpv6DynamicRSEntry
        MAX-ACCESS not-accessible
        STATUS current
        DESCRIPTION
            "The RPR Ipv6 Dynamic Ring Selection Table that contains the Ipv6
             ring selection information by dynamic ring selection and static
             ring selection."
        ::= { hpnicfRprRS 3 }

    hpnicfRprIpv6DynamicRSEntry OBJECT-TYPE
        SYNTAX HpnicfRprIpv6DynamicRSEntry
        MAX-ACCESS not-accessible
        STATUS current
        DESCRIPTION
            "An entry in the RPR Ipv6 Ring Selection Table."
        INDEX { hpnicfRprIpv6DynamicRSIfIndex, hpnicfRprIpv6DynamicRSMacAddress }
        ::= { hpnicfRprIpv6DynamicRSTable 1 }

    HpnicfRprIpv6DynamicRSEntry ::=
        SEQUENCE {
            hpnicfRprIpv6DynamicRSIfIndex
                InterfaceIndex,
            hpnicfRprIpv6DynamicRSMacAddress
                MacAddress,
            hpnicfRprIpv6DynamicRSRingletID
                HpnicfRprRingletID,
            hpnicfRprIpv6DynamicRSTtl
                INTEGER
        }

    hpnicfRprIpv6DynamicRSIfIndex OBJECT-TYPE
        SYNTAX InterfaceIndex
        MAX-ACCESS not-accessible
        STATUS current
        DESCRIPTION
            "The ifIndex of RPR interface."
        REFERENCE
            "RFC 2863, ifIndex"
        ::= { hpnicfRprIpv6DynamicRSEntry 1 }

    hpnicfRprIpv6DynamicRSMacAddress OBJECT-TYPE
        SYNTAX MacAddress
        MAX-ACCESS not-accessible
        STATUS current
        DESCRIPTION
            "The Ipv6 MAC address of the destination station on the ring."
        ::= { hpnicfRprIpv6DynamicRSEntry 2 }

    hpnicfRprIpv6DynamicRSRingletID OBJECT-TYPE
        SYNTAX HpnicfRprRingletID
        MAX-ACCESS read-only
        STATUS current
        DESCRIPTION
            "The identifier of the ring which frames are sent
             from the source station to the destination station."
        ::= { hpnicfRprIpv6DynamicRSEntry 3 }

    hpnicfRprIpv6DynamicRSTtl OBJECT-TYPE
        SYNTAX INTEGER
        MAX-ACCESS read-only
        STATUS current
        DESCRIPTION
            "The hops from source station to destination station by selected
             ringlet."
        ::= { hpnicfRprIpv6DynamicRSEntry 4 }

-- The RPR Ipv4 overall ring selection table

    hpnicfRprIpv4OverallRSTable OBJECT-TYPE
        SYNTAX SEQUENCE OF HpnicfRprIpv4OverallRSEntry
        MAX-ACCESS not-accessible
        STATUS current
        DESCRIPTION
            "The RPR Ipv4 Overall Ring Selection Table that contains the
             overall and active  ring selection infomation by dynamic ring
             selection and static ring selection."
        ::= { hpnicfRprRS 4 }

    hpnicfRprIpv4OverallRSEntry OBJECT-TYPE
        SYNTAX HpnicfRprIpv4OverallRSEntry
        MAX-ACCESS not-accessible
        STATUS current
        DESCRIPTION
            "An entry in the RPR Overall Ring Selection Table."
        INDEX { hpnicfRprIpv4OverallRSIfIndex, hpnicfRprIpv4OverallRSMacAddress }
        ::= { hpnicfRprIpv4OverallRSTable 1 }

    HpnicfRprIpv4OverallRSEntry ::=
        SEQUENCE {
            hpnicfRprIpv4OverallRSIfIndex
                InterfaceIndex,
            hpnicfRprIpv4OverallRSMacAddress
                MacAddress,
            hpnicfRprIpv4OverallRSType
                INTEGER,
            hpnicfRprIpv4OverallRSRingletID
                HpnicfRprRingletID,
            hpnicfRprIpv4OverallRSTtl
                INTEGER
        }

    hpnicfRprIpv4OverallRSIfIndex OBJECT-TYPE
        SYNTAX InterfaceIndex
        MAX-ACCESS not-accessible
        STATUS current
        DESCRIPTION
            "The ifIndex of RPR interface."
        REFERENCE
            "RFC 2863, ifIndex"
        ::= { hpnicfRprIpv4OverallRSEntry 1 }

    hpnicfRprIpv4OverallRSMacAddress OBJECT-TYPE
        SYNTAX MacAddress
        MAX-ACCESS not-accessible
        STATUS current
        DESCRIPTION
            "The MAC address of the destination station on the ring."
        ::= { hpnicfRprIpv4OverallRSEntry 2 }

    hpnicfRprIpv4OverallRSType OBJECT-TYPE
        SYNTAX INTEGER {
            static(1),
            dynamic(2)
        }
        MAX-ACCESS read-only
        STATUS current
        DESCRIPTION
            "The ring selection item type indicates static or dynamic."
        ::= { hpnicfRprIpv4OverallRSEntry 3 }

    hpnicfRprIpv4OverallRSRingletID OBJECT-TYPE
        SYNTAX HpnicfRprRingletID
        MAX-ACCESS read-only
        STATUS current
        DESCRIPTION
            "The identifier of the ring which frames are sent
             from the source station to the destination station."
        ::= { hpnicfRprIpv4OverallRSEntry 4 }

    hpnicfRprIpv4OverallRSTtl OBJECT-TYPE
        SYNTAX INTEGER
        MAX-ACCESS read-only
        STATUS current
        DESCRIPTION
            "The hops from source station to destination station  by
             selected ringlet."
        ::= { hpnicfRprIpv4OverallRSEntry 5 }

-- The RPR VRRP ring selection table

    hpnicfRprVrrpRSTable OBJECT-TYPE
        SYNTAX SEQUENCE OF HpnicfRprVrrpRSEntry
        MAX-ACCESS not-accessible
        STATUS current
        DESCRIPTION
            "The RPR VRRP Ring Selection Table that contains the ring
             selection information when the vrrp group is configured."
        ::= { hpnicfRprRS 5 }

    hpnicfRprVrrpRSEntry OBJECT-TYPE
        SYNTAX HpnicfRprVrrpRSEntry
        MAX-ACCESS not-accessible
        STATUS current
        DESCRIPTION
            "An entry in the RPR VRRP Ring Selection Table."
        INDEX { hpnicfRprVrrpRSIfIndex, hpnicfRprVrrpRSVirtualMacAddress }
        ::= { hpnicfRprVrrpRSTable 1 }

    HpnicfRprVrrpRSEntry ::=
        SEQUENCE {
            hpnicfRprVrrpRSIfIndex
                InterfaceIndex,
            hpnicfRprVrrpRSVirtualMacAddress
                MacAddress,
            hpnicfRprVrrpRSMacAddress
                MacAddress,
            hpnicfRprVrrpRSRingletID
                HpnicfRprRingletID,
            hpnicfRprVrrpRSTtl
                INTEGER
        }

    hpnicfRprVrrpRSIfIndex OBJECT-TYPE
        SYNTAX InterfaceIndex
        MAX-ACCESS not-accessible
        STATUS current
        DESCRIPTION
            "The ifIndex of RPR interface."
        REFERENCE
            "RFC 2863, ifIndex"
        ::= { hpnicfRprVrrpRSEntry 1 }

    hpnicfRprVrrpRSVirtualMacAddress OBJECT-TYPE
        SYNTAX MacAddress
        MAX-ACCESS not-accessible
        STATUS current
        DESCRIPTION
            "The virtual MAC address of the staion in VRRP group."
        ::= { hpnicfRprVrrpRSEntry 2 }


    hpnicfRprVrrpRSMacAddress OBJECT-TYPE
        SYNTAX MacAddress
        MAX-ACCESS read-only
        STATUS current
        DESCRIPTION
            "The MAC address of the station that is  the master in VRRP group."
        ::= { hpnicfRprVrrpRSEntry 3 }

    hpnicfRprVrrpRSRingletID OBJECT-TYPE
        SYNTAX HpnicfRprRingletID
        MAX-ACCESS read-only
        STATUS current
        DESCRIPTION
            "The identifier of the ring which frames are sent
             from the source station to the destination station."
        ::= { hpnicfRprVrrpRSEntry 4 }

    hpnicfRprVrrpRSTtl OBJECT-TYPE
        SYNTAX INTEGER
        MAX-ACCESS read-only
        STATUS current
        DESCRIPTION
            "The hops from source station to destination station by
             selected ringlet."
        ::= { hpnicfRprVrrpRSEntry 5 }


-- The RPR default ring identifier config Table

    hpnicfRprDefaultRingIDTable OBJECT-TYPE
        SYNTAX SEQUENCE OF HpnicfRprDefaultRingIDEntry
        MAX-ACCESS not-accessible
        STATUS current
        DESCRIPTION
            "The RPR Default RingID Table specify the default ringID."
        ::= { hpnicfRprRS 6 }

    hpnicfRprDefaultRingIDEntry OBJECT-TYPE
        SYNTAX HpnicfRprDefaultRingIDEntry
        MAX-ACCESS not-accessible
        STATUS current
        DESCRIPTION
            "An entry in the RPR Default RingID Table."
        INDEX { hpnicfRprDefaultRingIDIfIndex }
        ::= { hpnicfRprDefaultRingIDTable 1 }

    HpnicfRprDefaultRingIDEntry ::=
        SEQUENCE {
            hpnicfRprDefaultRingIDIfIndex
                InterfaceIndex,
            hpnicfRprDefaultConfigRingletID
                HpnicfRprRingletID,
            hpnicfRprDefaultActiveRingID
                HpnicfRprRingletID
        }

    hpnicfRprDefaultRingIDIfIndex OBJECT-TYPE
        SYNTAX InterfaceIndex
        MAX-ACCESS not-accessible
        STATUS current
        DESCRIPTION
            "The ifIndex of RPR interface."
        REFERENCE
            "RFC 2863, ifIndex"
        ::= { hpnicfRprDefaultRingIDEntry 1 }

    hpnicfRprDefaultConfigRingletID OBJECT-TYPE
        SYNTAX HpnicfRprRingletID
        MAX-ACCESS read-write
        STATUS current
        DESCRIPTION
            "The default identifier of the ring configured by user."
        ::= { hpnicfRprDefaultRingIDEntry 2 }

    hpnicfRprDefaultActiveRingID OBJECT-TYPE
        SYNTAX HpnicfRprRingletID
        MAX-ACCESS read-only
        STATUS current
        DESCRIPTION
            "The identifier of the default ring which is active currently.
             The default ring configured by user may be inactive."
        ::= { hpnicfRprDefaultRingIDEntry 3 }

-- The RPR defect report table

    hpnicfRprDefect OBJECT IDENTIFIER ::= { hpnicfRprObjects 5 }

    hpnicfRprDefectReportTable OBJECT-TYPE
        SYNTAX SEQUENCE OF HpnicfRprDefectReportEntry
        MAX-ACCESS not-accessible
        STATUS current
        DESCRIPTION
            "The RPR Defect Report Table that contains the trap information on
             the ring."
        ::= { hpnicfRprDefect 1 }

    hpnicfRprDefectReportEntry OBJECT-TYPE
        SYNTAX HpnicfRprDefectReportEntry
        MAX-ACCESS not-accessible
        STATUS current
        DESCRIPTION
            "An entry in the RPR Defect Report Table."
        INDEX { hpnicfRprDefectIfIndex }
        ::= { hpnicfRprDefectReportTable 1 }

    HpnicfRprDefectReportEntry ::=
        SEQUENCE {
            hpnicfRprDefectIfIndex
                InterfaceIndex,
            hpnicfRprDefectCurrentStatus
                BITS
        }

    hpnicfRprDefectIfIndex OBJECT-TYPE
        SYNTAX InterfaceIndex
        MAX-ACCESS not-accessible
        STATUS current
        DESCRIPTION
            "The ifIndex of RPR interface."
        REFERENCE
            "RFC 2863, ifIndex"
        ::= { hpnicfRprDefectReportEntry 1 }

    hpnicfRprDefectCurrentStatus OBJECT-TYPE
        SYNTAX BITS {
            topologyOpenRing(0),
            topoInstability(1),
            topoInconsistent(2),
            dulpMacAddress(3),
            dulpIPAddress(4),
            lrttDefect(5),
            protCfgDefect(6),
            jumboCfgDefect(7),
            excessReservedRateDefect(8),
            excessMaxStationNum(9),
            miscabling(10),
            backPressure(11)
        }
        MAX-ACCESS read-only
        STATUS current
        DESCRIPTION
            "Indicates the current status of RPR ring.
             This attribute is used to notify the management system that
             alarms generate or clear about some RPR ring."
        REFERENCE
            "IEEE 802.17 V3.3 Subclause 11.2.9."
        ::= { hpnicfRprDefectReportEntry 2 }

-- The priority to RPR service class map table

    hpnicfRprPriorityMap OBJECT IDENTIFIER ::= { hpnicfRprObjects 6 }

    hpnicfRprPriority2ClassMapTable OBJECT-TYPE
        SYNTAX SEQUENCE OF HpnicfRprPriority2ClassMapEntry
        MAX-ACCESS not-accessible
        STATUS current
        DESCRIPTION
            "The Table is for Class Of Service and RPR Service Class Mapping."
        ::= { hpnicfRprPriorityMap 1 }

    hpnicfRprPriority2ClassMapEntry OBJECT-TYPE
        SYNTAX HpnicfRprPriority2ClassMapEntry
        MAX-ACCESS not-accessible
        STATUS current
        DESCRIPTION
            "An entry in the COS to Service Class Map Table."
        INDEX { hpnicfRprPriority2ClassMapIfIndex,
                hpnicfRprPriority2ClassMapType,
                hpnicfRprPriorityValue
        }
        ::= { hpnicfRprPriority2ClassMapTable 1 }

    HpnicfRprPriority2ClassMapEntry ::=
        SEQUENCE {
            hpnicfRprPriority2ClassMapIfIndex
                InterfaceIndex,
            hpnicfRprPriority2ClassMapType
                INTEGER,
            hpnicfRprPriorityValue
                INTEGER,
            hpnicfRprPriority2ClassMap
                HpnicfRprServiceClass
        }

    hpnicfRprPriority2ClassMapIfIndex OBJECT-TYPE
        SYNTAX InterfaceIndex
        MAX-ACCESS not-accessible
        STATUS current
        DESCRIPTION
            "The ifIndex of RPR interface."
        REFERENCE
            "RFC 2863, ifIndex"
        ::= { hpnicfRprPriority2ClassMapEntry 1 }

    hpnicfRprPriority2ClassMapType OBJECT-TYPE
        SYNTAX INTEGER {
            tag(1),
            mpls(2),
            ip(3)
        }
        MAX-ACCESS not-accessible
        STATUS current
        DESCRIPTION
            "The type of Priority,include tag, mpls, ip."
        ::= { hpnicfRprPriority2ClassMapEntry 2 }

    hpnicfRprPriorityValue OBJECT-TYPE
        SYNTAX INTEGER {
            pri0(1),
            pri1(2),
            pri2(3),
            pri3(4),
            pri4(5),
            pri5(6),
            pri6(7),
            pri7(8)
        }
        MAX-ACCESS not-accessible
        STATUS current
        DESCRIPTION
            "The priority of tag,mpls and ip, the value range is 0~7."
        ::= { hpnicfRprPriority2ClassMapEntry 3 }

    hpnicfRprPriority2ClassMap OBJECT-TYPE
        SYNTAX HpnicfRprServiceClass
        MAX-ACCESS read-write
        STATUS current
        DESCRIPTION
            "The RPR service class."
        REFERENCE
            "IEEE 802.17 V3.3 Subclause 7.3 Service class."
        ::= { hpnicfRprPriority2ClassMapEntry 4 }

-- The RPR rate-limit config table

    hpnicfRprRateLimitConfig OBJECT IDENTIFIER ::= { hpnicfRprObjects 7 }

    hpnicfRprRateLimitConfigTable  OBJECT-TYPE
        SYNTAX SEQUENCE OF HpnicfRprRateLimitConfigEntry
        MAX-ACCESS not-accessible
        STATUS current
        DESCRIPTION
            "The RPR Rate Limit Configuration Table that contains the rate
             limit infomation of RPR serviec class."
        ::= { hpnicfRprRateLimitConfig 1 }

    hpnicfRprRateLimitConfigEntry  OBJECT-TYPE
        SYNTAX HpnicfRprRateLimitConfigEntry
        MAX-ACCESS not-accessible
        STATUS current
        DESCRIPTION
            "An entry in the RPR Rate Limit Configuration Table."
        INDEX { hpnicfRprRateLimitConfigIfIndex,
                hpnicfRprRateLimitConfigRingletId,
                hpnicfRprRateLimitConfigServiceClass
        }
        ::= { hpnicfRprRateLimitConfigTable 1 }

    HpnicfRprRateLimitConfigEntry  ::=
        SEQUENCE {
            hpnicfRprRateLimitConfigIfIndex
                InterfaceIndex,
            hpnicfRprRateLimitConfigRingletId
                HpnicfRprRingletID,
            hpnicfRprRateLimitConfigServiceClass
                HpnicfRprServiceClass,
            hpnicfRprRateLimitConfigValue
                Integer32
        }

    hpnicfRprRateLimitConfigIfIndex OBJECT-TYPE
        SYNTAX InterfaceIndex
        MAX-ACCESS not-accessible
        STATUS current
        DESCRIPTION
            "The ifIndex of RPR interface."
        REFERENCE
            "RFC 2863, ifIndex"
        ::= { hpnicfRprRateLimitConfigEntry 1 }

    hpnicfRprRateLimitConfigRingletId OBJECT-TYPE
        SYNTAX HpnicfRprRingletID
        MAX-ACCESS not-accessible
        STATUS current
        DESCRIPTION
            "The identifier of the ring of RPR ringlet."
        ::= { hpnicfRprRateLimitConfigEntry 2 }

    hpnicfRprRateLimitConfigServiceClass OBJECT-TYPE
        SYNTAX HpnicfRprServiceClass
        MAX-ACCESS not-accessible
        STATUS current
        DESCRIPTION
            "The RPR service class."
        REFERENCE
            "IEEE 802.17 V3.3 Subclause 7.3 Service class."
        ::= { hpnicfRprRateLimitConfigEntry 3 }

    hpnicfRprRateLimitConfigValue OBJECT-TYPE
        SYNTAX Integer32
        MAX-ACCESS read-write
        STATUS current
        DESCRIPTION
            "The value of rate-limit that configured for diffrent service class.
             The unit is permillage."
        ::= { hpnicfRprRateLimitConfigEntry 4 }

-- The RPR mac address learning config table

    hpnicfRprMacAddrLearn  OBJECT IDENTIFIER ::= { hpnicfRprObjects 8 }

    hpnicfRprMacLearnCfgTable OBJECT-TYPE
        SYNTAX SEQUENCE OF HpnicfRprMacLearnCfgEntry
        MAX-ACCESS not-accessible
        STATUS current
        DESCRIPTION
            "The RPR MAC Address Table."
        ::= { hpnicfRprMacAddrLearn 1 }

    hpnicfRprMacLearnCfgEntry OBJECT-TYPE
        SYNTAX HpnicfRprMacLearnCfgEntry
        MAX-ACCESS not-accessible
        STATUS current
        DESCRIPTION
            "The entry of RPR MAC Address Table."
        INDEX { hpnicfRprMacLearnIfIndex, hpnicfRprMacLearnRprMac }
        ::= { hpnicfRprMacLearnCfgTable 1 }

    HpnicfRprMacLearnCfgEntry ::=
        SEQUENCE {
            hpnicfRprMacLearnIfIndex
                InterfaceIndex,
            hpnicfRprMacLearnRprMac
                MacAddress,
            hpnicfRprMacLearnType
                INTEGER,
            hpnicfRprMacLearnDestMac
                MacAddress,
            hpnicfRprMacLearnVlanId
                Integer32,
            hpnicfRprMacLearnRinglet
                HpnicfRprRingletID,
            hpnicfRprMacLearnTtl
                INTEGER,
            hpnicfRprMacLearnIsValid
                TruthValue,
            hpnicfRprMacLearnRowStatus
                RowStatus
        }

    hpnicfRprMacLearnIfIndex OBJECT-TYPE
        SYNTAX InterfaceIndex
        MAX-ACCESS not-accessible
        STATUS current
        DESCRIPTION
            "The ifIndex of RPR interface."
        REFERENCE
            "RFC 2863, ifIndex"
        ::= { hpnicfRprMacLearnCfgEntry 1 }

    hpnicfRprMacLearnRprMac OBJECT-TYPE
        SYNTAX MacAddress
        MAX-ACCESS not-accessible
        STATUS current
        DESCRIPTION
            "The MAC address of the RPR station."
        ::= { hpnicfRprMacLearnCfgEntry 2 }

    hpnicfRprMacLearnType OBJECT-TYPE
        SYNTAX INTEGER
        MAX-ACCESS read-create
        STATUS current
        DESCRIPTION
            "The type of MAC address item that the user built. The type
             includes static and dynamic."
        ::= { hpnicfRprMacLearnCfgEntry 3 }

    hpnicfRprMacLearnDestMac OBJECT-TYPE
        SYNTAX MacAddress
        MAX-ACCESS read-create
        STATUS current
        DESCRIPTION
            "The destination of MAC address."
        ::= { hpnicfRprMacLearnCfgEntry 4 }

    hpnicfRprMacLearnVlanId OBJECT-TYPE
        SYNTAX Integer32 (1..4094)
        MAX-ACCESS read-create
        STATUS current
        DESCRIPTION
            "The vlan ID that the MAC address learned from by RPR staion."
        ::= { hpnicfRprMacLearnCfgEntry 5 }

    hpnicfRprMacLearnRinglet OBJECT-TYPE
        SYNTAX HpnicfRprRingletID
        MAX-ACCESS read-create
        STATUS current
        DESCRIPTION
            "The identifier of the ring which frames are sent
             from the source station to the destination station."
        ::= { hpnicfRprMacLearnCfgEntry 6 }

    hpnicfRprMacLearnTtl OBJECT-TYPE
        SYNTAX INTEGER
        MAX-ACCESS read-only
        STATUS current
        DESCRIPTION
            "The hops from source station to destination station on the
             selected ringlet."
        ::= { hpnicfRprMacLearnCfgEntry 7 }

    hpnicfRprMacLearnIsValid OBJECT-TYPE
        SYNTAX TruthValue
        MAX-ACCESS read-only
        STATUS current
        DESCRIPTION
            "The flag identify whether the configured mac address is valid.
             If it is true, the configured mac address is valid,
             otherwise it's invalid."
        ::= { hpnicfRprMacLearnCfgEntry 8 }

    hpnicfRprMacLearnRowStatus OBJECT-TYPE
        SYNTAX RowStatus
        MAX-ACCESS read-create
        STATUS current
        DESCRIPTION
            "The status of this table entry.
             The status includes createAndGo, active and destroy."
        ::= { hpnicfRprMacLearnCfgEntry 9 }

-- The RPR table for trap

    hpnicfRprTrapVar OBJECT IDENTIFIER ::= { hpnicfRprObjects 9 }

    hpnicfRprTrapVarTable OBJECT-TYPE
        SYNTAX SEQUENCE OF HpnicfRprTrapVarEntry
        MAX-ACCESS not-accessible
        STATUS current
        DESCRIPTION
            "The RPR Defect Report Table that contains varible that
             used to bind in trap."
        ::= { hpnicfRprTrapVar 1 }

    hpnicfRprTrapVarEntry OBJECT-TYPE
        SYNTAX HpnicfRprTrapVarEntry
        MAX-ACCESS not-accessible
        STATUS current
        DESCRIPTION
            "An entry in the RPR Trap Var Table."
        INDEX { hpnicfRprTrapIfIndex }
        ::= { hpnicfRprTrapVarTable 1 }

    HpnicfRprTrapVarEntry ::=
        SEQUENCE {
            hpnicfRprTrapIfIndex
                InterfaceIndex,
            hpnicfRprTrapRinglet
                HpnicfRprRingletID,
            hpnicfRprTrapTopoMacAddress
                MacAddress,
            hpnicfRprTrapIpAddress
                InetAddress
        }

    hpnicfRprTrapIfIndex OBJECT-TYPE
        SYNTAX InterfaceIndex
        MAX-ACCESS accessible-for-notify
        STATUS current
        DESCRIPTION
            "The ifIndex of RPR interface. It is only used for trap to bind."
        REFERENCE
            "RFC 2863, ifIndex"
        ::= { hpnicfRprTrapVarEntry 1 }

     hpnicfRprTrapRinglet OBJECT-TYPE
        SYNTAX HpnicfRprRingletID
        MAX-ACCESS accessible-for-notify
        STATUS current
        DESCRIPTION
            "The span of RPR station. It is only used for trap to bind."
        ::= { hpnicfRprTrapVarEntry 2 }

     hpnicfRprTrapTopoMacAddress OBJECT-TYPE
        SYNTAX MacAddress
        MAX-ACCESS accessible-for-notify
        STATUS current
        DESCRIPTION
            "The MAC address of RPR station. It is only used for trap to bind."
        ::= { hpnicfRprTrapVarEntry 3 }

    hpnicfRprTrapIpAddress OBJECT-TYPE
        SYNTAX InetAddress
        MAX-ACCESS accessible-for-notify
        STATUS current
        DESCRIPTION
            "The IP address of RPR station. It is only used for trap to bind."
        ::= { hpnicfRprTrapVarEntry 4 }


-- The RPR Traps

    hpnicfRprTrap  OBJECT IDENTIFIER ::= { hpnicfRprObjects 10 }

    hpnicfRprTopologyOpenRing NOTIFICATION-TYPE
        OBJECTS { hpnicfRprTrapIfIndex, hpnicfRprTrapRinglet }
        STATUS  current
        DESCRIPTION
            "The topology openRing trap indicates that the RPR ring is opened."
        REFERENCE
            "IEEE 802.17 Subclause 3.2.77 open ring."
        ::= { hpnicfRprTrap 1 }

    hpnicfRprTopologyCloseRing NOTIFICATION-TYPE
        OBJECTS { hpnicfRprTrapIfIndex, hpnicfRprTrapRinglet }
        STATUS  current
        DESCRIPTION
            "The topology openRing trap indicates that the RPR ring is closed."
        REFERENCE
            "IEEE 802.17 Subclause 3.2.77 close ring."
        ::= { hpnicfRprTrap 2 }

    hpnicfRprTopologyInconsistent NOTIFICATION-TYPE
        OBJECTS { hpnicfRprTrapIfIndex }
        STATUS  current
        DESCRIPTION
            "The topology inconsistent trap indicates that the topology of
             RPR is inconsistent."
        REFERENCE
            "IEEE 802.17 Subclause 11.6.6.1 topology consistency."
        ::= { hpnicfRprTrap 3 }

    hpnicfRprTopologyInstability NOTIFICATION-TYPE
        OBJECTS { hpnicfRprTrapIfIndex }
        STATUS  current
        DESCRIPTION
            "The topology instability trap indicates that the topology of
             RPR is instability."
        ::= { hpnicfRprTrap 4 }


    hpnicfRprDuplicateMacAddress NOTIFICATION-TYPE
        OBJECTS { hpnicfRprTrapIfIndex, hpnicfRprTrapTopoMacAddress}
        STATUS  current
        DESCRIPTION
            "The duplicate MAC address trap indicates that the mac address
             of the station on the ring is dulplicate. That means there is the
             same MAC address between two stations on the ring."
        ::= { hpnicfRprTrap 5 }

    hpnicfRprDulplicateIPAddress NOTIFICATION-TYPE
        OBJECTS { hpnicfRprTrapIfIndex, hpnicfRprTrapIpAddress }
        STATUS  current
        DESCRIPTION
            "The dulplicate IP address trap indicates that the IP address of
             the station on the ring is dulplicate. That means there is the same
             IP address between two stations on the ring."
        ::= { hpnicfRprTrap 6 }

    hpnicfRprIncompleteLRTT NOTIFICATION-TYPE
        OBJECTS { hpnicfRprTrapIfIndex }
        STATUS  current
        DESCRIPTION
            "The incomplete LRTT trap indicates that LRTT is not completed."
        ::= { hpnicfRprTrap 7 }

    hpnicfRprProtecConfigInconsistent NOTIFICATION-TYPE
        OBJECTS { hpnicfRprTrapIfIndex }
        STATUS  current
        DESCRIPTION
            "The protection configuration inconsistent trap indicates that
             the configuration of protection mode on the ring is inconsistent.
             That is one station is configured steer mode while the other is
             configured wrap mode."
        ::= { hpnicfRprTrap 8 }

    hpnicfRprJumboConfigInconsistent NOTIFICATION-TYPE
        OBJECTS { hpnicfRprTrapIfIndex }
        STATUS  current
        DESCRIPTION
            "The jumbo configuration inconsistent trap indicates that the
             configuration of jumbo mode on the ring is inconsistent.
             That is one station supports jumbo frame while the other
             doesn't support jumbo frame."
        ::= { hpnicfRprTrap 9 }

    hpnicfRprExceedMaxReservRate NOTIFICATION-TYPE
        OBJECTS { hpnicfRprTrapIfIndex, hpnicfRprTrapRinglet }
        STATUS  current
        DESCRIPTION
            "The exceeded max reserved rate trap indicates that the rate
             on the ringlet exceeded the max reserved rate. The operator can
             configure reserved rate for every station, but the sum of all
             stations' reserved rate of each RPR ringlet can't exceed maximum."
        ::= { hpnicfRprTrap 10 }

    hpnicfRprExceedMaxStationNum NOTIFICATION-TYPE
        OBJECTS { hpnicfRprTrapIfIndex }
        STATUS  current
        DESCRIPTION
            "The exceeded max station number trap indicates that the number
             of the stations on the ring exceeded the max station number."
        ::= { hpnicfRprTrap 11 }

    hpnicfRprMiscabling NOTIFICATION-TYPE
        OBJECTS { hpnicfRprTrapIfIndex, hpnicfRprTrapRinglet }
        STATUS  current
        DESCRIPTION
            "The miscabling trap indicates that the miscabling event occurred."
        REFERENCE
            "IEEE 802.17 V3.0 Subclause 11.9.2.1 miscabling defect."
        ::= { hpnicfRprTrap 12 }

    hpnicfRprBackPressure NOTIFICATION-TYPE
        OBJECTS { hpnicfRprTrapIfIndex, hpnicfRprTrapRinglet, hpnicfRprPriority2ClassMap}
        STATUS  current
        DESCRIPTION
            "The back pressure trap indicates that the backpressure is generated
             on the ringlet. That is the data flow on the ringlet exceeded
             the range of rate-limit configured."
        ::= { hpnicfRprTrap 13 }

    hpnicfRprBackPressureOver NOTIFICATION-TYPE
        OBJECTS { hpnicfRprTrapIfIndex, hpnicfRprTrapRinglet, hpnicfRprPriority2ClassMap }
        STATUS  current
        DESCRIPTION
            "The back pressure over trap indicates that the backpressure is
             disappeared on the ringlet."
        ::= { hpnicfRprTrap 14 }

END
