-- ===========================================================================================================
-- Copyright (c) 2010-2014 Hewlett-Packard Development Company, L.P.
--
-- Description: context MIB
-- Reference:
-- Version: V1.0
-- History:
-- revision 1.0 2014-3-18 created by c08124
--
-- ============================================================================================================
HPN-ICF-CONTEXT-MIB DEFINITIONS ::= BEGIN

IMPORTS
    hpnicfCommon
        FROM HPN-ICF-OID-MIB
    Integer32, OBJECT-TYPE, MODULE-IDENTITY, NOTIFICATION-TYPE
        FROM SNMPv2-SMI
    DisplayString
        FROM SNMPv2-TC;

hpnicfContext MODULE-IDENTITY
    LAST-UPDATED "201403180000Z"
    ORGANIZATION
        ""
    CONTACT-INFO
        ""
    DESCRIPTION
        "This MIB contains objects for managing context operations."

    REVISION "201403180000Z"
    DESCRIPTION
        "Initial revision of this MIB module."
    ::= { hpnicfCommon 154 }

hpnicfContextTables OBJECT IDENTIFIER ::= { hpnicfContext 1 }

hpnicfContextControl OBJECT IDENTIFIER ::= { hpnicfContextTables 1 }


hpnicfContextControlTable OBJECT-TYPE
    SYNTAX SEQUENCE OF HpnicfContextControlEntry
    MAX-ACCESS not-accessible
    STATUS current
    DESCRIPTION
        "This table is used to configure contexts for a device and
         show context status info."
    ::= { hpnicfContextControl 1 }


hpnicfContextControlEntry OBJECT-TYPE
    SYNTAX HpnicfContextControlEntry
    MAX-ACCESS not-accessible
    STATUS current
    DESCRIPTION
        "An entry of the hpnicfContextControlTable.
         Each entry corresponds to one context."
    INDEX { hpnicfContextIndex }
    ::= { hpnicfContextControlTable 1 }

HpnicfContextControlEntry ::=
    SEQUENCE
        {
            hpnicfContextIndex
                Integer32,
            hpnicfContextName
                DisplayString
        }

hpnicfContextIndex OBJECT-TYPE
    SYNTAX Integer32 (1..2147483647)
    MAX-ACCESS accessible-for-notify
    STATUS current
    DESCRIPTION
        "The value range of Context ID depends on the device model."
    ::= { hpnicfContextControlEntry 1 }


hpnicfContextName OBJECT-TYPE
    SYNTAX DisplayString (SIZE (1..15))
    MAX-ACCESS read-only
    STATUS current
    DESCRIPTION
        "Specifies the context name,
         a case-sensitive string of 1 to 15 characters.
         The context name cannot be modified once created."
    ::= { hpnicfContextControlEntry 2 }


hpnicfContextNotification OBJECT IDENTIFIER ::= { hpnicfContext 8 }

hpnicfContextNotificationObjects OBJECT IDENTIFIER ::= { hpnicfContextNotification 0 }

hpnicfContextStateChangeToActive NOTIFICATION-TYPE
    OBJECTS {hpnicfContextIndex, hpnicfContextName}
    STATUS current
    DESCRIPTION
        "The hpnicfContextStateChangeToActive trap indicates
         that the context status has changed to active."
    ::= { hpnicfContextNotificationObjects 1 }

hpnicfContextStateChangeToInactive NOTIFICATION-TYPE
    OBJECTS {hpnicfContextIndex, hpnicfContextName}
    STATUS current
    DESCRIPTION
        "The hpnicfContextStateChangeToInactive trap indicates
         that the context status has changed to inactive."
    ::= { hpnicfContextNotificationObjects 2 }

END
