-- ===================================================================
-- Copyright (c) 2010-2014 Hewlett-Packard Development Company, L.P.
--
-- Description: Per-VLAN spanning tree (PVST) MIB
-- Reference:
-- Version: V1.0
-- History:
-- V1.0 2014-05-27 Created by wangmingjun.
-- ===================================================================
-- ===================================================================
--
-- Imported variables and types
--
-- ===================================================================

HPN-ICF-PVST-MIB DEFINITIONS ::= BEGIN

IMPORTS
    MODULE-IDENTITY, OBJECT-TYPE, Integer32, NOTIFICATION-TYPE
        FROM SNMPv2-SMI
    hpnicfCommon
        FROM HPN-ICF-OID-MIB;

hpnicfPvst MODULE-IDENTITY
    LAST-UPDATED "201405270000Z"
    ORGANIZATION
        ""
    CONTACT-INFO
        ""
    DESCRIPTION
        "This MIB defines objects for managing Per-VLAN spanning tree (PVST)."
    REVISION "201405270000Z"
    DESCRIPTION
        "The initial version of this MIB file."
    ::= { hpnicfCommon  131 }

-- =========================
-- Subtrees in the PVST MIB
-- =========================

hpnicfPvstObjects
    OBJECT IDENTIFIER ::= { hpnicfPvst 1 }

hpnicfPvstNotifications
    OBJECT IDENTIFIER ::= { hpnicfPvst 2 }

--  ==================================================================
--  PVST objects table
--  ==================================================================

--  ===============================
--  PVST VLAN table
--  ===============================

hpnicfPvstVlanConfigTable OBJECT-TYPE
    SYNTAX SEQUENCE OF HpnicfPvstVlanConfigEntry
    MAX-ACCESS  not-accessible
    STATUS      current
    DESCRIPTION
        "PVST VLAN configuration table."
    ::= { hpnicfPvstObjects 1 }

hpnicfPvstVlanConfigEntry OBJECT-TYPE
    SYNTAX      HpnicfPvstVlanConfigEntry
    MAX-ACCESS  not-accessible
    STATUS      current
    DESCRIPTION
        "PVST VLAN configuration table entry."
    INDEX {
              hpnicfPvstVlanID
          }
    ::= { hpnicfPvstVlanConfigTable 1 }

HpnicfPvstVlanConfigEntry ::=
    SEQUENCE
    {
        hpnicfPvstVlanID      Integer32
    }

hpnicfPvstVlanID OBJECT-TYPE
    SYNTAX      Integer32(1..4094)
    MAX-ACCESS  read-only
    STATUS      current
    DESCRIPTION
        "The index of the VLAN configuration table."
    ::= { hpnicfPvstVlanConfigEntry 1 }

--  ===============================
--  PVST VLAN port table
--  ===============================

hpnicfPvstVlanPortConfigTable OBJECT-TYPE
    SYNTAX SEQUENCE OF HpnicfPvstVlanPortConfigEntry
    MAX-ACCESS  not-accessible
    STATUS      current
    DESCRIPTION
        "PVST VLAN port configuration table."
        ::= { hpnicfPvstObjects 2 }

hpnicfPvstVlanPortConfigEntry OBJECT-TYPE
    SYNTAX      HpnicfPvstVlanPortConfigEntry
    MAX-ACCESS  not-accessible
    STATUS      current
    DESCRIPTION
        "PVST VLAN port configuration table entry."
    INDEX {
              hpnicfPvstPortVlanID,
              hpnicfPvstPortIndex
          }
    ::= { hpnicfPvstVlanPortConfigTable 1 }

HpnicfPvstVlanPortConfigEntry ::=
    SEQUENCE
    {
        hpnicfPvstPortVlanID     Integer32,
        hpnicfPvstPortIndex      Integer32
    }

hpnicfPvstPortVlanID       OBJECT-TYPE
    SYNTAX      Integer32(1..4094)
    MAX-ACCESS  read-only
    STATUS      current
    DESCRIPTION
        "The index of the VLAN."
    ::={ hpnicfPvstVlanPortConfigEntry 1 }

hpnicfPvstPortIndex OBJECT-TYPE
    SYNTAX      Integer32(1..2147483647)
    MAX-ACCESS  read-only
    STATUS      current
    DESCRIPTION
        "The index of the bridge port."
    ::={ hpnicfPvstVlanPortConfigEntry 2 }

--  ==================================================================
--  PVST notification table
--  ==================================================================

hpnicfPvstEvents
    OBJECT IDENTIFIER ::= { hpnicfPvstNotifications 0 }

hpnicfPvstVlanPortDetectedTc NOTIFICATION-TYPE
    OBJECTS  { hpnicfPvstPortVlanID , hpnicfPvstPortIndex }
    STATUS   current
    DESCRIPTION
        "The SNMP trap is generated when a port detects
         a topology change in a VLAN."
    ::= { hpnicfPvstEvents 1 }

hpnicfPvstVlanPortRcvdTc NOTIFICATION-TYPE
    OBJECTS  { hpnicfPvstPortVlanID , hpnicfPvstPortIndex }
    STATUS   current
    DESCRIPTION
        "The SNMP trap is generated when a port receives
         a topology change in a VLAN."
    ::= { hpnicfPvstEvents 2 }

END
