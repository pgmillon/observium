-- =========================================================================
-- Copyright (c) 2010-2014 Hewlett-Packard Development Company, L.P.
--
-- Description: The MIB is designed to set session configuration or get session information.
-- Reference:
-- Version: V1.0
-- History:
--  V1.0 2013-12-20 created by liqian 04379
--       Initial version.
-- =========================================================================
HPN-ICF-SESSION-MIB DEFINITIONS ::= BEGIN

IMPORTS
        hpnicfCommon
    FROM HPN-ICF-OID-MIB
        Unsigned32, OBJECT-TYPE, MODULE-IDENTITY
    FROM SNMPv2-SMI;

hpnicfSession MODULE-IDENTITY
    LAST-UPDATED "201312200000Z"
    ORGANIZATION
        ""
    CONTACT-INFO
        ""
    DESCRIPTION
        "The MIB is designed to manage sessions."

    -- Revision History
    REVISION     "201312200000Z"  -- December 26, 2013
    DESCRIPTION  "Initial version."

    ::= { hpnicfCommon 149 }

--
-- Table definitions
--

hpnicfSessionTables OBJECT IDENTIFIER ::= { hpnicfSession 1 }
-- ----------------------------------------------------------------------
  -- Session statistic table
-- ----------------------------------------------------------------------
hpnicfSessionStatTable OBJECT-TYPE
    SYNTAX  SEQUENCE OF HpnicfSessionStatEntry
    MAX-ACCESS  not-accessible
    STATUS  current
    DESCRIPTION
    "The statistics of sessions."
::= { hpnicfSessionTables 1 }

hpnicfSessionStatEntry OBJECT-TYPE
    SYNTAX  HpnicfSessionStatEntry
    MAX-ACCESS  not-accessible
    STATUS  current
    DESCRIPTION
    "An entry (conceptual row) representing session statistics information."
    INDEX { hpnicfSessionStatChassis, hpnicfSessionStatSlot, hpnicfSessionStatCPUID }
::= { hpnicfSessionStatTable 1 }

HpnicfSessionStatEntry ::= SEQUENCE {
    hpnicfSessionStatChassis          Unsigned32,
    hpnicfSessionStatSlot             Unsigned32,
    hpnicfSessionStatCPUID            Unsigned32,
    hpnicfSessionStatCount            Unsigned32,
    hpnicfSessionStatCreateRate       Unsigned32
    }

hpnicfSessionStatChassis   OBJECT-TYPE
    SYNTAX Unsigned32(0..65534)
    MAX-ACCESS  not-accessible
    STATUS  current
    DESCRIPTION
    "An IRF member device ID."
::= { hpnicfSessionStatEntry  1 }

hpnicfSessionStatSlot    OBJECT-TYPE
    SYNTAX Unsigned32(0..65534)
    MAX-ACCESS  not-accessible
    STATUS  current
    DESCRIPTION
    "The slot where the card resides."
::= { hpnicfSessionStatEntry  2 }

hpnicfSessionStatCPUID   OBJECT-TYPE
    SYNTAX Unsigned32(0..7)
    MAX-ACCESS  not-accessible
    STATUS  current
    DESCRIPTION
    "CPU ID."
::= { hpnicfSessionStatEntry  3 }

hpnicfSessionStatCount  OBJECT-TYPE
    SYNTAX Unsigned32
    MAX-ACCESS  read-only
    STATUS  current
    DESCRIPTION
    "The number of current sessions."
::= { hpnicfSessionStatEntry  4 }

hpnicfSessionStatCreateRate     OBJECT-TYPE
    SYNTAX Unsigned32
    MAX-ACCESS  read-only
    STATUS  current
    DESCRIPTION
    "The number of sessions per second."
::= { hpnicfSessionStatEntry  5 }

END
