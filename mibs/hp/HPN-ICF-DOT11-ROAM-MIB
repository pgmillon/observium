-- =====================================================================
-- Copyright (c) 2010-2013 Hewlett-Packard Development Company, L.P.
--
-- Description: The file defines a MIB to provide WLAN roaming configuration.
-- Reference:
-- Version: V1.2
-- History:
-- V1.0 2008-7-23 created by heziqi
-- V1.1 2009-05-07 modified by Li Yugang
--      Add hpnicfDot11RoamStatisGroup to hpnicfDot11ROAM.
-- V1.2 2009-12-24 modified for Guangdong Mobile
--      Add hpnicfDot11InterACRoamOutSuccCnt to hpnicfDot11RoamStatisGroup.
--      2010-08-04 modefied by l07769 for Guangdong CMCC
--      Add hpnicfDot11IntraACRoamingSuccCnt2, hpnicfDot11InterACRoamingSuccCnt2
--      and hpnicfDot11InterACRoamOutSuccCnt2 to hpnicfDot11RoamStatis2Group.
-- =====================================================================
HPN-ICF-DOT11-ROAM-MIB DEFINITIONS ::= BEGIN

IMPORTS
        TruthValue,
        MacAddress,
        RowStatus,
        TEXTUAL-CONVENTION
    FROM SNMPv2-TC
        MODULE-IDENTITY,
        OBJECT-TYPE,
        Integer32
    FROM SNMPv2-SMI
        InetAddressType,
        InetAddress
    FROM INET-ADDRESS-MIB
        hpnicfDot11
    FROM HPN-ICF-DOT11-REF-MIB;

hpnicfDot11ROAM MODULE-IDENTITY
    LAST-UPDATED "201008041800Z"        -- Aug 04, 2010 at 18:00 GMT
    ORGANIZATION
        ""
    CONTACT-INFO
        ""
    DESCRIPTION
        "This MIB provides information about WLAN roaming configuration.

        GLOSSARY

        IEEE 802.11
        Standard to encourage interoperability among
        wireless networking equipment.

        Access point (AP)
        Transmitter/receiver (transceiver) device
        that commonly connects and transports data
        between a wireless network and a wired network.

        Access control (AC)
        To control and manage multi-APs, it will bridge
        wireless and wired network.

        BSS
        IEEE 802.11 Basic Service Set (Radio Cell).  The
        BSS of an AP comprises of the stations directly
        associating with the AP.

        Radio
        The chip set to receive and send wireless signal.

        HA
        The AC to which a wireless station is connected by
        associating with an AP for the first time is the
        HA of the station.

        FA
        An AC that is other than the HA and to which a
        station is currently connected is an FA of the
        station.

        Fast-roam capable station
        A wireless station which directly associates to
        a fast-roam service (rsn+dot1X) with one AC for
        the first time.

        Roam-out station
        A wireless station which has associated with an
        AC other than the HA in the mobility-group is
        referred to as a roam-out station at its HA.

        Roam-in station
        A wireless station which has associated with an
        AC other than the HA in the mobility-group is
        referred to as a roam-in station at the FA.

        Intra-AC roaming
        A procedure where a wireless station roams from
        one AP to another AP, which are connected to the
        same AC.

        Inter-AC roaming
        A procedure where a wireless station roams from
        one AP to another AP, which are connected to
        different ACs.

        Inter-AC fast roaming capability
        If a station uses 802.1x (RSN) authentication
        through negotiation, this station has inter-AC
        fast roaming capability.

        WLAN-tunnel
        One type of layer 2 interface which is bound with
        an IACTP data tunnel and used to tunnel
        unicast/broadcast frames between ACs."

    REVISION "201008041800Z"        -- Aug 04, 2010 at 18:00 GMT
    DESCRIPTION
            "Modified to add new hpnicfDot11RoamStatis2Group."
    REVISION "200905072000Z"
    DESCRIPTION
            "Modified to add new hpnicfDot11RoamStatisGroup."
    REVISION "200807231200Z"
    DESCRIPTION
            "The initial revision of this MIB module."
    ::= { hpnicfDot11 10 }

-- ==================================================================
-- Textual Conventions
-- ==================================================================
HpnicfDot11RoamMobileTunnelType ::=  TEXTUAL-CONVENTION
    STATUS      current
    DESCRIPTION
        "The protocol type of the mobility-tunnel.
        This object has two defined values:
        - 'ipv4', which indicates that the protocol type of the mobility-tunnel
          is IPv4.
        - 'ipv6', which indicates that the protocol type of the mobility-tunnel
          is IPv6.
        "
    SYNTAX      INTEGER
        {
            ipv4(1),
            ipv6(2)
        }

HpnicfDot11RoamAuthMode ::=  TEXTUAL-CONVENTION
    STATUS      current
    DESCRIPTION
        "The authentication mode of the mobility-tunnel.
        This object has two defined values:
        - 'none', which indicates that the authentication mode of the
          mobility-tunnel is None.
        - 'md5', which indicates that the authentication mode of the
          mobility-tunnel is MD5.
        "
    SYNTAX      INTEGER
        {
            none(1),
            md5(2)
        }

HpnicfDot11RoamIACTPStatus ::=  TEXTUAL-CONVENTION
    STATUS      current
    DESCRIPTION
        "The status of IACTP state machine."
    SYNTAX      INTEGER
        {
            init(1),
            idle(2),
            joinRequestWait(3),
            joinResponseWait(4),
            joinConfirmWait(5),
            joinError(6),
            run(7)
        }

-- ==================================================================
-- Major sections
-- ==================================================================
hpnicfDot11RoamCfgGroup OBJECT IDENTIFIER  ::= { hpnicfDot11ROAM 1 }
--  Roaming Configuration Group has the following children:
--  hpnicfDot11MobGrpTable            ::= { hpnicfDot11RoamCfgGroup 1 }
--  hpnicfDot11MobGrpMemberTable      ::= { hpnicfDot11RoamCfgGroup 2 }

hpnicfDot11RoamStatusGroup OBJECT IDENTIFIER  ::= { hpnicfDot11ROAM 2 }
--  Roaming Status Group has the following children:
--  hpnicfDot11RoamInInfoTable             ::= { hpnicfDot11RoamStatusGroup 1 }
--  hpnicfDot11RoamOutInfoTable            ::= { hpnicfDot11RoamStatusGroup 2 }
--  hpnicfDot11RoamTrackTable              ::= { hpnicfDot11RoamStatusGroup 3 }

hpnicfDot11RoamStatisGroup OBJECT IDENTIFIER  ::= { hpnicfDot11ROAM 3 }
--  Roaming Statis Group has the following children:
--  hpnicfDot11IntraACRoamingSuccCnt       ::= { hpnicfDot11RoamStatusGroup 1 }
--  hpnicfDot11InterACRoamingSuccCnt       ::= { hpnicfDot11RoamStatusGroup 2 }

hpnicfDot11RoamStatis2Group OBJECT IDENTIFIER  ::= { hpnicfDot11ROAM 4 }
--  Roaming Statis Group has the following children:
--  hpnicfDot11IntraACRoamingSuccCnt2     ::= { hpnicfDot11RoamStatus2Group 1 }
--  hpnicfDot11InterACRoamingSuccCnt2     ::= { hpnicfDot11RoamStatus2Group 2 }
--  hpnicfDot11InterACRoamOutSuccCnt2     ::= { hpnicfDot11RoamStatus2Group 3 }

-- ==================================================================
-- hpnicfDot11RoamCfgGroup Definition
-- ==================================================================
-- ==================================================================
-- hpnicfDot11MobGrpTable Definition
-- ==================================================================
hpnicfDot11MobGrpTable OBJECT-TYPE
    SYNTAX      SEQUENCE OF HpnicfDot11MobGrpEntry
    MAX-ACCESS  not-accessible
    STATUS      current
    DESCRIPTION
        "The table defines the parameters for roaming group configuration."
    ::= { hpnicfDot11RoamCfgGroup 1 }

hpnicfDot11MobGrpEntry OBJECT-TYPE
    SYNTAX      HpnicfDot11MobGrpEntry
    MAX-ACCESS  not-accessible
    STATUS      current
    DESCRIPTION
        "This entry contains information of mobile group."
    INDEX
        {
            hpnicfDot11MobGrpName
        }
    ::= { hpnicfDot11MobGrpTable 1 }

HpnicfDot11MobGrpEntry ::= SEQUENCE
    {
        hpnicfDot11MobGrpName        OCTET STRING,
        hpnicfdot11MobGrpTunnelType  HpnicfDot11RoamMobileTunnelType,
        hpnicfDot11MobGrpSrcIPAddr   InetAddress,
        hpnicfDot11MobGrpAuthMode    HpnicfDot11RoamAuthMode,
        hpnicfDot11MobGrpAuthKey     OCTET STRING,
        hpnicfDot11MobGrpEnable      TruthValue,
        hpnicfDot11MobGrpRowStatus   RowStatus
    }

hpnicfDot11MobGrpName OBJECT-TYPE
    SYNTAX      OCTET STRING(SIZE(1..15))
    MAX-ACCESS  not-accessible
    STATUS      current
    DESCRIPTION
        "Represents the name of roam group."
    ::= { hpnicfDot11MobGrpEntry 1 }

hpnicfdot11MobGrpTunnelType OBJECT-TYPE
    SYNTAX      HpnicfDot11RoamMobileTunnelType
    MAX-ACCESS  read-create
    STATUS      current
    DESCRIPTION
        "Represents the protocol type of mobility-tunnel."
    DEFVAL      { ipv4 }
    ::= { hpnicfDot11MobGrpEntry 2 }

hpnicfDot11MobGrpSrcIPAddr OBJECT-TYPE
    SYNTAX      InetAddress
    MAX-ACCESS  read-create
    STATUS      current
    DESCRIPTION
        "Represents the IP address of tunnel source.  The IP address
         type must be the same as hpnicfdot11MobGrpTunnelType.
         The default value is zero."
    ::= { hpnicfDot11MobGrpEntry 3 }

hpnicfDot11MobGrpAuthMode OBJECT-TYPE
    SYNTAX      HpnicfDot11RoamAuthMode
    MAX-ACCESS  read-create
    STATUS      current
    DESCRIPTION
        "Represents the authentication mode of IACTP tunnel.
         This object can be used to enable IACTP control message
         integrity authentication."
    DEFVAL      { none }
    ::= { hpnicfDot11MobGrpEntry 4 }

hpnicfDot11MobGrpAuthKey OBJECT-TYPE
    SYNTAX      OCTET STRING(SIZE(0..16))
    MAX-ACCESS  read-create
    STATUS      current
    DESCRIPTION
        "Represents the authentication key of IACTP tunnel.
         Authentication key to be used with the given
         authentication method.
         This object can not be modified when the value of
         hpnicfDot11MobGrpAuthMode is 'none'."
    ::= { hpnicfDot11MobGrpEntry 5 }

hpnicfDot11MobGrpEnable OBJECT-TYPE
    SYNTAX      TruthValue
    MAX-ACCESS  read-create
    STATUS      current
    DESCRIPTION
        "State of a mobile group.
         'true'  : The WLAN mobility group will be enabled.
         'false' : The inter-AC tunnel communication for the
                   mobility group will be disabled.
         A mobility group can be enabled only when the source
         IP address is configured.  The other objects in this entry
         can become effective only when mobility group is enabled.
         The other objects in this entry can not be modified
         after enabling mobility group."
    DEFVAL      { false }
    ::= { hpnicfDot11MobGrpEntry 6 }

hpnicfDot11MobGrpRowStatus OBJECT-TYPE
    SYNTAX      RowStatus
    MAX-ACCESS  read-create
    STATUS      current
    DESCRIPTION
        "The status of this table entry."
    ::= { hpnicfDot11MobGrpEntry 7 }

-- ==================================================================
-- hpnicfDot11MobGrpMemberTable Definition
-- ==================================================================

hpnicfDot11MobGrpMemberTable OBJECT-TYPE
    SYNTAX      SEQUENCE OF HpnicfDot11MobGrpMemberEntry
    MAX-ACCESS  not-accessible
    STATUS      current
    DESCRIPTION
        "The table defines the parameters for roaming member configuration."
    ::= { hpnicfDot11RoamCfgGroup 2 }

hpnicfDot11MobGrpMemberEntry OBJECT-TYPE
    SYNTAX      HpnicfDot11MobGrpMemberEntry
    MAX-ACCESS  not-accessible
    STATUS      current
    DESCRIPTION
        "This entry contains information of mobile group member."
    INDEX
        {
            hpnicfDot11MobGrpName,
            hpnicfDot11MobGrpMemberIpAddr
        }
    ::= { hpnicfDot11MobGrpMemberTable 1 }

HpnicfDot11MobGrpMemberEntry ::= SEQUENCE
    {
        hpnicfDot11MobGrpMemberIpAddr      InetAddress,
        hpnicfDot11MobGrpMemberStatus      HpnicfDot11RoamIACTPStatus,
        hpnicfDot11MobGrpMemberIf          OCTET STRING,
        hpnicfDot11MobGrpMemberUpTime      Integer32,
        hpnicfDot11MobGrpMemberRowStatus   RowStatus
    }

hpnicfDot11MobGrpMemberIpAddr OBJECT-TYPE
    SYNTAX      InetAddress
    MAX-ACCESS  not-accessible
    STATUS      current
    DESCRIPTION
        "Represents the IP address of group member.  It can not be
         the same as the source IP address of the mobile group.
         The address type must be the same as the hpnicfdot11MobGrpTunnelType."
    ::= { hpnicfDot11MobGrpMemberEntry 1 }

hpnicfDot11MobGrpMemberStatus OBJECT-TYPE
    SYNTAX      HpnicfDot11RoamIACTPStatus
    MAX-ACCESS  read-only
    STATUS      current
    DESCRIPTION
        "Represents the status of group member."
    ::= { hpnicfDot11MobGrpMemberEntry 2 }

hpnicfDot11MobGrpMemberIf OBJECT-TYPE
    SYNTAX      OCTET STRING
    MAX-ACCESS  read-only
    STATUS      current
    DESCRIPTION
        "Represents the tunnel interface name of group member."
    ::= { hpnicfDot11MobGrpMemberEntry 3 }

hpnicfDot11MobGrpMemberUpTime OBJECT-TYPE
    SYNTAX      Integer32
    UNITS       "second"
    MAX-ACCESS  read-only
    STATUS      current
    DESCRIPTION
        "Represents the sustaining time from tunnel up.  If tunnel
         is down, MemberUpTime is zero."
    ::= { hpnicfDot11MobGrpMemberEntry 4 }

hpnicfDot11MobGrpMemberRowStatus OBJECT-TYPE
    SYNTAX      RowStatus
    MAX-ACCESS  read-create
    STATUS      current
    DESCRIPTION
        "The status of this table entry."
    ::= { hpnicfDot11MobGrpMemberEntry 5 }

-- ==================================================================
-- hpnicfDot11RoamStatusGroup Definition
-- ==================================================================
-- ==================================================================
-- hpnicfDot11RoamInInfoTable Definition
-- ==================================================================
hpnicfDot11RoamInInfoTable OBJECT-TYPE
    SYNTAX      SEQUENCE OF HpnicfDot11RoamInInfoEntry
    MAX-ACCESS  not-accessible
    STATUS      current
    DESCRIPTION
        "The table can used to display the information of roaming in client."
    ::= { hpnicfDot11RoamStatusGroup 1 }

hpnicfDot11RoamInInfoEntry OBJECT-TYPE
    SYNTAX      HpnicfDot11RoamInInfoEntry
    MAX-ACCESS  not-accessible
    STATUS      current
    DESCRIPTION
        "This entry contains information of roaming in client."
    INDEX
        {
            hpnicfDot11RoamClientMAC
        }
    ::= { hpnicfDot11RoamInInfoTable 1 }

HpnicfDot11RoamInInfoEntry ::= SEQUENCE
    {
        hpnicfDot11RoamClientMAC         MacAddress,
        hpnicfDot11RoamInClientBSSID     MacAddress,
        hpnicfDot11RoamInClientVlanID    Integer32,
        hpnicfDot11RoamInHomeACIPType    InetAddressType,
        hpnicfDot11RoamInHomeACIPAddr    InetAddress
    }

hpnicfDot11RoamClientMAC OBJECT-TYPE
    SYNTAX      MacAddress
    MAX-ACCESS  not-accessible
    STATUS      current
    DESCRIPTION
        "Represents the MAC address of roaming in client."
    ::= { hpnicfDot11RoamInInfoEntry 1 }

hpnicfDot11RoamInClientBSSID OBJECT-TYPE
    SYNTAX      MacAddress
    MAX-ACCESS  read-only
    STATUS      current
    DESCRIPTION
        "Represents BSSID of the AP to which the Roam-In client is associated."
    ::= { hpnicfDot11RoamInInfoEntry 2 }

hpnicfDot11RoamInClientVlanID OBJECT-TYPE
    SYNTAX      Integer32
    MAX-ACCESS  read-only
    STATUS      current
    DESCRIPTION
        "Represents the VLAN ID of Roam-In client."
    ::= { hpnicfDot11RoamInInfoEntry 3 }

hpnicfDot11RoamInHomeACIPType OBJECT-TYPE
    SYNTAX      InetAddressType
    MAX-ACCESS  read-only
    STATUS      current
    DESCRIPTION
        "Represents the protocol type of home AC address."
    ::= { hpnicfDot11RoamInInfoEntry 4 }

hpnicfDot11RoamInHomeACIPAddr OBJECT-TYPE
    SYNTAX      InetAddress
    MAX-ACCESS  read-only
    STATUS      current
    DESCRIPTION
        "Represents the address of home AC."
    ::= { hpnicfDot11RoamInInfoEntry 5 }

-- ==================================================================
-- hpnicfDot11RoamOutInfoTable Definition
-- ==================================================================

hpnicfDot11RoamOutInfoTable OBJECT-TYPE
    SYNTAX      SEQUENCE OF HpnicfDot11RoamOutInfoEntry
    MAX-ACCESS  not-accessible
    STATUS      current
    DESCRIPTION
        "The table can used to display the information of roaming out client."
    ::= { hpnicfDot11RoamStatusGroup 2 }

hpnicfDot11RoamOutInfoEntry OBJECT-TYPE
    SYNTAX      HpnicfDot11RoamOutInfoEntry
    MAX-ACCESS  not-accessible
    STATUS      current
    DESCRIPTION
        "This entry contains information of roaming out client."
    INDEX
        {
            hpnicfDot11RoamClientMAC
        }
    ::= { hpnicfDot11RoamOutInfoTable 1 }

HpnicfDot11RoamOutInfoEntry ::= SEQUENCE
    {
        hpnicfDot11RoamOutClientBSSID       MacAddress,
        hpnicfDot11RoamOutClientVlanID      Integer32,
        hpnicfDot11RoamOutForeignACIPType   InetAddressType,
        hpnicfDot11RoamOutForeignACIPAddr   InetAddress,
        hpnicfDot11RoamOutClientUpTime      Integer32
    }

hpnicfDot11RoamOutClientBSSID OBJECT-TYPE
    SYNTAX      MacAddress
    MAX-ACCESS  read-only
    STATUS      current
    DESCRIPTION
        "Represents the BSSID of the AP to which the Roam-Out client is
         associated."
    ::= { hpnicfDot11RoamOutInfoEntry 1 }

hpnicfDot11RoamOutClientVlanID OBJECT-TYPE
    SYNTAX      Integer32
    MAX-ACCESS  read-only
    STATUS      current
    DESCRIPTION
        "Represents the VLAN ID of Roam-Out client."
    ::= { hpnicfDot11RoamOutInfoEntry 2 }

hpnicfDot11RoamOutForeignACIPType OBJECT-TYPE
    SYNTAX      InetAddressType
    MAX-ACCESS  read-only
    STATUS      current
    DESCRIPTION
        "Represents the protocol type of foreign AC address."
    ::= { hpnicfDot11RoamOutInfoEntry 3 }

hpnicfDot11RoamOutForeignACIPAddr OBJECT-TYPE
    SYNTAX      InetAddress
    MAX-ACCESS  read-only
    STATUS      current
    DESCRIPTION
        "Represents the address of foreign AC."
    ::= { hpnicfDot11RoamOutInfoEntry 4 }

hpnicfDot11RoamOutClientUpTime OBJECT-TYPE
    SYNTAX      Integer32
    UNITS       "second"
    MAX-ACCESS  read-only
    STATUS      current
    DESCRIPTION
        "Represents how long the Roam-Out client is associated with the foreign
         AC."
    ::= { hpnicfDot11RoamOutInfoEntry 5 }

-- ==================================================================
-- hpnicfDot11RoamTrackTable Definition
-- ==================================================================
hpnicfDot11RoamTrackTable OBJECT-TYPE
    SYNTAX      SEQUENCE OF HpnicfDot11RoamTrackEntry
    MAX-ACCESS  not-accessible
    STATUS      current
    DESCRIPTION
        "The table contains the roam-track information of a
         specified client on the client's HA."
    ::= { hpnicfDot11RoamStatusGroup 3 }

hpnicfDot11RoamTrackEntry OBJECT-TYPE
    SYNTAX      HpnicfDot11RoamTrackEntry
    MAX-ACCESS  not-accessible
    STATUS      current
    DESCRIPTION
        "This entry contains information of a specified client on the
         client's HA."
    INDEX
        {
            hpnicfDot11RoamTrackIndex
        }
    ::= { hpnicfDot11RoamTrackTable 1 }

HpnicfDot11RoamTrackEntry ::= SEQUENCE
    {
        hpnicfDot11RoamTrackIndex        Integer32,
        hpnicfDot11RoamTrackClientMAC    MacAddress,
        hpnicfDot11RoamTrackBSSID        MacAddress,
        hpnicfDot11RoamTrackUpTime       Integer32,
        hpnicfDot11RoamTrackACIPType     InetAddressType,
        hpnicfDot11RoamTrackACIPAddr     InetAddress
    }

hpnicfDot11RoamTrackIndex OBJECT-TYPE
    SYNTAX      Integer32
    MAX-ACCESS  not-accessible
    STATUS      current
    DESCRIPTION
        "Represents the index of this entry."
    ::= { hpnicfDot11RoamTrackEntry 1 }

hpnicfDot11RoamTrackClientMAC OBJECT-TYPE
    SYNTAX      MacAddress
    MAX-ACCESS  read-only
    STATUS      current
    DESCRIPTION
        "Represents the MAC address of the roamed client."
    ::= { hpnicfDot11RoamTrackEntry 2 }

hpnicfDot11RoamTrackBSSID OBJECT-TYPE
    SYNTAX      MacAddress
    MAX-ACCESS  read-only
    STATUS      current
    DESCRIPTION
        "Represents the BSSID of the AP with which the client is associated."
    ::= { hpnicfDot11RoamTrackEntry 3 }

hpnicfDot11RoamTrackUpTime OBJECT-TYPE
    SYNTAX      Integer32
    UNITS       "second"
    MAX-ACCESS  read-only
    STATUS      current
    DESCRIPTION
        "Represents how long the client is associated with the BSSID."
    ::= { hpnicfDot11RoamTrackEntry 4 }

hpnicfDot11RoamTrackACIPType OBJECT-TYPE
    SYNTAX      InetAddressType
    MAX-ACCESS  read-only
    STATUS      current
    DESCRIPTION
        "Represents the protocol type of the IP address of the access
         controller with which the client is connected."
    ::= { hpnicfDot11RoamTrackEntry 5 }

hpnicfDot11RoamTrackACIPAddr OBJECT-TYPE
    SYNTAX      InetAddress
    MAX-ACCESS  read-only
    STATUS      current
    DESCRIPTION
        "Represents the IP address of the access controller with which
         the client is connected."
    ::= { hpnicfDot11RoamTrackEntry 6 }

-- ==================================================================
-- hpnicfDot11RoamStatisGroup Definition
-- ==================================================================
hpnicfDot11IntraACRoamingSuccCnt OBJECT-TYPE
    SYNTAX      Integer32
    MAX-ACCESS  read-only
    STATUS      current
    DESCRIPTION
        "Represents the count of client successfully roam Intra-AC."
    ::= { hpnicfDot11RoamStatisGroup 1 }

hpnicfDot11InterACRoamingSuccCnt OBJECT-TYPE
    SYNTAX      Integer32
    MAX-ACCESS  read-only
    STATUS      current
    DESCRIPTION
        "Represents the count of client successfully roam in Inter-AC."
    ::= { hpnicfDot11RoamStatisGroup 2 }

hpnicfDot11InterACRoamOutSuccCnt OBJECT-TYPE
    SYNTAX      Integer32
    MAX-ACCESS  read-only
    STATUS      current
    DESCRIPTION
        "Represents the count of client successfully roam out Inter-AC."
    ::= { hpnicfDot11RoamStatisGroup 3 }

-- ==================================================================
-- End of hpnicfDot11RoamStatisGroup Definition
-- ==================================================================

-- ==================================================================
-- hpnicfDot11RoamStatis2Group Definition
-- ==================================================================
hpnicfDot11IntraACRoamingSuccCnt2 OBJECT-TYPE
    SYNTAX      Counter32
    MAX-ACCESS  read-only
    STATUS      current
    DESCRIPTION
        "Represents the count of client successfully roam Intra-AC in Counter32."
    ::= { hpnicfDot11RoamStatis2Group 1 }

hpnicfDot11InterACRoamingSuccCnt2 OBJECT-TYPE
    SYNTAX      Counter32
    MAX-ACCESS  read-only
    STATUS      current
    DESCRIPTION
        "Represents the count of client successfully roam in Inter-AC in Counter32."
    ::= { hpnicfDot11RoamStatis2Group 2 }

hpnicfDot11InterACRoamOutSuccCnt2 OBJECT-TYPE
    SYNTAX      Counter32
    MAX-ACCESS  read-only
    STATUS      current
    DESCRIPTION
        "Represents the count of client successfully roam out Inter-AC in Counter32."
    ::= { hpnicfDot11RoamStatis2Group 3 }

-- ==================================================================
-- End of hpnicfDot11RoamStatis2Group Definition
-- ==================================================================
END
