HP-ICF-POE-MIB DEFINITIONS ::= BEGIN

IMPORTS
    MODULE-IDENTITY, OBJECT-TYPE, Integer32 
            FROM SNMPv2-SMI
        TruthValue
            FROM SNMPv2-TC
        MODULE-COMPLIANCE, OBJECT-GROUP
            FROM SNMPv2-CONF
        hpicfCommon 
            FROM HP-ICF-OID
        pethPsePortEntry
            FROM POWER-ETHERNET-MIB
	entPhysicalIndex
	    FROM ENTITY-MIB;

hpicfPoe MODULE-IDENTITY
   LAST-UPDATED "201005261036Z"  -- May 26, 2010
   ORGANIZATION "HP Networking"
   CONTACT-INFO " Hewlett Packard Company
                  8000 Foothills Blvd.
                  Roseville, CA 95747"
   DESCRIPTION
          "This MIB module describes management objects
           used to manage Power Source Equipment (PSE)."
   
   REVISION     "201005261036Z"  -- May 26, 2010
   DESCRIPTION  "Add table for PSE features, and deprecate scalar globals."

   REVISION     "200911180000Z" --November 18,  2009
   DESCRIPTION  "Add objects to support POE power parameters"

   REVISION     "200702010000Z"  -- February 01, 2007
   DESCRIPTION  "Add objects to support POE allocation."                    

   REVISION     "200506060000Z"  -- June 06, 2005
   DESCRIPTION  "Add objects to support POE global characteristics."                    

   REVISION     "200407070000Z"  -- July 07, 2004
   DESCRIPTION  "Original creation of mib module."  

::= { hpicfPOE 1 }

hpicfPOE        OBJECT IDENTIFIER ::= { hpicfCommon 9 } 

-- ------------------------------------------------------------
-- PSE Objects extension 
-- (AUGMENTS pethPsePortTable )
-- ------------------------------------------------------------
hpicfPoePethPsePortTable OBJECT-TYPE
     SYNTAX      SEQUENCE OF HpicfPoePethPsePortEntry
     MAX-ACCESS  not-accessible
     STATUS      current
     DESCRIPTION "This table supplements the table 'pethPsePortTable'
                  in ieee802af.mib."
::= { hpicfPoe 1 }

hpicfPoePethPsePortEntry OBJECT-TYPE
     SYNTAX      HpicfPoePethPsePortEntry 
     MAX-ACCESS  not-accessible
     STATUS      current
     DESCRIPTION "The fields in these entries will be used to supplement
                  fields in 'pethPsePortEntry in ieee802af.mib."
     AUGMENTS { pethPsePortEntry }
::= { hpicfPoePethPsePortTable 1 }


HpicfPoePethPsePortEntry ::=
     SEQUENCE {
         hpicfPoePethPsePortCurrent                Integer32,
         hpicfPoePethPsePortVoltage                Integer32,
         hpicfPoePethPsePortPower                  Integer32,
         hpicfPoePethPsePortPowerAllocateBy        INTEGER,
         hpicfPoePethPsePortPowerValue             Integer32,
         hpicfPoePethPsePortLLDPDetect             INTEGER,
         hpicfPoePethPsePortPoePlusPowerValue      Integer32,
         hpicfPoePethPsePortActualPower            Integer32
     }

hpicfPoePethPsePortCurrent OBJECT-TYPE
     SYNTAX      Integer32 (0..65535)
     MAX-ACCESS  read-only
     STATUS      current
     DESCRIPTION "This field specifies the current supplied at this port.
                  This value is specified in milli amperes(mA)."
     DEFVAL     { 0 }
::= { hpicfPoePethPsePortEntry 1 }

hpicfPoePethPsePortVoltage OBJECT-TYPE
     SYNTAX      Integer32 (0..65535)
     MAX-ACCESS  read-only
     STATUS      current
     DESCRIPTION "This field specifies the Voltage supplied at this port.
                  This value is specified in 10's of volts (dV)"
     DEFVAL     { 0 }
::= { hpicfPoePethPsePortEntry 2 }

hpicfPoePethPsePortPower OBJECT-TYPE
     SYNTAX      Integer32 (0..65535)
     MAX-ACCESS  read-only
     STATUS      current
     DESCRIPTION "This field specifies the Power supplied at this port.
                  This value is specified in milliwatts (mW)."
     DEFVAL     { 0 } 
::= { hpicfPoePethPsePortEntry 3 }

hpicfPoePethPsePortPowerAllocateBy OBJECT-TYPE
     SYNTAX      INTEGER {
                 usage(1),
                 class(2),
                 value(3)
     }
     MAX-ACCESS  read-write
     STATUS      current
     DESCRIPTION "This field specifies the power allocation method for this port.
                  The default value is usage."
     DEFVAL     { 1 } 
::= { hpicfPoePethPsePortEntry 4 }

hpicfPoePethPsePortPowerValue OBJECT-TYPE
     SYNTAX      Integer32 (0..17)
     MAX-ACCESS  read-write
     STATUS      current
     DESCRIPTION "This field specifies the power allocation defined for this port.
                  This value is specified in Watts (W)."
     DEFVAL     { 17 } 
::= { hpicfPoePethPsePortEntry 5 }

hpicfPoePethPsePortLLDPDetect OBJECT-TYPE
     SYNTAX      INTEGER {
                        disabled(1),
                        enabled(2)
                 }
     MAX-ACCESS  read-write
     STATUS      current
     DESCRIPTION "This field specifies if power should be allocated using
                  LLDP advertised information regarding the PD." 
     DEFVAL     { 1 } 
::= { hpicfPoePethPsePortEntry 6 }

hpicfPoePethPsePortPoePlusPowerValue OBJECT-TYPE
     SYNTAX      Integer32 (0..255)
     MAX-ACCESS  read-write
     STATUS      current
     DESCRIPTION "This field specifies the power allocation defined for this port.
                  Use this object for equipment supporting high power, that is greater
                  than 15 Watts. This value is specified in Watts (W). 
                  Maximum supported is 33W"
     DEFVAL     { 17 } 
::= { hpicfPoePethPsePortEntry 7 }

hpicfPoePethPsePortActualPower OBJECT-TYPE
     SYNTAX      Integer32
     UNITS       "milli-watts"
     MAX-ACCESS  read-only
     STATUS      current
     DESCRIPTION "This field specifies the actual power drained by the device
                  connected to this port."
     DEFVAL     { 0 } 
::= { hpicfPoePethPsePortEntry 8 }

-- ------------------------------------------------------------
-- Power Over Ethernet (POE) Global information - applies to
-- the entire chassis. These global values have been
-- deprecated. In a stack, they will provide information
-- pertinent only to the stack commander switch.
-- ------------------------------------------------------------

hpicfPoeAllowPreStdDetect   OBJECT-TYPE
        SYNTAX      TruthValue
        MAX-ACCESS  read-write
        STATUS      deprecated
        DESCRIPTION "This object is used to configure the default
                     POE power detection mode.
                     A value of TRUE - indicates that power 
                     pre-802.3af-standard devices.
                     A value of FALSE - indicates that only 
                     pre-802.3af compliant devices are allowed.
                     The default value is true. In a stack, this
                     value pertains only to the commander switch."
        ::= { hpicfPoe 3 }

hpicfPoePowerRedundancy   OBJECT-TYPE
        SYNTAX INTEGER   {
                  none(1),
                  nPlus1(2),
                  full(3)
        }     
        MAX-ACCESS  read-write
        STATUS      deprecated
        DESCRIPTION "This object is used to configure the
                     POE power redundancy mode.
                     A value of none(1) - means that all available power
                     can be allocated to powered devices.
                     A value of nPlus1(2) - means that one of the highest
                     power supplies is held in reserve and that in
                     the event of a single power supply failure, no 
                     no powered devices will be shut down.
                     A value of full(3) - means that half of the available
                     power supplies are held in reserve.
                     The default value is none(1). In a stack, this
                     value pertains only to the commander switch."
        ::= { hpicfPoe 4 }

hpicfPoeExtPwrSupplyCount  OBJECT-TYPE
        SYNTAX Integer32 (1..2147483647)
        MAX-ACCESS  read-write
        STATUS      deprecated
        DESCRIPTION "This object is used to configure the number
                     of external power supplies expected to
                     be connected to the chassis.
                     The default value is 1. In a stack, this
                     value pertains only to the commander switch."
        ::= { hpicfPoe 5 }

-- ------------------------------------------------------------
-- Power Over Ethernet (POE) per-PSE information - applies
-- to each power-source equipment (PSE). 
-- ------------------------------------------------------------

   hpicfPseFeaturesTable OBJECT-TYPE
      SYNTAX       SEQUENCE OF HpicfPseFeaturesEntry
      MAX-ACCESS   not-accessible
      STATUS       current
      DESCRIPTION  "This table describes the features of each power source
                   equipment (PSE). On standalone switches (both stackable
                   and chassis switches) there shall be only one entry in
                   this table. In a stack, there shall be one entry for
                   each stack member."
   ::= { hpicfPoe 6 }

   hpicfPseFeaturesEntry OBJECT-TYPE
      SYNTAX       HpicfPseFeaturesEntry
      MAX-ACCESS   not-accessible
      STATUS       current
      DESCRIPTION  "A row in the PSE features table, signifying a single
                    power source equipment."
      INDEX        {entPhysicalIndex}
      ::= { hpicfPseFeaturesTable 1 }

   HpicfPseFeaturesEntry ::=
      SEQUENCE {
         hpicfPseAllowPreStdDetect   TruthValue,
         hpicfPsePowerRedundancy     INTEGER,
         hpicfPseExtPwrSupplyCount   Integer32,
         hpicfPseAvailablePower      Integer32,
         hpicfPseUsedPower           Integer32,
         hpicfPseFailoverPower       Integer32,
         hpicfPseRedundantPower      Integer32
      }

   hpicfPseAllowPreStdDetect   OBJECT-TYPE
      SYNTAX      TruthValue
      MAX-ACCESS  read-write
      STATUS      current
      DESCRIPTION "This object is used to configure the default POE power
                  detection mode for this power source equipment.
                  A value of TRUE - indicates that power
                  pre-802.3af-standard devices.  A value of FALSE -
                  indicates that only pre-802.3af compliant devices are
                  allowed.  The default value is true."
      ::= { hpicfPseFeaturesEntry 1 }

   hpicfPsePowerRedundancy   OBJECT-TYPE
      SYNTAX      INTEGER   {
                     none(1),
                     nPlus1(2),
                     full(3)
                  }
      MAX-ACCESS  read-write
      STATUS      current
      DESCRIPTION "This object is used to configure the POE power redundancy
                  mode for this power source equipment.
                  A value of none(1) - means that all available power can be
                  allocated to powered devices.
                  A value of nPlus1(2) - means that one of the highest power
                  supplies is held in reserve and that in the event of a
                  single power supply failure, no powered devices will be
                  shut down.
                  A value of full(3) - means that half of the available power
                  supplies are held in reserve.
                  The default value is none(1)."
      ::= { hpicfPseFeaturesEntry 2 }

   hpicfPseExtPwrSupplyCount  OBJECT-TYPE
      SYNTAX      Integer32 (1..2147483647)
      MAX-ACCESS  read-write
      STATUS      current
      DESCRIPTION "This object is used to configure the number of external
                  power supplies expected to be connected to the Power Source
                  Equipment.  The default value is 1."
      ::= { hpicfPseFeaturesEntry 3 }

   hpicfPseAvailablePower  OBJECT-TYPE
      SYNTAX      Integer32 (0..2147483647)
      UNITS       "Watts"
      MAX-ACCESS  read-only
      STATUS      current
      DESCRIPTION "This field specifies the total power available on this
                  Power source equipment. This includes internal and external
                  power supplies."
      ::= { hpicfPseFeaturesEntry 4 }

   hpicfPseUsedPower        OBJECT-TYPE
      SYNTAX      Integer32 (0..2147483647)
      UNITS       "Watts"
      MAX-ACCESS  read-only
      STATUS      current
      DESCRIPTION "This field specifies the total power allocated on the
                  Power Source Equipment. This is the sum of the power
                  allocated to all the ports on the PSE."
      ::= { hpicfPseFeaturesEntry 5 }

   hpicfPseFailoverPower   OBJECT-TYPE
      SYNTAX      Integer32 (0..2147483647)
      UNITS       "Watts"
      MAX-ACCESS  read-only
      STATUS      current
      DESCRIPTION "This field specifies the failover power for this
                  Power Source Equipment."
      ::= { hpicfPseFeaturesEntry 6 }

   hpicfPseRedundantPower  OBJECT-TYPE
      SYNTAX      Integer32 (0..2147483647)
      UNITS       "Watts"
      MAX-ACCESS  read-only
      STATUS      current
      DESCRIPTION "This field specifies the redundancy POE power available
                  to the Power Source Equipment."
      ::= { hpicfPseFeaturesEntry 7 }


-- ------------------------------------------------------------
-- Power Over Ethernet (POE) power supply information - applies
-- to each power supply.
-- ------------------------------------------------------------

   hpicfPoePowerSupplyTable        OBJECT-TYPE
      SYNTAX      SEQUENCE OF HpicfPoePowerSupplyEntry
      MAX-ACCESS  not-accessible
      STATUS      current
      DESCRIPTION "This table contains one row per power supply available 
                  to the switch."
      ::={hpicfPoe 7}

   hpicfPoePowerSupplyEntry        OBJECT-TYPE
      SYNTAX      HpicfPoePowerSupplyEntry
      MAX-ACCESS  not-accessible
      STATUS      current
      DESCRIPTION "Information about a particular power supply. Each entry 
                  provides information about power supply whether it is 
                  external or internal, if it is poe/poePlus and the 
                  capacity of the power supply."
      INDEX       {entPhysicalIndex}
      ::={hpicfPoePowerSupplyTable 1}

   HpicfPoePowerSupplyEntry::=
      SEQUENCE{
         hpicfPoePowerSupplySourceType        INTEGER,
         hpicfPoePowerSupplyType              INTEGER,
         hpicfPoePowerSupplyCapacity          Integer32
      }

   hpicfPoePowerSupplySourceType        OBJECT-TYPE
      SYNTAX      INTEGER{
                     internal(1),
                     external(2)
                  }
      MAX-ACCESS  read-only
      STATUS      current
      DESCRIPTION "This field specifies whether the power supply is external
                  or internal. Stackable switch has inbuilt power supply and
                  can have upto 1 external power supply.  Chassis switch can
                  have upto 2 internal power supplies for 6 slot and upto 4
                  for 12 slot. Chassis switch can have upto 2 external power
                  supplies."
      ::={hpicfPoePowerSupplyEntry 1}

   hpicfPoePowerSupplyType OBJECT-TYPE
      SYNTAX      INTEGER{
                     poe(1),
                     poePlus(2),
                     notPresent(3),
                     fault(4)
                  }        
      MAX-ACCESS  read-only
      STATUS      current
      DESCRIPTION "This field specifies the type of the power supply,
                  poe or poePlus."
      ::={hpicfPoePowerSupplyEntry 2}

   hpicfPoePowerSupplyCapacity     OBJECT-TYPE
      SYNTAX      Integer32 (0..2147483647)
      UNITS       "Watts"
      MAX-ACCESS  read-only
      STATUS      current
      DESCRIPTION "This field specifies the capacity of the power supply."
      ::={hpicfPoePowerSupplyEntry 3}

-- ------------------------------------------------------------
-- Conformance information
-- ------------------------------------------------------------

hpicfPoeConformance OBJECT IDENTIFIER ::= { hpicfPoe  2 }

hpicfPoeCompliances OBJECT IDENTIFIER ::= { hpicfPoeConformance 1 }
hpicfPoeGroups      OBJECT IDENTIFIER ::= { hpicfPoeConformance 2 }

-- ------------------------------------------------------------
-- compliance statements
-- ------------------------------------------------------------

hpicfPoeCompliance MODULE-COMPLIANCE
        STATUS      deprecated
        DESCRIPTION "
                A compliance statement for HP Routing switches with PoE 
                capability"
        MODULE
        MANDATORY-GROUPS {  hpicfPoePethPsePortTableGroup }

        GROUP       hpicfPoePethPsePortTableGroup
        DESCRIPTION "A Collection of Object(s) that display
                     the current poe port status information."
                
        ::= { hpicfPoeCompliances 1 }

hpicfPoeCompliance1 MODULE-COMPLIANCE
        STATUS      deprecated
        DESCRIPTION "
                A compliance statement for HP Routing switches with PoE 
                capability"
        MODULE
        MANDATORY-GROUPS {  hpicfPoePethPsePortTableGroup,
                            hpicfPoeGlobalGroup }

        GROUP       hpicfPoePethPsePortTableGroup
        DESCRIPTION "A Collection of Object(s) that display
                     the current poe port status information."
                     
        GROUP       hpicfPoeGlobalGroup
        DESCRIPTION "A Collection of Object(s) that control
                     the global (entire chassis) poe 
                     configuration."

        ::= { hpicfPoeCompliances 2 }

hpicfPoeCompliance2 MODULE-COMPLIANCE
        STATUS      current
        DESCRIPTION "
                A compliance statement for HP Routing switches with PoE
                capability"
        MODULE
        MANDATORY-GROUPS {  hpicfPoePethPsePortTableGroup,
                            hpicfPseFeaturesGroup,
                            hpicfPoePowerSupplyGroup
                         }

        GROUP       hpicfPoePethPsePortTableGroup
        DESCRIPTION "A Collection of Object(s) that display
                     the current poe port status information."

        GROUP       hpicfPseFeaturesGroup
        DESCRIPTION "A Collection of Object(s) that provide information
                     about each power source equipment instance."

        GROUP       hpicfPoePowerSupplyGroup
        DESCRIPTION "A collection of Object(s) related to power supplies."


        ::= { hpicfPoeCompliances 3 }

hpicfPoePethPsePortTableGroup OBJECT-GROUP
        OBJECTS     { 
                      hpicfPoePethPsePortCurrent,
                      hpicfPoePethPsePortVoltage,
                      hpicfPoePethPsePortPower, 
                      hpicfPoePethPsePortPowerAllocateBy,
                      hpicfPoePethPsePortPowerValue,
                      hpicfPoePethPsePortLLDPDetect,
                      hpicfPoePethPsePortPoePlusPowerValue,
                      hpicfPoePethPsePortActualPower
                    }
        STATUS      current
        DESCRIPTION "A collection of objects allowing configuration of
                    PoE PSE Port table"
        ::= { hpicfPoeGroups 1 }


hpicfPoeGlobalGroup OBJECT-GROUP
        OBJECTS     { 
                      hpicfPoeAllowPreStdDetect,
                      hpicfPoePowerRedundancy,
                      hpicfPoeExtPwrSupplyCount}
        STATUS      deprecated
        DESCRIPTION "A collection of objects related to the global
                     configuration of POE on a given chassis."
        ::= { hpicfPoeGroups 2 }

hpicfPseFeaturesGroup OBJECT-GROUP
        OBJECTS     { 
                      hpicfPseAllowPreStdDetect,
                      hpicfPsePowerRedundancy,
                      hpicfPseExtPwrSupplyCount,
                      hpicfPseAvailablePower,
                      hpicfPseUsedPower,
                      hpicfPseFailoverPower,
                      hpicfPseRedundantPower
                    }
        STATUS      current
        DESCRIPTION "A Collection of Object(s) that provide information
                     about each power source equipment instance."
        ::= { hpicfPoeGroups 3 }

hpicfPoePowerSupplyGroup OBJECT-GROUP
        OBJECTS         {
                        hpicfPoePowerSupplySourceType,
                        hpicfPoePowerSupplyType,
                        hpicfPoePowerSupplyCapacity}
        STATUS          current
        DESCRIPTION     " A collection of objects related to Power Supply. "
        ::= { hpicfPoeGroups 4 }

END
