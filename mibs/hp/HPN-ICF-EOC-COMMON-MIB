-- =================================================================
-- Copyright (c) 2010-2014 Hewlett-Packard Development Company, L.P.
--
-- Description:
-- Reference:
-- Version: V1.7
-- History:
-- V1.0 created by liujingya.
--     Initial version of the MIB
-- V1.1 2008-1-29 Adjusted the structure of some tables and the value of
--     some objects by liujingya.
-- V1.2 2008-5-19 Added hpnicfEOCComUniAdminStatus, hpnicfEOCComCnuSoftwareVersion,
--     modified description of hpnicfEOCComUniUpLineRate and
--     hpnicfEOCComUniDownLineRate by liujingya.
-- V1.3 2008-7-30 updated by xujun
--     add hpnicfEOCComCnuRateDropThr, hpnicfEOCComCnuTxRate, hpnicfEOCComCnuRxRate,
--     hpnicfEOCComCnuTxRateDrop, hpnicfEOCComCnuRxRateDrop, hpnicfEOCCnuTxRateDropTrap,
--     hpnicfEOCCnuTxRateDropRecoverTrap, hpnicfEOCCnuRxRateDropTrap and
--     hpnicfEOCCnuRxRateDropRecoverTrap by xujun
-- V1.4 2009-2-13 Added hpnicfEOCCnuFWDownLoadErrTrap,
--     hpnicfEOCCnuFWDownLoadErrReTrap, hpnicfEOCCnuDeviceTypeErrTrap,
--     hpnicfEOCCnuDeviceTypeErrReTrap, hpnicfEOCCnuAutoUpdateErrTrap,
--     hpnicfEOCCnuAutoUpdateSuccTrap and
--     modified MAX-ACCESS of hpnicfEOCComCnuDeviceType by liujingya.
-- V1.5 2010-1-7 Added hpnicfEocComCnuTypeIdx, hpnicfEOCComCnuDescripton,
--     hpnicfEOCComCltMaxAllowToAccess, hpnicfEocComCnuNumber by xujun
-- V1.6 2011-12-28 updated by gaoguangping
--     Added hpnicfEOCLoopbackDetectTrap, hpnicfEOCLoopbackRecoverTrap;
--     Modified hpnicfEOCComCnuLinkState.
-- V1.7 2013-08-20 Added hpnicfEOCComCnuTempIndex by xujun
-- =================================================================
HPN-ICF-EOC-COMMON-MIB DEFINITIONS ::= BEGIN

IMPORTS
        hpnicfCommon
    FROM HPN-ICF-OID-MIB
        ifIndex, ifDescr
    FROM IF-MIB
        Integer32, Unsigned32, TimeTicks, OBJECT-TYPE, MODULE-IDENTITY,
        NOTIFICATION-TYPE, Gauge32
    FROM SNMPv2-SMI
        IANAifType
    FROM IANAifType-MIB
        MacAddress, RowStatus, DisplayString, TruthValue
    FROM SNMPv2-TC
        hpnicfHPEOCDownLoadCNUFWResult
    FROM HPN-ICF-HPEOC-MIB;


hpnicfEOCCommon MODULE-IDENTITY
    LAST-UPDATED "200709111008Z"
    ORGANIZATION
        ""
    CONTACT-INFO
        ""
    DESCRIPTION
        "
        The objects in this MIB module are used to manage and
        display common configuration between Ethernet Passive
        Optical Network (EOC) port which are based on the Ethernet
        in the First Mile (EFM) Passive Optical Network(PON) as
        defined in IEEE Draft P802.3ah/D3.0 clause 60, 64, 65..
        and Ethernet Over Cable (EOC) which is based on HomePlug
        AV Specification.
        "
    ::= { hpnicfCommon 83 }

--
-- hpnicfEOCCommonSysMan
--
hpnicfEOCCommonSysMan OBJECT IDENTIFIER ::= { hpnicfEOCCommon 1 }

hpnicfEOCCommonSysScalarObjects OBJECT IDENTIFIER ::= { hpnicfEOCCommonSysMan 1 }

hpnicfEOCCommonSysVersion OBJECT-TYPE
    SYNTAX     OCTET STRING
    MAX-ACCESS read-only
    STATUS     current
    DESCRIPTION
        "
        Eoc version.  If the object length is
        zero, it means the version is unknown.
        The length is up to 1024.
        "
    ::= { hpnicfEOCCommonSysScalarObjects 1 }

hpnicfEOCCommonUpLinkMacAddress OBJECT-TYPE
    SYNTAX     MacAddress
    MAX-ACCESS read-only
    STATUS     current
    DESCRIPTION
        "
        EOC CLT's uplink device's mac address.
        "
    ::= { hpnicfEOCCommonSysScalarObjects 2 }


--
-- hpnicfEOCCommonCltMan
--
hpnicfEOCCommonCltMan OBJECT IDENTIFIER ::= { hpnicfEOCCommon 2 }

--
-- hpnicfEOCCommonCltManTable
--
hpnicfEOCCommonCltManTable OBJECT-TYPE
    SYNTAX     SEQUENCE OF HpnicfEOCCommonCltManEntry
    MAX-ACCESS not-accessible
    STATUS     current
    DESCRIPTION
        "
        This table defines the primary parameters of the
        CLT configuration.
        "
    ::= { hpnicfEOCCommonCltMan 1 }

hpnicfEOCCommonCltManEntry OBJECT-TYPE
    SYNTAX     HpnicfEOCCommonCltManEntry
    MAX-ACCESS not-accessible
    STATUS     current
    DESCRIPTION
        "
        The entry of the table hpnicfEOCCommonCltManTable.
        "
    INDEX
        {
            ifIndex
        }
    ::= { hpnicfEOCCommonCltManTable 1 }

HpnicfEOCCommonCltManEntry ::= SEQUENCE
    {
        hpnicfEOCCommonCltAutoAuthorize    TruthValue,
        hpnicfEOCCommonCltMaxAllowToAccess Integer32
    }

hpnicfEOCCommonCltAutoAuthorize OBJECT-TYPE
    SYNTAX     TruthValue
    MAX-ACCESS read-write
    STATUS     current
    DESCRIPTION
        "
        This value determines whether software performs
        self-authorization for each Cable Network Unit(CNU)
        registering to the network.  Setting it to false
        means for every CNU registering, software requires
        external authorization, and until it's done the
        CNU is not authenticated.  True value means software
        authorizes each CNU registering to the network
        automatically.
        "
    DEFVAL
        {
            false
        }
    ::= { hpnicfEOCCommonCltManEntry 1 }

hpnicfEOCCommonCltMaxAllowToAccess OBJECT-TYPE
    SYNTAX     Integer32
    MAX-ACCESS read-write
    STATUS     current
    DESCRIPTION
         "
         This value determines how many CNU can be bound
         in this CLT. If the number of CNU is more than this
         value , then the rest of CNU should not be allow to
         access.
         "
    DEFVAL
        {
            253
        }
    ::= { hpnicfEOCCommonCltManEntry 2 }

--
-- hpnicfEOCComCnuMan
--

hpnicfEOCComCnuMan OBJECT IDENTIFIER ::= { hpnicfEOCCommon 3 }

hpnicfEOCComCnuScalarObjects OBJECT IDENTIFIER ::= { hpnicfEOCComCnuMan 1 }

hpnicfEOCComCnuMaxDownBWMinVal OBJECT-TYPE
    SYNTAX     Integer32
    MAX-ACCESS read-only
    STATUS     current
    DESCRIPTION
        "
        The lower limit of total-bandwidth which is confined to
        hpnicfEOCComCnuMaxDownBW."
    ::= { hpnicfEOCComCnuScalarObjects 1 }

hpnicfEOCComCnuMaxDownBWMaxVal OBJECT-TYPE
    SYNTAX     Integer32
    MAX-ACCESS read-only
    STATUS     current
    DESCRIPTION
        "
        The upper limit of total-bandwidth which is confined to
        hpnicfEOCComCnuMaxDownBW."
    ::= { hpnicfEOCComCnuScalarObjects 2 }

hpnicfEOCComCnuSlaHighPriBWMinVal OBJECT-TYPE
    SYNTAX     Integer32
    MAX-ACCESS read-only
    STATUS     current
    DESCRIPTION
        "
        The lower limit of high priority bandwidth which is confined to
        hpnicfEOCComCnuSlaHighPriBW."
    ::= { hpnicfEOCComCnuScalarObjects 3 }

hpnicfEOCComCnuSlaHighPriBWMaxVal OBJECT-TYPE
    SYNTAX     Integer32
    MAX-ACCESS read-only
    STATUS     current
    DESCRIPTION
        "
        The upper limit of high priority bandwidth which is confined to
        hpnicfEOCComCnuSlaHighPriBW."
    ::= { hpnicfEOCComCnuScalarObjects 4 }

hpnicfEOCComCnuMaxUpBWMinVal OBJECT-TYPE
    SYNTAX     Integer32
    MAX-ACCESS read-only
    STATUS     current
    DESCRIPTION
        "
        The lower limit of total-bandwidth which is confined to
        hpnicfEOCComCnuMaxUpBW."
    ::= { hpnicfEOCComCnuScalarObjects 5 }

hpnicfEOCComCnuMaxUpBWMaxVal OBJECT-TYPE
    SYNTAX     Integer32
    MAX-ACCESS read-only
    STATUS     current
    DESCRIPTION
        "
        The upper limit of total-bandwidth which is confined to
        hpnicfEOCComCnuMaxUpBW."
    ::= { hpnicfEOCComCnuScalarObjects 6 }

hpnicfEOCComCnuAttenThrA OBJECT-TYPE
    SYNTAX     Integer32
    MAX-ACCESS read-write
    STATUS     current
    DESCRIPTION
        "
        The value of cnu's average attenuation good level thresholds.
        "
    ::= { hpnicfEOCComCnuScalarObjects 7 }

hpnicfEOCComCnuAttenThrB OBJECT-TYPE
    SYNTAX     Integer32
    MAX-ACCESS read-write
    STATUS     current
    DESCRIPTION
        "
        The value of cnu's average attenuation normal level thresholds.
        "
    ::= { hpnicfEOCComCnuScalarObjects 8 }

hpnicfEOCComCnuRateDropThr OBJECT-TYPE
    SYNTAX     Integer32
    MAX-ACCESS read-write
    STATUS     current
    DESCRIPTION
        "
        The value of cnu's Tx/Rx rate drop thresholds.
        "
    ::= { hpnicfEOCComCnuScalarObjects 9 }

--
-- hpnicfEOCComCnuSysManTable
--

hpnicfEOCComCnuSysManTable OBJECT-TYPE
    SYNTAX     SEQUENCE OF HpnicfEOCComCnuSysManEntry
    MAX-ACCESS not-accessible
    STATUS     current
    DESCRIPTION
        "
        This table implements the management of CNUs(Coax Network Unit).
        "
    ::= { hpnicfEOCComCnuMan 2 }

hpnicfEOCComCnuSysManEntry OBJECT-TYPE
    SYNTAX     HpnicfEOCComCnuSysManEntry
    MAX-ACCESS not-accessible
    STATUS     current
    DESCRIPTION
        "
        The entry of the table hpnicfEOCComCnuSysManTable.
        "
    INDEX
        {
            ifIndex
        }
    ::= { hpnicfEOCComCnuSysManTable 1 }

HpnicfEOCComCnuSysManEntry ::= SEQUENCE
    {
        hpnicfEOCComCnuCableIfindex    Integer32,
        hpnicfEOCComCnuDeviceType      DisplayString,
        hpnicfEOCComCnuDeviceAlias     DisplayString,
        hpnicfEOCComCnuDescr           DisplayString,
        hpnicfEOCComCnuUpTime          TimeTicks,
        hpnicfEOCComCnuVLANType        INTEGER,
        hpnicfEOCComCnuPvid            Integer32,
        hpnicfEOCComCnuVlanTag         INTEGER,
        hpnicfEOCComCnuReset           INTEGER,
        hpnicfEOCComCnuDeregister      INTEGER,
        hpnicfEOCComCnuSave            INTEGER,
        hpnicfEOCComCnuAccess          INTEGER
    }

hpnicfEOCComCnuCableIfindex OBJECT-TYPE
    SYNTAX     Integer32
    MAX-ACCESS read-only
    STATUS     current
    DESCRIPTION
        "
        The index of cable port which uniquely identifies the cable
        port of one device.
        "
    ::= { hpnicfEOCComCnuSysManEntry 1 }

hpnicfEOCComCnuDeviceType OBJECT-TYPE
    SYNTAX     DisplayString
    MAX-ACCESS read-write
    STATUS     current
    DESCRIPTION
        "
        The type of the EOC CNU(Coax Network Unit).
        "
    ::= { hpnicfEOCComCnuSysManEntry 2 }

hpnicfEOCComCnuDeviceAlias OBJECT-TYPE
    SYNTAX DisplayString
    MAX-ACCESS read-write
    STATUS current
    DESCRIPTION
        "
        EOC CNU's alias which display as the device's name,
        it's recommended to set it uniquely and understandably.
        "
    ::= { hpnicfEOCComCnuSysManEntry 3 }

hpnicfEOCComCnuDescr OBJECT-TYPE
    SYNTAX     DisplayString
    MAX-ACCESS read-write
    STATUS     current
    DESCRIPTION
        "
        User's description, including user's address,
        name, telephone number and so on.
        "
    ::= { hpnicfEOCComCnuSysManEntry 4 }

hpnicfEOCComCnuUpTime OBJECT-TYPE
    SYNTAX     TimeTicks
    MAX-ACCESS read-only
    STATUS     current
    DESCRIPTION
        "
        The time since the CNU last registered to the network.
        "
    ::= { hpnicfEOCComCnuSysManEntry 5 }

hpnicfEOCComCnuVLANType OBJECT-TYPE
    SYNTAX     INTEGER
        {
            vLANTrunk(1),
            access(2),
            hybrid(3),
            fabric(4)
        }
    MAX-ACCESS read-write
    STATUS     current
    DESCRIPTION
        "port vlan types.
        hybrid (3) port can carry multiple VLANs.
        If fabric function is supported, fabric(4) means the port is
        a fabric port."
    ::= { hpnicfEOCComCnuSysManEntry 6 }

hpnicfEOCComCnuPvid OBJECT-TYPE
    SYNTAX     Integer32 (1..4094)
    MAX-ACCESS read-write
    STATUS     current
    DESCRIPTION
        "
        The PVID, the VLAN ID assigned to untagged frames or
        Priority-Tagged frames received on cable interface.
        "
    REFERENCE
        "
        IEEE 802.1Q/D11 Section 12.10.1.1
        "
    DEFVAL
        {
            1
        }
    ::= { hpnicfEOCComCnuSysManEntry 7 }

hpnicfEOCComCnuVlanTag OBJECT-TYPE
    SYNTAX     INTEGER
        {
            tagged(1),
            untagged(2)
        }
    MAX-ACCESS read-write
    STATUS     current
    DESCRIPTION
        "
        VLAN is set tagged or untagged on cable interface.
        "
    ::= { hpnicfEOCComCnuSysManEntry 8 }

hpnicfEOCComCnuReset OBJECT-TYPE
    SYNTAX     INTEGER
        {
            running(1),
            reset(2)
        }
    MAX-ACCESS read-write
    STATUS     current
    DESCRIPTION
        "
        This variable is used to reset the CNU device. The
        interface may be unavailable while the reset occurs and
        data may be lost. During reading operation it returns
        the state of the CNU device. running(1) indicates and
        operates normal operation, reset(2) indicates and
        operates reset mode. Writing can be done all the time.
        "
    ::= { hpnicfEOCComCnuSysManEntry 9 }

hpnicfEOCComCnuDeregister OBJECT-TYPE
    SYNTAX     INTEGER
        {
            deregister(1)
        }
    MAX-ACCESS read-write
    STATUS     current
    DESCRIPTION
        "
        deregister CNU.
        "
    ::= { hpnicfEOCComCnuSysManEntry 10 }

hpnicfEOCComCnuSave OBJECT-TYPE
    SYNTAX     INTEGER
        {
            save(1),
            running(2)
        }
    MAX-ACCESS read-write
    STATUS     current
    DESCRIPTION
        "
        Save the UNI and CNU related configurations to
        the CNU.
        "
    ::= { hpnicfEOCComCnuSysManEntry 11 }

hpnicfEOCComCnuAccess OBJECT-TYPE
    SYNTAX     INTEGER
        {
            access(1),
            notaccess(2)
        }
    MAX-ACCESS read-write
    STATUS     current
    DESCRIPTION
        "
        Control whether the user can access to the network.
        "
    ::= { hpnicfEOCComCnuSysManEntry 12 }

--
-- hpnicfEOCComCnuMacTable
--

hpnicfEOCComCnuMacTable OBJECT-TYPE
    SYNTAX     SEQUENCE OF HpnicfEOCComCnuMacEntry
    MAX-ACCESS not-accessible
    STATUS     current
    DESCRIPTION
        "
        This table implements the management of CNUs.
        "
    ::= { hpnicfEOCComCnuMan 3 }

hpnicfEOCComCnuMacEntry OBJECT-TYPE
    SYNTAX     HpnicfEOCComCnuMacEntry
    MAX-ACCESS not-accessible
    STATUS     current
    DESCRIPTION
        "
        The entry of the table hpnicfEOCComCnuMacTable.
        "
    INDEX
        {
            ifIndex
        }
    ::= { hpnicfEOCComCnuMacTable 1 }

HpnicfEOCComCnuMacEntry ::= SEQUENCE
    {
        hpnicfEOCComCnuMacAddress    MacAddress,
        hpnicfEOCComCnuRowStatus     RowStatus,
        hpnicfEOCComCnuTempIndex     Integer32
    }

hpnicfEOCComCnuMacAddress OBJECT-TYPE
    SYNTAX     MacAddress
    MAX-ACCESS read-create
    STATUS     current
    DESCRIPTION
        "
        EOC CNU's MAC address.
        "
    ::= { hpnicfEOCComCnuMacEntry 1 }

hpnicfEOCComCnuRowStatus OBJECT-TYPE
    SYNTAX     RowStatus
    MAX-ACCESS read-create
    STATUS     current
    DESCRIPTION
        "
        Operation status.
        "
    ::= { hpnicfEOCComCnuMacEntry 2 }
    
hpnicfEOCComCnuTempIndex OBJECT-TYPE
    SYNTAX     Integer32
    MAX-ACCESS read-write
    STATUS     current
    DESCRIPTION
        "
        EOC CNU's model index from hpnicfHPEOCTemplateIndex,
        If configure 0, the CNU select no model.
        "
    ::= { hpnicfEOCComCnuMacEntry 3 }
    
--
-- hpnicfEOCComCnuInfoTable
--

hpnicfEOCComCnuInfoTable OBJECT-TYPE
    SYNTAX     SEQUENCE OF HpnicfEOCComCnuInfoEntry
    MAX-ACCESS not-accessible
    STATUS     current
    DESCRIPTION
        "
        Primary status of the specified CNU.
        There will be one row in this table for each
        information in the system.
        "
    ::= { hpnicfEOCComCnuMan 4 }

hpnicfEOCComCnuInfoEntry OBJECT-TYPE
    SYNTAX     HpnicfEOCComCnuInfoEntry
    MAX-ACCESS not-accessible
    STATUS     current
    DESCRIPTION
        "
        The entry of the hpnicfEOCComCnuInfoTable.
        "
    INDEX
        {
            ifIndex
        }
    ::= { hpnicfEOCComCnuInfoTable 1 }

HpnicfEOCComCnuInfoEntry ::= SEQUENCE
    {
        hpnicfEOCComCnuHardwareVersion    DisplayString,
        hpnicfEOCComCnuPCBVersion         OCTET STRING,
        hpnicfEOCComCnuLinkState          INTEGER,
        hpnicfEOCComCnuAttenuation        Integer32,
        hpnicfEOCComCnuSoftwareVersion    DisplayString,
        hpnicfEOCComCnuTxRate             Integer32,
        hpnicfEOCComCnuRxRate             Integer32,
        hpnicfEOCComCnuTxRateDrop         Integer32,
        hpnicfEOCComCnuRxRateDrop         Integer32
    }

hpnicfEOCComCnuHardwareVersion OBJECT-TYPE
    SYNTAX     DisplayString
    MAX-ACCESS read-only
    STATUS     current
    DESCRIPTION
        "
        EOC CNU's hardware version.  If the object length is
        zero, it means the version is unknown.
        "
    ::= { hpnicfEOCComCnuInfoEntry 1 }

hpnicfEOCComCnuPCBVersion OBJECT-TYPE
    SYNTAX     OCTET STRING (SIZE(0..255))
    MAX-ACCESS read-only
    STATUS     current
    DESCRIPTION
        "
        EOC CNU's PCB version.
        "
    ::= { hpnicfEOCComCnuInfoEntry 2 }

hpnicfEOCComCnuLinkState OBJECT-TYPE
    SYNTAX     INTEGER
        {
            physicaldown(1),
            linkdown(2),
            linkup(3),
            loopback(4)
        }
    MAX-ACCESS read-only
    STATUS     current
    DESCRIPTION
        "
        The cable port's link state.  The physicaldown(1) state indicates
        that the CNU is not powered on.  The linkdown(2) state indicates
        that the CNU is powered on, but registers fail.  The linkup(3)
        state indicates that the CNU is powered on, and registers
        successful.  The loopback(4) state indecates that the CNU is
        powered on and registers successful, but loopback has detected.
        "
    ::= { hpnicfEOCComCnuInfoEntry 3 }

hpnicfEOCComCnuAttenuation OBJECT-TYPE
    SYNTAX     Integer32
    MAX-ACCESS read-only
    STATUS     current
    DESCRIPTION
        "
        The cnu's average attenuation.
        "
    ::= { hpnicfEOCComCnuInfoEntry 4 }

hpnicfEOCComCnuSoftwareVersion OBJECT-TYPE
    SYNTAX     DisplayString
    MAX-ACCESS read-only
    STATUS     current
    DESCRIPTION
        "
        EOC CNU's software version.  If the object length is
        zero, it means the version is unknown.
        "
    ::= { hpnicfEOCComCnuInfoEntry 5 }

hpnicfEOCComCnuTxRate OBJECT-TYPE
    SYNTAX     Integer32
    MAX-ACCESS read-only
    STATUS     current
    DESCRIPTION
        "
        The cnu's capability of tx speed in unit of 1Mbps.
        "
    ::= { hpnicfEOCComCnuInfoEntry 6 }

hpnicfEOCComCnuRxRate OBJECT-TYPE
    SYNTAX     Integer32
    MAX-ACCESS read-only
    STATUS     current
    DESCRIPTION
        "
        The cnu's capability of rx speed in unit of 1Mbps.
        "
    ::= { hpnicfEOCComCnuInfoEntry 7 }

hpnicfEOCComCnuTxRateDrop OBJECT-TYPE
    SYNTAX     Integer32
    MAX-ACCESS read-only
    STATUS     current
    DESCRIPTION
        "
        The cnu's capability droping of tx
        speed from it's history max value in unit of %.
        "
    ::= { hpnicfEOCComCnuInfoEntry 8 }

hpnicfEOCComCnuRxRateDrop OBJECT-TYPE
    SYNTAX     Integer32
    MAX-ACCESS read-only
    STATUS     current
    DESCRIPTION
        "
        The cnu's capability droping of rx
        speed from it's history max value in unit of %.
        "
    ::= { hpnicfEOCComCnuInfoEntry 9 }

--
-- hpnicfEOCComCnuBandWidthTable
--

hpnicfEOCComCnuBandWidthTable OBJECT-TYPE
    SYNTAX     SEQUENCE OF HpnicfEOCComCnuBandWidthEntry
    MAX-ACCESS not-accessible
    STATUS     current
    DESCRIPTION
        "
        Set bandwidth parameters.
        "
    ::= { hpnicfEOCComCnuMan 5 }

hpnicfEOCComCnuBandWidthEntry OBJECT-TYPE
    SYNTAX     HpnicfEOCComCnuBandWidthEntry
    MAX-ACCESS not-accessible
    STATUS     current
    DESCRIPTION
        "
        The entry of table hpnicfEOCComCnuBandWidthTable.
        It is a pre-configuration.
        "
    INDEX
        {
            ifIndex
        }
    ::= { hpnicfEOCComCnuBandWidthTable 1 }

HpnicfEOCComCnuBandWidthEntry ::= SEQUENCE
    {
        hpnicfEOCComCnuMaxDownBW       Integer32,
        hpnicfEOCComCnuSlaHighPriBW    Integer32,
        hpnicfEOCComCnuMaxUpBW         Integer32
    }

hpnicfEOCComCnuMaxDownBW OBJECT-TYPE
    SYNTAX     Integer32
    MAX-ACCESS read-write
    STATUS     current
    DESCRIPTION
        "
        Maximum bandwidth allowed for the CNU,
        measured in Kbit/s.
        "
    ::= { hpnicfEOCComCnuBandWidthEntry 1 }

hpnicfEOCComCnuSlaHighPriBW OBJECT-TYPE
    SYNTAX     Integer32
    MAX-ACCESS read-write
    STATUS     current
    DESCRIPTION
        "
        High priority bandwidth - measured in Kbit/s.
        The value of this object should be the multiple of
        the value of hpnicfEOCComCnuMaxUpBW.
        The high priority bandwidth should not be larger than the maximum
        bandwidth.
        "
    ::= { hpnicfEOCComCnuBandWidthEntry 2 }

hpnicfEOCComCnuMaxUpBW OBJECT-TYPE
    SYNTAX     Integer32
    MAX-ACCESS read-write
    STATUS     current
    DESCRIPTION
        "
        Total bandwidth - measured in Kbit/s.
        The value of this object should be the multiple of
        the value of hpnicfEOCComCnuSlaHighPriBW.
        The total bandwidth should be larger than the high priority bandwidth.
        "
    ::= { hpnicfEOCComCnuBandWidthEntry 3 }




--
-- hpnicfEOCComUniMan
--

hpnicfEOCComUniMan OBJECT IDENTIFIER ::= { hpnicfEOCCommon 4 }

hpnicfEOCComUniManTable OBJECT-TYPE
    SYNTAX     SEQUENCE OF HpnicfEOCComUniManEntry
    MAX-ACCESS not-accessible
    STATUS     current
    DESCRIPTION
        "
        This table defines several user network interface(UNI) system
        parameters.
        "
    ::= { hpnicfEOCComUniMan 1 }

hpnicfEOCComUniManEntry OBJECT-TYPE
    SYNTAX     HpnicfEOCComUniManEntry
    MAX-ACCESS not-accessible
    STATUS     current
    DESCRIPTION
        "
        The entry of hpnicfEOCComUniManTable.
        "
    INDEX
        {
            ifIndex,
            hpnicfEOCUniIndex
        }
    ::= { hpnicfEOCComUniManTable 1 }

HpnicfEOCComUniManEntry ::= SEQUENCE
    {
        hpnicfEOCUniIndex               Unsigned32,
        hpnicfEOCComUniDescr            DisplayString,
        hpnicfEOCComUniStatus           INTEGER,
        hpnicfEOCComUniSpeed            INTEGER,
        hpnicfEOCComUniDuplex           INTEGER,
        hpnicfEOCComUniCurrentSpeed     Gauge32,
        hpnicfEOCComUniCurrentDuplex    INTEGER,
        hpnicfEOCComUniMdi              INTEGER,
        hpnicfEOCComUniFlowControl      TruthValue,
        hpnicfEOCComUniCountReset       INTEGER,
        hpnicfEOCComUniAlias            DisplayString,
        hpnicfEOCComUniType             IANAifType,
        hpnicfEOCComUniVLANType         INTEGER,
        hpnicfEOCComUniPvid             Integer32,
        hpnicfEOCComUniVlanTag          INTEGER,
        hpnicfEOCComUniPriority         Integer32,
        hpnicfEOCComUniUpLineRate       Unsigned32,
        hpnicfEOCComUniDownLineRate     Unsigned32,
        hpnicfEOCComUniAdminStatus      INTEGER
    }

hpnicfEOCUniIndex OBJECT-TYPE
    SYNTAX     Unsigned32
    MAX-ACCESS not-accessible
    STATUS     current
    DESCRIPTION
        "
        The index value which uniquely identifies the FE(Fast Ethernet)
        interface of the CNU.
        "
    ::= { hpnicfEOCComUniManEntry 1 }

hpnicfEOCComUniDescr OBJECT-TYPE
    SYNTAX     DisplayString
    MAX-ACCESS read-only
    STATUS     current
    DESCRIPTION
        "
        A textual string containing information about the interface.  This
        string should include the name of the manufacturer, the product
        name and the version of the interface hardware and software.
        "
    ::= { hpnicfEOCComUniManEntry 2 }

hpnicfEOCComUniStatus OBJECT-TYPE
    SYNTAX     INTEGER
        {
            up(1),
            down(2),
            testing(3)
        }
    MAX-ACCESS read-write
    STATUS     current
    DESCRIPTION
        "
        The desired state of the user network interface. When a managed
        system initializes, all user network interfaces start with down
        state. The testing state indicates that no operational packets
        can be passed. As a result of either explicit management action or
        per configuration information retained by the managed system,
        hpnicfEOCComUniStatus is then changed to either the up or
        testing states (or remains in the down state).
        "
    ::= { hpnicfEOCComUniManEntry 3 }

hpnicfEOCComUniSpeed OBJECT-TYPE
    SYNTAX     INTEGER
        {
            auto(1),
            s10M(10),
            s100M(100)
        }
    MAX-ACCESS read-write
    STATUS     current
    DESCRIPTION
        "
        User network interface speed.
        "
    ::= { hpnicfEOCComUniManEntry 4 }

hpnicfEOCComUniDuplex OBJECT-TYPE
    SYNTAX     INTEGER
        {
            full(1),
            half(2),
            auto(3)
        }
    MAX-ACCESS read-write
    STATUS     current
    DESCRIPTION
        "
        User network interface mode.
        "
    ::= { hpnicfEOCComUniManEntry 5 }

hpnicfEOCComUniCurrentSpeed OBJECT-TYPE
    SYNTAX     Gauge32
    MAX-ACCESS read-only
    STATUS     current
    DESCRIPTION
        "
        An estimate of the interface's current bandwidth in
        bits per second.  For interfaces which do not vary in
        bandwidth or for those where no accurate estimation
        can be made, this object should contain the nominal
        bandwidth.  If the bandwidth of the interface is
        greater than the maximum value reportable by this
        object then this object should report its maximum
        value (4,294,967,295).  For a sub-layer which
        has no concept of bandwidth, this object should be
        zero.
        "
    ::= { hpnicfEOCComUniManEntry 6 }

hpnicfEOCComUniCurrentDuplex OBJECT-TYPE
    SYNTAX     INTEGER
        {
            full(1),
            half(2),
            unknown(3)
        }
    MAX-ACCESS read-only
    STATUS     current
    DESCRIPTION
        "
        The current mode of operation of the MAC
        entity.  'unknown' indicates that the current
        duplex mode could not be determined.

        Management control of the duplex mode is
        accomplished through the MAU MIB.  When
        an interface does not support autonegotiation,
        or when autonegotiation is not enabled, the
        duplex mode is controlled using
        ifMauDefaultType.  When autonegotiation is
        supported and enabled, duplex mode is controlled
        using ifMauAutoNegAdvertisedBits.  In either
        case, the currently operating duplex mode is
        reflected both in this object and in ifMauType.

        Note that this object provides redundant
        information with ifMauType.  Normally, redundant
        objects are discouraged.  However, in this
        instance, it allows a management application to
        determine the duplex status of an interface
        without having to know every possible value of
        ifMauType.  This was felt to be sufficiently
        valuable to justify the redundancy.
        "
    REFERENCE
        "
        [IEEE 802.3 Std.], 30.3.1.1.32, aDuplexStatus.
        "
    ::= { hpnicfEOCComUniManEntry 7 }

hpnicfEOCComUniMdi OBJECT-TYPE
    SYNTAX     INTEGER
        {
            mdi-ii(1),
            mdi-x(2),
            mdi-auto(3)
        }
    MAX-ACCESS read-write
    STATUS     current
    DESCRIPTION
        "Type of the line connected to UNI interface:
        mdi-ii(straight-through cable),
        mdi-x (crossover cable),
        mdi-auto (auto-sensing)."
    DEFVAL
        {
            mdi-auto
        }
    ::= { hpnicfEOCComUniManEntry 8 }

hpnicfEOCComUniFlowControl OBJECT-TYPE
    SYNTAX      TruthValue
    MAX-ACCESS  read-write
    STATUS      current
    DESCRIPTION
        "Flow control status.
        true(1)  - Flow control status enable.
        false(2) - Flow control status disable."
    DEFVAL
        {
            false
        }
    ::= { hpnicfEOCComUniManEntry 9 }

hpnicfEOCComUniCountReset OBJECT-TYPE
    SYNTAX      INTEGER
        {
            reset(1)
        }
    MAX-ACCESS  read-write
    STATUS      current
    DESCRIPTION
        "Reset the counter which is about packets of the interface,
        then the counter will change to zero.  There is no sense in
        reading this object."
    ::= { hpnicfEOCComUniManEntry 10 }

hpnicfEOCComUniAlias OBJECT-TYPE
    SYNTAX     DisplayString
    MAX-ACCESS read-write
    STATUS     current
    DESCRIPTION
        "
        This object is an 'alias' name for the interface as
        specified by a network manager, and provides a non-
        volatile 'handle' for the interface.

        On the first instantiation of an interface, the value
        of hpnicfEOCComUniAlias associated with that interface is the
        zero-length string.  As and when a value is written
        into an instance of hpnicfEOCComUniAlias through a network
        management set operation, then the agent must retain
        the supplied value in the hpnicfEOCComUniAlias instance associated
        with the same interface for as long as that interface
        remains instantiated, including across all re-
        initializations/reboots of the network management
        system, including those which result in a change of
        the interface's ifIndex and hpnicfEOCUniIndex value.

        An example of the value which a network manager might
        store in this object for a WAN interface is the
        (Telco's) circuit number/identifier of the interface.

        Some agents may support write-access only for
        interfaces having particular values of hpnicfEOCComUniType.  An
        agent which supports write access to this object is
        required to keep the value in non-volatile storage,
        but it may limit the length of new values depending on
        how much storage is already occupied by the current
        values for other interfaces.
        "
    ::= { hpnicfEOCComUniManEntry 11 }

hpnicfEOCComUniType OBJECT-TYPE
    SYNTAX     IANAifType
    MAX-ACCESS read-only
    STATUS     current
    DESCRIPTION
        "
        The type of interface.  Additional values for hpnicfEOCComUniType
        are assigned by the Internet Assigned Numbers
        Authority(IANA), through updating the syntax of the
        IANAifType textual convention.
        "
    ::= { hpnicfEOCComUniManEntry 12 }

hpnicfEOCComUniVLANType OBJECT-TYPE
    SYNTAX     INTEGER
        {
            vLANTrunk(1),
            access(2),
            hybrid(3),
            fabric(4)
        }
    MAX-ACCESS read-write
    STATUS     current
    DESCRIPTION
        "port vlan types.
        hybrid (3) port can carry multiple VLANs.
        If fabric function is supported, fabric(4) means the port is
        a fabric port."
    ::= { hpnicfEOCComUniManEntry 13 }

hpnicfEOCComUniPvid OBJECT-TYPE
    SYNTAX     Integer32 (1..4094)
    MAX-ACCESS read-write
    STATUS     current
    DESCRIPTION
        "
        The PVID, the VLAN ID assigned to untagged frames or
        Priority-Tagged frames received on this port.
        "
    REFERENCE
        "
        IEEE 802.1Q/D11 Section 12.10.1.1
        "
    DEFVAL
        {
            1
        }
    ::= { hpnicfEOCComUniManEntry 14 }

hpnicfEOCComUniVlanTag OBJECT-TYPE
    SYNTAX     INTEGER
        {
            tagged(1),
            untagged(2)
        }
    MAX-ACCESS read-write
    STATUS     current
    DESCRIPTION
        "
        VLAN is set tagged or untagged.
        "
    ::= { hpnicfEOCComUniManEntry 15 }

hpnicfEOCComUniPriority OBJECT-TYPE
    SYNTAX     Integer32 (0..7)
    MAX-ACCESS read-write
    STATUS     current
    DESCRIPTION
        "
        The default ingress User Priority for this port.  This
        only has effect on media, such as Ethernet, that do not
        support native User Priority.
        "
    ::= { hpnicfEOCComUniManEntry 16 }

hpnicfEOCComUniUpLineRate OBJECT-TYPE
    SYNTAX     Unsigned32
    MAX-ACCESS read-write
    STATUS     current
    DESCRIPTION
        "
        The max speed upload in units of 1,000 bits per second
        on this interface.  The value should between 0 and 100Mbps.
        If the value is 0, it means that the upload speed is only
        restricted by the physical line.
        "
    ::= { hpnicfEOCComUniManEntry 17 }

hpnicfEOCComUniDownLineRate OBJECT-TYPE
    SYNTAX     Unsigned32
    MAX-ACCESS read-write
    STATUS     current
    DESCRIPTION
        "
        The max speed download in units of 1,000 bits per second
        on this interface.  The value should between 0 and 100Mbps.
        If the value is 0, it means that the download speed is only
        restricted by the physical line.
        "
    ::= { hpnicfEOCComUniManEntry 18 }

hpnicfEOCComUniAdminStatus OBJECT-TYPE
    SYNTAX      INTEGER
        {
            up(1),
            down(2)
        }
    MAX-ACCESS  read-write
    STATUS      current
    DESCRIPTION
        "
        Control if open or close the UNI.  If choose up(1), means the UNI is
        opened and packets can pass it.  If choose down(2), means the UNI is
        closed and all packets will be discard.
        "
    ::= { hpnicfEOCComUniManEntry 19 }

--
-- hpnicfEOCComUniCountTable
--
hpnicfEOCComUniCountTable OBJECT-TYPE
    SYNTAX      SEQUENCE OF HpnicfEOCComUniCountEntry
    MAX-ACCESS  not-accessible
    STATUS      current
    DESCRIPTION
        "A list of interface counter about frames entries."
    ::= { hpnicfEOCComUniMan 2 }

hpnicfEOCComUniCountEntry OBJECT-TYPE
    SYNTAX      HpnicfEOCComUniCountEntry
    MAX-ACCESS  not-accessible
    STATUS      current
    DESCRIPTION
        "An entry containing management information applicable
        to a particular interface."
    INDEX
        {
            ifIndex,
            hpnicfEOCUniIndex
        }
    ::= { hpnicfEOCComUniCountTable 1 }

HpnicfEOCComUniCountEntry ::= SEQUENCE
    {
        hpnicfEOCUniInPkts                     Unsigned32,
        hpnicfEOCUniInUPkts                    Unsigned32,
        hpnicfEOCUniInBPkts                    Unsigned32,
        hpnicfEOCUniInMPkts                    Unsigned32,
        hpnicfEOCUniInPausePkts                Unsigned32,
        hpnicfEOCUniInTotalErrors              Unsigned32,
        hpnicfEOCUniInCRCErrs                  Unsigned32,
        hpnicfEOCUniInUndersizePkts            Unsigned32,
        hpnicfEOCUniInOversizePkts             Unsigned32,
        hpnicfEOCUniInErrorbyOther             Unsigned32,
        hpnicfEOCUniInOctets                   Unsigned32,
        hpnicfEOCUniOutPkts                    Unsigned32,
        hpnicfEOCUniOutUPkts                   Unsigned32,
        hpnicfEOCUniOutBPkts                   Unsigned32,
        hpnicfEOCUniOutMPkts                   Unsigned32,
        hpnicfEOCUniOutPausePkts               Unsigned32,
        hpnicfEOCUniOutTotalErrors             Unsigned32,
        hpnicfEOCUniOutCollisions              Unsigned32,
        hpnicfEOCUniOutDelayExceedDsds         Unsigned32,
        hpnicfEOCUniOutErrorbyOther            Unsigned32,
        hpnicfEOCUniOutDroppedFrames           Unsigned32,
        hpnicfEOCUniOutOctets                  Unsigned32
    }

hpnicfEOCUniInPkts OBJECT-TYPE
    SYNTAX     Unsigned32
    MAX-ACCESS read-only
    STATUS     current
    DESCRIPTION
        "The total number of packets (including bad packets,
        broadcast packets, and multicast packets) received."
    ::= { hpnicfEOCComUniCountEntry 1 }

hpnicfEOCUniInUPkts  OBJECT-TYPE
    SYNTAX     Unsigned32
    MAX-ACCESS read-only
    STATUS     current
    DESCRIPTION
        "The total number of good packets received that are
        directed to the unicast address.  Note that this
        does not include multicast and broadcast packets."
    ::= { hpnicfEOCComUniCountEntry 2 }

hpnicfEOCUniInBPkts  OBJECT-TYPE
    SYNTAX     Unsigned32
    MAX-ACCESS read-only
    STATUS     current
    DESCRIPTION
        "The total number of good packets received that are
        directed to the broadcast address.  Note that this
        does not include multicast packets."
    ::= { hpnicfEOCComUniCountEntry 3 }

hpnicfEOCUniInMPkts  OBJECT-TYPE
    SYNTAX     Unsigned32
    MAX-ACCESS read-only
    STATUS     current
    DESCRIPTION
        "The total number of good packets received that are
        directed to a multicast address.  Note that this number
        does not include packets directed to the broadcast address."
    ::= { hpnicfEOCComUniCountEntry 4 }

hpnicfEOCUniInPausePkts  OBJECT-TYPE
    SYNTAX     Unsigned32
    MAX-ACCESS read-only
    STATUS     current
    DESCRIPTION
        "A count of MAC Control packets received on this
        interface by the pause(flow control) operation.
        This counter does not increment when the
        interface is in a half-duplex mode.
        Discontinuities in the value of this counter can
        occur at re-initialization of the management
        system."
    ::= { hpnicfEOCComUniCountEntry 5 }

hpnicfEOCUniInTotalErrors  OBJECT-TYPE
    SYNTAX     Unsigned32
    MAX-ACCESS read-only
    STATUS     current
    DESCRIPTION
        "Total count of the error packets received on this interface."
    ::= { hpnicfEOCComUniCountEntry 6 }

hpnicfEOCUniInCRCErrs  OBJECT-TYPE
    SYNTAX     Unsigned32
    MAX-ACCESS read-only
    STATUS     current
    DESCRIPTION
        "The total number of packets received that
        had a length (excluding framing bits, but
        including FCS octets) of between 64 and 1518
        octets, inclusive, but had either a bad
        Frame Check Sequence (FCS) with an integral
        number of octets (FCS Error) or a bad FCS with
        a non-integral number of octets (Alignment Error)."
    ::= { hpnicfEOCComUniCountEntry 7 }

hpnicfEOCUniInUndersizePkts  OBJECT-TYPE
    SYNTAX     Unsigned32
    MAX-ACCESS read-only
    STATUS     current
    DESCRIPTION
        "The total number of packets received that are
        less than 64 octets long (excluding framing bits,
        but including FCS octets) and are otherwise well formed."
    ::= { hpnicfEOCComUniCountEntry 8 }

hpnicfEOCUniInOversizePkts  OBJECT-TYPE
    SYNTAX     Unsigned32
    MAX-ACCESS read-only
    STATUS     current
    DESCRIPTION
        "The total number of packets received that are
        longer than 1518 octets (excluding framing bits,
        but including FCS octets) and are otherwise well formed."
    ::= { hpnicfEOCComUniCountEntry 9 }

hpnicfEOCUniInErrorbyOther   OBJECT-TYPE
    SYNTAX     Unsigned32
    MAX-ACCESS read-only
    STATUS     current
    DESCRIPTION
        "The total number of other error packets received on this interface."
    ::= { hpnicfEOCComUniCountEntry 10 }

hpnicfEOCUniInOctets   OBJECT-TYPE
    SYNTAX     Unsigned32
    MAX-ACCESS read-only
    STATUS     current
    DESCRIPTION
        "The total number of octets received on this interface."
    ::= { hpnicfEOCComUniCountEntry 11 }

hpnicfEOCUniOutPkts OBJECT-TYPE
    SYNTAX     Unsigned32
    MAX-ACCESS read-only
    STATUS     current
    DESCRIPTION
        "The total number of packets (including bad packets,
        broadcast packets, and multicast packets) sent."
    ::= { hpnicfEOCComUniCountEntry 12 }

hpnicfEOCUniOutUPkts OBJECT-TYPE
    SYNTAX     Unsigned32
    MAX-ACCESS read-only
    STATUS     current
    DESCRIPTION
        "The total number of good packets sent that are
        directed to the unicast address.  Note that this
        does not include multicast and broadcast packets."
    ::= { hpnicfEOCComUniCountEntry 13 }

hpnicfEOCUniOutBPkts  OBJECT-TYPE
    SYNTAX     Unsigned32
    MAX-ACCESS read-only
    STATUS     current
    DESCRIPTION
        "The total number of good packets sent that are
        directed to the broadcast address.  Note that this
        does not include multicast packets."
    ::= { hpnicfEOCComUniCountEntry 14 }

hpnicfEOCUniOutMPkts  OBJECT-TYPE
    SYNTAX     Unsigned32
    MAX-ACCESS read-only
    STATUS     current
    DESCRIPTION
        "The total number of good packets sent that are
        directed to a multicast address.  Note that this number
        does not include packets directed to the broadcast address."
    ::= { hpnicfEOCComUniCountEntry 15 }

hpnicfEOCUniOutPausePkts  OBJECT-TYPE
    SYNTAX     Unsigned32
    MAX-ACCESS read-only
    STATUS     current
    DESCRIPTION
        "The total number of MAC control packets sent on this
        interface by the pause operation.  This counter does
        not increment when the interface is in a half-duplex mode.
        Discontinuities in the value of this counter can
        occur at re-initialization of the management system."
    ::= { hpnicfEOCComUniCountEntry 16 }

hpnicfEOCUniOutTotalErrors  OBJECT-TYPE
    SYNTAX     Unsigned32
    MAX-ACCESS read-only
    STATUS     current
    DESCRIPTION
        "The total number of error packets sent on this interface."
    ::= { hpnicfEOCComUniCountEntry 17 }

hpnicfEOCUniOutCollisions  OBJECT-TYPE
    SYNTAX     Unsigned32
    MAX-ACCESS read-only
    STATUS     current
    DESCRIPTION
        "The best estimate of the total number of collisions
        on this Ethernet segment.
        The value returned will depend on the location of the
        RMON probe.  Section 8.2.1.3 (10BASE-5) and section
        10.3.1.3 (10BASE-2) of IEEE standard 802.3 states that a
        station must detect a collision, in the receive mode, if
        three or more stations are transmitting simultaneously.  A
        repeater port must detect a collision when two or more
        stations are transmitting simultaneously.  Thus a probe
        placed on a repeater port could record more collisions
        than a probe connected to a station on the same segment
        could.  Probe location plays a much smaller role when considering
        10BASE-T.  14.2.1.4 (10BASE-T) of IEEE standard 802.3
        defines a collision as the simultaneous presence of signals
        on the DO and RD circuits (transmitting and receiving
        at the same time).  A 10BASE-T station can only detect
        collisions when it is transmitting.  Thus probes placed on
        a station and a repeater, should report the same number of
        collisions.  Note also that an RMON probe inside a repeater should
        ideally report collisions between the repeater and one or
        more other hosts (transmit collisions as defined by IEEE
        802.3k) plus receiver collisions observed on any coax
        segments to which the repeater is connected."
    ::= { hpnicfEOCComUniCountEntry 18 }

hpnicfEOCUniOutDelayExceedDsds  OBJECT-TYPE
    SYNTAX     Unsigned32
    MAX-ACCESS read-only
    STATUS  current
    DESCRIPTION
        "The number of packets discarded by this port due
        to excessive transit delay through the bridge.  It
        is incremented by both transparent and source route bridges."
    ::= { hpnicfEOCComUniCountEntry 19 }

hpnicfEOCUniOutErrorbyOther  OBJECT-TYPE
    SYNTAX     Unsigned32
    MAX-ACCESS read-only
    STATUS     current
    DESCRIPTION
        "The total number of other error packets sent on this interface.
        Other error packets means the error packets out of collision packets
        and excessive delayed packets."
    ::= { hpnicfEOCComUniCountEntry 20 }

hpnicfEOCUniOutDroppedFrames OBJECT-TYPE
    SYNTAX     Unsigned32
    MAX-ACCESS read-only
    STATUS     current
    DESCRIPTION
        "The total number of frames dropped because of buffer failure."
    ::= { hpnicfEOCComUniCountEntry 21 }

hpnicfEOCUniOutOctets   OBJECT-TYPE
    SYNTAX     Unsigned32
    MAX-ACCESS read-only
    STATUS     current
    DESCRIPTION
        "The total number of octets transmitted out of the interface."
    ::= { hpnicfEOCComUniCountEntry 22 }

--
-- hpnicfEOCCommon NOTIFICATION
--

hpnicfEOCCommonTrap OBJECT IDENTIFIER ::= { hpnicfEOCCommon 5 }

hpnicfEOCTrapPrefix OBJECT IDENTIFIER ::= {hpnicfEOCCommonTrap 0}

hpnicfEOCCnuRegExcessTrap NOTIFICATION-TYPE
    OBJECTS
        {
            ifIndex,
            ifDescr
        }
    STATUS current
    DESCRIPTION
        "
        A hpnicfEOCCnuRegExcessTrap notification is sent when the
        number of registered CNUs exceeds the limit.
        "
    ::= { hpnicfEOCTrapPrefix 1 }

hpnicfEOCCnuRegExcessRecoverTrap NOTIFICATION-TYPE
    OBJECTS
        {
            ifIndex,
            ifDescr
        }
    STATUS current
    DESCRIPTION
        "
        A hpnicfEOCCnuRegExcessRecoverTrap notification is sent when
        hpnicfEOCCnuRegExcessTrap is detected and then recoverd.
        "
    ::= { hpnicfEOCTrapPrefix 2 }

hpnicfEOCCnuRegSuccTrap NOTIFICATION-TYPE
    OBJECTS
        {
            ifIndex,
            ifDescr
        }
    STATUS current
    DESCRIPTION
        "
        A hpnicfEOCCnuRegSuccTrap notification is sent when a
        CNU registers successful.
        "
    ::= { hpnicfEOCTrapPrefix 3 }

hpnicfEOCCnuOffLineTrap NOTIFICATION-TYPE
    OBJECTS
        {
            ifIndex,
            ifDescr
        }
    STATUS current
    DESCRIPTION
        "
        A hpnicfEOCCnuOffLineTrap notification is sent when a
        CNU offline.
        "
    ::= { hpnicfEOCTrapPrefix 4 }

hpnicfEOCCnuLinkupTrap NOTIFICATION-TYPE
    OBJECTS
        {
            ifIndex,
            ifDescr
        }
    STATUS current
    DESCRIPTION
        "
        A hpnicfEOCCnuLinkupTrap notification is sent when a
        CNU linkup.
        "
    ::= { hpnicfEOCTrapPrefix 5 }

hpnicfEOCOamDisconnectTrap NOTIFICATION-TYPE
    OBJECTS
        {
            ifIndex,
            ifDescr
        }
    STATUS current
    DESCRIPTION
        "
        A hpnicfEOCOamDisconnectionTrap notification is sent when
        LLID's OAM link is disconnected.
        "
    ::= { hpnicfEOCTrapPrefix 6 }

hpnicfEOCOamDisconnectRecoverTrap NOTIFICATION-TYPE
    OBJECTS
        {
            ifIndex,
            ifDescr
        }
    STATUS current
    DESCRIPTION
        "
        A hpnicfEOCOamDisconnectionRecoverTrap notification is sent when
        LLID's OAM link is disconnected and then connected.
        "
    ::= { hpnicfEOCTrapPrefix 7 }


hpnicfEOCBandwidthNotEnoughTrap NOTIFICATION-TYPE
    OBJECTS
        {
            ifIndex,
            ifDescr
        }
    STATUS current
    DESCRIPTION
        "
        Bandwidth is not enough, cnu can not bind now.
        "
    ::= { hpnicfEOCTrapPrefix 8 }

hpnicfEOCCnuAttenuationTrap NOTIFICATION-TYPE
    OBJECTS
        {
            ifIndex,
            ifDescr,
            hpnicfEOCComCnuMacAddress,
            hpnicfEOCComCnuAttenuation
        }
    STATUS current
    DESCRIPTION
        "
        A hpnicfHPEOCCnuAttenuationTrap notification is sent when a
        CNU's attenuation is changing.
        "
    ::= { hpnicfEOCTrapPrefix 9 }

hpnicfEOCCnuRegFailTrap NOTIFICATION-TYPE
    OBJECTS
        {
            ifIndex,
            ifDescr
        }
    STATUS current
    DESCRIPTION
        "
        A hpnicfEOCCnuRegFailTrap notification is sent when a
        CNU registers fail.
        "
    ::= { hpnicfEOCTrapPrefix 10 }

hpnicfEOCCLTCablePortErrorTrap NOTIFICATION-TYPE
    OBJECTS
        {
            ifIndex,
            ifDescr
        }
    STATUS current
    DESCRIPTION
        "
        A hpnicfEOCCLTCablePortErrorTrap notification is sent when the
        hardware of cable port occurs error or CLT's vlan is configged
        error.
        "
    ::= { hpnicfEOCTrapPrefix 11 }

hpnicfEOCCLTCablePortErrReTrap NOTIFICATION-TYPE
    OBJECTS
        {
            ifIndex,
            ifDescr
        }
    STATUS current
    DESCRIPTION
        "
        A hpnicfEOCCLTCablePortErrReTrap notification is sent when cable port
        error and then recovered.
        "
    ::= { hpnicfEOCTrapPrefix 12 }

hpnicfEOCCnuTxRateDropTrap NOTIFICATION-TYPE
    OBJECTS
        {
            ifIndex,
            ifDescr,
            hpnicfEOCComCnuMacAddress,
            hpnicfEOCComCnuTxRateDrop
        }
    STATUS current
    DESCRIPTION
        "
        A hpnicfEOCCnuTxRateDropTrap notification is sent when cable port
        rate of TX capability drop exceeded threshold.
        "
    ::= { hpnicfEOCTrapPrefix 13 }

hpnicfEOCCnuTxRateDropRecoverTrap NOTIFICATION-TYPE
    OBJECTS
        {
            ifIndex,
            ifDescr,
            hpnicfEOCComCnuMacAddress,
            hpnicfEOCComCnuTxRateDrop
        }
    STATUS current
    DESCRIPTION
        "
        A hpnicfEOCCnuTxRateDropRecoverTrap notification is sent when cable port
        rate of TX capability recover from the recent rate-drop trap.
        "
    ::= { hpnicfEOCTrapPrefix 14 }

hpnicfEOCCnuRxRateDropTrap NOTIFICATION-TYPE
    OBJECTS
        {
            ifIndex,
            ifDescr,
            hpnicfEOCComCnuMacAddress,
            hpnicfEOCComCnuRxRateDrop
        }
    STATUS current
    DESCRIPTION
        "
        A hpnicfEOCCnuRxRateDropTrap notification is sent when cable port
        rate of RX capability drop exceeded threshold.
        "
    ::= { hpnicfEOCTrapPrefix 15 }

hpnicfEOCCnuRxRateDropRecoverTrap NOTIFICATION-TYPE
    OBJECTS
        {
            ifIndex,
            ifDescr,
            hpnicfEOCComCnuMacAddress,
            hpnicfEOCComCnuRxRateDrop
        }
    STATUS current
    DESCRIPTION
        "
        A hpnicfEOCCnuRxRateDropRecoverTrap notification is sent when cable port
        rate of RX capability recover from the recent rate-drop trap.
        "
    ::= { hpnicfEOCTrapPrefix 16 }

hpnicfEOCCnuFWDownLoadErrTrap NOTIFICATION-TYPE
    OBJECTS
        {
            hpnicfHPEOCDownLoadCNUFWResult
        }
    STATUS current
    DESCRIPTION
        "
        A hpnicfEOCCnuFWDownLoadErrTrap notification is sent when CLT can't
        download CNU firmware from the server successfully.
        "
    ::= { hpnicfEOCTrapPrefix 17 }

hpnicfEOCCnuFWDownLoadErrReTrap NOTIFICATION-TYPE
    STATUS current
    DESCRIPTION
        "
        A hpnicfEOCCnuFWDownLoadErrReTrap notification is sent when CLT recover
        from the download CNU firmware error.
        "
    ::= { hpnicfEOCTrapPrefix 18 }

hpnicfEOCCnuDeviceTypeErrTrap NOTIFICATION-TYPE
    OBJECTS
        {
            ifIndex,
            ifDescr,
            hpnicfEOCComCnuMacAddress,
            hpnicfEOCComCnuDeviceType
        }
    STATUS current
    DESCRIPTION
        "
        A hpnicfEOCCnuDeviceTypeErrTrap notification is sent when the online CNU
        doesn't match the type which user defined earlier.
        "
    ::= { hpnicfEOCTrapPrefix 19 }

hpnicfEOCCnuDeviceTypeErrReTrap NOTIFICATION-TYPE
    OBJECTS
        {
            ifIndex,
            ifDescr,
            hpnicfEOCComCnuMacAddress
        }
    STATUS current
    DESCRIPTION
        "
        A hpnicfEOCCnuDeviceTypeErrReTrap notification is sent when the online CNU
        doesn't match the type which user defined earlier and then recover.
        "
    ::= { hpnicfEOCTrapPrefix 20 }

hpnicfEOCCnuAutoUpdateErrTrap NOTIFICATION-TYPE
    OBJECTS
        {
            ifIndex,
            ifDescr,
            hpnicfEOCComCnuMacAddress
        }
    STATUS current
    DESCRIPTION
        "
        A hpnicfEOCCnuAutoUpdateErrTrap notification is sent when the online CNU
        doesn't auto update successfully.
        "
    ::= { hpnicfEOCTrapPrefix 21 }

hpnicfEOCCnuAutoUpdateSuccTrap NOTIFICATION-TYPE
    OBJECTS
        {
            ifIndex,
            ifDescr,
            hpnicfEOCComCnuMacAddress
        }
    STATUS current
    DESCRIPTION
        "
        A hpnicfEOCCnuAutoUpdateSuccTrap notification is sent when the online CNU
        auto update successfully.
        "
    ::= { hpnicfEOCTrapPrefix 22 }

hpnicfEOCLoopbackDetectTrap NOTIFICATION-TYPE
    OBJECTS
        {
            ifIndex,
            ifDescr,
            hpnicfEOCComCnuMacAddress
        }
    STATUS current
    DESCRIPTION
        "
        A hpnicfEOCLoopbackDetectTrap notification is sent when the loopback between
        the ethernet ports of CNU or CLT is found.
        "
    ::= { hpnicfEOCTrapPrefix 23 }

hpnicfEOCLoopbackRecoverTrap NOTIFICATION-TYPE
    OBJECTS
        {
            ifIndex,
            ifDescr,
            hpnicfEOCComCnuMacAddress
        }
    STATUS current
    DESCRIPTION
        "
        A hpnicfEOCLoopbackRecoverTrap notification is sent when the loopback between
        the ethernet ports of CNU or CLT is recover.
        "
    ::= { hpnicfEOCTrapPrefix 24 }

--
-- hpnicfEOCComOnLineCnuMan
--

hpnicfEOCComOnLineCnuMan OBJECT IDENTIFIER ::= { hpnicfEOCCommon 6 }
--
-- hpnicfEOCComCnuTypeTable
--
hpnicfEOCComCnuTypeTable OBJECT-TYPE
    SYNTAX     SEQUENCE OF HpnicfEOCComCnuTypeEntry
    MAX-ACCESS not-accessible
    STATUS     current
    DESCRIPTION
        "
        This table defines the description of cnu typ.
        "
    ::= { hpnicfEOCComOnLineCnuMan 1 }

hpnicfEOCComCnuTypeEntry OBJECT-TYPE
    SYNTAX     HpnicfEOCComCnuTypeEntry
    MAX-ACCESS not-accessible
    STATUS     current
    DESCRIPTION
        "
        The entry of the table hpnicfEOCComCnuTypeTable.
        "
    INDEX
        {
            hpnicfEOCComCnuTypeIdx
        }
    ::= { hpnicfEOCComCnuTypeTable 1 }

HpnicfEOCComCnuTypeEntry ::= SEQUENCE
    {
        hpnicfEOCComCnuTypeIdx    Unsigned32,
        hpnicfEOCComCnuDescripton DisplayString
    }

hpnicfEOCComCnuTypeIdx OBJECT-TYPE
    SYNTAX     Unsigned32
    MAX-ACCESS not-accessible
    STATUS     current
    DESCRIPTION
        "
        A unique value for each cnu types.  Its value
        ranges between 1 and the value of cny typess.
        "
    ::= { hpnicfEOCComCnuTypeEntry 1 }

hpnicfEOCComCnuDescripton OBJECT-TYPE
    SYNTAX     DisplayString
    MAX-ACCESS read-only
    STATUS     current
    DESCRIPTION
        "
        The description for unique cnu types.
        "
    ::= { hpnicfEOCComCnuTypeEntry 2 }

--
-- hpnicfEOCComCnuNumTable
--

hpnicfEOCComCnuNumTable OBJECT-TYPE
    SYNTAX     SEQUENCE OF HpnicfEOCComCnuNumEntry
    MAX-ACCESS not-accessible
    STATUS     current
    DESCRIPTION
        "
        This table defines the number of cnu registered in variable types
        of the CLT .
        "
    ::= { hpnicfEOCComOnLineCnuMan 2 }

hpnicfEOCComCnuNumEntry OBJECT-TYPE
    SYNTAX     HpnicfEOCComCnuNumEntry
    MAX-ACCESS not-accessible
    STATUS     current
    DESCRIPTION
        "
        The entry of the table hpnicfEOCComCnuNumTable.
        "
    INDEX
        {
            ifIndex,
            hpnicfEOCComCnuTypeIdx
        }
    ::= { hpnicfEOCComCnuNumTable 1 }

HpnicfEOCComCnuNumEntry ::= SEQUENCE
    {
        hpnicfEOCComCnuNumber     Integer32
    }

hpnicfEOCComCnuNumber OBJECT-TYPE
    SYNTAX     Integer32
    MAX-ACCESS read-only
    STATUS     current
    DESCRIPTION
        "
        The number of special type of cnu that has been registerd in clt.
        "
    ::= { hpnicfEOCComCnuNumEntry 1 }

END
