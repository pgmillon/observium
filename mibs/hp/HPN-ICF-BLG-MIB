-- ==================================================================
-- Copyright (c) 2010-2013 Hewlett-Packard Development Company, L.P.
--
-- Description: This MIB file is used for management of Balance Group
--              information.
-- Reference:
-- Version: V1.0
-- History:
--   V1.0 2009-09-15 Created by xupengfei02152
-- ==================================================================
HPN-ICF-BLG-MIB DEFINITIONS ::= BEGIN

IMPORTS
    hpnicfCommon
        FROM HPN-ICF-OID-MIB
    Integer32, Counter64, OBJECT-TYPE, MODULE-IDENTITY
        FROM SNMPv2-SMI
    TEXTUAL-CONVENTION
        FROM SNMPv2-TC;

hpnicfBlg MODULE-IDENTITY
    LAST-UPDATED "200909151111Z"
    ORGANIZATION
        ""
    CONTACT-INFO
        ""
    DESCRIPTION
        "This MIB module defines a set of basic objects for
        configuring switches and routers to set/get balance
        group information."
    REVISION
        "200909151111Z"
    DESCRIPTION
        "The initial version of this MIB."

   ::= { hpnicfCommon 108 }

CounterClear ::= TEXTUAL-CONVENTION
    STATUS  current
    DESCRIPTION
        "Cleared: reset the value of the group's counter.
         Nouse: 'nouse' will be returned when getting."
    SYNTAX INTEGER
    {
        cleared(1),
        nouse(2)
    }

hpnicfBlgObjects OBJECT IDENTIFIER  ::= { hpnicfBlg 1 }

hpnicfBlgStatsTable  OBJECT-TYPE
    SYNTAX SEQUENCE OF HpnicfBlgStatsEntry
    MAX-ACCESS not-accessible
    STATUS current
    DESCRIPTION
        "This table contains the statistics information
        about balance groups."
    ::= { hpnicfBlgObjects 1 }

hpnicfBlgStatsEntry OBJECT-TYPE
    SYNTAX HpnicfBlgStatsEntry
    MAX-ACCESS not-accessible
    STATUS current
    DESCRIPTION
        "This list contains statistics information."
    INDEX { hpnicfBlgIndex }
    ::= { hpnicfBlgStatsTable 1 }

HpnicfBlgStatsEntry ::=
   SEQUENCE
   {
       hpnicfBlgIndex
           Integer32,
       hpnicfBlgGroupTxPacketCount
           Counter64,
       hpnicfBlgGroupRxPacketCount
           Counter64,
       hpnicfBlgGroupTxByteCount
           Counter64,
       hpnicfBlgGroupRxByteCount
           Counter64,
       hpnicfBlgGroupCountClear
           CounterClear
   }

hpnicfBlgIndex OBJECT-TYPE
    SYNTAX      Integer32 (1..2147483647)
    MAX-ACCESS  not-accessible
    STATUS      current
    DESCRIPTION
        "The index of the balance group."
    ::= { hpnicfBlgStatsEntry 1 }

hpnicfBlgGroupTxPacketCount OBJECT-TYPE
    SYNTAX      Counter64
    MAX-ACCESS  read-only
    STATUS      current
    DESCRIPTION
        "When retrieved, this object returns the count of
        packets the balance group has sent."
    ::= { hpnicfBlgStatsEntry 2 }

hpnicfBlgGroupRxPacketCount OBJECT-TYPE
    SYNTAX      Counter64
    MAX-ACCESS  read-only
    STATUS      current
    DESCRIPTION
        "When retrieved, this object returns the count of
        packets the balance group has received."
    ::= { hpnicfBlgStatsEntry 3 }

hpnicfBlgGroupTxByteCount OBJECT-TYPE
    SYNTAX      Counter64
    MAX-ACCESS  read-only
    STATUS      current
    DESCRIPTION
        "When retrieved, this object returns the count of
        bytes the balance group has sent."
    ::= { hpnicfBlgStatsEntry 4 }

hpnicfBlgGroupRxByteCount OBJECT-TYPE
    SYNTAX      Counter64
    MAX-ACCESS  read-only
    STATUS      current
    DESCRIPTION
        "When retrieved, this object returns the count of
        bytes the balance group has received."
    ::= { hpnicfBlgStatsEntry 5 }

hpnicfBlgGroupCountClear OBJECT-TYPE
    SYNTAX CounterClear
    MAX-ACCESS read-write
    STATUS current
    DESCRIPTION
        "This object is used to reset the counter of the balance group.
        Read operation is meaningless."
    ::= { hpnicfBlgStatsEntry 6 }

END
