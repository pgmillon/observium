-- =============================================================
-- Copyright (c) 2010-2013 Hewlett-Packard Development Company, L.P.
--
-- Description: This file describes the MIB implementation of ATM
-- Reference:  extension of RFC 1695
-- Version: V1.1
-- History:
--   V1.0 Initial Version  by lizhiyong
--   V1.1 Add node hpnicfAal5VccState and Trap hpnicfAal5VccStateChange
-- =============================================================
HPN-ICF-AAL5-MIB DEFINITIONS ::= BEGIN

IMPORTS
        MODULE-IDENTITY,
        OBJECT-TYPE,
        Integer32,
        NOTIFICATION-TYPE,
        Counter32
    FROM SNMPv2-SMI
        MODULE-COMPLIANCE,
        OBJECT-GROUP,
        NOTIFICATION-GROUP
    FROM SNMPv2-CONF
        ifIndex
    FROM RFC1213-MIB
        hpnicfAAL5
    FROM HPN-ICF-OID-MIB;

hpnicfAAL5MIB  MODULE-IDENTITY
    LAST-UPDATED    "200411041350Z"
    ORGANIZATION
        ""
    CONTACT-INFO
        ""
    DESCRIPTION
        "This MIB file provides AAL5 specific information
        that are excluded by RFC 1695 "
    REVISION        "200411041350Z"
    DESCRIPTION
        "Initial version of this MIB module."
    ::= { hpnicfAAL5 1 }


hpnicfAal5MIBObjects OBJECT IDENTIFIER ::= { hpnicfAAL5MIB 1 }
hpnicfAal5MIBTraps OBJECT IDENTIFIER ::= { hpnicfAAL5MIB 0 }

hpnicfAal5VccTable OBJECT-TYPE
    SYNTAX       SEQUENCE OF HPN-ICFAal5VccEntry
    MAX-ACCESS   not-accessible
    STATUS       current
    DESCRIPTION
        "This table extends AAL5 VCC performance
         parameters which definded in aal5VccEntry of RFC1695."
    ::= { hpnicfAal5MIBObjects 1 }

hpnicfAal5VccEntry OBJECT-TYPE
    SYNTAX         HPN-ICFAal5VccEntry
    MAX-ACCESS     not-accessible
    STATUS         current
    DESCRIPTION
        "This list contains the additional AAL5 VCC performance
         parameters which are not definded in aal5VccEntry
         of RFC1695."
    INDEX { ifIndex, hpnicfAal5VccVpi, hpnicfAal5VccVci }
    ::= { hpnicfAal5VccTable 1 }

HPN-ICFAal5VccEntry ::= SEQUENCE  {
    hpnicfAal5VccVpi        Integer32,
    hpnicfAal5VccVci        Integer32,
    hpnicfAal5VccInPkts     Counter32,
    hpnicfAal5VccOutPkts    Counter32,
    hpnicfAal5VccInOctets   Counter32,
    hpnicfAal5VccOutOctets  Counter32,
    hpnicfAal5VccState      INTEGER
    }

hpnicfAal5VccVpi              OBJECT-TYPE
    SYNTAX         Integer32  (0..4095)
    MAX-ACCESS     not-accessible
    STATUS         current
    DESCRIPTION
        "The VPI value of the AAL5 VCC."
    ::= { hpnicfAal5VccEntry 1 }

hpnicfAal5VccVci             OBJECT-TYPE
    SYNTAX         Integer32  (0..65535)
    MAX-ACCESS     not-accessible
    STATUS         current
    DESCRIPTION
        "The VCI value of the AAL5 VCC."
    ::= { hpnicfAal5VccEntry 2 }

hpnicfAal5VccInPkts          OBJECT-TYPE
    SYNTAX          Counter32
    MAX-ACCESS      read-only
    STATUS          current
    DESCRIPTION
        "The number of AAL5 CPCS PDUs received."
    ::= { hpnicfAal5VccEntry 3 }

hpnicfAal5VccOutPkts        OBJECT-TYPE
    SYNTAX          Counter32
    MAX-ACCESS      read-only
    STATUS          current
    DESCRIPTION
        "The number of AAL5 CPCS PDUs transmitted."
    ::= { hpnicfAal5VccEntry 4 }

hpnicfAal5VccInOctets       OBJECT-TYPE
    SYNTAX          Counter32
    MAX-ACCESS      read-only
    STATUS          current
    DESCRIPTION
        "The number of AAL5 CPCS PDU octets received."
    ::= { hpnicfAal5VccEntry 5 }

hpnicfAal5VccOutOctets     OBJECT-TYPE
    SYNTAX          Counter32
    MAX-ACCESS      read-only
    STATUS          current
    DESCRIPTION
        "The number of AAL5 CPCS PDU octets transmitted."
    ::= { hpnicfAal5VccEntry 6 }

hpnicfAal5VccState OBJECT-TYPE
    SYNTAX   INTEGER    {
                invalid (1),
                active (2),
                inactive (3)
            }
    MAX-ACCESS   read-only
    STATUS   current
    DESCRIPTION
        "Indicates whether the particular virtual circuit is
        operational. 'Active' indicates the particular virtual
        circuit is operational.  'Inactive' indicates the circuit
        is temporarily disabled.  'Invalid' indicates the circuit
        is deleted"
    DEFVAL { active }
        ::= { hpnicfAal5VccEntry 7 }

hpnicfAal5VccStateChange   NOTIFICATION-TYPE
    OBJECTS  { hpnicfAal5VccState }
    STATUS          current
    DESCRIPTION
        "The status of AAL5 VCC."
    ::= { hpnicfAal5MIBTraps 1 }


-- Conformance Information

hpnicfAal5MIBConformance OBJECT IDENTIFIER ::= { hpnicfAAL5MIB 3 }
hpnicfAal5MIBCompliances OBJECT IDENTIFIER ::= { hpnicfAal5MIBConformance 1 }
hpnicfAal5MIBGroups      OBJECT IDENTIFIER ::= { hpnicfAal5MIBConformance 2 }

-- Compliance Statement
hpnicfAal5MIBCompliance MODULE-COMPLIANCE
    STATUS  current
    DESCRIPTION
        "The compliance statement."
    MODULE  -- this module
    MANDATORY-GROUPS { hpnicfAal5MIBGroup }
    GROUP       hpnicfAal5NotificationGroup
    DESCRIPTION
        "This optional group defines the asynchronous
        notifications generated by ATM Systems."
    ::= { hpnicfAal5MIBCompliances 1 }

-- units of conformance:

hpnicfAal5MIBGroup OBJECT-GROUP
    OBJECTS {
        hpnicfAal5VccInPkts,
        hpnicfAal5VccOutPkts,
        hpnicfAal5VccInOctets,
        hpnicfAal5VccOutOctets
    }
    STATUS  current
    DESCRIPTION
        "A collection of objects."
    ::= { hpnicfAal5MIBGroups 1 }

hpnicfAal5NotificationGroup NOTIFICATION-GROUP
    NOTIFICATIONS { hpnicfAal5VccStateChange }
    STATUS  current
    DESCRIPTION
        "Traps which may be used to enhance event driven
        management of the interface."
    ::= { hpnicfAal5MIBGroups 2 }

END
