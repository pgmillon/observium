-- =====================================================================
-- Copyright (c) 2010-2014 Hewlett-Packard Development Company, L.P.
--
-- Description:
--      This MIB module is intended for the management of Fibre Channel (FC)
--      Name Server.
-- Reference:
-- Version: V1.0
-- History:
--   V1.0 Initial version
--        created by qiaoxinghua 2014-03-03
-- =====================================================================
HPN-ICF-FC-NAME-SERVER-MIB DEFINITIONS ::= BEGIN

IMPORTS
    hpnicfSan, hpnicfVsanIndex
        FROM HPN-ICF-VSAN-MIB
    HpnicfFcNameId
        FROM HPN-ICF-FC-TC-MIB
    OBJECT-TYPE, MODULE-IDENTITY, NOTIFICATION-TYPE
        FROM SNMPv2-SMI
    TruthValue
        FROM SNMPv2-TC;

hpnicfFcNameServer MODULE-IDENTITY
    LAST-UPDATED "201403031018Z"    -- March 03, 2014 at 10:18 GMT
    ORGANIZATION
        ""
    CONTACT-INFO
        ""
    DESCRIPTION
        "This MIB module is intended for the management of Fibre Channel (FC)
         Name Server."
    REVISION "201403031018Z"
    DESCRIPTION
        "Initial version of this MIB module."
    ::= { hpnicfSan 10 }

-- Node definitions
hpnicfFcNameServerMibObjects OBJECT IDENTIFIER ::= { hpnicfFcNameServer 1 }

-- FC Name Server Notifications
hpnicfFcNsNotification OBJECT IDENTIFIER ::= { hpnicfFcNameServerMibObjects 1 }

hpnicfFcNsNotificationPrefix   OBJECT IDENTIFIER ::= { hpnicfFcNsNotification 0 }
hpnicfFcNsNotificationSwitch   OBJECT IDENTIFIER ::= { hpnicfFcNsNotification 1 }
hpnicfFcNsObjsForNotification  OBJECT IDENTIFIER ::= { hpnicfFcNsNotification 2 }

hpnicfFcNsPortLoginNotify NOTIFICATION-TYPE
    OBJECTS    { hpnicfVsanIndex,
                 hpnicfFcNsLocalSwitchWWN,
                 hpnicfFcNsFloginPortWWN }
    STATUS     current
    DESCRIPTION
    "This notification will be generated when an entry is added to the
     Name Server database by Nx_Port locally logging in."
    ::= { hpnicfFcNsNotificationPrefix 1 }

hpnicfFcNsPortLogoutNotify NOTIFICATION-TYPE
    OBJECTS    { hpnicfVsanIndex,
                 hpnicfFcNsLocalSwitchWWN,
                 hpnicfFcNsFloginPortWWN }
    STATUS     current
    DESCRIPTION
    "This notification will be generated when an entry is deleted from
     the Name Server database by Nx_Port locally logging out."
    ::= { hpnicfFcNsNotificationPrefix 2 }

hpnicfFcNsPortLoginNotifyEnable OBJECT-TYPE
    SYNTAX     TruthValue
    MAX-ACCESS read-write
    STATUS     current
    DESCRIPTION
    "This object is used to determine whether hpnicfFcNsPortLoginNotify
     will be generated for Nx_Port locally logging in."
    ::= { hpnicfFcNsNotificationSwitch 1 }

hpnicfFcNsPortLogoutNotifyEnable OBJECT-TYPE
    SYNTAX     TruthValue
    MAX-ACCESS read-write
    STATUS     current
    DESCRIPTION
    "This object is used to determine whether hpnicfFcNsPortLogoutNotify
     will be generated for Nx_Port locally logging out."
    ::= { hpnicfFcNsNotificationSwitch 2 }

hpnicfFcNsLocalSwitchWWN OBJECT-TYPE
    SYNTAX     HpnicfFcNameId
    MAX-ACCESS accessible-for-notify
    STATUS     current
    DESCRIPTION
        "The world wide name of the local switch."
    ::= { hpnicfFcNsObjsForNotification 1 }

hpnicfFcNsFloginPortWWN OBJECT-TYPE
    SYNTAX     HpnicfFcNameId
    MAX-ACCESS accessible-for-notify
    STATUS     current
    DESCRIPTION
        "The world wide name of the local logged-in Nx_Port."
    ::= { hpnicfFcNsObjsForNotification 2 }

END
