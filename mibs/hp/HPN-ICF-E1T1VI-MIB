-- =============================================================
-- Copyright (c) 2010-2013 Hewlett-Packard Development Company, L.P.
--
-- Description: E1T1VI MIB
-- Reference:
-- Version: V1.2
-- History:
--   V1.0 2007-04-05 Initial Version by yandehan
--   V1.1 2009-06-08 modified by TONGWEI
--        Added hpnicfE1T1VIUsingTimeslotsRatio
--          and hpnicfE1T1VINotifications
--   V1.2 2010-04-08 modified by TONGWEI
--        Added hpnicfE1T1VIGeneral
-- =============================================================
HPN-ICF-E1T1VI-MIB DEFINITIONS ::= BEGIN
    IMPORTS
        MODULE-IDENTITY, OBJECT-TYPE, Integer32, NOTIFICATION-TYPE
            FROM SNMPv2-SMI
        ifIndex, ifDescr
            FROM RFC1213-MIB
        hpnicfCommon
            FROM HPN-ICF-OID-MIB;


-- =============================================================
-- E1T1VI Module
-- =============================================================
hpnicfE1T1VI MODULE-IDENTITY
    LAST-UPDATED    "201004081855Z"         -- Apr. 8, 2010 at 18:55 GMT
    ORGANIZATION
        ""
    CONTACT-INFO
        ""
    DESCRIPTION
        "This MIB provides E1/T1 voice interface information that are
        excluded by RFC 1213 and RFC 2233"
    REVISION        "201004081855Z"
    DESCRIPTION
        "To fix bugs in the MIB file."
    REVISION        "200906081741Z"
    DESCRIPTION
        "To fix bugs in the MIB file."
    REVISION        "200704051542Z"
    DESCRIPTION
        "Initial version of this MIB module."
    ::= { hpnicfCommon 76 }


hpnicfE1T1VITable OBJECT-TYPE
    SYNTAX      SEQUENCE OF HpnicfE1T1VIEntry
    MAX-ACCESS  not-accessible
    STATUS      current
    DESCRIPTION
        "This table contains E1/T1 voice interface information,
        such as the total number of using time slot."
    ::= { hpnicfE1T1VI 1 }

hpnicfE1T1VIEntry OBJECT-TYPE
    SYNTAX      HpnicfE1T1VIEntry
    MAX-ACCESS  not-accessible
    STATUS      current
    DESCRIPTION
        "This entry contains E1/T1 voice interface information.
        The index of this Entry is ifIndex defined in ifTable
        of RFC1213-MIB."
    INDEX
        {
            ifIndex
        }
    ::= { hpnicfE1T1VITable 1 }

HpnicfE1T1VIEntry ::= SEQUENCE
    {
        hpnicfE1T1VIUsingTimeslots    Integer32,
        hpnicfE1T1VIUsingTimeslotsRatio    Integer32
    }

hpnicfE1T1VIUsingTimeslots OBJECT-TYPE
    SYNTAX      Integer32
    MAX-ACCESS  read-only
    STATUS      current
    DESCRIPTION
        "The total number of using time slots on this interface."
    ::= { hpnicfE1T1VIEntry 1 }

hpnicfE1T1VIUsingTimeslotsRatio OBJECT-TYPE
    SYNTAX      Integer32
    MAX-ACCESS  read-only
    STATUS      current
    DESCRIPTION
        "The total ratio of using time slots on this interface."
    ::= { hpnicfE1T1VIEntry 2 }

hpnicfE1T1VINotifications OBJECT IDENTIFIER ::= { hpnicfE1T1VI 2 }
hpnicfE1T1VITrapPrefix    OBJECT IDENTIFIER ::= { hpnicfE1T1VINotifications 0 }

hpnicfE1T1VITrapTimeSlot NOTIFICATION-TYPE
    OBJECTS { ifIndex, ifDescr }
    STATUS current
    DESCRIPTION
        "This trap is sent to the manager under the following
         condidion: All the available time slots of a E1/T1
         voice interface has been in use."
    ::= { hpnicfE1T1VITrapPrefix 1 }

hpnicfE1T1VIGeneral  OBJECT IDENTIFIER ::= { hpnicfE1T1VI 3 }

hpnicfE1T1VITrapTimeSlotEnable OBJECT-TYPE
    SYNTAX  INTEGER {
            enable(1),
            disable(2)
        }
    MAX-ACCESS  read-write
    STATUS      current
    DESCRIPTION
        "This attribute controls whether the hpnicfE1T1VITrapTimeSlot trap will
        be sent or not."
    DEFVAL { enable }
    ::= { hpnicfE1T1VIGeneral 1 }

END
