-- =============================================================================
-- Copyright (c) 2010-2013 Hewlett-Packard Development Company, L.P.
--
-- Description:
--   The file defines a MIB to provide WLAN configuration extended.
-- Reference:
-- Version: V1.2
-- History:
--   V1.0 2007-04-25 Initial version, created by shiyang (Richard)
--   V1.1 2008-07-17 Changed by chenwei
--        Add hpnicfDot11LoadBalanceTrafficGap and
--        hpnicfDot11LoadBalanceSessionGap to hpnicfDot11LBGlobalGroup.
--   V1.2 2010-02-22 Changed by Wang Chunsheng
--        Add new table of hpnicfDot11LBRadioGroupTable for hpnicfDot11LoadBalance.
--        2010-06-02 Changed by Yin Junjie
--        Add new node hpnicfDot11LBTrafficThresKbps and
--        hpnicfDot11LBTrafficGapKbps to hpnicfDot11LBGlobalGroup.
-- =============================================================================
HPN-ICF-DOT11-CFGEXT-MIB DEFINITIONS ::= BEGIN

IMPORTS
        TruthValue,
        RowStatus
    FROM SNMPv2-TC
        MODULE-IDENTITY,
        OBJECT-TYPE,
        Integer32,
        Unsigned32
    FROM SNMPv2-SMI
        hpnicfDot11
    FROM HPN-ICF-DOT11-REF-MIB;

hpnicfDot11CFGEXT MODULE-IDENTITY
    LAST-UPDATED "201006021400Z"        -- Jun 02, 2010 at 14:00 GMT
    ORGANIZATION
        ""
    CONTACT-INFO
        ""
    DESCRIPTION
        "This MIB provides information for WLAN configuration extended.
        The HPN-ICF-DOT11-CFG-MIB define MIB objects for WLAN basic configuration,
        while this MIB will define MIB objects for load balance these kinds
        feature.

        GLOSSARY

        IEEE 802.11
        Standard to encourage interoperability among
        wireless networking equipment.

        Access point (AP)
        Transmitter/receiver (transceiver) device
        that commonly connects and transports data
        between a wireless network and a wired network.

        Access control (AC)
        To control and manage multi-APs, it will bridge
        wireless and wired network.

        Fat AP
        Applied in the home, SOHO and so on, and it could
        work independently without help from AC.

        Fit AP
        Applied in the enterprise environment, it will work
        under the control and management from AC.

        Control And Provisioning of Wireless Access Points Protocol
        The short name of protocol is CAPWAP. AC will control
        and manage AP by CAPWAP tunnel protocol defined by IETF.
        Also, a data tunnel will be set up between AC and AP.

        BSS
        IEEE 802.11 Basic Service Set (Radio Cell).  The
        BSS of an AP comprises of the stations directly
        associating with the AP.

        Radio
        The chip set to receive and send wireless signal.

        Association
        The service used to establish access point
        or station mapping and enable station invocation
        of the distribution system services.
        (Wireless clients attempt to connect to
        access points.)

        Basic Rate
        A data rate that is mandatory for client
        devices to support in order for them to achieve
        successful association.

        MSDU
        MAC Service Data Unit, it is frame format defined by
        802.11.

        TU
        It is 1,024 microseconds (ms), which is about 1
        millisecond.

        AKM
        The authentication and key management method defined by
        802.11i, and which includes 802.1x and pre-shared key."

    REVISION "201006021400Z"        -- Jun 02, 2010 at 14:00 GMT
    DESCRIPTION
        "Modified to add new nodes."
    REVISION "200704252000Z"        -- Apr. 25, 2007 at 20:00 GMT
    DESCRIPTION
        "The initial revision of this MIB module."
    ::= { hpnicfDot11 6 }

-- *****************************************************************************
-- *  Major sections
-- *****************************************************************************
--  Load Balancing Group
--  DEFINED AS "The group to provide the configuration information
--  for load balancing feature.
hpnicfDot11LoadBalance OBJECT IDENTIFIER   ::= { hpnicfDot11CFGEXT 1 }
hpnicfDot11LBGlobalGroup OBJECT IDENTIFIER ::= { hpnicfDot11LoadBalance 1 }

-- *****************************************************************************
-- *  hpnicfDot11LBGlobalGroup Definition
-- *****************************************************************************
hpnicfDot11LoadBalanceTrafficEnable OBJECT-TYPE
    SYNTAX      TruthValue
    MAX-ACCESS  read-write
    STATUS      current
    DESCRIPTION
        "Represents whether enable load balancing according to station
        traffic."
    ::= { hpnicfDot11LBGlobalGroup 1 }

hpnicfDot11LoadBalanceTrafficThres OBJECT-TYPE
    SYNTAX      Integer32
    MAX-ACCESS  read-write
    STATUS      current
    DESCRIPTION
        "Represents the threshold value for Traffic based load balancing."
    ::= { hpnicfDot11LBGlobalGroup 2 }

hpnicfDot11LoadBalanceSessionEnable OBJECT-TYPE
    SYNTAX      TruthValue
    MAX-ACCESS  read-write
    STATUS      current
    DESCRIPTION
        "Represents whether enable load balancing according to station
        session number."
    ::= { hpnicfDot11LBGlobalGroup 3 }

hpnicfDot11LoadBalanceSessionThres OBJECT-TYPE
    SYNTAX      Integer32
    MAX-ACCESS  read-write
    STATUS      current
    DESCRIPTION
        "Represents the threshold value for session number based
        load balancing."
    ::= { hpnicfDot11LBGlobalGroup 4 }

hpnicfDot11LoadBalanceTrafficGap OBJECT-TYPE
    SYNTAX      Integer32 (10..40)
    MAX-ACCESS  read-write
    STATUS      current
    DESCRIPTION
        "Traffic gap threshold.  Load balancing is carried out for a radio
        when the traffic threshold and session gap are exceeded."
    DEFVAL { 20 }
    ::= { hpnicfDot11LBGlobalGroup 5 }

hpnicfDot11LoadBalanceSessionGap OBJECT-TYPE
    SYNTAX      Integer32 (1..8)
    MAX-ACCESS  read-write
    STATUS      current
    DESCRIPTION
        "Session gap threshold.  Load balancing is carried out for a radio
        when the session threshold and session gap are exceeded."
    DEFVAL { 4 }
    ::= { hpnicfDot11LBGlobalGroup 6 }

hpnicfDot11LBTrafficThresKbps OBJECT-TYPE
    SYNTAX      Integer32
    UNITS       "kbps"
    MAX-ACCESS  read-write
    STATUS      current
    DESCRIPTION
        "Represents the threshold value for Traffic based load balancing."
    ::= { hpnicfDot11LBGlobalGroup 7 }

hpnicfDot11LBTrafficGapKbps OBJECT-TYPE
    SYNTAX      Integer32
    UNITS       "kbps"
    MAX-ACCESS  read-write
    STATUS      current
    DESCRIPTION
        "Traffic gap threshold. Load balancing is carried out for a radio
        when the traffic threshold gap are exceeded."
    ::= { hpnicfDot11LBGlobalGroup 8 }

-- *****************************************************************************
-- *  End of hpnicfDot11LBGlobalGroup Definition
-- *****************************************************************************

-- *****************************************************************************
-- *  hpnicfDot11LBRadioGroup Definition
-- *****************************************************************************
hpnicfDot11LBRadioGroupTable OBJECT-TYPE
    SYNTAX SEQUENCE OF HpnicfDot11LBRadioGroupEntry
    MAX-ACCESS not-accessible
    STATUS current
    DESCRIPTION
        "This table defines load balance radio group."
    ::= { hpnicfDot11LoadBalance 2 }

hpnicfDot11LBRadioGroupEntry OBJECT-TYPE
    SYNTAX      HpnicfDot11LBRadioGroupEntry
    MAX-ACCESS  not-accessible
    STATUS      current
    DESCRIPTION
        "Each entry contains information of one load balance radio group."
    INDEX
        {
            hpnicfDot11LBRadioGroupId
        }
    ::= { hpnicfDot11LBRadioGroupTable 1 }

HpnicfDot11LBRadioGroupEntry ::= SEQUENCE
    {
        hpnicfDot11LBRadioGroupId        Unsigned32,
        hpnicfDot11LBRadioGroupDesc      OCTET STRING,
        hpnicfDot11LBRadioGroupRowStatus RowStatus
    }

hpnicfDot11LBRadioGroupId OBJECT-TYPE
    SYNTAX      Unsigned32
    MAX-ACCESS  not-accessible
    STATUS      current
    DESCRIPTION
        "Represents load balance radio group ID."
    ::= { hpnicfDot11LBRadioGroupEntry 1 }

hpnicfDot11LBRadioGroupDesc OBJECT-TYPE
    SYNTAX      OCTET STRING
    MAX-ACCESS  read-create
    STATUS      current
    DESCRIPTION
        "Represents the description of load balance radio group."
    ::= { hpnicfDot11LBRadioGroupEntry 2 }

hpnicfDot11LBRadioGroupRowStatus OBJECT-TYPE
    SYNTAX      RowStatus
    MAX-ACCESS  read-create
    STATUS      current
    DESCRIPTION
        "The row status of this table entry."
    ::= { hpnicfDot11LBRadioGroupEntry 3 }

-- *****************************************************************************
-- *  End of hpnicfDot11LBRadioGroup Definition
-- *****************************************************************************

END
