-- ==========================================================================
-- Copyright (c) 2010-2013 Hewlett-Packard Development Company, L.P.
--
-- Description: The purpose of this MIB file is to provide the definition of
--              the voice interface general configuration.
-- Reference:
-- Version: V1.0
-- History:
-- V1.0 2007-12-10 Initial version, created by Qu Pingping
-- ==========================================================================
HPN-ICF-VOICE-IF-MIB DEFINITIONS ::= BEGIN

IMPORTS
        OBJECT-TYPE, MODULE-IDENTITY, Integer32
    FROM SNMPv2-SMI
        DisplayString
    FROM SNMPv2-TC
        ifIndex
    FROM IF-MIB
        hpnicfVoice
    FROM HPN-ICF-OID-MIB;

hpnicfVoiceInterface MODULE-IDENTITY
    LAST-UPDATED "200712101700Z"
    ORGANIZATION
        ""
    CONTACT-INFO
        ""
    DESCRIPTION
        "This MIB file is to provide the definition of the voice
        interface general configuration."
    REVISION "200712101700Z"
    DESCRIPTION
        "The initial version of this MIB file."
    ::= { hpnicfVoice 13 }

hpnicfVoiceIfObjects OBJECT IDENTIFIER ::= { hpnicfVoiceInterface 1 }

--===========================================================================
--                            hpnicfVoiceIfConfigTable
--
--===========================================================================
hpnicfVoiceIfConfigTable OBJECT-TYPE
    SYNTAX      SEQUENCE OF HPN-ICFVoiceIfConfigEntry
    MAX-ACCESS  not-accessible
    STATUS      current
    DESCRIPTION
        "The table contains configurable parameters for both analog
        voice interface and digital voice interface."
    ::= { hpnicfVoiceIfObjects 1 }

hpnicfVoiceIfConfigEntry OBJECT-TYPE
    SYNTAX      HPN-ICFVoiceIfConfigEntry
    MAX-ACCESS  not-accessible
    STATUS      current
    DESCRIPTION
        "The entry of voice interface table."
    INDEX
        {
            ifIndex
        }
    ::= { hpnicfVoiceIfConfigTable 1 }

HPN-ICFVoiceIfConfigEntry ::= SEQUENCE
    {
        hpnicfVoiceIfCfgCngOn                INTEGER,
        hpnicfVoiceIfCfgNonLinearSwitch      INTEGER,
        hpnicfVoiceIfCfgInputGain            Integer32,
        hpnicfVoiceIfCfgOutputGain           Integer32,
        hpnicfVoiceIfCfgEchoCancelSwitch     INTEGER,
        hpnicfVoiceIfCfgEchoCancelDelay      Integer32,
        hpnicfVoiceIfCfgTimerDialInterval    Integer32,
        hpnicfVoiceIfCfgTimerFirstDial       Integer32,
        hpnicfVoiceIfCfgPrivateline          DisplayString,
        hpnicfVoiceIfCfgRegTone              OCTET STRING
    }

hpnicfVoiceIfCfgCngOn OBJECT-TYPE
    SYNTAX      INTEGER
        {
            enable(1),
            disable(2)
        }
    MAX-ACCESS  read-write
    STATUS      current
    DESCRIPTION
        "This object indicates whether the silence gaps should be
        filled with background noise. It is applicable to FXO, FXS,
        E&M subscriber lines and E1/T1 voice subscriber line."
    DEFVAL { enable }
    ::= { hpnicfVoiceIfConfigEntry 1 }

hpnicfVoiceIfCfgNonLinearSwitch OBJECT-TYPE
    SYNTAX      INTEGER
        {
            enable(1),
            disable(2)
        }
    MAX-ACCESS  read-write
    STATUS      current
    DESCRIPTION
        "This object expresses the nonlinear processing is enable
        or disable for the voice interface. It is applicable to FXO,
        FXS, E&M subscriber lines and E1/T1 voice subscriber line.
        Currently, only digital voice subscriber lines can be set
        disabled."
    DEFVAL { enable }
    ::= { hpnicfVoiceIfConfigEntry 2 }

hpnicfVoiceIfCfgInputGain OBJECT-TYPE
    SYNTAX      Integer32(-140..139)
    MAX-ACCESS  read-write
    STATUS      current
    DESCRIPTION
        "This object indicates the amount of gain added to the receiver
        side of the voice interface. Unit is 0.1 db. It is applicable to
        FXO, FXS, E&M subscriber lines and E1/T1 voice subscriber line."
    DEFVAL { 0 }
    ::= { hpnicfVoiceIfConfigEntry 3 }

hpnicfVoiceIfCfgOutputGain OBJECT-TYPE
    SYNTAX      Integer32(-140..139)
    MAX-ACCESS  read-write
    STATUS      current
    DESCRIPTION
        "This object indicates the amount of gain added to the send side
        of the voice interface. Unit is 0.1 db. It is applicable to FXO,
        FXS, E&M subscriber lines and E1/T1 voice subscriber line."
    DEFVAL { 0 }
    ::= { hpnicfVoiceIfConfigEntry 4 }

hpnicfVoiceIfCfgEchoCancelSwitch OBJECT-TYPE
    SYNTAX      INTEGER
        {
            enable(1),
            disable(2)
        }
    MAX-ACCESS  read-write
    STATUS      current
    DESCRIPTION
        "This object indicates whether the echo cancellation is enabled.
        It is applicable to FXO, FXS, E&M subscriber lines and E1/T1 voice
        subscriber line."
    DEFVAL { enable }
    ::= { hpnicfVoiceIfConfigEntry 5 }

hpnicfVoiceIfCfgEchoCancelDelay OBJECT-TYPE
    SYNTAX      Integer32(0..64)
    MAX-ACCESS  read-write
    STATUS      current
    DESCRIPTION
        "This object indicates the delay of the echo cancellation for
        the voice interface. This value couldn't be modified unless
        hpnicfVoiceIfCfgEchoCancelSwitch is enable. Unit is milliseconds.
        It is applicable to FXO, FXS, E&M subscriber lines and E1/T1
        voice subscriber line. The default value of this object is 32."
    ::= { hpnicfVoiceIfConfigEntry 6 }

hpnicfVoiceIfCfgTimerDialInterval OBJECT-TYPE
    SYNTAX      Integer32(1..300)
    MAX-ACCESS  read-write
    STATUS      current
    DESCRIPTION
        "The interval, in seconds, between two dialing numbers.
        The default value of this object is 10 seconds. It is
        applicable to FXO, FXS, E&M subscriber lines and E1/T1 with
        loop-start or ground-start protocol voice subscriber line."
    ::= { hpnicfVoiceIfConfigEntry 7 }

hpnicfVoiceIfCfgTimerFirstDial OBJECT-TYPE
    SYNTAX      Integer32(1..300)
    MAX-ACCESS  read-write
    STATUS      current
    DESCRIPTION
        "The period of time, in seconds, before dialing the first
        number. The default value of this object is 10 seconds. It
        is applicable to FXO, FXS subscriber lines and E1/T1 with
        loop-start or ground-start protocol voice subscriber line."
    ::= { hpnicfVoiceIfConfigEntry 8 }

hpnicfVoiceIfCfgPrivateline OBJECT-TYPE
    SYNTAX      DisplayString(SIZE(0..31))
    MAX-ACCESS  read-write
    STATUS      current
    DESCRIPTION
        "This object indicates the E.164 phone number for plar mode.
        It is applicable to FXO, FXS, E&M subscriber lines and E1/T1
        voice subscriber line."
    ::= { hpnicfVoiceIfConfigEntry 9 }

hpnicfVoiceIfCfgRegTone OBJECT-TYPE
    SYNTAX      OCTET STRING(SIZE(0|2..3))
    MAX-ACCESS  read-write
    STATUS      current
    DESCRIPTION
        "This object uses 2 or 3 letter country code specify voice
        parameters of different countrys. This value will take effect
        on all voice interfaces of all cards on the device."
    ::= { hpnicfVoiceIfConfigEntry 10 }

END
