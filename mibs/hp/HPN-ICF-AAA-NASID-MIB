-- ==========================================================================
-- Copyright (c) 2010-2013 Hewlett-Packard Development Company, L.P.
--
-- Description: AAA Nas-id mib
-- Reference:
-- Version: V1.0
-- History:
--   V1.0 2011-03-09 created by wangbin
-- ==========================================================================
HPN-ICF-AAA-NASID-MIB DEFINITIONS ::= BEGIN

IMPORTS
    MODULE-IDENTITY, OBJECT-TYPE
        FROM SNMPv2-SMI
    hpnicfCommon
        FROM HPN-ICF-OID-MIB;

hpnicfAAANasId MODULE-IDENTITY
    LAST-UPDATED "201103090945Z"
    ORGANIZATION
        ""
    CONTACT-INFO
        ""
    DESCRIPTION
        "This MIB contains objects to
        manage configuration for AAA Nas-id feature.
        AAA presents authentication, authorization and accouting.
        NAS acts as the Network Access Server.
        Nas-id is an identifier that contains some strings identifying the NAS."
    REVISION "201103090945Z"
    DESCRIPTION
        "Initial version."
    ::= { hpnicfCommon 114 }

hpnicfAAANasIdObjects OBJECT IDENTIFIER ::= { hpnicfAAANasId 1 }

-- ==========================================================================
-- hpnicfAAANasIdTable OBJECT
-- ==========================================================================
hpnicfAAANasIdTable OBJECT-TYPE
    SYNTAX SEQUENCE OF HpnicfAAANasIdEntry
    MAX-ACCESS not-accessible
    STATUS current
    DESCRIPTION
    "The AAA Nas-id table."
::= { hpnicfAAANasIdObjects 1 }

hpnicfAAANasIdEntry OBJECT-TYPE
    SYNTAX HpnicfAAANasIdEntry
    MAX-ACCESS not-accessible
    STATUS current
    DESCRIPTION
    "The AAA Nas-id entry."
    INDEX { hpnicfAAANasIdName }
::= { hpnicfAAANasIdTable 1 }

HpnicfAAANasIdEntry ::= SEQUENCE {
    hpnicfAAANasIdName             OCTET STRING }

hpnicfAAANasIdName OBJECT-TYPE
    SYNTAX      OCTET STRING (SIZE(1..64))
    MAX-ACCESS  read-only
    STATUS      current
    DESCRIPTION
    "The Nas-id name."
::= { hpnicfAAANasIdEntry 1 }

END
