-- ====================================================================
-- Copyright (c) 2010-2013 Hewlett-Packard Development Company, L.P.
--
-- Description: IPv4 address MIB
-- Reference:
-- Version: V1.5
-- History:
--   V1.0 2005-11-22 Created by Wang Hui and Liu Jinguang
--        Initial version
--   V1.1 2006-03-16 Modify by Yu Hongqiang
--        Modify the description of some objects.
--   V1.2 2007-12-18 Modify by Zhangyinfei
--        Add enmu 'vrrp' for hpnicfIpAddrReadSourceType and hpnicfIpAddrReadCatalog
--   V1.3 2009-8-11 Modify by lifei
--        Add ip address change notify trap
--   V1.4 2010-03-06 Modify by Jianzhuang Ge
--        Add ipv4 address management table hpnicfIpv4AddrTable
--   V1.5 2011-11-28 Modify by zhangshuai
--        Add hpnicfIpAddrFirstTrapTime
-- ====================================================================
HPN-ICF-IP-ADDRESS-MIB DEFINITIONS ::= BEGIN

    IMPORTS
        hpnicfCommon
            FROM HPN-ICF-OID-MIB
        Integer32, IpAddress, OBJECT-TYPE, MODULE-IDENTITY, NOTIFICATION-TYPE,
        TimeTicks
            FROM SNMPv2-SMI
        RowStatus
            FROM SNMPv2-TC
        InetAddressType,InetAddress
            FROM INET-ADDRESS-MIB
        ifIndex
            FROM IF-MIB;

    hpnicfIpAddrMIB MODULE-IDENTITY
        LAST-UPDATED "200511220000Z"
        ORGANIZATION
            ""
        CONTACT-INFO
            ""
        DESCRIPTION
            "The MIB module for managing IPv4 address."
        REVISION "200511220000Z"
        DESCRIPTION
            "The initial revision of this MIB module."
        ::= { hpnicfCommon 67 }


--
-- Node definitions
--
    hpnicfIpAddressObjects OBJECT IDENTIFIER ::= { hpnicfIpAddrMIB 1 }

    hpnicfIpAddressConfig OBJECT IDENTIFIER ::= { hpnicfIpAddressObjects 1 }

    hpnicfIpAddrSetTable OBJECT-TYPE
        SYNTAX SEQUENCE OF HpnicfIpAddrSetEntry
        MAX-ACCESS not-accessible
        STATUS current
        DESCRIPTION
            "The table of address information is relevant to this
            entity's IPv4 addresses for setting. The address information
            that can be read and set in this table is a subset of the
            address information that can be read in hpnicfIpAddrReadTable
            and ipAddrTable in IP-MIB. This table is used to configure IPv4
            addresses of an interface identified by hpnicfIpAddrSetIfIndex.
            When users create or delete an entry in this table, the agent also
            increases or reduces a corresponding entry in the
            hpnicfIpAddrReadTable and ipAddrTable in IP-MIB.
            When an interface which has been assigned IPv6 address is deleted,
            the agent also deletes the entry corresponding to the interface
            in this table and hpnicfIpAddrReadTable.
            All IPv4 addresses in this table will also show in ipAddrTable in
            IP-MIB.
            "
        REFERENCE
            "RFC 2011"
        ::= { hpnicfIpAddressConfig 1 }

    hpnicfIpAddrSetEntry OBJECT-TYPE
        SYNTAX HpnicfIpAddrSetEntry
        MAX-ACCESS not-accessible
        STATUS current
        DESCRIPTION
            "Define the IPv4 address information.
            "
        INDEX { hpnicfIpAddrSetIfIndex, hpnicfIpAddrSetAddrType, hpnicfIpAddrSetAddr }
        ::= { hpnicfIpAddrSetTable 1 }

    HpnicfIpAddrSetEntry ::=
        SEQUENCE
        {
            hpnicfIpAddrSetIfIndex
                Integer32,
            hpnicfIpAddrSetAddrType
                InetAddressType,
            hpnicfIpAddrSetAddr
                InetAddress,
            hpnicfIpAddrSetMask
                IpAddress,
            hpnicfIpAddrSetSourceType
                INTEGER,
            hpnicfIpAddrSetCatalog
                INTEGER,
            hpnicfIpAddrSetRowStatus
                RowStatus
        }

    hpnicfIpAddrSetIfIndex OBJECT-TYPE
        SYNTAX Integer32 (1..2147483647)
        MAX-ACCESS not-accessible
        STATUS current
        DESCRIPTION
            "The index value which uniquely identifies the interface to
            which this entry is applicable. The interface identified by
            a particular value of this index is the same interface as
            identified by the same value of RFC 1573's ifIndex.
            "
        ::= { hpnicfIpAddrSetEntry 1 }

    hpnicfIpAddrSetAddrType OBJECT-TYPE
        SYNTAX InetAddressType
        MAX-ACCESS not-accessible
        STATUS current
        DESCRIPTION
            "The IP address type to which this entry's address information
            pertains. The value must be ipv4.
            "
        ::= { hpnicfIpAddrSetEntry 2 }

    hpnicfIpAddrSetAddr OBJECT-TYPE
        SYNTAX InetAddress
        MAX-ACCESS not-accessible
        STATUS current
        DESCRIPTION
            "The IPv4 address to which this entry's address information
            pertains.
            "
        ::= { hpnicfIpAddrSetEntry 3 }

    hpnicfIpAddrSetMask OBJECT-TYPE
        SYNTAX IpAddress
        MAX-ACCESS read-create
        STATUS current
        DESCRIPTION
            "The subnet mask associated with the IPv4 address of this
            entry. The value of the mask is an IPv4 address with all the
            network bits set to 1 and all the hosts bits set to 0.
            "
        ::= { hpnicfIpAddrSetEntry 4 }

    hpnicfIpAddrSetSourceType OBJECT-TYPE
        SYNTAX INTEGER
        {
            assignedIp(1)
        }
        MAX-ACCESS read-create
        STATUS current
        DESCRIPTION
            "Indicate the type of source of the IPv4 address."
        DEFVAL { assignedIp }
        ::= { hpnicfIpAddrSetEntry 5 }

    hpnicfIpAddrSetCatalog OBJECT-TYPE
        SYNTAX INTEGER
        {
            primary(1),
            sub(2)
        }
        MAX-ACCESS read-create
        STATUS current
        DESCRIPTION
            "Indicate the category of the IPv4 address."
        DEFVAL { primary }
        ::= { hpnicfIpAddrSetEntry 6 }

    hpnicfIpAddrSetRowStatus OBJECT-TYPE
        SYNTAX RowStatus
        MAX-ACCESS read-create
        STATUS current
        DESCRIPTION
            "This object is used to create a new row or delete an
            existing row in this table, only support active,
            createAndGo and destroy.
            "
        ::= { hpnicfIpAddrSetEntry 7 }

    hpnicfIpAddrReadTable OBJECT-TYPE
        SYNTAX SEQUENCE OF HpnicfIpAddrReadEntry
        MAX-ACCESS not-accessible
        STATUS current
        DESCRIPTION
            "The table of address information is relevant to this
            entity's IP addresses for reading. This is the extension
            of the ipAddrTable in IP-MIB.
            All IPv4 addresses in this table will also show in ipAddrTable
            in IP-MIB.
            "
        REFERENCE
            "RFC 2011"
        ::= { hpnicfIpAddressConfig 2 }

    hpnicfIpAddrReadEntry OBJECT-TYPE
        SYNTAX HpnicfIpAddrReadEntry
        MAX-ACCESS not-accessible
        STATUS current
        DESCRIPTION
            "Define the IPv4 address information.
            "
        INDEX { hpnicfIpAddrReadIfIndex, hpnicfIpAddrReadAddrType, hpnicfIpAddrReadAddr }
        ::= { hpnicfIpAddrReadTable 1 }

    HpnicfIpAddrReadEntry ::=
        SEQUENCE
        {
            hpnicfIpAddrReadIfIndex
                Integer32,
            hpnicfIpAddrReadAddrType
                InetAddressType,
            hpnicfIpAddrReadAddr
                InetAddress,
            hpnicfIpAddrReadMask
                IpAddress,
            hpnicfIpAddrReadSourceType
                INTEGER,
            hpnicfIpAddrReadCatalog
                INTEGER
        }

    hpnicfIpAddrReadIfIndex OBJECT-TYPE
        SYNTAX Integer32 (1..2147483647)
        MAX-ACCESS not-accessible
        STATUS current
        DESCRIPTION
            "The index value which uniquely identifies the interface to
            which this entry is applicable. The interface identified by
            a particular value of this index is the same interface as
            identified by the same value of RFC 1573's ifIndex.
            "
        ::= { hpnicfIpAddrReadEntry 1 }

    hpnicfIpAddrReadAddrType OBJECT-TYPE
        SYNTAX InetAddressType
        MAX-ACCESS not-accessible
        STATUS current
        DESCRIPTION
            "The IP address type to which this entry's address information
            pertains. The value must be ipv4.
            "
        ::= { hpnicfIpAddrReadEntry 2 }

    hpnicfIpAddrReadAddr OBJECT-TYPE
        SYNTAX InetAddress
        MAX-ACCESS not-accessible
        STATUS current
        DESCRIPTION
            "The IPv4 address to which this entry's address information
            pertains.
            "
        ::= { hpnicfIpAddrReadEntry 3 }

    hpnicfIpAddrReadMask OBJECT-TYPE
        SYNTAX IpAddress
        MAX-ACCESS read-only
        STATUS current
        DESCRIPTION
            "The subnet mask associated with the IPv4 address of this
            entry. The value of the mask is an IPv4 address with all the
            network bits set to 1 and all the hosts bits set to 0.
            "
        ::= { hpnicfIpAddrReadEntry 4 }

    hpnicfIpAddrReadSourceType OBJECT-TYPE
        SYNTAX INTEGER
        {
            assignedIp(1),
            cluster(2),
            dhcp(3),
            bootp(4),
            negotiate(5),
            unnumbered(6),
            vrrp(7)
        }
        MAX-ACCESS read-only
        STATUS current
        DESCRIPTION
            "Indicate the type of source of the IPv4 address."
        ::= { hpnicfIpAddrReadEntry 5 }

    hpnicfIpAddrReadCatalog OBJECT-TYPE
        SYNTAX INTEGER
        {
            primary(1),
            sub(2),
            cluster(3),
            vrrp(4)
        }
        MAX-ACCESS read-only
        STATUS current
        DESCRIPTION
            "Indicate the category of the IPv4 address."
        ::= { hpnicfIpAddrReadEntry 6 }

    hpnicfIpv4AddrTable OBJECT-TYPE
        SYNTAX SEQUENCE OF HpnicfIpv4AddrEntry
        MAX-ACCESS not-accessible
        STATUS current
        DESCRIPTION
            "This table is used to configure primary IPv4 address of an
             interface identified by ifIndex."
        ::= { hpnicfIpAddressConfig 3 }

    hpnicfIpv4AddrEntry OBJECT-TYPE
        SYNTAX HpnicfIpv4AddrEntry
        MAX-ACCESS not-accessible
        STATUS current
        DESCRIPTION
            "Define the IPv4 address information.
            "
        INDEX { ifIndex }
        ::= { hpnicfIpv4AddrTable 1 }

    HpnicfIpv4AddrEntry ::=
        SEQUENCE
        {
            hpnicfIpv4AddrAddr
                IpAddress,
            hpnicfIpv4AddrMask
                IpAddress,
            hpnicfIpv4AddrRowStatus
                RowStatus
        }

    hpnicfIpv4AddrAddr OBJECT-TYPE
        SYNTAX IpAddress
        MAX-ACCESS read-create
        STATUS current
        DESCRIPTION
            "The IPv4 address to which this entry's address information
            pertains.
            "
        ::= { hpnicfIpv4AddrEntry 1 }

    hpnicfIpv4AddrMask OBJECT-TYPE
        SYNTAX IpAddress
        MAX-ACCESS read-create
        STATUS current
        DESCRIPTION
            "The subnet mask associated with the IPv4 address of this
            entry.  The value of the mask is an IPv4 address with all the
            network bits set to 1 and all the hosts bits set to 0.
            "
        ::= { hpnicfIpv4AddrEntry 2 }

    hpnicfIpv4AddrRowStatus OBJECT-TYPE
        SYNTAX RowStatus
        MAX-ACCESS read-create
        STATUS current
        DESCRIPTION
            "This object is used to create a new row or delete an
            existing row in this table, only support active,
            notInService, createAndGo and destroy.
            "
        ::= { hpnicfIpv4AddrEntry 3 }

--
-- Define the IP Address Traps.
--

hpnicfIpAddrNotify OBJECT IDENTIFIER ::= { hpnicfIpAddrMIB 2 }

-- Scalar Objects for Notify
hpnicfIpAddrNotifyScalarObjects OBJECT IDENTIFIER ::= { hpnicfIpAddrNotify 1 }

hpnicfIpAddrNotifyIfIndex OBJECT-TYPE
    SYNTAX      Integer32 (1..2147483647)
    MAX-ACCESS  accessible-for-notify
    STATUS      current
    DESCRIPTION
        "The IP address IfIndex of specified interface on the device."
    ::= { hpnicfIpAddrNotifyScalarObjects 1 }

hpnicfIpAddrOldIpAddress OBJECT-TYPE
    SYNTAX      InetAddress
    MAX-ACCESS  accessible-for-notify
    STATUS      current
    DESCRIPTION
        "The Old IP address of specified interface on the device."
    ::= { hpnicfIpAddrNotifyScalarObjects 2 }

hpnicfIpAddrNewIpAddress OBJECT-TYPE
    SYNTAX      InetAddress
    MAX-ACCESS  accessible-for-notify
    STATUS      current
    DESCRIPTION
        "The New IP address of specified interface on the device."
    ::= { hpnicfIpAddrNotifyScalarObjects 3 }

hpnicfIpAddrFirstTrapTime OBJECT-TYPE
    SYNTAX      TimeTicks
    MAX-ACCESS  accessible-for-notify
    STATUS      current
    DESCRIPTION
        "Represents the first trap time."
    ::= { hpnicfIpAddrNotifyScalarObjects 4 }


-- Notification Objects
hpnicfIpAddrNotifyObjects OBJECT IDENTIFIER ::= { hpnicfIpAddrNotify 2 }

hpnicfIpAddrNotifyObjectsPrefix OBJECT IDENTIFIER ::= { hpnicfIpAddrNotifyObjects 0 }

hpnicfIpAddressChangeNotify NOTIFICATION-TYPE
    OBJECTS
        {
            hpnicfIpAddrNotifyIfIndex,
            hpnicfIpAddrOldIpAddress,
            hpnicfIpAddrNewIpAddress,
            hpnicfIpAddrFirstTrapTime
         }
    STATUS      current
    DESCRIPTION
        "This notification will be generated when the IP address of interface
        is changed.  The change maybe originate from NMS, DHCP server or
        administrator.

        This notification announces useful IP address change.  So it
        is triggered by significative IP address change."

    ::= { hpnicfIpAddrNotifyObjectsPrefix 1 }

END
