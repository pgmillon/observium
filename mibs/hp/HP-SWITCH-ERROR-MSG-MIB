-- Hp Switch Error Message MIB

HP-SWITCH-ERROR-MSG-MIB DEFINITIONS ::= BEGIN

    IMPORTS
        OBJECT-TYPE, MODULE-IDENTITY, Integer32
            FROM SNMPv2-SMI
        DateAndTime
            FROM SNMPv2-TC
        MODULE-COMPLIANCE, OBJECT-GROUP
            FROM SNMPv2-CONF
        hpSwitch
              FROM HP-ICF-OID;

hpSwitchErrorMsgMIB MODULE-IDENTITY
      LAST-UPDATED "200904060000Z"
      ORGANIZATION "HP Networking"
      CONTACT-INFO "Hewlett Packard Company
                    8000 Foothills Blvd.
                    Roseville, CA 95747"
      DESCRIPTION "This MIB module is for the Switch Error Messages
                   reporting with SNMP"
      REVISION    "200904060000Z"
      DESCRIPTION "First Revision"
      ::= { hpSwitch 68 }

--##################################################################
-- The HP Switch Error Message Tables
--
-- The tables contain the descriptive error messages for recent
-- failed management operations.  When a management station receives
-- a "Bad value" or other terse response, it may read this MIB to obtain
-- a more descriptive message about the error. In some cases this message
-- will include information about what the administrator should do to
-- remediate the problem.
-- This table contains 10 application entries with 10 error message
-- entries for each application. This table holds maximum 100 error 
-- message entries"
--##################################################################

hpSwitchErrorMsgObjects OBJECT IDENTIFIER ::= {hpSwitchErrorMsgMIB 1 }

hpSwitchErrorMsgTable OBJECT-TYPE
      SYNTAX       SEQUENCE OF HpSwitchErrorMsgEntry
      MAX-ACCESS   not-accessible
      STATUS       current
      DESCRIPTION  "This table contains the error status of the most recent 
                    SNMP operation for each of the management entities.
                    This table contains 10 application entries with 10 error
                    message entries for each application. This table holds
                    maximum 100 error message entries"
::= { hpSwitchErrorMsgObjects 1 }

hpSwitchErrorMsgEntry OBJECT-TYPE
      SYNTAX       HpSwitchErrorMsgEntry
      MAX-ACCESS   not-accessible
      STATUS       current
      DESCRIPTION  "An entry contains the information on the 
                   handle of the entity and the corresponding error
                   messages indexed with the SNMP sequence code."
      INDEX        { hpSwitchErrorEntityType,
                     hpSwitchErrorEntityHandle,
                     hpSwitchErrorSnmpSeqCode
                   }
      ::= { hpSwitchErrorMsgTable 1 }

HpSwitchErrorMsgEntry ::=
      SEQUENCE {
         hpSwitchErrorEntityType             INTEGER,
         hpSwitchErrorEntityHandle           OCTET STRING,
         hpSwitchErrorSnmpSeqCode            Integer32,
         hpSwitchErrorTime                   DateAndTime,
         hpSwitchErrorFailedOID              OBJECT IDENTIFIER,
         hpSwitchEntityErrorMsg              OCTET STRING,
         hpSwitchSnmpErrorCode               Integer32
        }

hpSwitchErrorEntityType OBJECT-TYPE
      SYNTAX      INTEGER {
                      others(1), 
                      cliSession(2),
                      webSession(3),
                      ipV4Address(4),
                      ipV6Address(5),
                      oaApplication(6) -- Open Architecture
                  }
      MAX-ACCESS  not-accessible
      STATUS      current
      DESCRIPTION "The management entity from which a SNMP request arrives.
                   For the CLI application the value will be (2).
                   The value will be (3) if the request is from a web 
                   application. If the management entity is a Net Management
                   application the value will be either (4) or (5) depending
                   on whether they are carrying an IPv4 or an IPv6 address.
                   For the OA (Open Architecture application the value
                   will be (6)."
      ::= { hpSwitchErrorMsgEntry 1 }

hpSwitchErrorEntityHandle OBJECT-TYPE
      SYNTAX       OCTET STRING (SIZE (0..96))
      MAX-ACCESS   not-accessible
      STATUS       current
      DESCRIPTION "The handle corresponding to the application performing 
                   the SNMP operation. The handle will denote an IP Address,
                   if the application is a Net management application. Or it
                   will be the session id of the CLI, WEB or the OA application"
      ::= { hpSwitchErrorMsgEntry 2 }

hpSwitchErrorSnmpSeqCode OBJECT-TYPE
      SYNTAX       Integer32 (0..2147483647)
      MAX-ACCESS   not-accessible
      STATUS       current
      DESCRIPTION  "This denotes the SNMP sequence code sent by the requester."
      ::= { hpSwitchErrorMsgEntry 3 }

hpSwitchErrorTime OBJECT-TYPE
      SYNTAX       DateAndTime 
      MAX-ACCESS   read-only
      STATUS       current
      DESCRIPTION  "This denotes the Date and Time when the SNMP set `request
                    processing has failed."
      ::= { hpSwitchErrorMsgEntry 4 }

hpSwitchErrorFailedOID OBJECT-TYPE
      SYNTAX       OBJECT IDENTIFIER 
      MAX-ACCESS   read-only
      STATUS       current
      DESCRIPTION  "This denotes the OID of the SNMP Object for which
                    the SNMP set request processing has failed." 
      ::= { hpSwitchErrorMsgEntry 5 }

hpSwitchEntityErrorMsg OBJECT-TYPE
      SYNTAX       OCTET STRING
      MAX-ACCESS   read-only
      STATUS       current
      DESCRIPTION  "An error message having descriptive information about 
                    the error for the failed SNMP set request."
      ::= { hpSwitchErrorMsgEntry 6 }

hpSwitchSnmpErrorCode OBJECT-TYPE
      SYNTAX       Integer32 (0..18)
      MAX-ACCESS   read-only
      STATUS       current
      DESCRIPTION  "The SNMP error code which is retuned when the SNMP set
                    request failed."
      ::= { hpSwitchErrorMsgEntry 7 }

--
-- Conformance Section
--
hpSwitchErrorMsgMIBConformance OBJECT IDENTIFIER ::=
                                 { hpSwitchErrorMsgMIB 2}
hpSwitchErrorMsgMIBCompliances  OBJECT IDENTIFIER ::=
                                 { hpSwitchErrorMsgMIBConformance 1 }
hpSwitchErrorMsgMIBGroups  OBJECT IDENTIFIER ::=
                                 { hpSwitchErrorMsgMIBConformance 2 }

--
-- Compliance statements
--

hpSwitchErrorMsgMIBCompliance  MODULE-COMPLIANCE
        STATUS      current
        DESCRIPTION "The compliance statement for switch error message entities"
        MODULE       -- this module
        MANDATORY-GROUPS { hpSwitchErrorMsgMIBGroup }

       ::= { hpSwitchErrorMsgMIBCompliances 1 }

hpSwitchErrorMsgMIBGroup OBJECT-GROUP
        OBJECTS     { hpSwitchErrorTime,
                      hpSwitchErrorFailedOID,
                      hpSwitchEntityErrorMsg,
                      hpSwitchSnmpErrorCode
                    }
        STATUS      current
        DESCRIPTION "A collection of objects for switch error message."
        ::= { hpSwitchErrorMsgMIBGroups 1 }

END
