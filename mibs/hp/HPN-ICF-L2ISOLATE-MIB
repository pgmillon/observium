-- =================================================================
-- Copyright (c) 2010-2013 Hewlett-Packard Development Company, L.P.
--
-- Description: This file describes the hpnicf MIB implementation of l2 isolation
-- Reference:
-- Version:     V1.0 Created by y04444 Initial version
-- History:
-- V1.0 Initial version
-- =================================================================
HPN-ICF-L2ISOLATE-MIB DEFINITIONS ::= BEGIN

IMPORTS
    TruthValue,
    MacAddress,
    RowStatus
        FROM SNMPv2-TC
    hpnicfCommon
        FROM HPN-ICF-OID-MIB
    OBJECT-TYPE, MODULE-IDENTITY, Integer32
        FROM SNMPv2-SMI;

hpnicfL2Isolate MODULE-IDENTITY
    LAST-UPDATED "200905060000Z"            -- May 06th, 2009 at 00:00 GMT
    ORGANIZATION
        ""
    CONTACT-INFO
        ""
    DESCRIPTION
        "The MIB module is used for l2 isolation."
    REVISION    "200905060000Z"
    DESCRIPTION
        "Initial version"
    ::= { hpnicfCommon 103 }

hpnicfL2IsolateObject OBJECT IDENTIFIER ::= { hpnicfL2Isolate 1 }

-- =================================================================
--  1st Table of hpnicfL2Isolate: hpnicfL2IsolateEnableTable
-- =================================================================
hpnicfL2IsolateEnableTable OBJECT-TYPE
    SYNTAX      SEQUENCE OF HpnicfL2IsolateEnableEntry
    MAX-ACCESS  not-accessible
    STATUS      current
    DESCRIPTION
        "A table for enabling/disabling layer-2-isolate for VLAN."
    ::= { hpnicfL2IsolateObject 1 }

hpnicfL2IsolateEnableEntry OBJECT-TYPE
    SYNTAX      HpnicfL2IsolateEnableEntry
    MAX-ACCESS  not-accessible
    STATUS      current
    DESCRIPTION
        "An entry for enabling/disabling layer-2-isolate for VLAN."
    INDEX
        {
            hpnicfL2IsolateVLANIndex
        }
    ::= { hpnicfL2IsolateEnableTable 1 }

HpnicfL2IsolateEnableEntry ::= SEQUENCE
    {
        hpnicfL2IsolateVLANIndex        Integer32,
        hpnicfL2IsolateEnable           TruthValue
    }

hpnicfL2IsolateVLANIndex OBJECT-TYPE
    SYNTAX      Integer32 (1..4094)
    MAX-ACCESS  not-accessible
    STATUS      current
    DESCRIPTION
        "Represents index of VLAN for layer-2-isolate."
    ::= { hpnicfL2IsolateEnableEntry 1 }

hpnicfL2IsolateEnable OBJECT-TYPE
    SYNTAX      TruthValue
    MAX-ACCESS  read-write
    STATUS      current
    DESCRIPTION
        "Represents the layer-2-isolate status of VLAN."
    ::= { hpnicfL2IsolateEnableEntry 2 }

-- =================================================================
--   2nd Table of hpnicfL2Isolate: hpnicfL2IsolatePermitMACTable
-- =================================================================
hpnicfL2IsolatePermitMACTable OBJECT-TYPE
    SYNTAX      SEQUENCE OF HpnicfL2IsolatePermitMACEntry
    MAX-ACCESS  not-accessible
    STATUS      current
    DESCRIPTION
        "A table represents the permitting MAC address for the specific VLAN."
    ::= { hpnicfL2IsolateObject 2 }

hpnicfL2IsolatePermitMACEntry OBJECT-TYPE
    SYNTAX      HpnicfL2IsolatePermitMACEntry
    MAX-ACCESS  not-accessible
    STATUS      current
    DESCRIPTION
        "Each entry represents the permitting MAC address for the specific VLAN."
    INDEX
        {
            hpnicfL2IsolateVLANIndex,
            hpnicfL2IsoLatePermitMAC
        }
    ::= { hpnicfL2IsolatePermitMACTable 1 }

HpnicfL2IsolatePermitMACEntry ::= SEQUENCE
    {
        hpnicfL2IsoLatePermitMAC            MacAddress,
        hpnicfL2IsoLatePermitMACRowStatus   RowStatus
    }

hpnicfL2IsoLatePermitMAC OBJECT-TYPE
    SYNTAX      MacAddress
    MAX-ACCESS  not-accessible
    STATUS      current
    DESCRIPTION
        "Represents the MAC address permitted in the VLAN."
    ::= { hpnicfL2IsolatePermitMACEntry 1 }

hpnicfL2IsoLatePermitMACRowStatus OBJECT-TYPE
    SYNTAX      RowStatus
    MAX-ACCESS  read-create
    STATUS      current
    DESCRIPTION
        "RowStatus. Three actions are used: active, CreateAndGo, destroy."
    ::= { hpnicfL2IsolatePermitMACEntry 2 }

END
