-- =============================================================================
-- Copyright (c) 2010-2013 Hewlett-Packard Development Company, L.P.
--
-- Description:MPLS-BGP-VPN-MIB 
-- Reference:This MIB was extracted from Draft-ietf-mpls-ldp-mib-01
-- Version: V1.6
-- History:
--  VERSION    AUTHOR/          Change Description
--  OLD/NEW     DATE
--                                                  
--  #/1.1     Lingesh M        + Initial create. 
--             27/08/99
--  #/1.2     27/09/99         + Replaced the MIB objects
--                                  - hpnicfMplsLdpLsrMaxIngressCrlspTnls
--                                  - hpnicfMplsLdpLsrMaxInbetwnCrlspTnls
--                               with hpnicfMplsLdpLsrMaxCrlspTnls
--  1.2/1.3   19/10/99         + Added hpnicfMplsLdpPeerType in Peer Table.
--            04/10/99         + Added hpnicfMplsLdpEntityIfTable.
--  1.3/1.4   23/11/99         + Added MIB object for Hello Hold Time in Entity
--                               Table, modified Cr-lsp Tnl index of type
--                               read-create to not-accessible.
--                             + Removed hpnicfMplsLdpSessionRowStatus mib-object.
--  
--   1.1      03/01/2k         + MPLS Release 1.0.0.0
--             Naren             
-- 
--   1.2      27/01/2k         + Modified for MPLS Implementation
--             Naren             Following objects are added in the Incarnation table
--                                 hpnicfMplsLdpLsrMaxVcmCapability                  
--                                 hpnicfMplsLdpLsrVcmPathVecInAllLblMapPresent      
--                                 hpnicfMplsLdpLsrRequestRetrytimerValue            
--                                 hpnicfMplsLdpLsrNumOfRequestRetryAttempts         
--                               Following Notifications are added
--                                 hpnicfMplsLdpIncarnUpEventFailure
--                                 hpnicfMplsLdpIncarnDownEventFailure
--                                 hpnicfMplsLdpEntityUpEventFailure
--                                 hpnicfMplsLdpEntityDownEventFailure
-- 
--   1.3      03/04/2k         + Changed FS related identification to hpnicf 
--             David             related identification.	
--   1.4      03/14/2003       add hpnicfMplsLdpSessionUpEventFailure and hpnicfMplsLdpSessionDownEventFailure
--   V1.5 2004-10-12 updated by gaolong
--        Change SYNTAX clause value from INTEGER to Unsigned because the value range is (1..4294967295).
--        Change MAX-ACCESS clause value of hpnicfMplsLdpCrlspTnlIndex to accessible-for-notify
--        because this index node is used when sending notification.
--   V1.6 2004-11-5  updated by liuxiaolong
--        Change DEFVAL clause value of hpnicfMplsLdpLsrHopCountLimit to 32.
-- ====================================================================================
--
-- Full Copyright Notice of the MIB that was extracted from Draft-ietf-mpls-ldp-mib-01 as follows:
--
--Copyright (C) The Internet Society (1999). All Rights Reserved.
--
--
--   This document and translations of it may be copied and furnished to
--   others, and derivative works that comment on or otherwise explain it
--   or assist in its implementation may be prepared, copied, published
--   and distributed, in whole or in part, without restriction of any
--   kind, provided that the above copyright notice and this paragraph are
--   included on all such copies and derivative works.  However, this
--   document itself may not be modified in any way, such as by removing
--   the copyright notice or references to the Internet Society or other
--   Internet organizations, except as needed for the  purpose of
--   developing Internet standards in which case the procedures for
--   copyrights defined in the Internet Standards process must be
--   followed, or as required to translate it into languages other than
--   English.
--
--   The limited permissions granted above are perpetual and will not be
--   revoked by the Internet Society or its successors or assigns.
--
--   This document and the information contained herein is provided on an
--   "AS IS" basis and THE INTERNET SOCIETY AND THE INTERNET ENGINEERING
--   TASK FORCE DISCLAIMS ALL WARRANTIES, EXPRESS OR IMPLIED, INCLUDING
--   BUT NOT LIMITED TO ANY WARRANTY THAT THE USE OF THE INFORMATION
--   HEREIN WILL NOT INFRINGE ANY RIGHTS OR ANY IMPLIED WARRANTIES OF
--   MERCHANTABILITY OR FITNESS FOR A PARTICULAR PURPOSE.
--
--   MPLS Label Distribution Protocol MIB Definitions
HPN-ICF-MPLS-LDP-MIB DEFINITIONS ::= BEGIN

     IMPORTS                  
         hpnicfMpls
             FROM HPN-ICF-OID-MIB
         OBJECT-TYPE, MODULE-IDENTITY, NOTIFICATION-TYPE,
         Integer32, Counter32, Unsigned32,IpAddress
             FROM SNMPv2-SMI
         MODULE-COMPLIANCE, OBJECT-GROUP, NOTIFICATION-GROUP
             FROM SNMPv2-CONF
         TEXTUAL-CONVENTION, TruthValue, RowStatus, TimeInterval
             FROM SNMPv2-TC;
             
     hpnicfMplsLdp MODULE-IDENTITY
         LAST-UPDATED "9906301200Z"     -- June 30, 1999 at 12:00 GMT
         ORGANIZATION
             ""
         CONTACT-INFO
             ""
         DESCRIPTION  "All rights reserved"
         REVISION     "9611082155Z"
         DESCRIPTION  "The MIB for MPLS LDP module.
                       This MIB has been derived from the MPLS Working 
                       group LDP MIB <drst-ietf-mpls-ldp-mib-01.txt> and
                       MPLS Working group TE MIB <draft-ietf-mpls-te-mib
                       -01.txt>."

         ::= { hpnicfMpls 2 }

     --********************************************************************
     -- MPLS LDP Textual Conventions
     --********************************************************************
     --

           DisplayString ::=
               OCTET STRING
          -- This data type is used to model textual information taken
          -- from the NVT ASCII character set.  By convention, objects
          -- with this syntax are declared as having
          --
                (SIZE (0..255))

           PhysAddress ::=
               OCTET STRING
          -- This data type is used to model media addresses.  For many
          -- types of media, this will be in a binary representation.
          -- For example, an ethernet address would be represented as
          -- a string of 6 octets.

	BitRate ::= INTEGER
	
	BurstSize ::= INTEGER
	
	
     MplsLsrIdentifier ::= TEXTUAL-CONVENTION
         STATUS      current
         DESCRIPTION
             "The Label Switch Router (LSR) identifier
             is the first 4 bytes or the IP Address component
             of the Label Distribution Protocol (LDP) identifier."
         SYNTAX      OCTET STRING (SIZE (4))

     MplsLdpGenAddr ::= TEXTUAL-CONVENTION
         STATUS      current
         DESCRIPTION
             "The value of an network layer or data link layer address."
         SYNTAX      OCTET STRING (SIZE (0..64))

     MplsLdpIdentifier ::= TEXTUAL-CONVENTION
         STATUS      current
         DESCRIPTION
             "The LDP identifier is a six octet quantity
             which is used to identify an Label Switch Router
             (LSR) label space.

             The first four octets encode an IP address
             assigned to the LSR, and the last two octets
             identify a specific label space within the LSR."
         SYNTAX      OCTET STRING (SIZE (6))

     AtmVpIdentifier ::= TEXTUAL-CONVENTION
          STATUS      current
          DESCRIPTION
              "The VPI value for a VPL. The value VPI=0 is not
              used for a VPL not associated with a VCL. For ATM
              UNIs supporting VPCs the VPI value ranges from 1
              to 255. For ATM UNIs supporting VCCs the VPI value
              ranges from 0 to 255.  The maximum VPI value
              cannot exceed the value allowable by
              atmInterfaceMaxVpiBits defined in ATM-MIB."
          SYNTAX INTEGER (0..4095)

     AtmVcIdentifier ::= TEXTUAL-CONVENTION
          STATUS      current
          DESCRIPTION
              "The VCI value for a VCL. The maximum VCI value
              cannot exceed the value allowable by
              atmInterfaceMaxVciBits defined in ATM-MIB."
          SYNTAX INTEGER (0..65535)

     AddressFamilyNumbers ::= TEXTUAL-CONVENTION
        STATUS        current
        DESCRIPTION
            "An address family.  Values are defined in RFC 1700 -
             Assigned Numbers.  All values may not be relevant in
             all contexts when used in this MIB, but are included
             for completeness."
        REFERENCE
            "RFC  1700   Assigned Numbers, Reynolds and  Postel,
             Oct. 1994"
        SYNTAX        INTEGER {
                        other(0),
                         ipv4(1),
                         ipv6(2),
                         nsap(3),
                         hdlc(4),
                         bbn1822(5),
                         ieee802(6),
                         e163(7),
                         e164(8),
                         f69(9),
                         x121(10),
                         ipx(11),
                         appleTalk(12),
                         decnetIV(13),
                         banyanVines(14),
                         e164WithNsap(15)
                     }


     MplsLabel ::= TEXTUAL-CONVENTION
        STATUS        current
        DESCRIPTION
            "Represents an MPLS label.  Note that the contents of
             a  label  field are interpreted in an interface-type
             specific fashion.  For example, the label carried in
             the MPLS shim header is 20 bits wide and the top  12
             bits  must  be zero.  The frame relay label  can  be
             either 10, 17 or 23 bits wide depending on the  size
             of the DLCI field size and the top 22, 15, or 9 bits
             must  be  zero, respectively.  For an ATM interface,
             the  lowermost 16 bits are interpreted as  the  VCI,
             the  next  8 bits as the VPI and the remaining  bits
             must  be  zero.   Also  note the  permissible  label
             values  are  also a function of the interface  type.
             For  example,  the value 3 has special semantics  in
             the  control plane for an MPLS shim header label and
             is not a valid label value in the datapath."
        REFERENCE
            "1.  MPLS  Label Stack Encoding, Rosen et al,  draft-
             ietf-mpls-label-encaps-04.txt, April 1999.
            2.  Use  of  Label Switching on Frame Relay Networks,
             Conta et al, draft-ietf-mpls-fr-03.txt, Nov. 1998."
        SYNTAX INTEGER
     
     MplsTunnelIndex ::= TEXTUAL-CONVENTION
        STATUS        current
        DESCRIPTION
            "Index into mplsTunnelTable."
        SYNTAX        INTEGER (0..65535)
     
     hpnicfMplsLdpObjects       OBJECT IDENTIFIER ::= { hpnicfMplsLdp 1 }
     hpnicfMplsLdpNotifications OBJECT IDENTIFIER ::= { hpnicfMplsLdp 2 }

     --****************************************************************
     -- MPLS LDP Objects
     --****************************************************************

     hpnicfMplsLdpLsrObjects            OBJECT IDENTIFIER ::= { hpnicfMplsLdpObjects 1 }
     hpnicfMplsLdpEntityObjects         OBJECT IDENTIFIER ::= { hpnicfMplsLdpObjects 2 }
     hpnicfMplsLdpPeerObjects           OBJECT IDENTIFIER ::= { hpnicfMplsLdpObjects 3 }
     hpnicfMplsLdpSessionObjects        OBJECT IDENTIFIER ::= { hpnicfMplsLdpObjects 4 }
     hpnicfMplsLdpHelloAdjacencyObjects OBJECT IDENTIFIER ::= { hpnicfMplsLdpObjects 5 }
     hpnicfMplsLdpCrlspTnlObjects       OBJECT IDENTIFIER ::= { hpnicfMplsLdpObjects 6 }

     --
     -- The MPLS Label Distribution Protocol Label Switch Router Objects
     --
     hpnicfMplsLdpLsrIncarnTable OBJECT-TYPE
         SYNTAX      SEQUENCE OF HpnicfMplsLdpLsrIncarnEntry
         MAX-ACCESS  not-accessible
         STATUS      current
         DESCRIPTION
             "MPLS provides support for multiple incarnations of the 
              MPLS Stack in a target. The LSR defined in the standard <IETF
              DRAFT> MIB is treated as an incarnation in this MIB. Using a
              local policy the Network administrator must group the LDP Entities
              that should be placed in an incarnation."
         ::= { hpnicfMplsLdpLsrObjects 1 }

     hpnicfMplsLdpLsrIncarnEntry OBJECT-TYPE
         SYNTAX      HpnicfMplsLdpLsrIncarnEntry
         MAX-ACCESS  not-accessible
         STATUS      current
         DESCRIPTION
             "An entry in this table represents an LSR incarnation.
              All the entries in this table are created initially when the 
              LDP is initiated. The row status of each entry will be in 
              'notInService' state initially. The row status must be set to
              'active' after the necessary configurations are complete with
              respect to an incarnation.

              Currenlty the LSR ID of the incarnation is the only mandatory
              parameter that must be set before the rowStatus is set to 
              'active'.

              An LSR Incarnation Entity is uniquely indexed by its Incarnation
              Identifier."
         INDEX       {  hpnicfMplsLdpLsrIncarnID }
         ::= { hpnicfMplsLdpLsrIncarnTable 1 }

     HpnicfMplsLdpLsrIncarnEntry ::= SEQUENCE {
         hpnicfMplsLdpLsrID                                MplsLsrIdentifier,
         hpnicfMplsLdpLsrLoopDetectionPresent              TruthValue,
         hpnicfMplsLdpLsrLoopDetectionAdminStatus          INTEGER,
         hpnicfMplsLdpLsrPathVectorLimit                   INTEGER,
         hpnicfMplsLdpLsrHopCountLimit                     INTEGER,
         hpnicfMplsLdpLsrLoopPreventionPresent             TruthValue,
         hpnicfMplsLdpLsrLoopPreventionAdminStatus         INTEGER,
         hpnicfMplsLdpLsrLabelRetentionMode                INTEGER,
         hpnicfMplsLdpLsrIncarnID                          INTEGER,
         hpnicfMplsLdpLsrMaxLdpEntities                    INTEGER,
         hpnicfMplsLdpLsrMaxLocalPeers                     INTEGER,
         hpnicfMplsLdpLsrMaxRemotePeers                    INTEGER,
         hpnicfMplsLdpLsrMaxIfaces                         INTEGER,
         hpnicfMplsLdpLsrMaxLsps                           INTEGER,
         hpnicfMplsLdpLsrMaxCrlspTnls                      INTEGER,
         hpnicfMplsLdpLsrMaxErhopPerCrlspTnl               INTEGER,
         hpnicfMplsLdpLsrRowStatus                         RowStatus,
         hpnicfMplsLdpLsrMaxVcmCapability                  INTEGER,  
         hpnicfMplsLdpLsrVcmPathVecInAllLblMapPresent      TruthValue,
         hpnicfMplsLdpLsrRequestRetrytimerValue            INTEGER,
         hpnicfMplsLdpLsrNumOfRequestRetryAttempts         INTEGER
    }

     hpnicfMplsLdpLsrID OBJECT-TYPE
         SYNTAX      MplsLsrIdentifier
         MAX-ACCESS  read-write   
         STATUS      current
         DESCRIPTION
             "The LSR's Identifier."
         ::= { hpnicfMplsLdpLsrIncarnEntry 1 }

     hpnicfMplsLdpLsrLoopDetectionPresent OBJECT-TYPE
         SYNTAX      TruthValue
         MAX-ACCESS  read-only
         STATUS      current
         DESCRIPTION
             "A indication of whether this LSR supports loop detection.  A 
             value of 'true' indicates this LSR does support loop detection.  
             A value of 'false' indicates this LSR does not support
             loop detection."
         DEFVAL  { true }
         ::= { hpnicfMplsLdpLsrIncarnEntry 2 }

     hpnicfMplsLdpLsrLoopDetectionAdminStatus OBJECT-TYPE
         SYNTAX      INTEGER {
                         enabled(1),
                         disabled(2)
                     }
         MAX-ACCESS  read-write
         STATUS      current
         DESCRIPTION
             "To enable loop detection the value of this object should be 
             'enabled(1)'.  Otherwise, to turn off loop detection, set this 
             value to 'disabled(2)'."
         DEFVAL  { enabled }
         ::= { hpnicfMplsLdpLsrIncarnEntry 3 }

     hpnicfMplsLdpLsrPathVectorLimit OBJECT-TYPE
         SYNTAX      INTEGER
         MAX-ACCESS  read-write
         STATUS      current
         DESCRIPTION
             "This object only has meaning if hpnicfMplsLdpLsrLoopDetectionPresent 
             has the value of 'true'.

             The value of this object represents the limit of path vectors which
             this LSR uses to treat the message as if it had traversed a loop."
         DEFVAL  { 32 }
         ::= { hpnicfMplsLdpLsrIncarnEntry 4 }

     hpnicfMplsLdpLsrHopCountLimit OBJECT-TYPE
         SYNTAX      INTEGER
         MAX-ACCESS  read-write
         STATUS      current
         DESCRIPTION
             "This object only has meaning if hpnicfMplsLdpLsrLoopDetectionPresent 
             has the value of 'true'.

             The value of this object represents the limit on the Hop Count 
             which this LSR uses to treat the message as if it had traversed a 
             loop."
         DEFVAL  { 32 }
         ::= { hpnicfMplsLdpLsrIncarnEntry 5 }

     hpnicfMplsLdpLsrLoopPreventionPresent OBJECT-TYPE
         SYNTAX      TruthValue
         MAX-ACCESS  read-only
         STATUS      current
         DESCRIPTION
             "A indication of whether this LSR supports loop prevention.  A 
             value of 'true' indicates this LSR does support loop prevention.  
             A value of 'false' indicates this LSR does not support loop 
             prevention.

             Current release of MPLS does not provide support to assign
             this MIB object with a value 'true'."
         DEFVAL  { false }
         ::= { hpnicfMplsLdpLsrIncarnEntry 6 }

     hpnicfMplsLdpLsrLoopPreventionAdminStatus OBJECT-TYPE
         SYNTAX      INTEGER {
                         enabled(1),
                         disabled(2)
                     }
         MAX-ACCESS  read-write
         STATUS      current
         DESCRIPTION
             "To enable loop prevention the value of this object should be 
             'enabled(1)'.  Otherwise, to turn off loop prevention, set this 
             value to 'disabled(2)'.

             Current release of MPLS does not provide support to assign
             this MIB object with a value 'enabled'."
         DEFVAL  { disabled }
         ::= { hpnicfMplsLdpLsrIncarnEntry 7 }

     hpnicfMplsLdpLsrLabelRetentionMode OBJECT-TYPE
         SYNTAX      INTEGER {
                         conservative(1),
                         liberal(2)
                     }
         MAX-ACCESS  read-write
         STATUS      current
         DESCRIPTION
             "The LSR can be configured to use either conservative or liberal 
              label retention mode.

             If the value of this object is conservative(1) then advertized 
             label mappings are retained only if they will be used to forward 
             packets, i.e. if label came from a valid next hop.  If the value of
             this object is liberal(2) then all advertized label mappings are 
             retained whether they are from a valid next hop or not.

             Current release of MPLS does not provide support to assign
             this MIB object with a value 'liberal'."
         DEFVAL  { conservative }
         ::= { hpnicfMplsLdpLsrIncarnEntry 8 }

     hpnicfMplsLdpLsrIncarnID   OBJECT-TYPE
         SYNTAX     INTEGER
         MAX-ACCESS read-only
         STATUS     current
         DESCRIPTION 
             "The incarnation acts as index to all the elements in this
              table."
         ::= { hpnicfMplsLdpLsrIncarnEntry  9 }
 
     hpnicfMplsLdpLsrMaxLdpEntities OBJECT-TYPE
         SYNTAX      INTEGER (1..1024)
         MAX-ACCESS  read-write
         STATUS      current
         DESCRIPTION
             "The maximum number of LDP entities that can be supported by this
              Incarnation."
         ::= { hpnicfMplsLdpLsrIncarnEntry 10 }

     hpnicfMplsLdpLsrMaxLocalPeers OBJECT-TYPE
         SYNTAX      INTEGER (1..1024)
         MAX-ACCESS  read-write
         STATUS      current
         DESCRIPTION
             "The maximum number of Local LDP peers that can be supported by 
              this Incarnation."
         ::= { hpnicfMplsLdpLsrIncarnEntry 11 }

     hpnicfMplsLdpLsrMaxRemotePeers OBJECT-TYPE
         SYNTAX      INTEGER (1..1024)
         MAX-ACCESS  read-write
         STATUS      current
         DESCRIPTION
             "The maximum number of Remote LDP peers that can be supported by 
              this Incarnation."
         ::= { hpnicfMplsLdpLsrIncarnEntry 12 }

     hpnicfMplsLdpLsrMaxIfaces OBJECT-TYPE
         SYNTAX      INTEGER
         MAX-ACCESS  read-write
         STATUS      current
         DESCRIPTION
             "The maximum number of Label enabled Interfaces that can be 
              supported by this Incarnation."
         ::= { hpnicfMplsLdpLsrIncarnEntry 13 }

     hpnicfMplsLdpLsrMaxLsps OBJECT-TYPE
         SYNTAX      INTEGER
         MAX-ACCESS  read-write
         STATUS      current
         DESCRIPTION
             "The maximum number of Label Switched Paths that can be 
              supported by this Incarnation."
         ::= { hpnicfMplsLdpLsrIncarnEntry 14 }

     hpnicfMplsLdpLsrMaxCrlspTnls OBJECT-TYPE
         SYNTAX      INTEGER
         MAX-ACCESS  read-write
         STATUS      current
         DESCRIPTION
             "The maximum number of CRLSPs that can be supported by this
             Incarnation."
         ::= { hpnicfMplsLdpLsrIncarnEntry 15 }


     hpnicfMplsLdpLsrMaxErhopPerCrlspTnl OBJECT-TYPE
         SYNTAX      INTEGER
         MAX-ACCESS  read-write
         STATUS      current
         DESCRIPTION
             " The maximum number of ER-Hops that can be supported in a 
              CRLSP tunnel."
         ::= { hpnicfMplsLdpLsrIncarnEntry 16 }

     hpnicfMplsLdpLsrRowStatus OBJECT-TYPE
         SYNTAX      RowStatus
         MAX-ACCESS  read-create
         STATUS      current
              DESCRIPTION
                  "An object that allows entries in this table to
                  be created and deleted using the
                  RowStatus convention."
         ::= { hpnicfMplsLdpLsrIncarnEntry 17 }

     hpnicfMplsLdpLsrMaxVcmCapability OBJECT-TYPE
         SYNTAX      INTEGER
         MAX-ACCESS  read-write
         STATUS      current
         DESCRIPTION
                  "  "
         ::= { hpnicfMplsLdpLsrIncarnEntry 18 }

     hpnicfMplsLdpLsrVcmPathVecInAllLblMapPresent OBJECT-TYPE
         SYNTAX      TruthValue
         MAX-ACCESS  read-write
         STATUS      current
         DESCRIPTION
                  "  "
         ::= { hpnicfMplsLdpLsrIncarnEntry 19 }

     hpnicfMplsLdpLsrRequestRetrytimerValue  OBJECT-TYPE
         SYNTAX      INTEGER
         MAX-ACCESS  read-write
         STATUS      current
         DESCRIPTION
                  "  "
         ::= { hpnicfMplsLdpLsrIncarnEntry 20 }

     hpnicfMplsLdpLsrNumOfRequestRetryAttempts OBJECT-TYPE
         SYNTAX      INTEGER
         MAX-ACCESS  read-write
         STATUS      current
         DESCRIPTION
                  "  "
         ::= { hpnicfMplsLdpLsrIncarnEntry 21 }


     --
     -- The MPLS Label Distribution Protocol Entity Table
     --

     hpnicfMplsLdpEntityTable OBJECT-TYPE
         SYNTAX      SEQUENCE OF HpnicfMplsLdpEntityEntry
         MAX-ACCESS  not-accessible
         STATUS      current
         DESCRIPTION
             "This table contains information about the
             MPLS Label Distribution Protocol Entities which
             exist on this Label Switch Router (LSR)."
         ::= { hpnicfMplsLdpEntityObjects 1 }

     hpnicfMplsLdpEntityEntry OBJECT-TYPE
         SYNTAX      HpnicfMplsLdpEntityEntry
         MAX-ACCESS  not-accessible
         STATUS      current
         DESCRIPTION
             "An entry in this table represents an LDP entity.
             An entry can be created by a network administrator
             or by an SNMP agent as instructed by LDP.

             An LPD Entity is uniquely indexed by its LPD
             Identifier."
         INDEX       {   hpnicfMplsLdpLsrIncarnID, hpnicfMplsLdpEntityIfIndex  }
         ::= { hpnicfMplsLdpEntityTable 1 }

     HpnicfMplsLdpEntityEntry ::= SEQUENCE {
         hpnicfMplsLdpEntityID                            MplsLdpIdentifier,
         hpnicfMplsLdpEntityLabelSpaceType                INTEGER,
         hpnicfMplsLdpEntityDefVpi                        AtmVpIdentifier,
         hpnicfMplsLdpEntityDefVci                        AtmVcIdentifier,
         hpnicfMplsLdpEntityUnlabTrafVpi                  AtmVpIdentifier,
         hpnicfMplsLdpEntityUnlabTrafVci                  AtmVcIdentifier,
         hpnicfMplsLdpEntityMergeCapability               INTEGER,
         hpnicfMplsLdpEntityVcDirectionality              INTEGER,
         hpnicfMplsLdpEntityWellKnownDiscoveryPort        INTEGER,
         hpnicfMplsLdpEntityMtu                           INTEGER,
         hpnicfMplsLdpEntityKeepAliveHoldTimer            INTEGER,
         hpnicfMplsLdpEntityFailedInitSessionThreshold    INTEGER,
         hpnicfMplsLdpEntityLabelDistributionMethod       INTEGER,
         hpnicfMplsLdpEntityLabelAllocationMethod         INTEGER,
         hpnicfMplsLdpEntityHelloHoldTimer                INTEGER,
         hpnicfMplsLdpEntityRowStatus                     RowStatus
     }

     hpnicfMplsLdpEntityID OBJECT-TYPE
         SYNTAX      MplsLdpIdentifier
         MAX-ACCESS  accessible-for-notify
         STATUS      current
         DESCRIPTION
             "The LDP identifier which uniquely identifies
             the LDP Entity.  This is s six octet quantity
             which is used to identify an Label Switch Router
             (LSR) label space.

             The first four octets encode an IP address
             assigned to the LSR, and the last two octets
             identify a specific label space within the
             LSR."
         REFERENCE
             "LDP Specification, Section on LDP Identifiers."
         ::= { hpnicfMplsLdpEntityEntry 1 }


     hpnicfMplsLdpEntityLabelSpaceType OBJECT-TYPE
         SYNTAX      INTEGER {
                         unknown(1),
                         perInterface(2),
                         perPlatform(3)
                         }
         MAX-ACCESS  read-create
         STATUS      current
         DESCRIPTION
             "The type of label spaces associated with this
             LDP Entity.  The values are

                'unknown(1)'        The type of label space is
                                    not known.

                'perInterface(2)'   The type of label space is
                                    tied to an interface.
                'perPlatform(3)'    The type of label space is
                                    tied to the platform."
         REFERENCE
             "LDP Specification, Section on Label Spaces."
         ::= { hpnicfMplsLdpEntityEntry 2 }

     hpnicfMplsLdpEntityDefVpi OBJECT-TYPE
         SYNTAX      AtmVpIdentifier
         MAX-ACCESS  read-create
         STATUS      current
         DESCRIPTION
             "The Default VPI value used in the label for the default
             VPI."
         ::= { hpnicfMplsLdpEntityEntry 3 }

     hpnicfMplsLdpEntityDefVci OBJECT-TYPE
         SYNTAX      AtmVcIdentifier
         MAX-ACCESS  read-create
         STATUS      current
         DESCRIPTION
             "The Default VCI value used in the label for the default
             VCI."
         ::= { hpnicfMplsLdpEntityEntry  4 }

     hpnicfMplsLdpEntityUnlabTrafVpi OBJECT-TYPE
         SYNTAX      AtmVpIdentifier
         MAX-ACCESS  read-create
         STATUS      current
         DESCRIPTION
             "VPI value of the VCC supporting unlabeled traffic."
         DEFVAL  { 0 }
         ::= { hpnicfMplsLdpEntityEntry 5 }

     hpnicfMplsLdpEntityUnlabTrafVci OBJECT-TYPE
         SYNTAX      AtmVcIdentifier
         MAX-ACCESS  read-create
         STATUS      current
         DESCRIPTION
             "VCI value of the VCC supporting unlabeled traffic."
         DEFVAL  { 32 }
         ::= { hpnicfMplsLdpEntityEntry 6 }

     hpnicfMplsLdpEntityMergeCapability OBJECT-TYPE
         SYNTAX      INTEGER {
                         noMerge(0),
                         vpMerge(1),
                         vcMerge(2),
                         vpVcMerge(3)
                      }
         MAX-ACCESS  read-create
         STATUS      current
         DESCRIPTION
             "Sets the merge capability for this LDP entity.

              Current Release of MPLS does not provide support for
              any kind of Merge."
         REFERENCE
             "draft-ietf-mpls-ldp-04.txt, Section 3.5.3"
         ::= { hpnicfMplsLdpEntityEntry 7 }

     hpnicfMplsLdpEntityVcDirectionality OBJECT-TYPE
         SYNTAX      INTEGER {
                         bidirectional(1),
                         unidirectional(2)
                     }
         MAX-ACCESS  read-create
         STATUS      current
         DESCRIPTION
             "Sets the VC directionality for this LDP entity."
         REFERENCE
             "draft-ietf-mpls-ldp-04.txt, Section 3.5.3"
         ::= { hpnicfMplsLdpEntityEntry 8 }

     hpnicfMplsLdpEntityWellKnownDiscoveryPort OBJECT-TYPE
         SYNTAX      INTEGER
         MAX-ACCESS  read-create
         STATUS      current
         DESCRIPTION
             "The well known LDP Discovery Port."
         ::= { hpnicfMplsLdpEntityEntry 9 }

     hpnicfMplsLdpEntityMtu OBJECT-TYPE
         SYNTAX      INTEGER (0..65535)
         MAX-ACCESS  read-create
         STATUS      current
         DESCRIPTION
             "The maximum transmission unit (MTU) that was configured
             for this entity."
         ::= { hpnicfMplsLdpEntityEntry 10 }

     hpnicfMplsLdpEntityKeepAliveHoldTimer OBJECT-TYPE
         SYNTAX      INTEGER (1..65535)
         UNITS       "seconds"
         MAX-ACCESS  read-create
         STATUS      current
         DESCRIPTION
             "The two octet value which is the proposed keep alive hold
             timer for this LDP Entity."
         ::= { hpnicfMplsLdpEntityEntry 11 }

     hpnicfMplsLdpEntityFailedInitSessionThreshold OBJECT-TYPE
         SYNTAX      INTEGER
         MAX-ACCESS  read-create
         STATUS      current
         DESCRIPTION
             "When attempting to establish a session with a
             given Peer, the given LDP Entity should
             send out a notification when exceeding this threshold.
             A value of 0 (zero) for this object
             indicates that the threshold is infinity.
             In other words, a notification will not
             be sent if the value of this object is 0 (zero)."
         ::= { hpnicfMplsLdpEntityEntry 12 }


     hpnicfMplsLdpEntityLabelDistributionMethod OBJECT-TYPE
         SYNTAX      INTEGER {
                        downstreamOnDemand(1),
                        downstreamUnsolicited(2)
                     }
         MAX-ACCESS  read-create
         STATUS      current
         DESCRIPTION
             "For any given LDP session, the method of
             label distribution must be specified.
 
             Current release of MPLS does not provide support for
             'downstreamUnsolicited'."
         REFERENCE
             "draft-ietf-mpls-arch-04.txt [20]."
         ::= { hpnicfMplsLdpEntityEntry 13 }

     hpnicfMplsLdpEntityLabelAllocationMethod OBJECT-TYPE
         SYNTAX      INTEGER {
                        ordered(1),
                        independent(2)
                     }
         MAX-ACCESS  read-create
         STATUS      current
         DESCRIPTION
             "For any given LDP session, the method of
             label allocation must be specified. Label can be allocated
             in either ordered mode or in the independent mode."
         DEFVAL  { ordered }
         ::= { hpnicfMplsLdpEntityEntry 14 }

     hpnicfMplsLdpEntityHelloHoldTimer OBJECT-TYPE
         SYNTAX      INTEGER (1..65535)
         UNITS       "seconds"
         MAX-ACCESS  read-create
         STATUS      current
         DESCRIPTION
             "The two octet value which is the proposed hello hold
             timer for this LDP Entity."
         ::= { hpnicfMplsLdpEntityEntry 15 }
     
     hpnicfMplsLdpEntityRowStatus OBJECT-TYPE
         SYNTAX      RowStatus
         MAX-ACCESS  read-create
         STATUS      current
              DESCRIPTION
                  "An object that allows entries in this table to
                  be created and deleted using the
                  RowStatus convention."
         ::= { hpnicfMplsLdpEntityEntry 16 }

     --
     -- The MPLS LDP Entity Interface Table
     --

     hpnicfMplsLdpEntityIfTable OBJECT-TYPE
         SYNTAX      SEQUENCE OF HpnicfMplsLdpEntityIfEntry
         MAX-ACCESS  not-accessible
         STATUS      current
         DESCRIPTION
             "This table contains information about the
             interfaces that are associated with an LDP Entity.
             There should be atleast one interface associated with
             each LDP Entity. If the LDP Entity supports 'per interface
             based label space' label type then, atmost one interface can be 
             associated with the LDP entity. If the LDP Entity supports
             'per platform based label space' label type then, more than one
             interface can be associated with the LDP Entity."
         ::= { hpnicfMplsLdpEntityObjects 2 }

     hpnicfMplsLdpEntityIfEntry OBJECT-TYPE
         SYNTAX      HpnicfMplsLdpEntityIfEntry
         MAX-ACCESS  not-accessible
         STATUS      current
         DESCRIPTION
             "An entry in this table represents an Interface that is
             associated with a LDP entity.

             An entry can be created by a network administrator
             or by an SNMP agent as instructed by LDP.

             An interface (row in this table) can be created/deleted only when 
             the associted LDP Entity row status has the value notInService 
             or notReady."
         INDEX       {   hpnicfMplsLdpLsrIncarnID, hpnicfMplsLdpEntityIfIndex }
         ::= { hpnicfMplsLdpEntityIfTable 1 }

     HpnicfMplsLdpEntityIfEntry ::= SEQUENCE {
         hpnicfMplsLdpEntityIfIndex                       Unsigned32,
         hpnicfMplsLdpEntityIfIpv4Address                 IpAddress,
         hpnicfMplsLdpEntityIfRowStatus                   RowStatus
     }

     hpnicfMplsLdpEntityIfIndex OBJECT-TYPE
         SYNTAX      Unsigned32 (1..4294967295)
         MAX-ACCESS  not-accessible
         STATUS      current
         DESCRIPTION
             "Identifier that uniquely identifies the Interface with 
             respect to an LDP Entity.
             
             The ifIndex value corresponds to the IfIndex value of the
             MIB-II"
         ::= { hpnicfMplsLdpEntityIfEntry 1 }

     hpnicfMplsLdpEntityIfIpv4Address OBJECT-TYPE
        SYNTAX        IpAddress
        MAX-ACCESS    read-create
        STATUS        current
        DESCRIPTION
            "The IPv4 address associated with the interface."
        ::= { hpnicfMplsLdpEntityIfEntry 2 }

     hpnicfMplsLdpEntityIfRowStatus OBJECT-TYPE
         SYNTAX      RowStatus
         MAX-ACCESS  read-create
         STATUS      current
              DESCRIPTION
                  "An object that allows entries in this table to
                  be created and deleted using the
                  RowStatus convention."
         ::= { hpnicfMplsLdpEntityIfEntry 3 }

     --
     -- The MPLS LDP Entity Configurable ATM Label Range Table
     --

     hpnicfMplsLdpEntityConfAtmLabelRangeTable OBJECT-TYPE
         SYNTAX SEQUENCE OF HpnicfMplsLdpEntityConfAtmLabelRangeEntry
         MAX-ACCESS not-accessible
         STATUS current
         DESCRIPTION
             "The MPLS LDP Entity Configurable ATM Label Range Table.
             The purpose of this table is to provide a mechanism
             for specifying a contiguous range of vpi's
             with a contiguous range of vci's, or a 'label range'
             for LDP Entities.

             LDP Entities which use ATM must have at least one
             entry in this table."
         ::= { hpnicfMplsLdpEntityObjects 3 }

     hpnicfMplsLdpEntityConfAtmLabelRangeEntry OBJECT-TYPE
         SYNTAX HpnicfMplsLdpEntityConfAtmLabelRangeEntry
         MAX-ACCESS not-accessible
         STATUS current
         DESCRIPTION
             "A row in the LDP Entity Configurable ATM Label
             Range Table.  One entry in this table contains
             information on a single range of labels
             represented by the configured Upper and Lower
             Bounds VPI/VCI pairs.
             NOTE:  The ranges for a specific LDP Entity
             are UNIQUE and non-overlapping.  For example,
             for a specific LDP Entity index, there could
             be one entry having ConfLowerBound vpi/vci == 0/32, and
             ConfUpperBound vpi/vci == 0/100, and a second entry for this
             same interface with ConfLowerBound vpi/vci == 0/101 and
             ConfUpperBound vpi/vci == 0/200.  However, there could not be
             a third entry with ConfLowerBound vpi/vci == 0/200 and
             ConfUpperBound vpi/vci == 0/300 because this label range overlaps
             with the second entry (i.e. both entries now have 0/200).

             A row will not be created unless a unique and non-overlapping
             range is specified.  Thus, row creation implies a one-shot
             row creation of LDP EntityID and ConfLowerBound vpi/vci and
             ConfUpperBound vpi/vci.  At least one label range entry
             for a specific LDP Entity MUST include the default VPI/VCI
             values denoted in the LDP Entity Table."
         INDEX { hpnicfMplsLdpLsrIncarnID, hpnicfMplsLdpEntityIfIndex,
                 hpnicfMplsLdpEntityConfAtmLabelRangeLowerBoundVPI,
                 hpnicfMplsLdpEntityConfAtmLabelRangeLowerBoundVCI  }
         ::= { hpnicfMplsLdpEntityConfAtmLabelRangeTable 1 }

     HpnicfMplsLdpEntityConfAtmLabelRangeEntry ::= SEQUENCE {
         hpnicfMplsLdpEntityConfAtmLabelRangeLowerBoundVPI  AtmVpIdentifier,
         hpnicfMplsLdpEntityConfAtmLabelRangeLowerBoundVCI  AtmVcIdentifier,
         hpnicfMplsLdpEntityConfAtmLabelRangeUpperBoundVPI  AtmVpIdentifier,
         hpnicfMplsLdpEntityConfAtmLabelRangeUpperBoundVCI  AtmVcIdentifier,
         hpnicfMplsLdpEntityConfAtmLabelRangeRowStatus      RowStatus
     }

     hpnicfMplsLdpEntityConfAtmLabelRangeLowerBoundVPI OBJECT-TYPE
         SYNTAX AtmVpIdentifier
         MAX-ACCESS not-accessible
         STATUS current
         DESCRIPTION
             "The minimum VPI number configured for this range."
         ::= { hpnicfMplsLdpEntityConfAtmLabelRangeEntry 1 }

     hpnicfMplsLdpEntityConfAtmLabelRangeLowerBoundVCI OBJECT-TYPE
         SYNTAX AtmVcIdentifier
         MAX-ACCESS not-accessible
         STATUS current
         DESCRIPTION
             "The minimum VCI number configured for this range."
         ::= { hpnicfMplsLdpEntityConfAtmLabelRangeEntry 2 }

     hpnicfMplsLdpEntityConfAtmLabelRangeUpperBoundVPI OBJECT-TYPE
         SYNTAX AtmVpIdentifier
         MAX-ACCESS read-create
         STATUS current
         DESCRIPTION
             "The maximum VPI number configured for this range."
         ::= { hpnicfMplsLdpEntityConfAtmLabelRangeEntry 3 }

     hpnicfMplsLdpEntityConfAtmLabelRangeUpperBoundVCI OBJECT-TYPE
         SYNTAX AtmVcIdentifier
         MAX-ACCESS read-create
         STATUS current
         DESCRIPTION
             "The maximum VCI number configured for this range."
        ::= { hpnicfMplsLdpEntityConfAtmLabelRangeEntry 4 }

     hpnicfMplsLdpEntityConfAtmLabelRangeRowStatus OBJECT-TYPE
         SYNTAX RowStatus
         MAX-ACCESS read-create
         STATUS current
              DESCRIPTION
                  "An object that allows entries in this
                  table to be created and deleted using
                  the RowStatus convention."
         ::= { hpnicfMplsLdpEntityConfAtmLabelRangeEntry 5 }


     --
     -- The MPLS LDP Entity Statistics Table
     --

     hpnicfMplsLdpEntityStatsTable OBJECT-TYPE
         SYNTAX      SEQUENCE OF HpnicfMplsLdpEntityStatsEntry
         MAX-ACCESS  not-accessible
         STATUS      current
         DESCRIPTION
             "This table is a read-only table which augments
             the MplsLdpConfEntityTable.  The purpose of this
             table is to keep statistical information about
             the LDP Entities on the LSR."
         ::= { hpnicfMplsLdpEntityObjects 4 }

     hpnicfMplsLdpEntityStatsEntry OBJECT-TYPE
         SYNTAX      HpnicfMplsLdpEntityStatsEntry
         MAX-ACCESS  not-accessible
         STATUS      current
         DESCRIPTION
             "A row in this table contains statistical information
             about an LDP Entity."
         AUGMENTS       {   hpnicfMplsLdpEntityEntry  }
         ::= { hpnicfMplsLdpEntityStatsTable 1 }

     HpnicfMplsLdpEntityStatsEntry ::= SEQUENCE {
         hpnicfMplsLdpAttemptedSessions      Counter32
     }

     hpnicfMplsLdpAttemptedSessions OBJECT-TYPE
         SYNTAX      Counter32
         MAX-ACCESS  read-only
         STATUS      current
         DESCRIPTION
             "A count of the total attempted sessions for
             this LDP Entity."
         ::= { hpnicfMplsLdpEntityStatsEntry 1 }


     --
     -- The MPLS LDP Peer Table
     --


     hpnicfMplsLdpPeerTable OBJECT-TYPE
         SYNTAX      SEQUENCE OF HpnicfMplsLdpPeerEntry
         MAX-ACCESS  not-accessible
         STATUS      current
         DESCRIPTION
             "Information about LDP peers which have been discovered
             by the LDP Entities that are managed by this agent."
         ::= { hpnicfMplsLdpPeerObjects 1 }

     hpnicfMplsLdpPeerEntry OBJECT-TYPE
         SYNTAX      HpnicfMplsLdpPeerEntry
         MAX-ACCESS  not-accessible
         STATUS      current
         DESCRIPTION
             "Information about a single Peer."
         INDEX       { hpnicfMplsLdpLsrIncarnID, hpnicfMplsLdpEntityIfIndex,
                       hpnicfMplsLdpPeerIndex }
         ::= { hpnicfMplsLdpPeerTable 1 }

     HpnicfMplsLdpPeerEntry ::= SEQUENCE {
         hpnicfMplsLdpPeerIndex                      Unsigned32,
         hpnicfMplsLdpPeerID                         MplsLdpIdentifier,
         hpnicfMplsLdpPeerInternetworkAddrType       AddressFamilyNumbers,
         hpnicfMplsLdpPeerInternetworkAddr           MplsLdpGenAddr,
         hpnicfMplsLdpPeerDefaultMtu                 INTEGER,
         hpnicfMplsLdpPeerKeepAliveHoldTimer         INTEGER,
         hpnicfMplsLdpPeerLabelDistributionMethod    INTEGER,
         hpnicfMplsLdpPeerType                       INTEGER,
         hpnicfMplsLdpPeerRowStatus                  RowStatus
     }

     hpnicfMplsLdpPeerIndex OBJECT-TYPE
         SYNTAX      Unsigned32 (1..4294967295)
         MAX-ACCESS  not-accessible
         STATUS      current
         DESCRIPTION
             "An identifier for the LDP peer that is unique within the
              scope of this agent."
         ::= { hpnicfMplsLdpPeerEntry 1 }

     hpnicfMplsLdpPeerID OBJECT-TYPE
         SYNTAX      MplsLdpIdentifier
         MAX-ACCESS  read-create
         STATUS      current
         DESCRIPTION
             "The LDP identifier of this LDP Peer."
         ::= { hpnicfMplsLdpPeerEntry 2 }

     hpnicfMplsLdpPeerInternetworkAddrType OBJECT-TYPE
         SYNTAX      AddressFamilyNumbers
         MAX-ACCESS  read-create
         STATUS      current
         DESCRIPTION
             "The type of the internetwork layer address of this
             LDP peer. This object indicates how the value of
             hpnicfMplsLdpPeerInternetworkAddr is to be interpreted."
         ::= { hpnicfMplsLdpPeerEntry 3 }

     hpnicfMplsLdpPeerInternetworkAddr OBJECT-TYPE
         SYNTAX      MplsLdpGenAddr
         MAX-ACCESS  read-create
         STATUS      current
         DESCRIPTION
             "The value of the internetwork layer address of this LDP peer."
         ::= { hpnicfMplsLdpPeerEntry 4 }

     hpnicfMplsLdpPeerDefaultMtu OBJECT-TYPE
         SYNTAX      INTEGER (0..65535)
         MAX-ACCESS  read-create
         STATUS      current
         DESCRIPTION
             "The default maximum transmission unit (MTU) of the
             LDP Peer."
         DEFVAL      { 9180 }
         ::= { hpnicfMplsLdpPeerEntry 5 }

     hpnicfMplsLdpPeerKeepAliveHoldTimer OBJECT-TYPE
         SYNTAX      INTEGER (1..65535)
         UNITS       "seconds"
         MAX-ACCESS  read-create
         STATUS      current
         DESCRIPTION
             "The two octet unsigned non zero INTEGER that indicates
             the number of seconds that this Peer proposes for the
             value of the KeepAlive Interval."
         ::= { hpnicfMplsLdpPeerEntry 6 }

     hpnicfMplsLdpPeerLabelDistributionMethod OBJECT-TYPE
         SYNTAX      INTEGER {
                        downstreamOnDemand(1),
                        downstreamUnsolicited(2)
                     }
         MAX-ACCESS  read-create
         STATUS      current
         DESCRIPTION
             "For any given LDP session, the method of
             label distribution must be specified."
         REFERENCE
             "draft-ietf-mpls-arch-05.txt [20]."
         ::= { hpnicfMplsLdpPeerEntry 7 }

     hpnicfMplsLdpPeerType OBJECT-TYPE
         SYNTAX      INTEGER {
                        local(1),
                        remote(2)
                     }
         MAX-ACCESS  read-create
         STATUS      current
         DESCRIPTION
             "Indicates whether a peer is a local peer or a remote peer"
         ::= { hpnicfMplsLdpPeerEntry 8 } 
     
     hpnicfMplsLdpPeerRowStatus OBJECT-TYPE
         SYNTAX      RowStatus
         MAX-ACCESS  read-create
         STATUS      current
         DESCRIPTION
             "An object that allows entries in this table to be created
             and deleted using the RowStatus convention."
         ::= { hpnicfMplsLdpPeerEntry 9 }

     --
     -- The MPLS LDP Peer Configurable ATM Label Range Table
     --

     hpnicfMplsLdpPeerConfAtmLabelRangeTable OBJECT-TYPE
         SYNTAX SEQUENCE OF HpnicfMplsLdpPeerConfAtmLabelRangeEntry
         MAX-ACCESS not-accessible
         STATUS current
         DESCRIPTION
             "The MPLS LDP Peer Configurable ATM Label Range Table.
             The purpose of this table is to provide a mechanism
             for specifying a contiguous range of vpi's with a contiguous
             range of vci's, or a 'label range' for LDP Peers.
             LDP Peers which use ATM must have at least one
             entry in this table."
         ::= { hpnicfMplsLdpPeerObjects 2 }

     hpnicfMplsLdpPeerConfAtmLabelRangeEntry OBJECT-TYPE
         SYNTAX HpnicfMplsLdpPeerConfAtmLabelRangeEntry
         MAX-ACCESS not-accessible
         STATUS current
         DESCRIPTION
             "A row in the LDP Peer Configurable ATM Label Range Table.
             One entry in this table contains information
             on a single range of labels represented by
             the configured Upper and Lower Bounds VPI/VCI pairs.

             NOTE:  The ranges for a specific LDP Peer
             are UNIQUE and non-overlapping.  For example,
             for a specific LDP Peer index, there could
             be one entry having ConfLowerBound vpi/vci == 0/32, and
             ConfUpperBound vpi/vci == 0/100, and a second entry for this
             same interface with ConfLowerBound vpi/vci == 0/101 and
             ConfUpperBound vpi/vci == 0/200.  However, there could not be
             a third entry with ConfLowerBound vpi/vci == 0/200 and
             ConfUpperBound vpi/vci == 0/300 because this label range overlaps
             with the second entry (i.e. both entries now have 0/200).

             A row will not be created unless a unique and non-overlapping
             range is specified.  Thus, row creation implies a one-shot
             row creation of LDP PeerIndex and ConfLowerBound vpi/vci and
             ConfUpperBound vpi/vci.  At least one label range entry
             for a specific LDP Peer MUST include the default VPI/VCI
             values denoted in the LDP Peer Table."
         INDEX { hpnicfMplsLdpLsrIncarnID, hpnicfMplsLdpEntityIfIndex,
                 hpnicfMplsLdpPeerIndex,
                 hpnicfMplsLdpPeerConfAtmLabelRangeLowerBoundVPI,
                 hpnicfMplsLdpPeerConfAtmLabelRangeLowerBoundVCI  }
         ::= { hpnicfMplsLdpPeerConfAtmLabelRangeTable 1 }

     HpnicfMplsLdpPeerConfAtmLabelRangeEntry ::= SEQUENCE {
         hpnicfMplsLdpPeerConfAtmLabelRangeLowerBoundVPI      AtmVpIdentifier,
         hpnicfMplsLdpPeerConfAtmLabelRangeLowerBoundVCI      AtmVcIdentifier,
         hpnicfMplsLdpPeerConfAtmLabelRangeUpperBoundVPI      AtmVpIdentifier,
         hpnicfMplsLdpPeerConfAtmLabelRangeUpperBoundVCI      AtmVcIdentifier
     }

     hpnicfMplsLdpPeerConfAtmLabelRangeLowerBoundVPI OBJECT-TYPE
         SYNTAX AtmVpIdentifier
         MAX-ACCESS not-accessible
         STATUS current
         DESCRIPTION
             "The minimum VPI number configured for this range."
         ::= { hpnicfMplsLdpPeerConfAtmLabelRangeEntry 1 }

     hpnicfMplsLdpPeerConfAtmLabelRangeLowerBoundVCI OBJECT-TYPE
         SYNTAX AtmVcIdentifier
         MAX-ACCESS not-accessible
         STATUS current
         DESCRIPTION
             "The minimum VCI number configured for this range."
         ::= { hpnicfMplsLdpPeerConfAtmLabelRangeEntry 2 }

     hpnicfMplsLdpPeerConfAtmLabelRangeUpperBoundVPI OBJECT-TYPE
         SYNTAX AtmVpIdentifier
         MAX-ACCESS read-only  
         STATUS current
         DESCRIPTION
             "The maximum VPI number configured for this range."
         ::= { hpnicfMplsLdpPeerConfAtmLabelRangeEntry 3 }

     hpnicfMplsLdpPeerConfAtmLabelRangeUpperBoundVCI OBJECT-TYPE
         SYNTAX AtmVcIdentifier
         MAX-ACCESS read-only  
         STATUS current
         DESCRIPTION
             "The maximum VCI number configured for this range."
        ::= { hpnicfMplsLdpPeerConfAtmLabelRangeEntry 4 }

     --
     -- The MPLS LDP Sessions Table
     --


     hpnicfMplsLdpSessionTable OBJECT-TYPE
         SYNTAX      SEQUENCE OF HpnicfMplsLdpSessionEntry
         MAX-ACCESS  not-accessible
         STATUS      current
         DESCRIPTION
             "A table of Sessions between the LDP Entities and
             LDP Peers."
         ::= { hpnicfMplsLdpSessionObjects 1 }

     hpnicfMplsLdpSessionEntry OBJECT-TYPE
         SYNTAX      HpnicfMplsLdpSessionEntry
         MAX-ACCESS  not-accessible
         STATUS      current
         DESCRIPTION
             "An entry in this table represents information on a
             single session between an LDP Entity and LDP Peer."
         INDEX       { hpnicfMplsLdpLsrIncarnID,
                       hpnicfMplsLdpEntityIfIndex,
                       hpnicfMplsLdpPeerIndex,
                       hpnicfMplsLdpSessionIndex
                     }
         ::= { hpnicfMplsLdpSessionTable 1 }

     HpnicfMplsLdpSessionEntry ::= SEQUENCE {
         hpnicfMplsLdpSessionIndex                          Unsigned32,
         hpnicfMplsLdpSessionID                             MplsLdpIdentifier,
         hpnicfMplsLdpSessionProtocolVersion                INTEGER,
         hpnicfMplsLdpSessionKeepAliveHoldTimeRemaining     TimeInterval,
         hpnicfMplsLdpSessionRole                           INTEGER,
         hpnicfMplsLdpSessionState                          INTEGER,
         hpnicfMplsLdpSessionAtmLabelRangeLowerBoundVPI     AtmVpIdentifier,
         hpnicfMplsLdpSessionAtmLabelRangeLowerBoundVCI     AtmVcIdentifier,
         hpnicfMplsLdpSessionAtmLabelRangeUpperBoundVPI     AtmVpIdentifier,
         hpnicfMplsLdpSessionAtmLabelRangeUpperBoundVCI     AtmVcIdentifier
     }

     hpnicfMplsLdpSessionIndex OBJECT-TYPE
         SYNTAX      Unsigned32 (1..4294967295)
         MAX-ACCESS  not-accessible
         STATUS      current
         DESCRIPTION
             "An unique identifier for this entry such that it
             identifies a specific LDP Session."
         ::= { hpnicfMplsLdpSessionEntry 1 }

     hpnicfMplsLdpSessionID OBJECT-TYPE
         SYNTAX      MplsLdpIdentifier
         MAX-ACCESS  read-only
         STATUS      current
         DESCRIPTION
             "The LDP Session identifier."
         ::= { hpnicfMplsLdpSessionEntry 2 }

     hpnicfMplsLdpSessionProtocolVersion OBJECT-TYPE
              SYNTAX      INTEGER(0..65535)
              MAX-ACCESS  read-only
              STATUS      current
              DESCRIPTION
                  "The version of the LDP Protocol which
                  this session is using."
              ::= { hpnicfMplsLdpSessionEntry 3 }

     hpnicfMplsLdpSessionKeepAliveHoldTimeRemaining OBJECT-TYPE
         SYNTAX      TimeInterval
         MAX-ACCESS  read-only
         STATUS      current
         DESCRIPTION
             "The keep alive hold time remaining for this session."
         ::= { hpnicfMplsLdpSessionEntry 4 }

     hpnicfMplsLdpSessionRole OBJECT-TYPE
         SYNTAX      INTEGER {
                        active(1),
                        passive(2)
                     }
         MAX-ACCESS  read-only
         STATUS      current
         DESCRIPTION
             "An indication of whether the LDP Entity associated with
             this session is acting in an 'active' role or
             a 'passive' role."
         ::= { hpnicfMplsLdpSessionEntry 5 }

     hpnicfMplsLdpSessionState OBJECT-TYPE
         SYNTAX      INTEGER {
                        nonexistent(1),
                        initialized(2),
                        openrec(3),
                        opensent(4),
                        operational(5)
                     }
         MAX-ACCESS  read-only
         STATUS      current
         DESCRIPTION
             "The current state of the session, all of the
             states 1 - 5 are based on the state machine for
             session negotiation behavior."
         ::= { hpnicfMplsLdpSessionEntry 6 }

     hpnicfMplsLdpSessionAtmLabelRangeLowerBoundVPI OBJECT-TYPE
         SYNTAX AtmVpIdentifier
         MAX-ACCESS read-only
         STATUS current
         DESCRIPTION
             "The minimum VPI number for this range."
         ::= { hpnicfMplsLdpSessionEntry 7 }

     hpnicfMplsLdpSessionAtmLabelRangeLowerBoundVCI OBJECT-TYPE
         SYNTAX AtmVcIdentifier
         MAX-ACCESS read-only
         STATUS current
         DESCRIPTION
             "The minimum VCI number for this range."
         ::= { hpnicfMplsLdpSessionEntry 8 }

     hpnicfMplsLdpSessionAtmLabelRangeUpperBoundVPI OBJECT-TYPE
         SYNTAX AtmVpIdentifier
         MAX-ACCESS read-only
         STATUS current
         DESCRIPTION
             "The maximum VPI number for this range."
         ::= { hpnicfMplsLdpSessionEntry 9 }

     hpnicfMplsLdpSessionAtmLabelRangeUpperBoundVCI OBJECT-TYPE
         SYNTAX AtmVcIdentifier
         MAX-ACCESS read-only
         STATUS current
         DESCRIPTION
             "The maximum VCI number for this range."
         ::= { hpnicfMplsLdpSessionEntry 10 }



     --
     -- The MPLS LDP Hello Adjacency Table
     --


     hpnicfMplsLdpHelloAdjacencyTable OBJECT-TYPE
         SYNTAX      SEQUENCE OF HpnicfMplsLdpHelloAdjacencyEntry
         MAX-ACCESS  not-accessible
         STATUS      current
         DESCRIPTION
             "A table of Hello Adjacencies for Sessions."
         ::= { hpnicfMplsLdpHelloAdjacencyObjects 1 }

     hpnicfMplsLdpHelloAdjacencyEntry OBJECT-TYPE
         SYNTAX      HpnicfMplsLdpHelloAdjacencyEntry
         MAX-ACCESS  not-accessible
         STATUS      current
         DESCRIPTION
             "Each row represents a single LDP Hello Adjacency.
             An LDP Session can have one or more Hello adjacencies."
         INDEX       { hpnicfMplsLdpLsrIncarnID,
                       hpnicfMplsLdpEntityIfIndex, 
                       hpnicfMplsLdpPeerIndex,
                       hpnicfMplsLdpSessionIndex,
                       hpnicfMplsLdpHelloAdjacencyIndex }
         ::= { hpnicfMplsLdpHelloAdjacencyTable 1 }

     HpnicfMplsLdpHelloAdjacencyEntry ::= SEQUENCE {
         hpnicfMplsLdpHelloAdjacencyIndex                  Unsigned32,
         hpnicfMplsLdpHelloAdjacencyHoldTimeRemaining      TimeInterval
     }

     hpnicfMplsLdpHelloAdjacencyIndex OBJECT-TYPE
         SYNTAX      Unsigned32 (1..4294967295)
         MAX-ACCESS  not-accessible
         STATUS      current
         DESCRIPTION
             "An identifier for the adjacency."
         ::= { hpnicfMplsLdpHelloAdjacencyEntry 1 }

     hpnicfMplsLdpHelloAdjacencyHoldTimeRemaining OBJECT-TYPE
         SYNTAX      TimeInterval
         MAX-ACCESS  read-only
         STATUS      current
         DESCRIPTION
             "The time remaining for this Hello Adjacency."
         ::= { hpnicfMplsLdpHelloAdjacencyEntry 2 }

     --
     -- FSMPLS- CRLSP Table
     --

     hpnicfMplsLdpCrlspTnlTable OBJECT-TYPE
        SYNTAX        SEQUENCE OF HpnicfMplsLdpCrlspTnlEntry
        MAX-ACCESS    not-accessible
        STATUS        current
        DESCRIPTION
            "The hpnicfMplsLdpCrlspTnlTable allows new CRLSP MPLS tunnels
             to be created. The ER hops associated with a CRLSP tunnel
             are to be configured using the hpnicfMplsLdpCrlspErHopTable."
        ::= { hpnicfMplsLdpCrlspTnlObjects 1 }
     
     hpnicfMplsLdpCrlspTnlEntry OBJECT-TYPE
        SYNTAX        HpnicfMplsLdpCrlspTnlEntry
        MAX-ACCESS    not-accessible
        STATUS        current
        DESCRIPTION
            "An  entry  in this table represents an CRLSP MPLS  tunnel.
             An  entry  can be created by a network administrator."
        INDEX  {  hpnicfMplsLdpLsrIncarnID,  hpnicfMplsLdpCrlspTnlIndex  }
           ::= { hpnicfMplsLdpCrlspTnlTable 1 }
     
     HpnicfMplsLdpCrlspTnlEntry ::= SEQUENCE {
           hpnicfMplsLdpCrlspTnlIndex                 MplsTunnelIndex,
           hpnicfMplsLdpCrlspTnlName                  DisplayString,
           hpnicfMplsLdpCrlspTnlDirection             INTEGER,
           hpnicfMplsLdpCrlspTnlSignallingProto       INTEGER,
           hpnicfMplsLdpCrlspTnlSetupPrio             INTEGER,
           hpnicfMplsLdpCrlspTnlHoldingPrio           INTEGER,
           hpnicfMplsLdpCrlspTnlPeakDataRate          BitRate,
           hpnicfMplsLdpCrlspTnlPeakBurstSize         BurstSize,
           hpnicfMplsLdpCrlspTnlCommittedDataRate     BitRate,
           hpnicfMplsLdpCrlspTnlCommittedBurstSize    BurstSize,
           hpnicfMplsLdpCrlspTnlExcessBurstSize       BurstSize,
           hpnicfMplsLdpCrlspTnlIsPinned              TruthValue,
           hpnicfMplsLdpCrlspTnlFrequency             INTEGER,
           hpnicfMplsLdpCrlspTnlWeight                INTEGER,
           hpnicfMplsLdpCrlspTnlRowStatus             RowStatus
        }
     
     hpnicfMplsLdpCrlspTnlIndex OBJECT-TYPE
        SYNTAX        MplsTunnelIndex
        MAX-ACCESS    accessible-for-notify
        STATUS        current
        DESCRIPTION
            "Uniquely identifies this row."
        ::= { hpnicfMplsLdpCrlspTnlEntry 1 }
     
     hpnicfMplsLdpCrlspTnlName OBJECT-TYPE
        SYNTAX        DisplayString
        MAX-ACCESS    read-create
        STATUS        current
        DESCRIPTION
            "The 'canonical' name assigned to the tunnel that can
             be  used  to refer to it on the 'console' port."
        ::= { hpnicfMplsLdpCrlspTnlEntry 2 }
     
     
     hpnicfMplsLdpCrlspTnlDirection OBJECT-TYPE
        SYNTAX        INTEGER { in(1), out(2), inOut(3) }
        MAX-ACCESS    read-create
        STATUS        current
        DESCRIPTION
            "Whether   this  tunnel  is  unidirectional-incoming,
             unidirectional-outgoing, or bidirectional."
        ::= { hpnicfMplsLdpCrlspTnlEntry 3 }
     
     
     hpnicfMplsLdpCrlspTnlSignallingProto OBJECT-TYPE
        SYNTAX        INTEGER { none(1), ldp(2), rsvp(3) }
        MAX-ACCESS    read-create
        STATUS        current
        DESCRIPTION
            "The  signaling protocol, if any, that  set  up  this
             tunnel."
        DEFVAL        { none }
        ::= { hpnicfMplsLdpCrlspTnlEntry 4 }
     
     hpnicfMplsLdpCrlspTnlSetupPrio OBJECT-TYPE
        SYNTAX        INTEGER (0..7)
        MAX-ACCESS    read-create
        STATUS        current
        DESCRIPTION
            "The setup priority of this tunnel."
        REFERENCE
            "Extensions to RSVP for LSP Tunnels, Awduche  et  al,
             Internet  Draft <draft-mpls-rsvp-lsp-tunnel-02.txt>,
             March  1999., Constraint-Based LSP Setup using  LDP,
             Jamoussi,  Internet  Draft  <draft-ietf-mpls-cr-ldp-
             01.txt>, Feb. 1999."
        ::= { hpnicfMplsLdpCrlspTnlEntry 5 }
     
     hpnicfMplsLdpCrlspTnlHoldingPrio OBJECT-TYPE
        SYNTAX        INTEGER (0..7)
        MAX-ACCESS    read-create
        STATUS        current
        DESCRIPTION
            "The holding priority for this tunnel."
        REFERENCE
            "  Extensions to RSVP for LSP Tunnels, Awduche et al,
             Internet  Draft <draft-mpls-rsvp-lsp-tunnel-02.txt>,
             March  1999., Constraint-Based LSP Setup using  LDP,
             Jamoussi,  Internet  Draft  <draft-ietf-mpls-cr-ldp-
             01.txt>, Feb. 1999."
        ::= { hpnicfMplsLdpCrlspTnlEntry 6 }
     
     hpnicfMplsLdpCrlspTnlPeakDataRate OBJECT-TYPE
        SYNTAX        BitRate
        UNITS         "bits per second"
        MAX-ACCESS    read-create
        STATUS        current
        DESCRIPTION
            "The peak rate - the maximum rate at which traffic will be sent on the
             CRLSP."
        REFERENCE
            "Section 4.3.1.2, Constraint-Based LSP Setup using LDP, Jamoussi, et.
             al, <draft-ietf-mpls-crldp-02.txt>, August 1999."
        DEFVAL        { 0 }
        ::= { hpnicfMplsLdpCrlspTnlEntry 7 }
     
     hpnicfMplsLdpCrlspTnlPeakBurstSize OBJECT-TYPE
        SYNTAX        BurstSize
        UNITS         "bytes"
        MAX-ACCESS    read-create
        STATUS        current
        DESCRIPTION
            "The peak burst size - the maximum burst size of the traffic that can 
             occur in the established CRLSP."
        REFERENCE
            "Section 4.3, Constraint-Based LSP Setup using LDP, Jamoussi, et.
             al, <draft-ietf-mpls-crldp-02.txt>, August 1999."
        DEFVAL        { 0 }
        ::= { hpnicfMplsLdpCrlspTnlEntry 8 }
     
     hpnicfMplsLdpCrlspTnlCommittedDataRate OBJECT-TYPE
        SYNTAX        BitRate
        UNITS         "bits per second"
        MAX-ACCESS    read-create
        STATUS        current
        DESCRIPTION
            "The committed rate - the committed rate at which traffic will be sent on the
             CRLSP."
        REFERENCE
            "Section 4.3.1.3, Constraint-Based LSP Setup using LDP, Jamoussi, et.
             al, <draft-ietf-mpls-crldp-02.txt>, August 1999."
        DEFVAL        { 0 }
        ::= { hpnicfMplsLdpCrlspTnlEntry 9 }
     
     hpnicfMplsLdpCrlspTnlCommittedBurstSize OBJECT-TYPE
        SYNTAX        BurstSize
        UNITS         "bytes"
        MAX-ACCESS    read-create
        STATUS        current
        DESCRIPTION
            "The committed burst size - the committed burst size of the traffic 
             that will be handled in the established CRLSP."
        REFERENCE
            "Section 4.3, Constraint-Based LSP Setup using LDP, Jamoussi, et.
             al, <draft-ietf-mpls-crldp-02.txt>, August 1999."
        DEFVAL        { 0 }
        ::= { hpnicfMplsLdpCrlspTnlEntry 10 }
     
     hpnicfMplsLdpCrlspTnlExcessBurstSize OBJECT-TYPE
        SYNTAX        BurstSize
        UNITS         "bytes"
        MAX-ACCESS    read-create
        STATUS        current
        DESCRIPTION
            "The Excess burst size - the excess burst size limit to be used
             for traffic conditioning at the ingress of the CRLSP."
        REFERENCE
            "Section 4.3.1.4, Constraint-Based LSP Setup using LDP, Jamoussi, et.
             al, <draft-ietf-mpls-crldp-02.txt>, August 1999."
        DEFVAL        { 0 }
        ::= { hpnicfMplsLdpCrlspTnlEntry 11 }
     
     hpnicfMplsLdpCrlspTnlIsPinned OBJECT-TYPE
        SYNTAX        TruthValue
        MAX-ACCESS    read-create
        STATUS        current
        DESCRIPTION
            "Indicates  whether  the loose-routed  hops  of  this
             tunnel are to be pinned."
        DEFVAL        { false }
        ::= { hpnicfMplsLdpCrlspTnlEntry 12 }
     
     hpnicfMplsLdpCrlspTnlFrequency OBJECT-TYPE
        SYNTAX        INTEGER (0..2)
        MAX-ACCESS    read-create
        STATUS        current
        DESCRIPTION
            "Indicates the frequency of usage of the established CRLSP."
        REFERENCE
            "Section 4.3.1.1, Constraint-Based LSP Setup using LDP, Jamoussi, et.
             al, <draft-ietf-mpls-crldp-02.txt>, August 1999."
        ::= { hpnicfMplsLdpCrlspTnlEntry 13 }
     
     hpnicfMplsLdpCrlspTnlWeight OBJECT-TYPE
        SYNTAX        INTEGER (0..255)
        MAX-ACCESS    read-create
        STATUS        current
        DESCRIPTION
            "Indicates the weight that is the established CRLSP."
        REFERENCE
            "Section 4.3, Constraint-Based LSP Setup using LDP, Jamoussi, et.
             al, <draft-ietf-mpls-crldp-02.txt>, August 1999."
        ::= { hpnicfMplsLdpCrlspTnlEntry 14 }
     
     hpnicfMplsLdpCrlspTnlRowStatus OBJECT-TYPE
        SYNTAX        RowStatus
        MAX-ACCESS    read-create
        STATUS        current
        DESCRIPTION
            "For controlling the state of this row.
             The status can be set to 'active' only when atleast one ERHOP
             is created in the hpnicfMplsLdpErHopTable, associated with this
             tunnel."
        ::= { hpnicfMplsLdpCrlspTnlEntry 15 }

    -- 
    -- Er-Hop Table
    --

     hpnicfMplsLdpCrlspErHopTable  OBJECT-TYPE
        SYNTAX        SEQUENCE OF HpnicfMplsLdpCrlspErHopEntry
        MAX-ACCESS    not-accessible
        STATUS        current
        DESCRIPTION
            "The hpnicfMplsLdpCrlspErHopTable is used to indicate the hops,
             strict  or  loose,  for an MPLS  CRLSP tunnel  defined  in
             hpnicfMplsLdpCrlspTnlTable. 
     
             There must be atleast one entry in this table for each CRLSP tunnel 
             that is supported in the hpnicfMplsLdpCrlspTnlTable.
             
             The first row in the table  is  the
             first hop after the origination point of the tunnel."
        ::= { hpnicfMplsLdpCrlspTnlObjects 2 }
     
     hpnicfMplsLdpCrlspErHopEntry  OBJECT-TYPE
        SYNTAX        HpnicfMplsLdpCrlspErHopEntry
        MAX-ACCESS    not-accessible
        STATUS        current
        DESCRIPTION
            "An  entry in this table represents a tunnel hop.  An
             entry  is  created  by a network  administrator  for
             signalled ERLSP set up by LDP or RSVP."
        INDEX  {  hpnicfMplsLdpLsrIncarnID, 
                  hpnicfMplsLdpCrlspTnlIndex, hpnicfMplsLdpCrlspErHopIndex  }
           ::= { hpnicfMplsLdpCrlspErHopTable 1 }
     
     HpnicfMplsLdpCrlspErHopEntry ::= SEQUENCE {
           hpnicfMplsLdpCrlspErHopIndex              INTEGER,
           hpnicfMplsLdpCrlspErHopAddrType           INTEGER,
           hpnicfMplsLdpCrlspErHopIpv4Addr           IpAddress,
           hpnicfMplsLdpCrlspErHopIpv4PrefixLen      INTEGER,
           hpnicfMplsLdpCrlspErHopStrictOrLoose      INTEGER,
           hpnicfMplsLdpCrlspErHopRowStatus          RowStatus
        }
     
     hpnicfMplsLdpCrlspErHopIndex OBJECT-TYPE
        SYNTAX        INTEGER
        MAX-ACCESS    not-accessible
        STATUS        current
        DESCRIPTION
            "Secondary  index  into  this table  identifying  the
             particular hop."
        ::= { hpnicfMplsLdpCrlspErHopEntry 1 }
     
     hpnicfMplsLdpCrlspErHopAddrType OBJECT-TYPE
        SYNTAX        INTEGER { ipV4(1) }
        MAX-ACCESS    read-create
        STATUS        current
        DESCRIPTION
            "Address type of this hop."
        DEFVAL        { ipV4 }
        ::= { hpnicfMplsLdpCrlspErHopEntry 2 }
     
     hpnicfMplsLdpCrlspErHopIpv4Addr OBJECT-TYPE
        SYNTAX        IpAddress
        MAX-ACCESS    read-create
        STATUS        current
        DESCRIPTION
            "If hpnicfMplsLdpCrlspErHopAddrType is ipV4(1), IPv4 address of
             this  hop.  This object is not significant otherwise
             and should return a value of 0."
        ::= { hpnicfMplsLdpCrlspErHopEntry 3 }
     
     hpnicfMplsLdpCrlspErHopIpv4PrefixLen OBJECT-TYPE
        SYNTAX        INTEGER (1..32)
        MAX-ACCESS    read-create
        STATUS        current
        DESCRIPTION
            "If  hpnicfMplsLdpCrlspErHopAddrType is ipV4(1), prefix  length
             for  this  hop's IPv4 address.  This object  is  not
             significant otherwise and should return a  value  of
             0."
        ::= { hpnicfMplsLdpCrlspErHopEntry 4 }
     
     hpnicfMplsLdpCrlspErHopStrictOrLoose OBJECT-TYPE
        SYNTAX        INTEGER { strict(1), loose(2) }
        MAX-ACCESS    read-create
        STATUS        current
        DESCRIPTION
            "Whether this is a strict or loose hop."
        ::= { hpnicfMplsLdpCrlspErHopEntry 5 }
     
     hpnicfMplsLdpCrlspErHopRowStatus OBJECT-TYPE
        SYNTAX        RowStatus
        MAX-ACCESS    read-create
        STATUS        current
        DESCRIPTION
            "For creating, modifying and deleting this row."
        ::= { hpnicfMplsLdpCrlspErHopEntry 6 }

     ---
     --- Notifications
     ---

     hpnicfMplsLdpNotificationPrefix   OBJECT IDENTIFIER ::=
                                      { hpnicfMplsLdpNotifications 0 }

     hpnicfMplsLdpFailedInitSessionThresholdExceeded NOTIFICATION-TYPE
     OBJECTS     {
			hpnicfMplsLdpLsrIncarnID, hpnicfMplsLdpEntityID,
                        hpnicfMplsLdpEntityFailedInitSessionThreshold
                 }
     STATUS      current
   DESCRIPTION   "This notification is generated whenever the value
             of hpnicfMplsLdpEntityFailedInitSessionThreshold is
             exceeded."
   ::= { hpnicfMplsLdpNotificationPrefix 1 }

--          OBJECTS     { hpnicfMplsLdpLsrIncarnID, hpnicfMplsLdpEntityID,
--                        hpnicfMplsLdpEntityFailedInitSessionThreshold
--                      }
--          STATUS      current
--          DESCRIPTION
--             "This notification is generated whenever the value
--             of hpnicfMplsLdpEntityFailedInitSessionThreshold is
--             exceeded."
--          ::= { hpnicfMplsLdpNotificationPrefix 1 }

     hpnicfMplsLdpCrlspTunnelUp NOTIFICATION-TYPE
     OBJECTS     {
			hpnicfMplsLdpLsrIncarnID, hpnicfMplsLdpEntityID,
                  hpnicfMplsLdpCrlspTnlIndex 
                 }
        STATUS      current
        DESCRIPTION
            "This notification is generated by the Ingress LSR of the CRLSP tunnel
             on the receipt of Label mapping message from the downstream LSR for
             the LAbel request sent for the CRLSP tunnel."
        ::= { hpnicfMplsLdpNotificationPrefix 2 }
  
     hpnicfMplsLdpCrlspTunnelDown NOTIFICATION-TYPE
     OBJECTS     {
		hpnicfMplsLdpLsrIncarnID, hpnicfMplsLdpEntityID,
                  hpnicfMplsLdpCrlspTnlIndex }
        STATUS      current
        DESCRIPTION
            "This notification is generated when a CRLSP Row status is modified
             to destroy the CRLSP tunnel.  - due to pre-emption etc.,"
        ::= { hpnicfMplsLdpNotificationPrefix 3 }
     
     hpnicfMplsLdpCrlspTunnelSetupFailure NOTIFICATION-TYPE
     OBJECTS     { hpnicfMplsLdpLsrIncarnID, hpnicfMplsLdpEntityID,
                  hpnicfMplsLdpCrlspTnlIndex }
        STATUS      current
        DESCRIPTION
            "This notification is generated by the Ingress LSR of the CRLSP tunnel
             on the receipt of Nak message from the downstream LSR for
             the Label request sent for the CRLSP tunnel. This can occur due to
             improper ER hop values being set, or Traffic resources not available
             etc.,"
        ::=  { hpnicfMplsLdpNotificationPrefix 4 } 


     hpnicfMplsLdpIncarnUpEventFailure  NOTIFICATION-TYPE
     OBJECTS     { hpnicfMplsLdpLsrIncarnID}
        STATUS      current
        DESCRIPTION
            "This notification is generated by LDP to notify 
             the Incarnation UP Event failure"
        ::= { hpnicfMplsLdpNotificationPrefix 11 } 

     hpnicfMplsLdpIncarnDownEventFailure NOTIFICATION-TYPE
     OBJECTS     { hpnicfMplsLdpLsrIncarnID }
        STATUS      current
        DESCRIPTION
            "This notification is generated by LDP to notify 
             the Incarnation DOWN Event failure"
        ::= { hpnicfMplsLdpNotificationPrefix 12 } 

     hpnicfMplsLdpEntityUpEventFailure NOTIFICATION-TYPE
     OBJECTS     { hpnicfMplsLdpLsrIncarnID, hpnicfMplsLdpEntityID}
        STATUS      current
        DESCRIPTION
            "This notification is generated by LDP to notify 
             the ENTITY UP Event failure"
        ::= { hpnicfMplsLdpNotificationPrefix 13 }


     hpnicfMplsLdpEntityDownEventFailure NOTIFICATION-TYPE
     OBJECTS     { hpnicfMplsLdpLsrIncarnID, hpnicfMplsLdpEntityID }
        STATUS      current
        DESCRIPTION
            "This notification is generated by LDP to notify 
             the ENTITY  DOWN Event failure"
        ::= { hpnicfMplsLdpNotificationPrefix 14 }
        hpnicfMplsLdpSessionUpEventFailure NOTIFICATION-TYPE
     OBJECTS     { hpnicfMplsLdpSessionID, hpnicfMplsLdpSessionState }
        STATUS      current
        DESCRIPTION
            "Generation of this trap occurs when the 
            value of 'hpnicfMplsLdpSessionState' enters
             the 'operational(5)' state."
        ::= { hpnicfMplsLdpNotificationPrefix 15 }  
        
     hpnicfMplsLdpSessionDownEventFailure NOTIFICATION-TYPE
     OBJECTS     { hpnicfMplsLdpSessionID, hpnicfMplsLdpSessionState }
        STATUS      current
        DESCRIPTION
            "Generation of this trap occurs when the 
            value of 'hpnicfMplsLdpSessionState' leaves 
            the 'operational(5)' state."
        ::= { hpnicfMplsLdpNotificationPrefix 16 }      

-- End of notifications.
END
