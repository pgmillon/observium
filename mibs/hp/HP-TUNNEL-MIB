HP-TUNNEL-MIB DEFINITIONS ::= BEGIN
    IMPORTS
        MODULE-IDENTITY, OBJECT-TYPE, Integer32, Unsigned32
            FROM SNMPv2-SMI
        RowStatus, TEXTUAL-CONVENTION 
            FROM SNMPv2-TC
        MODULE-COMPLIANCE, OBJECT-GROUP   
            FROM SNMPv2-CONF
        InterfaceIndex
            FROM IF-MIB
        tunnelIfEntry, tunnelInetConfigEntry
            FROM TUNNEL-MIB
        hpSwitch
            FROM HP-ICF-OID;

    hpTunnelMIB MODULE-IDENTITY
        LAST-UPDATED "201007220000Z"   -- July 22nd  2010
        ORGANIZATION "HP Networking"
        CONTACT-INFO "Hewlett Packard Company
                      8000 Foothills Blvd.
                      Roseville, CA 95747"
        DESCRIPTION  "The MIB module for managing the tunnel 
                      interfaces"

        REVISION      "201007220000Z"   -- July 22nd 2010
        DESCRIPTION   "The initial revision of this MIB module"
        
        ::= { hpSwitch  77}


    hpTunnelNotifications OBJECT IDENTIFIER ::= { hpTunnelMIB 0 }
    hpTunnelObjects       OBJECT IDENTIFIER ::= { hpTunnelMIB 1 }
    hpTunnelConformance   OBJECT IDENTIFIER ::= { hpTunnelMIB 2 }

--
-- Textual Conventions
--
    HpTunnelType ::= TEXTUAL-CONVENTION
            STATUS         current
            DESCRIPTION    
                  "The encapsulation method used by a tunnel."
            SYNTAX     INTEGER {
                          unspecified(1),    -- none of the following
                          direct4in4(2),
                          direct6in4(3),
                          direct6in4Ipsec(4),
                          direct6in6(5),
                          ipsecIpv4(6),
                          ipsecIpv6(7)
                     }
--
-- MIB objects
--

--
-- hp Tunnel Config Table
--
    hpTunnelConfigTable OBJECT-TYPE  
        SYNTAX      SEQUENCE OF HpTunnelConfigEntry
        MAX-ACCESS  not-accessible
        STATUS      current
        DESCRIPTION
                  "This table is used to provision a tunnel without 
                  having to configure the source and destination 
                  endpoints of the tunnel."
        ::= { hpTunnelObjects 1 }

    hpTunnelConfigEntry OBJECT-TYPE
        SYNTAX      HpTunnelConfigEntry
        MAX-ACCESS  not-accessible
        STATUS      current
        DESCRIPTION
                  "A set of objects that are used to create a tunnel."
        INDEX    { hpTunnelID }
        ::= { hpTunnelConfigTable 1 }

    HpTunnelConfigEntry ::= SEQUENCE {
                          hpTunnelID                 Integer32,
                          hpTunnelIfIndex            InterfaceIndex,
                          hpTunnelRowStatus          RowStatus
                    }       

    hpTunnelID   OBJECT-TYPE
        SYNTAX      Integer32 (1..2147483647)
        MAX-ACCESS  not-accessible
        STATUS      current
        DESCRIPTION
                  "An identifier to configure the tunnel."
        ::= { hpTunnelConfigEntry 1 }

    hpTunnelIfIndex OBJECT-TYPE
        SYNTAX          InterfaceIndex
        MAX-ACCESS      read-only
        STATUS          current
        DESCRIPTION
                  "The interface index associated with this tunnel 
                  entry."
        ::= { hpTunnelConfigEntry 2 }

    hpTunnelRowStatus OBJECT-TYPE
        SYNTAX                RowStatus
        MAX-ACCESS            read-create
        STATUS                current
        DESCRIPTION
                  "The status of this row, by which new entries may be
                  created, or old entries deleted from this table."
        ::= { hpTunnelConfigEntry 3 }
        
--
--  Augments to tunnelIfTable
--
    hpTunnelIfTable  OBJECT-TYPE
        SYNTAX      SEQUENCE OF HpTunnelIfEntry
        MAX-ACCESS  not-accessible
        STATUS      current
        DESCRIPTION
                  "This table augments the tunnelIfTable."
        ::= { hpTunnelObjects 2 }

    hpTunnelIfEntry OBJECT-TYPE
        SYNTAX      HpTunnelIfEntry
        MAX-ACCESS  not-accessible
        STATUS      current
        DESCRIPTION
                  "A set of objects as an augment to tunnelIfTable."
        AUGMENTS    { tunnelIfEntry }
        ::= { hpTunnelIfTable 1 }

    HpTunnelIfEntry ::= SEQUENCE {
        hpTunnelIfMTU        Unsigned32,
        hpTunnelEncapsMethod HpTunnelType
        }
        

    hpTunnelIfMTU    OBJECT-TYPE
        SYNTAX            Unsigned32
        MAX-ACCESS        read-write
        STATUS            current
        DESCRIPTION
                  "The size of the largest packet which can be 
                  sent/received on the interface, specified in 
                  octets. For interfaces that are used for 
                  transmitting network datagrams, this is the size 
                  of the largest network datagram that can be sent 
                  on this interface."
        DEFVAL {1280}
        ::= { hpTunnelIfEntry 3 }

    hpTunnelEncapsMethod OBJECT-TYPE
        SYNTAX                HpTunnelType
        MAX-ACCESS            read-write
        STATUS                current
        DESCRIPTION
                  "The encapsulation method used by the tunnel."
        ::= { hpTunnelIfEntry 4 }
  
--
--  Augments to tunnelInetConfigTable
--
    hpTunnelInetConfigTable  OBJECT-TYPE
        SYNTAX      SEQUENCE OF HpTunnelInetConfigEntry
        MAX-ACCESS  not-accessible
        STATUS      current
        DESCRIPTION
                  "This table augments the tunnelInetConfigTable."
        ::= { hpTunnelObjects 3 }

    hpTunnelInetConfigEntry OBJECT-TYPE
        SYNTAX      HpTunnelInetConfigEntry
        MAX-ACCESS  not-accessible
        STATUS      current
        DESCRIPTION
                  "A set of objects as an augment to tunnelInetConfigTable."
        AUGMENTS    { tunnelInetConfigEntry }
        ::= { hpTunnelInetConfigTable 1 }

    HpTunnelInetConfigEntry ::= SEQUENCE {
        hpTunnelInetConfigEncapsMethod       HpTunnelType
        }

    hpTunnelInetConfigEncapsMethod OBJECT-TYPE
        SYNTAX                HpTunnelType
        MAX-ACCESS            read-write
        STATUS                current
        DESCRIPTION
                  "The encapsulation method used by this tunnel."
        ::= { hpTunnelInetConfigEntry 1 }

  -- conformance information

    hpTunnelMIBCompliances
        OBJECT IDENTIFIER ::= { hpTunnelConformance 1 }
    hpTunnelMIBGroups 
        OBJECT IDENTIFIER ::= { hpTunnelConformance 2 }

    hpTunnelMIBCompliance MODULE-COMPLIANCE
        STATUS  current
        DESCRIPTION
                  "The compliance statement for the HP Tunnel MIB."
        MODULE  -- this module
        MANDATORY-GROUPS  { hpTunnelProvisionGroup, hpTunnelInetConfigGroup }
        ::= { hpTunnelMIBCompliances 1 }

   -- units of conformance

    hpTunnelProvisionGroup OBJECT-GROUP
        OBJECTS { hpTunnelIfIndex,hpTunnelEncapsMethod,
                  hpTunnelIfMTU,  
                  hpTunnelRowStatus
         }
        STATUS  current
        DESCRIPTION
                  "A collection of objects to support creation of 
                  a tunnel."
        ::= { hpTunnelMIBGroups 1 }

    hpTunnelInetConfigGroup OBJECT-GROUP
        OBJECTS {
            hpTunnelInetConfigEncapsMethod
        }
        STATUS  current
        DESCRIPTION
                  "A collection of objects to augment 
                  tunnelInetConfigTable."
        ::= { hpTunnelMIBGroups 2 }

END
