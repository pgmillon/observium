-- ===========================================================
-- Copyright (c) 2010-2013 Hewlett-Packard Development Company, L.P.
--
-- Description:
-- The information of EPON fiber backup.
-- Reference:
-- Version: V1.0
-- History:
-- V1.0 created by zhaodan.
-- Initial version for hpnicfEponFBMibObjects of hpnicfEpon.
-- ===========================================================
HPN-ICF-EPON-FB-MIB DEFINITIONS ::= BEGIN

IMPORTS
        hpnicfEpon
    FROM HPN-ICF-OID-MIB
        Integer32, OBJECT-TYPE, MODULE-IDENTITY
    FROM SNMPv2-SMI
        RowStatus
    FROM SNMPv2-TC;


hpnicfEponFBMibObjects MODULE-IDENTITY
    LAST-UPDATED "200711271008Z"
    ORGANIZATION
        ""
    CONTACT-INFO
        ""
    DESCRIPTION
        "
        The objects in this MIB module are used to manage and
        display current configuration of fiber backup groups
        based on EPON OLT port.
        "
    ::= { hpnicfEpon 6 }

hpnicfEponFBMIB OBJECT IDENTIFIER ::= { hpnicfEponFBMibObjects 1 }
--
-- hpnicfEponFBMIBTable
--

hpnicfEponFBMIBTable OBJECT-TYPE
    SYNTAX      SEQUENCE OF HpnicfEponFBMIBEntry
    MAX-ACCESS  not-accessible
    STATUS      current
    DESCRIPTION
        "This table defines several optical fiber-backup system parameters."
    ::= { hpnicfEponFBMIB  1 }

hpnicfEponFBMIBEntry OBJECT-TYPE
    SYNTAX      HpnicfEponFBMIBEntry
    MAX-ACCESS  not-accessible
    STATUS      current
    DESCRIPTION
        "The entry of hpnicfEponFBMIBTable."
    INDEX
        {
            hpnicfEponFBGroupIndex
        }
    ::= { hpnicfEponFBMIBTable 1}


HpnicfEponFBMIBEntry ::= SEQUENCE
    {
        hpnicfEponFBGroupIndex          Integer32,
        hpnicfEponFBGroupRowStatus      RowStatus,
        hpnicfEponFBMasterPort          Integer32,
        hpnicfEponFBSlavePort           Integer32,
        hpnicfEponFBMasterPortStatus    INTEGER,
        hpnicfEponFBSlavePortStatus     INTEGER,
        hpnicfEponFBSwitchover          INTEGER
    }

hpnicfEponFBGroupIndex OBJECT-TYPE
    SYNTAX      Integer32
    MAX-ACCESS  not-accessible
    STATUS      current
    DESCRIPTION
        "The EPON fiber-backup group ID."
    ::= { hpnicfEponFBMIBEntry 1 }

hpnicfEponFBGroupRowStatus OBJECT-TYPE
    SYNTAX      RowStatus
    MAX-ACCESS  read-create
    STATUS      current
    DESCRIPTION
        "This object allows entry to be created and deleted
        from the hpnicfEponFBMIBTable."
    ::= { hpnicfEponFBMIBEntry 2 }

hpnicfEponFBMasterPort OBJECT-TYPE
    SYNTAX      Integer32
    MAX-ACCESS  read-create
    STATUS      current
    DESCRIPTION
        "OLT port ifindex of the fiber-backup group.
        Use it to set or get the group master port."
    ::= { hpnicfEponFBMIBEntry 3 }

hpnicfEponFBSlavePort OBJECT-TYPE
    SYNTAX      Integer32
    MAX-ACCESS  read-create
    STATUS      current
    DESCRIPTION
        "OLT port ifindex of the fiber-backup group.
        Use it to set or get the group slave port.
        hpnicfEponFBSlavePort must be set after hpnicfEponFBMasterPort.
        "
    ::= { hpnicfEponFBMIBEntry 4 }

hpnicfEponFBMasterPortStatus OBJECT-TYPE
    SYNTAX      INTEGER
        {
            active(1),
            down(2)
        }
    MAX-ACCESS  read-only
    STATUS      current
    DESCRIPTION
        "The master port status of the fiber-backup group.
        The active state indicates that the port's role is master, the olt chip is right
        and the optical module is inserted.
        The down state indicates others conditions."
    ::= { hpnicfEponFBMIBEntry 5 }

hpnicfEponFBSlavePortStatus OBJECT-TYPE
    SYNTAX      INTEGER
        {
            ready(1),
            down(2)
        }
    MAX-ACCESS  read-only
    STATUS      current
    DESCRIPTION
        "The slave port status of the fiber-backup group.
        The ready state indicates that the port's role is slave, the olt chip is right
        and optical module is inserted.
        The down state indicates others conditions."
    ::= { hpnicfEponFBMIBEntry 6 }

hpnicfEponFBSwitchover OBJECT-TYPE
    SYNTAX      INTEGER
        {
            false(1),
            true(2)
        }
    MAX-ACCESS  read-create
    STATUS      current
    DESCRIPTION
        "Switch the fiber backup group's two port manually.
        The group must has two ports
        and the value of hpnicfEponFBSlavePortStatus must be ready before Switchover.
        after Switchover the port's role will be changed.
        The value true is for switch-over.  The default value is false."
    ::= { hpnicfEponFBMIBEntry 7 }

END
