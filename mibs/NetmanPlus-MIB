--   NETMANPLUS-MIB { iso org(3) dod(6) internet(1) private(4)
--   enterprises(1) riello(5491) }

NetmanPlus-MIB DEFINITIONS ::= BEGIN

-- Title: NetmanPlus MIB    - vars for UPS types: NetmanPlus
-- Version: 1.1 by Michele Marcon
-- Date: 09.12.2008

IMPORTS
   enterprises, IpAddress, TimeTicks, Gauge
      FROM RFC1155-SMI
   DisplayString
      FROM RFC1213-MIB
   OBJECT-TYPE
      FROM RFC-1212
   TRAP-TYPE
      FROM RFC-1215;


rielloMIB              OBJECT IDENTIFIER ::=  { enterprises 5491 }

netmanplus             OBJECT IDENTIFIER ::=  { rielloMIB 6 }

netConfiguration       OBJECT IDENTIFIER ::=  { netmanplus 1 }
services               OBJECT IDENTIFIER ::=  { netmanplus 2 }
emailConfiguration     OBJECT IDENTIFIER ::=  { netmanplus 3 }
wolConfiguration       OBJECT IDENTIFIER ::=  { netmanplus 4 }
trapReceivers          OBJECT IDENTIFIER ::=  { netmanplus 5 }
hostsList              OBJECT IDENTIFIER ::=  { netmanplus 6 }
communities            OBJECT IDENTIFIER ::=  { netmanplus 7 }
upsConfiguration       OBJECT IDENTIFIER ::=  { netmanplus 8 }
modemConfiguration     OBJECT IDENTIFIER ::=  { netmanplus 9 }
commands               OBJECT IDENTIFIER ::=  { netmanplus 10}
otherConfig            OBJECT IDENTIFIER ::=  { netmanplus 11}

-- object types

-- the netmanplus configuration group

nLocalAddress OBJECT-TYPE
   SYNTAX NetworkAddress
   ACCESS read-only
   STATUS mandatory
   DESCRIPTION
      "Netman IP address."
   ::= { netConfiguration 1 }

nNetworkId OBJECT-TYPE
   SYNTAX NetworkAddress
   ACCESS read-only
   STATUS mandatory
   DESCRIPTION
      "Netman network mask."
   ::= { netConfiguration 2 }

nGatewayAddress OBJECT-TYPE
   SYNTAX NetworkAddress
   ACCESS read-only
   STATUS mandatory
   DESCRIPTION
      "Gateway IP address."
   ::= { netConfiguration 3 }

nHostname OBJECT-TYPE
   SYNTAX NetworkAddress
   ACCESS read-only
   STATUS mandatory
   DESCRIPTION
      "Netman host name."
   ::= { netConfiguration 4 }

nUDPPortNumber OBJECT-TYPE
   SYNTAX WORD
   ACCESS read-only
   STATUS mandatory
   DESCRIPTION
      "Port, where is enabled UDP communication 1."
   ::= { netConfiguration 5 }

nMailserver OBJECT-TYPE
   SYNTAX NetworkAddress
   ACCESS read-only
   STATUS mandatory
   DESCRIPTION
      "Mail server IP address."
   ::= { netConfiguration 6 }

nPrimaryDNS OBJECT-TYPE
   SYNTAX NetworkAddress
   ACCESS read-only
   STATUS mandatory
   DESCRIPTION
      "Primary DNS IP address."
   ::= { netConfiguration 7 }

nSecondaryDNS OBJECT-TYPE
   SYNTAX NetworkAddress
   ACCESS read-only
   STATUS mandatory
   DESCRIPTION
      "Secondary DNS IP address."
   ::= { netConfiguration 8 }

nDHCPEnabled OBJECT-TYPE
   SYNTAX INTEGER {
   Disabled (0),
   Enabled  (1),
   }
   ACCESS read-only
   STATUS mandatory
   DESCRIPTION
      "DHCP client active."
   ::= { netConfiguration 9 }

-- the netmanplus services group

nTelnetConnection OBJECT-TYPE
   SYNTAX INTEGER {
   Disabled (0),
   Enabled  (1),
   }
   ACCESS read-write
   STATUS mandatory
   DESCRIPTION
      "Enable telnet connection."
   ::= { services 1 }

nHTTPConnection OBJECT-TYPE
   SYNTAX INTEGER{
   Disabled (0),
   Enabled  (1),
   }
   ACCESS read-write
   STATUS mandatory
   DESCRIPTION
      "Enable HTTP connection."
   ::= { services 2 }

nModemConnection OBJECT-TYPE
   SYNTAX INTEGER{
   Disabled (0),
   Enabled  (1),
   }
   ACCESS read-write
   STATUS mandatory
   DESCRIPTION
      "Enable modem connection."
   ::= { services 3 }

nModemRxConnection OBJECT-TYPE
   SYNTAX INTEGER{
   Disabled (0),
   Enabled  (1),
   }
   ACCESS read-write
   STATUS mandatory
   DESCRIPTION
      "Enable modem receive connection."
   ::= { services 4 }

nSNMPConnection OBJECT-TYPE
   SYNTAX INTEGER{
   Disabled (0),
   Enabled  (1),
   }
   ACCESS read-write
   STATUS mandatory
   DESCRIPTION
      "Enable SNMP connection."
   ::= { services 5 }

nUDPConnection OBJECT-TYPE
   SYNTAX INTEGER{
   Disabled (0),
   Enabled  (1),
   }
   ACCESS read-write
   STATUS mandatory
   DESCRIPTION
      "Enable UDP connection."
   ::= { services 6 }

nFTPConnection OBJECT-TYPE
   SYNTAX INTEGER{
   Disabled (0),
   Enabled  (1),
   }
   ACCESS read-write
   STATUS mandatory
   DESCRIPTION
      "Enable FTP connection."
   ::= { services 7 }

nDatalog OBJECT-TYPE
   SYNTAX INTEGER{
   Disabled (0),
   Enabled  (1),
   }
   ACCESS read-write
   STATUS mandatory
   DESCRIPTION
      "Enable Data logging."
   ::= { services 8 }

nEmail OBJECT-TYPE
   SYNTAX INTEGER{
   Disabled (0),
   Enabled  (1),
   }
   ACCESS read-write
   STATUS mandatory
   DESCRIPTION
      "Enable Email."
   ::= { services 9 }

nReport OBJECT-TYPE
   SYNTAX INTEGER{
   Disabled (0),
   Enabled  (1),
   }
   ACCESS read-write
   STATUS mandatory
   DESCRIPTION
      "Enable Email report."
   ::= { services 10 }

nSerialN OBJECT-TYPE
   SYNTAX INTEGER{
   Disabled (0),
   Enabled  (1),
   }
   ACCESS read-write
   STATUS mandatory
   DESCRIPTION
      "Enable Serial Network."
   ::= { services 11 }

nSensors OBJECT-TYPE
   SYNTAX INTEGER{
   Disabled (0),
   Enabled  (1),
   }
   ACCESS read-write
   STATUS mandatory
   DESCRIPTION
      "Enable environmental sensors."
   ::= { services 12 }

nWakeOnLan OBJECT-TYPE
   SYNTAX INTEGER{
   Disabled (0),
   Enabled  (1),
   }
   ACCESS read-write
   STATUS mandatory
   DESCRIPTION
      "Enable Data logging."
   ::= { services 13 }

-- the netman emailConfiguration group

nEmail1 OBJECT-TYPE
   SYNTAX DisplayString  (SIZE (0..20))
   ACCESS read-only
   STATUS mandatory
   DESCRIPTION
      "First email address."
   ::= { emailConfiguration 1 }

nEmail2 OBJECT-TYPE
   SYNTAX DisplayString  (SIZE (0..20))
   ACCESS read-only
   STATUS mandatory
   DESCRIPTION
      "Second email address."
   ::= { emailConfiguration 2 }

nEmail3 OBJECT-TYPE
   SYNTAX DisplayString  (SIZE (0..20))
   ACCESS read-only
   STATUS mandatory
   DESCRIPTION
      "Third email address."
   ::= { emailConfiguration 3 }

nSenderAddress OBJECT-TYPE
   SYNTAX DisplayString  (SIZE (0..20))
   ACCESS read-only
   STATUS mandatory
   DESCRIPTION
      "Email address of the sender."
   ::= { emailConfiguration 4 }

nCustomer OBJECT-TYPE
   SYNTAX DisplayString  (SIZE (0..20))
   ACCESS read-only
   STATUS mandatory
   DESCRIPTION
      "Custom information."
   ::= { emailConfiguration 5 }

nReportInterval OBJECT-TYPE
   SYNTAX DisplayString  (SIZE (0..20))
   ACCESS read-only
   STATUS mandatory
   DESCRIPTION
      "Report interval expressed in number of days."
   ::= { emailConfiguration 6 }

nUserName OBJECT-TYPE
   SYNTAX DisplayString  (SIZE (0..20))
   ACCESS read-only
   STATUS mandatory
   DESCRIPTION
      "User name for SNMP-AUTH. This field is blank when standard SNMP is used."
   ::= { emailConfiguration 7 }

nPassword OBJECT-TYPE
   SYNTAX DisplayString  (SIZE (0..20))
   ACCESS read-only
   STATUS mandatory
   DESCRIPTION
      "Password for SNMP-AUTH. This field is blank when standard SNMP is used."
   ::= { emailConfiguration 8 }

nEmailLogic1 OBJECT-TYPE
   SYNTAX WORD
   ACCESS read-only
   STATUS mandatory
   DESCRIPTION
      "Email logic for email 1."
   ::= { emailConfiguration 9 }

nEmailLogic2 OBJECT-TYPE
   SYNTAX WORD
   ACCESS read-only
   STATUS mandatory
   DESCRIPTION
      "Email logic for email 2."
   ::= { emailConfiguration 10 }

nEmailLogic3 OBJECT-TYPE
   SYNTAX WORD
   ACCESS read-only
   STATUS mandatory
   DESCRIPTION
      "Email logic for email 3."
   ::= { emailConfiguration 11 }

-- the netman wolConfiguration group

nWOLAddress1 OBJECT-TYPE
   SYNTAX DisplayString  (SIZE (0..20))
   ACCESS read-only
   STATUS mandatory
   DESCRIPTION
      "MAC address 1 for Wake-On-Lan"
   ::= { wolConfiguration 1 }

nWOLAddress2 OBJECT-TYPE
   SYNTAX DisplayString  (SIZE (0..20))
   ACCESS read-only
   STATUS mandatory
   DESCRIPTION
      "MAC address 2 for Wake-On-Lan"
   ::= { wolConfiguration 2 }

nWOLAddress3 OBJECT-TYPE
   SYNTAX DisplayString  (SIZE (0..20))
   ACCESS read-only
   STATUS mandatory
   DESCRIPTION
      "MAC address 3 for Wake-On-Lan"
   ::= { wolConfiguration 3 }

nWOLAddress4 OBJECT-TYPE
   SYNTAX DisplayString  (SIZE (0..20))
   ACCESS read-only
   STATUS mandatory
   DESCRIPTION
      "MAC address 4 for Wake-On-Lan"
   ::= { wolConfiguration 4 }

nWOLAddress5 OBJECT-TYPE
   SYNTAX DisplayString  (SIZE (0..20))
   ACCESS read-only
   STATUS mandatory
   DESCRIPTION
      "MAC address 5 for Wake-On-Lan"
   ::= { wolConfiguration 5 }

nWOLAddress6 OBJECT-TYPE
   SYNTAX DisplayString  (SIZE (0..20))
   ACCESS read-only
   STATUS mandatory
   DESCRIPTION
      "MAC address 6 for Wake-On-Lan"
   ::= { wolConfiguration 6 }

nWOLAddress7 OBJECT-TYPE
   SYNTAX DisplayString  (SIZE (0..20))
   ACCESS read-only
   STATUS mandatory
   DESCRIPTION
      "MAC address 7 for Wake-On-Lan"
   ::= { wolConfiguration 7 }

nWOLAddress8 OBJECT-TYPE
   SYNTAX DisplayString  (SIZE (0..20))
   ACCESS read-only
   STATUS mandatory
   DESCRIPTION
      "MAC address 8 for Wake-On-Lan"
   ::= { wolConfiguration 8 }

nWOLDelay1 OBJECT-TYPE
   SYNTAX DisplayString  (SIZE (0..4))
   ACCESS read-only
   STATUS mandatory
   DESCRIPTION
      "Delay for MAC address 1 for Wake-On-Lan"
   ::= { wolConfiguration 9 }

nWOLDelay2 OBJECT-TYPE
   SYNTAX DisplayString  (SIZE (0..4))
   ACCESS read-only
   STATUS mandatory
   DESCRIPTION
      "Delay for MAC address 2 for Wake-On-Lan"
   ::= { wolConfiguration 10}

nWOLDelay3 OBJECT-TYPE
   SYNTAX DisplayString  (SIZE (0..4))
   ACCESS read-only
   STATUS mandatory
   DESCRIPTION
      "Delay for MAC address 3 for Wake-On-Lan"
   ::= { wolConfiguration 11}

nWOLDelay4 OBJECT-TYPE
   SYNTAX DisplayString  (SIZE (0..4))
   ACCESS read-only
   STATUS mandatory
   DESCRIPTION
      "Delay for MAC address 4 for Wake-On-Lan"
   ::= { wolConfiguration 12}

nWOLDelay5 OBJECT-TYPE
   SYNTAX DisplayString  (SIZE (0..4))
   ACCESS read-only
   STATUS mandatory
   DESCRIPTION
      "Delay for MAC address 5 for Wake-On-Lan"
   ::= { wolConfiguration 13}

nWOLDelay6 OBJECT-TYPE
   SYNTAX DisplayString  (SIZE (0..4))
   ACCESS read-only
   STATUS mandatory
   DESCRIPTION
      "Delay for MAC address 6 for Wake-On-Lan"
   ::= { wolConfiguration 14}

nWOLDelay7 OBJECT-TYPE
   SYNTAX DisplayString  (SIZE (0..4))
   ACCESS read-only
   STATUS mandatory
   DESCRIPTION
      "Delay for MAC address 7 for Wake-On-Lan"
   ::= { wolConfiguration 15}

nWOLDelay8 OBJECT-TYPE
   SYNTAX DisplayString  (SIZE (0..4))
   ACCESS read-only
   STATUS mandatory
   DESCRIPTION
      "Delay for MAC address 8 for Wake-On-Lan"
   ::= { wolConfiguration 16}

-- the netman trapReceivers group

nTrapsReceiverAddress1 OBJECT-TYPE
   SYNTAX NetworkAddress
   ACCESS read-write
   STATUS mandatory
   DESCRIPTION
      "1. IP address where are sended traps."
   ::= { trapReceivers 1 }

nTrapsReceiverAddress2 OBJECT-TYPE
   SYNTAX NetworkAddress
   ACCESS read-write
   STATUS mandatory
   DESCRIPTION
      "2. IP address where are sended traps."
   ::= { trapReceivers 2 }

nTrapsReceiverAddress3 OBJECT-TYPE
   SYNTAX NetworkAddress
   ACCESS read-write
   STATUS mandatory
   DESCRIPTION
      "3. IP address where are sended traps."
   ::= { trapReceivers 3 }

nTrapsReceiverAddress4 OBJECT-TYPE
   SYNTAX NetworkAddress
   ACCESS read-write
   STATUS mandatory
   DESCRIPTION
      "4. IP address where are sended traps."
   ::= { trapReceivers 4 }

nTrapsReceiverAddress5 OBJECT-TYPE
   SYNTAX NetworkAddress
   ACCESS read-write
   STATUS mandatory
   DESCRIPTION
      "5. IP address where are sended traps."
   ::= { trapReceivers 5 }

nTrapsReceiverAddress6 OBJECT-TYPE
   SYNTAX NetworkAddress
   ACCESS read-write
   STATUS mandatory
   DESCRIPTION
      "6. IP address where are sended traps."
   ::= { trapReceivers 6 }

nTrapsReceiverAddress7 OBJECT-TYPE
   SYNTAX NetworkAddress
   ACCESS read-write
   STATUS mandatory
   DESCRIPTION
      "7. IP address where are sended traps."
   ::= { trapReceivers 7 }

-- the netman hostsList group

nHostAddress1 OBJECT-TYPE
   SYNTAX NetworkAddress
   ACCESS read-write
   STATUS mandatory
   DESCRIPTION
      "1. Host IP address."
   ::= { hostsList 1 }

nHostAddress2 OBJECT-TYPE
   SYNTAX NetworkAddress
   ACCESS read-write
   STATUS mandatory
   DESCRIPTION
      "2. Host IP address."
   ::= { hostsList 2 }

nHostAddress3 OBJECT-TYPE
   SYNTAX NetworkAddress
   ACCESS read-write
   STATUS mandatory
   DESCRIPTION
      "3. Host IP address."
   ::= { hostsList 3 }

nHostAddress4 OBJECT-TYPE
   SYNTAX NetworkAddress
   ACCESS read-write
   STATUS mandatory
   DESCRIPTION
      "4. Host IP address."
   ::= { hostsList 4 }

nHostAddress5 OBJECT-TYPE
   SYNTAX NetworkAddress
   ACCESS read-write
   STATUS mandatory
   DESCRIPTION
      "5. Host IP address."
   ::= { hostsList 5 }

nHostAddress6 OBJECT-TYPE
   SYNTAX NetworkAddress
   ACCESS read-write
   STATUS mandatory
   DESCRIPTION
      "6. Host IP address."
   ::= { hostsList 6 }

nHostAddress7 OBJECT-TYPE
   SYNTAX NetworkAddress
   ACCESS read-write
   STATUS mandatory
   DESCRIPTION
      "7. Host IP address."
   ::= { hostsList 7 }

-- the netman community group

nGetCommunity OBJECT-TYPE
   SYNTAX DisplayString  (SIZE (0..20))
   ACCESS read-write
   STATUS mandatory
   DESCRIPTION
      "SNMP get community."
   ::= { communities 1 }

nSetCommunity OBJECT-TYPE
   SYNTAX DisplayString  (SIZE (0..20))
   ACCESS read-write
   STATUS mandatory
   DESCRIPTION
      "SNMP set community."
   ::= { communities 2 }

nTrapCommunity OBJECT-TYPE
   SYNTAX DisplayString  (SIZE (0..20))
   ACCESS read-write
   STATUS mandatory
   DESCRIPTION
      "SNMP trap community."
   ::= { communities 3 }

-- the netman upsConfiguration group

nPRTKcode OBJECT-TYPE
   SYNTAX DisplayString  (SIZE (0..16))
   ACCESS read-write
   STATUS mandatory
   DESCRIPTION
      "PRTK code of UPS."
   ::= { upsConfiguration 1 }

nUPSName OBJECT-TYPE
   SYNTAX DisplayString  (SIZE (0..16))
   ACCESS read-write
   STATUS mandatory
   DESCRIPTION
      "Name of UPS."
   ::= { upsConfiguration 2 }

nUPSAddress OBJECT-TYPE
   SYNTAX INTEGER
   ACCESS read-write
   STATUS mandatory
   DESCRIPTION
      "Communication address of UPS."
   ::= { upsConfiguration 3 }

nSerialNumber OBJECT-TYPE
   SYNTAX DisplayString  (SIZE (0..12))
   ACCESS read-write
   STATUS mandatory
   DESCRIPTION
      "Serial number of UPS."
   ::= { upsConfiguration 4 }

nUPSStatus OBJECT-TYPE
   SYNTAX DisplayString
   ACCESS read-only
   STATUS mandatory
   DESCRIPTION
      "Status of UPS."
   ::= { upsConfiguration 5 }

-- the netman modemConfiguration group

nPhoneNumber1 OBJECT-TYPE
   SYNTAX DisplayString  (SIZE (0..20))
   ACCESS read-only
   STATUS mandatory
   DESCRIPTION
      "First phone number to make connection."
   ::= { modemConfiguration 1 }

nPhoneNumber2 OBJECT-TYPE
   SYNTAX DisplayString  (SIZE (0..20))
   ACCESS read-only
   STATUS mandatory
   DESCRIPTION
      "Second phone number to make connection."
   ::= { modemConfiguration 2 }

nPhoneNumber3 OBJECT-TYPE
   SYNTAX DisplayString  (SIZE (0..20))
   ACCESS read-only
   STATUS mandatory
   DESCRIPTION
      "Third phone number to make connection."
   ::= { modemConfiguration 3 }

nInitialString OBJECT-TYPE
   SYNTAX DisplayString  (SIZE (0..20))
   ACCESS read-only
   STATUS mandatory
   DESCRIPTION
      "Initialization string for setup the modem."
   ::= { modemConfiguration 4 }

nDialString OBJECT-TYPE
   SYNTAX DisplayString  (SIZE (0..20))
   ACCESS read-only
   STATUS mandatory
   DESCRIPTION
      "AT Dial string."
   ::= { modemConfiguration 5 }

nNumberOfRepeat OBJECT-TYPE
   SYNTAX INTEGER
   ACCESS read-only
   STATUS mandatory
   DESCRIPTION
      "Number of try to make connection."
   ::= { modemConfiguration 6 }

nDelayBetweenCalls OBJECT-TYPE
   SYNTAX INTEGER
   ACCESS read-only
   STATUS mandatory
   DESCRIPTION
      "Delay between two calls."
   ::= { modemConfiguration 7 }

nModemLogic1 OBJECT-TYPE
   SYNTAX WORD
   ACCESS read-only
   STATUS mandatory
   DESCRIPTION
      "Modem logic for phone number 1."
   ::= { modemConfiguration 8 }

nModemLogic2 OBJECT-TYPE
   SYNTAX WORD
   ACCESS read-only
   STATUS mandatory
   DESCRIPTION
      "Modem logic for phone number 2."
   ::= { modemConfiguration 9 }

nModemLogic3 OBJECT-TYPE
   SYNTAX WORD
   ACCESS read-only
   STATUS mandatory
   DESCRIPTION
      "Modem logic for phone number 3."
   ::= { modemConfiguration 10 }

nModemLogicANDOR OBJECT-TYPE
   SYNTAX WORD
   ACCESS read-only
   STATUS mandatory
   DESCRIPTION
      "Modem AND/OR logic for all phone numbers."
   ::= { modemConfiguration 11 }

-- the netman commands group

nCommands OBJECT-TYPE
   SYNTAX INTEGER{
   None   (0),
   ResetNetman (1),
   StartUpgradeFirmware (2),
   WriteConfiguration (3),
   RestoreOriginalConfiguration (4),
   }
   ACCESS read-write
   STATUS mandatory
   DESCRIPTION
      "Commands for Netman: Reset Netman, save changed configuration,
	Upgrade Netman with new firmware, Restore original configuration..."
   ::= { commands 1 }

-- the netman otherConfig group

nClock OBJECT-TYPE
   SYNTAX TimeTicks
   ACCESS read-only
   STATUS mandatory
   DESCRIPTION
      "Current time according to the internal clock. Value is in milliseconds since January 1, 2000, 00:00:00 GMT"
   ::= { otherConfig 1 }

nLogfrequency OBJECT-TYPE
   SYNTAX WORD
   ACCESS read-write
   STATUS mandatory
   DESCRIPTION
      "Frequency for data logging (sec.)."
   ::= { otherConfig 2 }

END
