-- =============================================================
-- Copyright (c) 2004-2009 by HH3C Technologies. All rights reserved.
--
-- Description:
-- Reference:
-- Version: V1.1
-- History:
--   V1.0 2009-04-30 Initial Version by jinyi
--   V1.1 2009-12-30 added hh3cAccessMediaChanged by jinyi
-- =============================================================
HH3C-3GMODEM-MIB DEFINITIONS ::= BEGIN
    IMPORTS
        MODULE-IDENTITY, OBJECT-TYPE, NOTIFICATION-TYPE, Integer32, Unsigned32
            FROM SNMPv2-SMI
        TEXTUAL-CONVENTION
            FROM SNMPv2-TC
        SnmpAdminString
            FROM SNMP-FRAMEWORK-MIB
        hh3cCommon
            FROM HH3C-OID-MIB;

hh3c3GModem MODULE-IDENTITY
    LAST-UPDATED    "200904301200Z"
    ORGANIZATION
        "Hangzhou H3C Tech. Co., Ltd."
    CONTACT-INFO
        "Platform Team Hangzhou H3C Tech. Co., Ltd.
        Hai-Dian District Beijing P.R. China
        http://www.h3c.com
        Zip:100085
        "
    DESCRIPTION
        "The information about the wireless card and the UIM
         (User Identification Module)."
    REVISION        "200904301200Z"
    DESCRIPTION
        "Initial version of this MIB module."
    ::= { hh3cCommon 98 }

Hh3cUIMStatusType ::= TEXTUAL-CONVENTION
    STATUS      current
    DESCRIPTION
        "The status of the UIM."
    SYNTAX      INTEGER
        {
            absent(1),      -- the UIM is absent
            initial(2),     -- the UIM is initial
            fault(3),       -- something wrong in UIM
            unprotected(4), -- the UIM is not protected with PIN
                            -- (Personal Identification Number) and can be
                            -- used normally
            protected(5),   -- the UIM is protected with PIN and can be
                            -- used normally
            pinLocked(6),   -- the UIM is locked, and need be unlocked with PIN
            pukLocked(7),   -- the UIM is locked, and need be unlocked with PUK
                            -- (PIN Unblocking Key)
            selfDestruct(8) -- the UIM is destruct by itself
        }

hh3c3GModemObjects     OBJECT IDENTIFIER ::= { hh3c3GModem 1 }

hh3cWirelessCard OBJECT IDENTIFIER ::= { hh3c3GModemObjects 1 }
hh3cUIM OBJECT IDENTIFIER ::= { hh3c3GModemObjects 2 }

-- The wireless card table
hh3cWirelessCardTable OBJECT-TYPE
    SYNTAX      SEQUENCE OF Hh3cWirelessCardEntry
    MAX-ACCESS  not-accessible
    STATUS      current
    DESCRIPTION
        "This table contains one row per wireless card."
    ::= { hh3cWirelessCard 1 }

hh3cWirelessCardEntry OBJECT-TYPE
    SYNTAX      Hh3cWirelessCardEntry
    MAX-ACCESS  not-accessible
    STATUS      current
    DESCRIPTION
        "Information about a particular wireless card."
    INDEX { hh3cWirelessCardIndex }
    ::= { hh3cWirelessCardTable 1 }

Hh3cWirelessCardEntry ::= SEQUENCE
    {
        hh3cWirelessCardIndex               Integer32,
        hh3cWirelessCardModelName           SnmpAdminString,
        hh3cWirelessCardMfgName             SnmpAdminString,
        hh3cWirelessCardDescription         SnmpAdminString,
        hh3cWirelessCardSerialNumber        SnmpAdminString,
        hh3cWirelessCardCMIIID              SnmpAdminString,
        hh3cWirelessCardHardwareVersion     SnmpAdminString,
        hh3cWirelessCardFirmwareVersion     SnmpAdminString,
        hh3cWirelessCardPRLVersion          SnmpAdminString
    }

hh3cWirelessCardIndex OBJECT-TYPE
    SYNTAX      Integer32 (1..2147483647)
    MAX-ACCESS  not-accessible
    STATUS      current
    DESCRIPTION
        "The index for this entry."
    ::= { hh3cWirelessCardEntry 1 }

hh3cWirelessCardModelName OBJECT-TYPE
    SYNTAX      SnmpAdminString
    MAX-ACCESS  read-only
    STATUS      current
    DESCRIPTION
        "The model name of this card."
    ::= { hh3cWirelessCardEntry 2 }

hh3cWirelessCardMfgName OBJECT-TYPE
    SYNTAX      SnmpAdminString
    MAX-ACCESS  read-only
    STATUS      current
    DESCRIPTION
        "The name of the manufacturer of this card."
    ::= { hh3cWirelessCardEntry 3 }

hh3cWirelessCardDescription OBJECT-TYPE
    SYNTAX      SnmpAdminString
    MAX-ACCESS  read-only
    STATUS      current
    DESCRIPTION
        "The textual description of this card."
    ::= { hh3cWirelessCardEntry 4 }

hh3cWirelessCardSerialNumber OBJECT-TYPE
    SYNTAX      SnmpAdminString (SIZE (0..32))
    MAX-ACCESS  read-only
    STATUS      current
    DESCRIPTION
        "The vendor-specific serial number string for this card."
    ::= { hh3cWirelessCardEntry 5 }

hh3cWirelessCardCMIIID OBJECT-TYPE
    SYNTAX      SnmpAdminString (SIZE (0..32))
    MAX-ACCESS  read-only
    STATUS      current
    DESCRIPTION
        "The card ID of CMII (Ministry of Information Industry of China)."
    ::= { hh3cWirelessCardEntry 6 }

hh3cWirelessCardHardwareVersion OBJECT-TYPE
    SYNTAX      SnmpAdminString
    MAX-ACCESS  read-only
    STATUS      current
    DESCRIPTION
        "The vendor-specific hardware version string for this card."
    ::= { hh3cWirelessCardEntry 7 }

hh3cWirelessCardFirmwareVersion OBJECT-TYPE
    SYNTAX      SnmpAdminString
    MAX-ACCESS  read-only
    STATUS      current
    DESCRIPTION
        "The vendor-specific firmware version string for this card."
    ::= { hh3cWirelessCardEntry 8 }

hh3cWirelessCardPRLVersion OBJECT-TYPE
    SYNTAX      SnmpAdminString
    MAX-ACCESS  read-only
    STATUS      current
    DESCRIPTION
        "The preferred roaming list version for this card."
    ::= { hh3cWirelessCardEntry 9 }

-- The UIM information table
hh3cUIMInfoTable OBJECT-TYPE
    SYNTAX      SEQUENCE OF Hh3cUIMInfoEntry
    MAX-ACCESS  not-accessible
    STATUS      current
    DESCRIPTION
        "This table contains one row per UIM."
    ::= { hh3cUIM 1 }

hh3cUIMInfoEntry OBJECT-TYPE
    SYNTAX      Hh3cUIMInfoEntry
    MAX-ACCESS  not-accessible
    STATUS      current
    DESCRIPTION
        "The information about the UIM."
    INDEX { hh3cWirelessCardIndex, hh3cUIMIndex }
    ::= { hh3cUIMInfoTable 1 }

Hh3cUIMInfoEntry ::= SEQUENCE
    {
        hh3cUIMIndex          Integer32,
        hh3cUIMStatus         Hh3cUIMStatusType,
        hh3cUIMImsi           SnmpAdminString,
        hh3cUIMPin            SnmpAdminString,
        hh3cUIMVoltage        Unsigned32,
        hh3cUIMProvider       SnmpAdminString,
        hh3cUIMSignal         Integer32,
        hh3cUIMTryPinPukTimes Unsigned32,
        hh3cUIMOldPin         SnmpAdminString
    }

hh3cUIMIndex OBJECT-TYPE
    SYNTAX      Integer32 (0..2147483647)
    MAX-ACCESS  not-accessible
    STATUS      current
    DESCRIPTION
        "The index for this entry."
    ::= { hh3cUIMInfoEntry 1 }

hh3cUIMStatus OBJECT-TYPE
    SYNTAX      Hh3cUIMStatusType
    MAX-ACCESS  read-only
    STATUS      current
    DESCRIPTION
        "The status about this UIM."
    ::= { hh3cUIMInfoEntry 2 }

hh3cUIMImsi OBJECT-TYPE
    SYNTAX      SnmpAdminString (SIZE (0..32))
    MAX-ACCESS  read-only
    STATUS      current
    DESCRIPTION
        "The IMSI (International Mobile Subscriber Identification Number) about
        this UIM.  If this information is unknown to the agent, then this object
        will be returned a zero-length string."
    ::= { hh3cUIMInfoEntry 3 }

hh3cUIMPin OBJECT-TYPE
    SYNTAX      SnmpAdminString (SIZE (0..9))
    MAX-ACCESS  read-only
    STATUS      current
    DESCRIPTION
        "The PIN about this UIM.  If this information is unknown to the agent,
        then this object will be returned a zero-length string."
    ::= { hh3cUIMInfoEntry 4 }

hh3cUIMVoltage OBJECT-TYPE
    SYNTAX      Unsigned32(0..4294967295)
    UNITS       "milli-volt"
    MAX-ACCESS  read-only
    STATUS      current
    DESCRIPTION
        "The voltage about this UIM.  If this information is unknown to the
        agent, then this object will be returned 4294967295."
    ::= { hh3cUIMInfoEntry 5 }

hh3cUIMProvider OBJECT-TYPE
    SYNTAX      SnmpAdminString (SIZE (0..32))
    MAX-ACCESS  read-only
    STATUS      current
    DESCRIPTION
        "The provider of mobile network.  If this information is unknown to the
        agent, then this object will be returned a zero-length string."
    ::= { hh3cUIMInfoEntry 6 }

hh3cUIMSignal OBJECT-TYPE
    SYNTAX      Integer32(0..31 | 99)
    MAX-ACCESS  read-only
    STATUS      current
    DESCRIPTION
        "The intensity of the signal about this UIM.
        A value of '99' means no signal."
    ::= { hh3cUIMInfoEntry 7 }

hh3cUIMTryPinPukTimes OBJECT-TYPE
    SYNTAX      Unsigned32(0..4294967295)
    MAX-ACCESS  read-only
    STATUS      current
    DESCRIPTION
        "The number of remaining times for unlocking PIN or PUK.
        The value is associated the same instance of hh3cUIMStatus.  If this
        information is unknown to the agent, then this object will be
        returned 4294967295."
    ::= { hh3cUIMInfoEntry 8 }

hh3cUIMOldPin OBJECT-TYPE
    SYNTAX      SnmpAdminString (SIZE (0..9))
    MAX-ACCESS  accessible-for-notify
    STATUS      current
    DESCRIPTION
            "The old PIN for this UIM."
    ::= { hh3cUIMInfoEntry 9 }

-- MIB trap definitions
hh3c3GModemTrap       OBJECT IDENTIFIER ::= { hh3c3GModem 2 }
hh3c3GModemTraps       OBJECT IDENTIFIER ::= { hh3c3GModem 3 }
hh3c3GModemTrapPrefix  OBJECT IDENTIFIER ::= { hh3c3GModemTraps 0 }

hh3cDevSerialNumber OBJECT-TYPE
    SYNTAX      SnmpAdminString (SIZE (0..32))
    MAX-ACCESS  accessible-for-notify
    STATUS      current
    DESCRIPTION
            "The serial number of the current device."
    ::= { hh3c3GModemTrap 1 }

hh3cDeviceOUI OBJECT-TYPE
    SYNTAX      SnmpAdminString (SIZE (0..64))
    MAX-ACCESS  accessible-for-notify
    STATUS      current
    DESCRIPTION
            "The OUI (Organizational Unique Identifier) of the current device."
    ::= { hh3c3GModemTrap 2 }

hh3cAccessMedia OBJECT-TYPE
    SYNTAX      INTEGER
        {
            unknown(1),
            air(2),
            cable(3)
        }
    MAX-ACCESS  accessible-for-notify
    STATUS      current
    DESCRIPTION
            "The current access media."
    ::= { hh3c3GModemTrap 3 }

hh3cWirelessCardInserted NOTIFICATION-TYPE
    OBJECTS
        {
            hh3cDeviceOUI,
            hh3cDevSerialNumber,
            hh3cWirelessCardSerialNumber,
            hh3cUIMImsi
        }
    STATUS      current
    DESCRIPTION
        "A hh3cWirelessCardInserted notification is generated when a wireless
        card is inserted."
   ::= { hh3c3GModemTrapPrefix 1 }

hh3cWirelessCardPulledOut NOTIFICATION-TYPE
    OBJECTS
        {
            hh3cDeviceOUI,
            hh3cDevSerialNumber,
            hh3cWirelessCardSerialNumber,
            hh3cUIMImsi
        }
    STATUS      current
    DESCRIPTION
        "A hh3cWirelessCardPulledOut notification is generated when a wireless
        card is pulled out."
   ::= { hh3c3GModemTrapPrefix 2 }

hh3cUIMPinInvalid NOTIFICATION-TYPE
    OBJECTS
        {
            hh3cDeviceOUI,
            hh3cDevSerialNumber,
            hh3cWirelessCardSerialNumber,
            hh3cUIMImsi
        }
    STATUS      current
    DESCRIPTION
        "A hh3cUIMPinInvalid notification is generated when UIM PIN is invalid."
   ::= { hh3c3GModemTrapPrefix 3 }

hh3cUIMPinChanged NOTIFICATION-TYPE
    OBJECTS
        {
            hh3cDeviceOUI,
            hh3cDevSerialNumber,
            hh3cWirelessCardSerialNumber,
            hh3cUIMImsi,
            hh3cUIMOldPin,
            hh3cUIMPin
        }
    STATUS      current
    DESCRIPTION
        "A hh3cUIMPinInvalid notification is generated when UIM PIN is changed."
   ::= { hh3c3GModemTrapPrefix 4 }

hh3cAccessMediaChanged NOTIFICATION-TYPE
    OBJECTS
        {
            hh3cDeviceOUI,
            hh3cDevSerialNumber,
            hh3cWirelessCardSerialNumber,
            hh3cUIMImsi,
            hh3cAccessMedia
        }
    STATUS      current
    DESCRIPTION
        "A hh3cAccessMediaChanged notification is generated when access media
         is changed."
   ::= { hh3c3GModemTrapPrefix 5 }
END
