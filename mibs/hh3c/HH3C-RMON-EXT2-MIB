-- ==================================================================
-- Copyright (c) 2004-2013 Hangzhou H3C Tech. Co., Ltd.  All rights reserved.
--
-- Description: This file describes the private MIB implementation of RMON
-- Reference:   the content of this file include part description from RFC2819
-- Version: V1.0
-- History:
--  v1.0 The initial version created by chenweifeng, 2012-06-19
-- ==================================================================
HH3C-RMON-EXT2-MIB DEFINITIONS ::= BEGIN

IMPORTS
    DisplayString                                   FROM SNMPv2-TC

    OBJECT-TYPE, MODULE-IDENTITY, OBJECT-IDENTITY,
    NOTIFICATION-TYPE, Integer32                    FROM SNMPv2-SMI

    OwnerString, EntryStatus                        FROM RMON-MIB

    hh3cCommon                                      FROM HH3C-OID-MIB;
-- ==================================================================
--
-- ======================= definition begin =========================
--
-- ==================================================================
hh3cRmonExt MODULE-IDENTITY
    LAST-UPDATED "201206190000Z"    -- June 19, 2012 at 16:05 GMT
    ORGANIZATION
        "Hangzhou H3C Tech. Co., Ltd."
    CONTACT-INFO
        "Platform Team Hangzhou H3C Tech. Co., Ltd.
        Hai-Dian District Beijing P.R. China
        http://www.h3c.com
        Zip:100085
        "
    DESCRIPTION
        "The private MIB module for managing remote monitoring
        device implementations."
    REVISION "201206190000Z"        -- June 19, 2012 at 16:06 GMT
    DESCRIPTION
        "The initial revision of this MIB module."
    ::= { hh3cCommon 125 }

hh3cRmonExtAlarmTable OBJECT-TYPE
    SYNTAX SEQUENCE OF Hh3cRmonExtAlarmEntry
    MAX-ACCESS not-accessible
    STATUS current
    DESCRIPTION
        "A list of alarm entries."
    ::= { hh3cRmonExt 1 }

hh3cRmonExtAlarmEntry OBJECT-TYPE
    SYNTAX Hh3cRmonExtAlarmEntry
    MAX-ACCESS not-accessible
    STATUS current
    DESCRIPTION
        "A list of parameters that set up a periodic checking
        for alarm conditions.  For example, an instance of the
        alarmValue object might be named alarmValue.8"
    INDEX { hh3cRmonExtAlarmIndex }
    ::= { hh3cRmonExtAlarmTable 1 }

Hh3cRmonExtAlarmEntry ::= SEQUENCE {
    hh3cRmonExtAlarmIndex                    Integer32,
    hh3cRmonExtAlarmInterval                 Integer32,
    hh3cRmonExtAlarmVariable                 DisplayString,
    hh3cRmonExtAlarmSympol                   DisplayString,
    hh3cRmonExtAlarmSampleType               INTEGER,
    hh3cRmonExtAlarmValue                    Integer32,
    hh3cRmonExtAlarmStartupAlarm             INTEGER,
    hh3cRmonExtAlarmRisingThreshold          Integer32,
    hh3cRmonExtAlarmFallingThreshold         Integer32,
    hh3cRmonExtAlarmRisingEvtIndex           Integer32,
    hh3cRmonExtAlarmFallingEvtIndex          Integer32,
    hh3cRmonExtAlarmStatCycle                Integer32,
    hh3cRmonExtAlarmStatType                 INTEGER,
    hh3cRmonExtAlarmOwner                    OwnerString,
    hh3cRmonExtAlarmStatus                   EntryStatus
}

hh3cRmonExtAlarmIndex OBJECT-TYPE
    SYNTAX Integer32 (1..65535)
    MAX-ACCESS read-only
    STATUS current
    DESCRIPTION
        "An index that uniquely identifies an entry in the
        alarm table.  Each such entry defines a
        diagnostic sample at a particular interval
        for an object on the device."
    ::= { hh3cRmonExtAlarmEntry 1 }

hh3cRmonExtAlarmInterval OBJECT-TYPE
    SYNTAX Integer32 (10..65535)
    MAX-ACCESS read-create
    STATUS current
    DESCRIPTION
        "The interval in seconds over which the data is
        sampled and compared with the rising and falling
        thresholds.  When setting this variable, care
        should be taken in the case of deltaValue
        sampling - the interval should be set short enough
        that the sampled variable is very unlikely to
        increase or decrease by more than 2^31 - 1 during
        a single sampling interval.

        This object may not be modified if the associated
        alarmStatus object is equal to valid."
    DEFVAL { 1800 }
    ::= { hh3cRmonExtAlarmEntry 2 }

hh3cRmonExtAlarmVariable OBJECT-TYPE
    SYNTAX DisplayString
    MAX-ACCESS read-create
    STATUS current
    DESCRIPTION
        "The object identifier of the particular variable to be
        sampled.  Only variables that resolve to an ASN.1 primitive
        type of INTEGER (INTEGER, Integer32, Unsigned32, Counter32,
        Counter64, Gauge, or TimeTicks) may be sampled.

        Because SNMP access control is articulated entirely
        in terms of the contents of MIB views, no access
        control mechanism exists that can restrict the value of
        this object to identify only those objects that exist
        in a particular MIB view.  Because there is thus no
        acceptable means of restricting the read access that
        could be obtained through the alarm mechanism, the
        probe must only grant write access to this object in
        those views that have read access to all objects on
        the probe.

        During a set operation, if the supplied variable name is
        not available in the selected MIB view, a badValue error
        must be returned.

        This object may not be modified if the associated
        alarmStatus object is equal to valid."
    ::= { hh3cRmonExtAlarmEntry 3 }

hh3cRmonExtAlarmSympol OBJECT-TYPE
    SYNTAX  DisplayString
    MAX-ACCESS read-create
    STATUS current
    DESCRIPTION
        "A comment describing this alarm entry.
        This object may not be modified if the associated
        alarmStatus object is equal to valid."
    ::= { hh3cRmonExtAlarmEntry 4 }

hh3cRmonExtAlarmSampleType OBJECT-TYPE
    SYNTAX INTEGER {
        absoluteValue(1),
        deltaValue(2),
        speedValue(3)
    }
    MAX-ACCESS read-create
    STATUS current
    DESCRIPTION
        "The method of sampling the selected variable and
        calculating the value to be compared against the
        thresholds.  If the value of this object is
        absoluteValue, the value of the selected variable
        will be compared directly with the thresholds at the
        end of the sampling interval.  If the value of this
        object is deltaValue, the value of the selected
        variable at the last sample will be subtracted from
        the current value, and the difference compared with
        the thresholds.

        This object may not be modified if the associated
        alarmStatus object is equal to valid."
    DEFVAL { absoluteValue }
    ::= { hh3cRmonExtAlarmEntry 5 }

hh3cRmonExtAlarmValue OBJECT-TYPE
    SYNTAX Integer32
    MAX-ACCESS read-only
    STATUS current
    DESCRIPTION
        "The value of the statistic during the last sampling
        period.  For example, if the sample type is deltaValue,
        this value will be the difference between the samples
        at the beginning and end of the period.  If the sample
        type is absoluteValue, this value will be the sampled
        value at the end of the period.
        This is the value that is compared with the rising and
        falling thresholds.

        The value during the current sampling period is not
        made available until the period is completed and will
        remain available until the next period completes."
    ::= { hh3cRmonExtAlarmEntry 6 }

hh3cRmonExtAlarmStartupAlarm OBJECT-TYPE
    SYNTAX INTEGER {
        risingAlarm(1),
        fallingAlarm(2),
        risingOrFallingAlarm(3)
    }
    MAX-ACCESS read-create
    STATUS current
    DESCRIPTION
        "The alarm that may be sent when this entry is first
        set to valid.  If the first sample after this entry
        becomes valid is greater than or equal to the
        risingThreshold and alarmStartupAlarm is equal to
        risingAlarm or risingOrFallingAlarm, then a single
        rising alarm will be generated.  If the first sample
        after this entry becomes valid is less than or equal
        to the fallingThreshold and alarmStartupAlarm is equal
        to fallingAlarm or risingOrFallingAlarm, then a
        single falling alarm will be generated.

        This object may not be modified if the associated
        alarmStatus object is equal to valid."
    DEFVAL { risingOrFallingAlarm }
    ::= { hh3cRmonExtAlarmEntry 7 }

hh3cRmonExtAlarmRisingThreshold OBJECT-TYPE
    SYNTAX Integer32
    MAX-ACCESS read-create
    STATUS current
    DESCRIPTION
        "A threshold for the sampled statistic.  When the current
        sampled value is greater than or equal to this threshold,
        and the value at the last sampling interval was less than
        this threshold, a single event will be generated.
        A single event will also be generated if the first
        sample after this entry becomes valid is greater than or
        equal to this threshold and the associated
        alarmStartupAlarm is equal to risingAlarm or
        risingOrFallingAlarm.

        After a rising event is generated, another such event
        will not be generated until the sampled value
        falls below this threshold and reaches the
        alarmFallingThreshold.

        This object may not be modified if the associated
        alarmStatus object is equal to valid."
    DEFVAL { 1 }
    ::= { hh3cRmonExtAlarmEntry 8 }

hh3cRmonExtAlarmFallingThreshold OBJECT-TYPE
    SYNTAX Integer32
    MAX-ACCESS read-create
    STATUS current
    DESCRIPTION
        "A threshold for the sampled statistic.  When the current
        sampled value is less than or equal to this threshold,
        and the value at the last sampling interval was greater than
        this threshold, a single event will be generated.
        A single event will also be generated if the first
        sample after this entry becomes valid is less than or
        equal to this threshold and the associated
        alarmStartupAlarm is equal to fallingAlarm or
        risingOrFallingAlarm.

        After a falling event is generated, another such event
        will not be generated until the sampled value
        rises above this threshold and reaches the
        alarmRisingThreshold.

        This object may not be modified if the associated
        alarmStatus object is equal to valid."
    DEFVAL { 0 }
    ::= { hh3cRmonExtAlarmEntry 9 }

hh3cRmonExtAlarmRisingEvtIndex OBJECT-TYPE
    SYNTAX Integer32 (0..65535)
    MAX-ACCESS read-create
    STATUS current
    DESCRIPTION
        "The index of the eventEntry that is
        used when a rising threshold is crossed.  The
        eventEntry identified by a particular value of
        this index is the same as identified by the same value
        of the eventIndex object.  If there is no
        corresponding entry in the eventTable, then
        no association exists.  In particular, if this value
        is zero, no associated event will be generated, as
        zero is not a valid event index.

        This object may not be modified if the associated
        alarmStatus object is equal to valid."
    DEFVAL { 0 }
    ::= { hh3cRmonExtAlarmEntry 10 }

hh3cRmonExtAlarmFallingEvtIndex OBJECT-TYPE
    SYNTAX Integer32 (0..65535)
    MAX-ACCESS read-create
    STATUS current
    DESCRIPTION
        "The index of the eventEntry that is
        used when a falling threshold is crossed.  The
        eventEntry identified by a particular value of
        this index is the same as identified by the same value
        of the eventIndex object.  If there is no
        corresponding entry in the eventTable, then
        no association exists.  In particular, if this value
        is zero, no associated event will be generated, as
        zero is not a valid event index.

        This object may not be modified if the associated
        alarmStatus object is equal to valid."
    DEFVAL { 0 }
    ::= { hh3cRmonExtAlarmEntry 11 }

hh3cRmonExtAlarmStatCycle             OBJECT-TYPE
    SYNTAX Integer32 (0..4294967)
    MAX-ACCESS read-create
    STATUS current
    DESCRIPTION
        "The lifetime (in seconds) starts when an alarm entry
        is set in valid state.

        If the entry has an infinite lifetime, the value of this
        object MUST be 0. Otherwise the value MUST be greater
        than the value of hh3cRmonExtAlarmInterval.

        This object may not be modified if the associated
        alarmStatus object is equal to valid."
    DEFVAL { 0 }
    ::= { hh3cRmonExtAlarmEntry 12 }

hh3cRmonExtAlarmStatType              OBJECT-TYPE
    SYNTAX INTEGER{
        forever(1),
        during(2)
    }
    MAX-ACCESS read-create
    STATUS current
    DESCRIPTION
        "This object indicates whether the entry has an
        infinite or limited lifetime.

        This object may not be modified if the associated
        alarmStatus object is equal to valid."
    DEFVAL { forever }
    ::= { hh3cRmonExtAlarmEntry 13 }

hh3cRmonExtAlarmOwner OBJECT-TYPE
    SYNTAX OwnerString
    MAX-ACCESS read-create
    STATUS current
    DESCRIPTION
        "The entity that configured this entry and is therefore
        using the resources assigned to it.

        The defalut value of this object is zero length string."
    ::= { hh3cRmonExtAlarmEntry 14 }

hh3cRmonExtAlarmStatus OBJECT-TYPE
    SYNTAX EntryStatus
    MAX-ACCESS read-create
    STATUS current
    DESCRIPTION
        "The status of this alarm entry."
    ::= { hh3cRmonExtAlarmEntry 15 }

--  extend from Remote Network Monitoring Traps

hh3cRmonExtEvent OBJECT-IDENTITY
    STATUS      current
    DESCRIPTION "Definition point for notifications."
    ::= { hh3cRmonExt 0 }

hh3cRmonExtRisingAlarm NOTIFICATION-TYPE
    OBJECTS{
        hh3cRmonExtAlarmIndex,
        hh3cRmonExtAlarmSympol,
        hh3cRmonExtAlarmSampleType,
        hh3cRmonExtAlarmValue,
        hh3cRmonExtAlarmRisingThreshold
    }
    STATUS   current
    DESCRIPTION
        "The SNMP trap that is generated when an alarm
        entry crosses its rising threshold and generates
        an event that is configured for sending SNMP
        traps."
    ::= { hh3cRmonExtEvent 1 }

hh3cRmonExtFallingAlarm NOTIFICATION-TYPE
    OBJECTS {
        hh3cRmonExtAlarmIndex,
        hh3cRmonExtAlarmSympol,
        hh3cRmonExtAlarmSampleType,
        hh3cRmonExtAlarmValue,
        hh3cRmonExtAlarmFallingThreshold
    }
    STATUS    current
    DESCRIPTION
        "The SNMP trap that is generated when an alarm
        entry crosses its falling threshold and generates
        an event that is configured for sending SNMP
        traps."
    ::= { hh3cRmonExtEvent 2 }

END
