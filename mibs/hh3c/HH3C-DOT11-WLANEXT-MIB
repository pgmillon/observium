-- =============================================================================
-- Copyright (C) 2006-2007 by H3C TECHNOLOGIES.  All rights reserved.
--
-- Description:
--   The file defines a MIB to provide more information for WLAN network.
-- Reference:
-- Version: V1.0
-- History:
--   V1.0 2007-06-08 Initial version, created by wanghao (Kumar)
-- =============================================================================
HH3C-DOT11-WLANEXT-MIB DEFINITIONS ::= BEGIN

IMPORTS
        MODULE-IDENTITY,
        OBJECT-TYPE,
        Integer32,
        Counter32
    FROM SNMPv2-SMI
        hh3cDot11,
        Hh3cDot11ObjectIDType,
        Hh3cDot11RadioScopeType,
        Hh3cDot11QosAcType
    FROM HH3C-DOT11-REF-MIB;

hh3cDot11WLANEXT MODULE-IDENTITY
    LAST-UPDATED "200706082000Z"            -- Jun. 08, 2007 at 20:00 GMT
    ORGANIZATION
        "Hangzhou H3C Technologies Co., Ltd."
    CONTACT-INFO
        "Platform Team H3C Technologies Co., Ltd.
         Hai-Dian District Beijing P.R. China
         http://www.h3c.com
         Zip: 100085"
    DESCRIPTION
        "This MIB provides more information for WLAN network.

        GLOSSARY

        IEEE 802.11
        Standard to encourage interoperability among
        wireless networking equipment.

        IEEE 802.11e
        Standard to define the MAC procedures to support
        LAN applications with Quality of Service (QoS) requirements,
        including the transport of voice, audio and video over
        IEEE 802.11 wireless LANs.

        Access point (AP)
        Transmitter/receiver (transceiver) device
        that commonly connects and transports data
        between a wireless network and a wired network.

        Access control (AC)
        To control and manage multi-APs, it will bridge
        wireless and wired network.

        Radio
        The chip set to receive and send wireless signal.

        Fat AP
        Applied in the home, SOHO and so on, and it could
        independently work without help from AC.

        Fit AP
        Applied in the enterprise environment, it will work
        under the control and management from AC.

        Control And Provisioning of Wireless Access Points Protocol
        The short name of protocol is CAPWAP. AC will control
        and manage AP by CAPWAP tunnel protocol defined by IETF.
        Also, a data tunnel will be set up between AC and AP.

        Basic Service Set
        The IEEE 802.11 BSS of an AP comprises of the
        stations directly associating with the AP. It will
        be identified by BSSID."

    REVISION "200706082000Z"        -- Jun 08, 2007 at 20:00 GMT
    DESCRIPTION
        "The initial revision of this MIB module."
    ::= { hh3cDot11 7 }

-- *****************************************************************************
-- *  Major sections
-- *****************************************************************************
--  RF Management Group
--  DEFINED AS "The group to provide the statistic information
--  for RF management feature.
hh3cDot11RFGroup OBJECT IDENTIFIER   ::= { hh3cDot11WLANEXT 1 }

--  The RF Management Group has the following children:
--  hh3cDot11RFSignalStatisTable  ::= { hh3cDot11RFGroup 1 }

--  Qos Group
--  DEFINED AS "The group to provide the statistic information
--  for Qos feature."
hh3cDot11QosGroup OBJECT IDENTIFIER  ::= { hh3cDot11WLANEXT 2 }

--  The Qos Group has the following children:
--  hh3cDot11QosStatisTable    ::= { hh3cDot11QosGroup 1 }
--  hh3cDot11QosAcStatisTable  ::= { hh3cDot11QosGroup 2 }

-- *****************************************************************************
-- *  hh3cDot11RFSignalStatisticTable Definition
-- *****************************************************************************
hh3cDot11RFSignalStatisTable OBJECT-TYPE
    SYNTAX      SEQUENCE OF Hh3cDot11RFSignalStatisEntry
    MAX-ACCESS  not-accessible
    STATUS      current
    DESCRIPTION
        "The table will describe statistic information of signal strength
        for AP radio."
    ::= { hh3cDot11RFGroup 1 }

hh3cDot11RFSignalStatisEntry OBJECT-TYPE
    SYNTAX      Hh3cDot11RFSignalStatisEntry
    MAX-ACCESS  not-accessible
    STATUS      current
    DESCRIPTION
        "Each entry contains the signal of each signal strength information of
        a specific AP."
    INDEX
        {
            hh3cDot11RFAPID,
            hh3cDot11RFRadioID
        }
    ::= { hh3cDot11RFSignalStatisTable 1 }

Hh3cDot11RFSignalStatisEntry ::= SEQUENCE
    {
        hh3cDot11RFAPID                     Hh3cDot11ObjectIDType,
        hh3cDot11RFRadioID                  Hh3cDot11RadioScopeType,
        hh3cDot11RFSignalStatisInterv       Integer32,
        hh3cDot11RFAverageSignalStrength    Integer32,
        hh3cDot11RFMaxSignalStrength        Integer32,
        hh3cDot11RFMinSignalStrength        Integer32
    }

hh3cDot11RFAPID OBJECT-TYPE
    SYNTAX      Hh3cDot11ObjectIDType
    MAX-ACCESS  not-accessible
    STATUS      current
    DESCRIPTION
        "To identify each AP, and AP is running status."
    ::= { hh3cDot11RFSignalStatisEntry 1 }

hh3cDot11RFRadioID OBJECT-TYPE
    SYNTAX      Hh3cDot11RadioScopeType
    MAX-ACCESS  not-accessible
    STATUS      current
    DESCRIPTION
        "Represents each radio."
    ::= { hh3cDot11RFSignalStatisEntry 2 }

hh3cDot11RFSignalStatisInterv OBJECT-TYPE
    SYNTAX      Integer32
    UNITS       "second"
    MAX-ACCESS  read-only
    STATUS      current
    DESCRIPTION
        "Represents the interval of statistic."
    ::= { hh3cDot11RFSignalStatisEntry 3 }

hh3cDot11RFAverageSignalStrength OBJECT-TYPE
    SYNTAX      Integer32
    UNITS       "dBm"
    MAX-ACCESS  read-only
    STATUS      current
    DESCRIPTION
        "Represents the average value of signal strength
        for stations on a specific radio."
    ::= { hh3cDot11RFSignalStatisEntry 4 }

hh3cDot11RFMaxSignalStrength OBJECT-TYPE
    SYNTAX      Integer32
    UNITS       "dBm"
    MAX-ACCESS  read-only
    STATUS      current
    DESCRIPTION
        "Represents the maximum value of signal strength
        for stations on a specific radio."
    ::= { hh3cDot11RFSignalStatisEntry 5 }

hh3cDot11RFMinSignalStrength OBJECT-TYPE
    SYNTAX      Integer32
    UNITS       "dBm"
    MAX-ACCESS  read-only
    STATUS      current
    DESCRIPTION
        "Represents the minimum value of signal strength
        for stations on a specific radio."
    ::= { hh3cDot11RFSignalStatisEntry 6 }
-- *****************************************************************************
-- *  End of hh3cDot11RFSignalStatisTable Definition
-- *****************************************************************************

-- *****************************************************************************
-- *  hh3cDot11QosStatisTable Definition
-- *****************************************************************************
hh3cDot11QosStatisTable OBJECT-TYPE
    SYNTAX      SEQUENCE OF Hh3cDot11QosStatisEntry
    MAX-ACCESS  not-accessible
    STATUS      current
    DESCRIPTION
        "The table defines the attributes for the Qos feature of radio."
    ::= { hh3cDot11QosGroup 1 }

hh3cDot11QosStatisEntry OBJECT-TYPE
    SYNTAX      Hh3cDot11QosStatisEntry
    MAX-ACCESS  not-accessible
    STATUS      current
    DESCRIPTION
        "Each entry contains information of the Qos attribute of each radio."
    INDEX
        {
            hh3cDot11QosAPID,
            hh3cDot11QosRadioID
        }
    ::= { hh3cDot11QosStatisTable 1 }

Hh3cDot11QosStatisEntry ::= SEQUENCE
    {
        hh3cDot11QosAPID               Hh3cDot11ObjectIDType,
        hh3cDot11QosRadioID            Hh3cDot11RadioScopeType,
        hh3cDot11QosAverageQueLen      Integer32,
        hh3cDot11QosDropFrameRatio     Integer32,
        hh3cDot11QosAverageDataRate    Integer32
    }

hh3cDot11QosAPID OBJECT-TYPE
    SYNTAX      Hh3cDot11ObjectIDType
    MAX-ACCESS  not-accessible
    STATUS      current
    DESCRIPTION
        "To uniquely identify a AP in running status."
    ::= { hh3cDot11QosStatisEntry 1 }

hh3cDot11QosRadioID OBJECT-TYPE
    SYNTAX      Hh3cDot11RadioScopeType
    MAX-ACCESS  not-accessible
    STATUS      current
    DESCRIPTION
        "Represents each radio."
    ::= { hh3cDot11QosStatisEntry 2 }

hh3cDot11QosAverageQueLen OBJECT-TYPE
    SYNTAX      Integer32
    MAX-ACCESS  read-only
    STATUS      current
    DESCRIPTION
        "The average frame numbers to be sent out in the queue."
    ::= { hh3cDot11QosStatisEntry 3 }

hh3cDot11QosDropFrameRatio OBJECT-TYPE
    SYNTAX      Integer32
    MAX-ACCESS  read-only
    STATUS      current
    DESCRIPTION
        "The ratio of dropped frames in a minute because of full queue."
    ::= { hh3cDot11QosStatisEntry 4 }

hh3cDot11QosAverageDataRate OBJECT-TYPE
    SYNTAX      Integer32
    UNITS       "Kbps"
    MAX-ACCESS  read-only
    STATUS      current
    DESCRIPTION
        "The average transmit data rate of radio."
    ::= { hh3cDot11QosStatisEntry 5 }
-- *****************************************************************************
-- *  End of hh3cDot11QosStatisTable Definition
-- *****************************************************************************

-- *****************************************************************************
-- *  hh3cDot11QosAcAttributeTable Definition
-- *****************************************************************************
hh3cDot11QosAcStatisTable OBJECT-TYPE
    SYNTAX      SEQUENCE OF Hh3cDot11QosAcStatisEntry
    MAX-ACCESS  not-accessible
    STATUS      current
    DESCRIPTION
        "The table defines the parameters for Qos access category."
    ::= { hh3cDot11QosGroup 2 }

hh3cDot11QosAcStatisEntry OBJECT-TYPE
    SYNTAX      Hh3cDot11QosAcStatisEntry
    MAX-ACCESS  not-accessible
    STATUS      current
    DESCRIPTION
        "Each entry contains information of each Qos access category."
    INDEX
        {
            hh3cDot11QosAPID,
            hh3cDot11QosRadioID,
            hh3cDot11QosAcType
        }
    ::= { hh3cDot11QosAcStatisTable 1 }

Hh3cDot11QosAcStatisEntry ::= SEQUENCE
    {
        hh3cDot11QosAcType         Hh3cDot11QosAcType,
        hh3cDot11AcDropFrameCnt    Counter32
    }

hh3cDot11QosAcType OBJECT-TYPE
    SYNTAX      Hh3cDot11QosAcType
    MAX-ACCESS  not-accessible
    STATUS      current
    DESCRIPTION
        "The access category type."
    ::= { hh3cDot11QosAcStatisEntry 1 }

hh3cDot11AcDropFrameCnt OBJECT-TYPE
    SYNTAX      Counter32
    MAX-ACCESS  read-only
    STATUS      current
    DESCRIPTION
        "The number of dropped frames in a minute for one specific access
        category because of full queue."
    ::= { hh3cDot11QosAcStatisEntry 2 }
-- *****************************************************************************
-- *  End of hh3cDot11AcAttributeTable Definition
-- *****************************************************************************
END
