-- ==========================================================================
-- Copyright (c) 2004-2010 Hangzhou H3C Tech. Co., Ltd. All rights reserved.
--
-- Description: The purpose of this MIB file is to provide the object definition
--              of the SNMP (Simple Network Management Protocol) extended
--              information.
-- Reference:
-- Version: V1.1
-- History:
-- V1.0 2009-04-07  Initial version, created by Lisong
-- V1.1 2010-03-12  Added hh3cSnmpExtReadCommunitySingle and
--                  hh3cSnmpExtWriteCommunitySingle by SongHao
-- ==========================================================================
HH3C-SNMP-EXT-MIB DEFINITIONS ::= BEGIN

IMPORTS
        OBJECT-TYPE, MODULE-IDENTITY, NOTIFICATION-TYPE, Integer32
    FROM SNMPv2-SMI
        OBJECT-GROUP, MODULE-COMPLIANCE, NOTIFICATION-GROUP
    FROM SNMPv2-CONF
        SnmpAdminString, SnmpSecurityLevel, SnmpSecurityModel
    FROM SNMP-FRAMEWORK-MIB
        hh3cCommon
    FROM HH3C-OID-MIB;

hh3cSnmpExt MODULE-IDENTITY
    LAST-UPDATED "200904071700Z"
    ORGANIZATION
        "Hangzhou H3C Technologies Co., Ltd."
    CONTACT-INFO
        "Platform Team H3C Technologies Co., Ltd.
         Hai-Dian District Beijing P.R. China
         Http://www.h3c.com
         Zip: 100085"
    DESCRIPTION
        "This MIB file is to provide the object definition of the SNMP extended
         information."
    REVISION "200904071700Z"
    DESCRIPTION
        "The initial version of this MIB file."
    ::= { hh3cCommon 104 }
--
-- Object definitions
--
hh3cSnmpExtScalarObjects OBJECT IDENTIFIER ::= { hh3cSnmpExt 1 }

hh3cSnmpExtTables        OBJECT IDENTIFIER ::= { hh3cSnmpExt 2 }

hh3cSnmpExtNotifications OBJECT IDENTIFIER ::= { hh3cSnmpExt 3 }

--
-- Scalar Objects
--
    hh3cSnmpExtSnmpChannel OBJECT-TYPE
        SYNTAX          Integer32(1..65535)
        MAX-ACCESS      read-write
        STATUS current
        DESCRIPTION
            "The channel number used by SNMP."
        DEFVAL { 161 }
        ::= { hh3cSnmpExtScalarObjects 1 }

    hh3cSnmpExtReadCommunitySingle OBJECT-TYPE
        SYNTAX          SnmpAdminString (SIZE(1..32))
        MAX-ACCESS      read-write
        STATUS          current
        DESCRIPTION     "The first read community."
        ::= { hh3cSnmpExtScalarObjects 2 }

    hh3cSnmpExtWriteCommunitySingle OBJECT-TYPE
        SYNTAX          SnmpAdminString (SIZE(1..32))
        MAX-ACCESS      read-write
        STATUS          current
        DESCRIPTION     "The first write community."
        ::= { hh3cSnmpExtScalarObjects 3 }

--
-- Table Objects
--
    hh3cSnmpExtCommunityTable OBJECT-TYPE
        SYNTAX SEQUENCE OF Hh3cSnmpExtCommunityEntry
        MAX-ACCESS      not-accessible
        STATUS          current
        DESCRIPTION     "Modify the extended properties of SNMP community or
                         user."
        ::= { hh3cSnmpExtTables 1 }

    hh3cSnmpExtCommunityEntry OBJECT-TYPE
        SYNTAX          Hh3cSnmpExtCommunityEntry
        MAX-ACCESS      not-accessible
        STATUS          current
        DESCRIPTION     "The entry of hh3cSnmpExtCommunityTable"
        INDEX {
                hh3cSnmpExtCommunitySecurityLevel,
                hh3cSnmpExtCommunitySecurityName
              }
        ::= { hh3cSnmpExtCommunityTable 1 }

    Hh3cSnmpExtCommunityEntry ::= SEQUENCE {
        hh3cSnmpExtCommunitySecurityLevel
            SnmpSecurityModel,
        hh3cSnmpExtCommunitySecurityName
            SnmpAdminString,
        hh3cSnmpExtCommunityName
            OCTET STRING,
        hh3cSnmpExtCommunityAclNum
            Integer32
    }

    hh3cSnmpExtCommunitySecurityLevel OBJECT-TYPE
        SYNTAX          SnmpSecurityModel
        MAX-ACCESS      not-accessible
        STATUS          current
        DESCRIPTION     "The Security Model of the specified community or user.
                         This object may not take the 'any' (0) value."
        ::= { hh3cSnmpExtCommunityEntry 1 }

    hh3cSnmpExtCommunitySecurityName OBJECT-TYPE
        SYNTAX          SnmpAdminString
        MAX-ACCESS      not-accessible
        STATUS          current
        DESCRIPTION     "The Security Name of the specified community or user."
        ::= { hh3cSnmpExtCommunityEntry 2 }

    hh3cSnmpExtCommunityName OBJECT-TYPE
        SYNTAX          OCTET STRING(SIZE(1..32))
        MAX-ACCESS      read-only
        STATUS          current
        DESCRIPTION     "The specified community name."
        ::= { hh3cSnmpExtCommunityEntry 3 }

    hh3cSnmpExtCommunityAclNum OBJECT-TYPE
        SYNTAX          Integer32 (0|2000..2999)
        MAX-ACCESS      read-write
        STATUS          current
        DESCRIPTION     "The specified ACL (Access Control List) number used by
                         the community or the user."
        DEFVAL          {0}
        ::= { hh3cSnmpExtCommunityEntry 4 }

--
-- Notification Objects
--

END
