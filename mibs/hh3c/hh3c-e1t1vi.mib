-- =============================================================
-- Copyright (c) 2004-2010 Hangzhou H3C Tech. Co., Ltd. All rights reserved.
--
-- Description: E1T1VI MIB
-- Reference:
-- Version: V1.2
-- History:
--   V1.0 2007-04-05 Initial Version by yandehan
--   V1.1 2009-06-08 modified by TONGWEI
--        Added hh3cE1T1VIUsingTimeslotsRatio
--          and hh3cE1T1VINotifications
--   V1.2 2010-04-08 modified by TONGWEI
--        Added hh3cE1T1VIGeneral
-- =============================================================
HH3C-E1T1VI-MIB DEFINITIONS ::= BEGIN
    IMPORTS
        MODULE-IDENTITY, OBJECT-TYPE, Integer32, NOTIFICATION-TYPE
            FROM SNMPv2-SMI
        ifIndex, ifDescr
            FROM RFC1213-MIB
        hh3cCommon
            FROM HH3C-OID-MIB;


-- =============================================================
-- E1T1VI Module
-- =============================================================
hh3cE1T1VI MODULE-IDENTITY
    LAST-UPDATED    "201004081855Z"         -- Apr. 8, 2010 at 18:55 GMT
    ORGANIZATION
        "Hangzhou H3C Technologies Co., Ltd."
    CONTACT-INFO
        "Platform Team H3C Technologies Co., Ltd.
         Hai-Dian District Beijing P.R. China
         http://www.h3c.com
         Zip: 100085"
    DESCRIPTION
        "This MIB provides E1/T1 voice interface information that are
        excluded by RFC 1213 and RFC 2233"
    REVISION        "201004081855Z"
    DESCRIPTION
        "To fix bugs in the MIB file."
    REVISION        "200906081741Z"
    DESCRIPTION
        "To fix bugs in the MIB file."
    REVISION        "200704051542Z"
    DESCRIPTION
        "Initial version of this MIB module."
    ::= { hh3cCommon 76 }


hh3cE1T1VITable OBJECT-TYPE
    SYNTAX      SEQUENCE OF Hh3cE1T1VIEntry
    MAX-ACCESS  not-accessible
    STATUS      current
    DESCRIPTION
        "This table contains E1/T1 voice interface information,
        such as the total number of using time slot."
    ::= { hh3cE1T1VI 1 }

hh3cE1T1VIEntry OBJECT-TYPE
    SYNTAX      Hh3cE1T1VIEntry
    MAX-ACCESS  not-accessible
    STATUS      current
    DESCRIPTION
        "This entry contains E1/T1 voice interface information.
        The index of this Entry is ifIndex defined in ifTable
        of RFC1213-MIB."
    INDEX
        {
            ifIndex
        }
    ::= { hh3cE1T1VITable 1 }

Hh3cE1T1VIEntry ::= SEQUENCE
    {
        hh3cE1T1VIUsingTimeslots    Integer32,
        hh3cE1T1VIUsingTimeslotsRatio    Integer32
    }

hh3cE1T1VIUsingTimeslots OBJECT-TYPE
    SYNTAX      Integer32
    MAX-ACCESS  read-only
    STATUS      current
    DESCRIPTION
        "The total number of using time slots on this interface."
    ::= { hh3cE1T1VIEntry 1 }

hh3cE1T1VIUsingTimeslotsRatio OBJECT-TYPE
    SYNTAX      Integer32
    MAX-ACCESS  read-only
    STATUS      current
    DESCRIPTION
        "The total ratio of using time slots on this interface."
    ::= { hh3cE1T1VIEntry 2 }

hh3cE1T1VINotifications OBJECT IDENTIFIER ::= { hh3cE1T1VI 2 }
hh3cE1T1VITrapPrefix    OBJECT IDENTIFIER ::= { hh3cE1T1VINotifications 0 }

hh3cE1T1VITrapTimeSlot NOTIFICATION-TYPE
    OBJECTS { ifIndex, ifDescr }
    STATUS current
    DESCRIPTION
        "This trap is sent to the manager under the following
         condidion: All the available time slots of a E1/T1
         voice interface has been in use."
    ::= { hh3cE1T1VITrapPrefix 1 }

hh3cE1T1VIGeneral  OBJECT IDENTIFIER ::= { hh3cE1T1VI 3 }

hh3cE1T1VITrapTimeSlotEnable OBJECT-TYPE
    SYNTAX  INTEGER {
            enable(1),
            disable(2)
        }
    MAX-ACCESS  read-write
    STATUS      current
    DESCRIPTION
        "This attribute controls whether the hh3cE1T1VITrapTimeSlot trap will
        be sent or not."
    DEFVAL { enable }
    ::= { hh3cE1T1VIGeneral 1 }

END
