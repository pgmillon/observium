-- =============================================================================
-- Copyright (c) 2004-2014 Hangzhou H3C Tech. Co., Ltd. All rights reserved.
--
-- Description: Multiprotocol Label Switching MIB
-- Reference:
-- Version: V1.0
-- History:
--   V1.0 2013-06-13 Initial version Created by Neng Yan
-- =============================================================================
HH3C-MPLSEXT-MIB DEFINITIONS ::= BEGIN
IMPORTS
    MODULE-IDENTITY, OBJECT-TYPE, Unsigned32
        FROM SNMPv2-SMI
    RowStatus, TruthValue
        FROM SNMPv2-TC
    hh3cCommon
        FROM HH3C-OID-MIB
    ;

-- =============================================================================
-- module identity part
-- =============================================================================
hh3cMplsExt MODULE-IDENTITY
    LAST-UPDATED
        "201306131800Z"        -- Jan 13, 2013 at 18:00 GMT
    ORGANIZATION
        "Hangzhou H3C Technologies Co., Ltd."
    CONTACT-INFO
        "Platform Team Hangzhou H3C Technologies Co., Ltd.
         Hai-Dian District Beijing P.R. China
         http://www.h3c.com
         Zip:100085"
    DESCRIPTION
        "Multiprotocol Label Switching MIB"
    REVISION
        "201306131800Z"   -- Jan 13, 2013 at 18:00 GMT
    DESCRIPTION
        "Initial version of this MIB."
    ::= { hh3cCommon 142 }

-- =============================================================================
-- object definition begin
-- =============================================================================
hh3cMplsExtObjects      OBJECT IDENTIFIER ::= { hh3cMplsExt 1 }

hh3cMplsExtScalarGroup  OBJECT IDENTIFIER ::= { hh3cMplsExtObjects 1 }

hh3cMplsExtLsrID    OBJECT-TYPE
    SYNTAX      OCTET STRING (SIZE (0..32))
    MAX-ACCESS  read-write
    STATUS      current
    DESCRIPTION
        "The Label Switching Router's Identifier."
    ::= { hh3cMplsExtScalarGroup 1 }

hh3cMplsExtLdpStatus    OBJECT-TYPE
    SYNTAX      TruthValue
    MAX-ACCESS  read-write
    STATUS      current
    DESCRIPTION
        "The global configuration of LDP(Label Distribution Protocol)."
    ::= { hh3cMplsExtScalarGroup 2 }

-- =============================================================================
-- hh3cMplsExtTable Definition
-- =============================================================================
hh3cMplsExtTable  OBJECT-TYPE
    SYNTAX      SEQUENCE OF Hh3cMplsExtEntry
    MAX-ACCESS  not-accessible
    STATUS      current
    DESCRIPTION
        "A table for configuring
        MPLS(Multiprotocol Label Switching) parameters."
    ::= { hh3cMplsExtObjects 2 }

hh3cMplsExtEntry   OBJECT-TYPE
    SYNTAX      Hh3cMplsExtEntry
    MAX-ACCESS  not-accessible
    STATUS      current
    DESCRIPTION
        "An entry for configuring MPLS parameters."
    INDEX
    {
        hh3cMplsExtIndex
    }
    ::= { hh3cMplsExtTable 1 }

Hh3cMplsExtEntry ::=
    SEQUENCE
    {
        hh3cMplsExtIndex               Unsigned32,
        hh3cMplsExtCapability          TruthValue,
        hh3cMplsExtMtu                 Unsigned32,
        hh3cMplsExtRowStatus           RowStatus
    }

hh3cMplsExtIndex   OBJECT-TYPE
    SYNTAX      Unsigned32(1..4294967295)
    MAX-ACCESS  not-accessible
    STATUS      current
    DESCRIPTION
        "Index of MPLS interface."
    ::= { hh3cMplsExtEntry 1 }

hh3cMplsExtCapability    OBJECT-TYPE
    SYNTAX      TruthValue
    MAX-ACCESS  read-create
    STATUS      current
    DESCRIPTION
        "The MPLS capability of an interface."
    DEFVAL { false }
    ::= { hh3cMplsExtEntry 2 }

hh3cMplsExtMtu     OBJECT-TYPE
    SYNTAX      Unsigned32(46..65535)
    MAX-ACCESS  read-create
    STATUS      current
    DESCRIPTION
        "The MPLS MTU(Maximum Transmission Unit) of an interface."
    ::= { hh3cMplsExtEntry 3 }

hh3cMplsExtRowStatus     OBJECT-TYPE
    SYNTAX      RowStatus
    MAX-ACCESS  read-create
    STATUS      current
    DESCRIPTION
        "Operation status of this table entry."
    ::= { hh3cMplsExtEntry 4 }
-- =============================================================================
-- End of hh3cMplsExtTable Definition
-- =============================================================================

-- =============================================================================
-- hh3cMplsExtLdpTable Definition
-- =============================================================================
hh3cMplsExtLdpTable     OBJECT-TYPE
    SYNTAX      SEQUENCE OF Hh3cMplsExtLdpEntry
    MAX-ACCESS  not-accessible
    STATUS      current
    DESCRIPTION
        "A table for configuring LDP parameters."
    ::= { hh3cMplsExtObjects 3 }

hh3cMplsExtLdpEntry     OBJECT-TYPE
    SYNTAX      Hh3cMplsExtLdpEntry
    MAX-ACCESS  not-accessible
    STATUS      current
    DESCRIPTION
        "An entry for configuring LDP parameters."
    INDEX
    {
        hh3cMplsExtLdpIndex
    }
    ::= { hh3cMplsExtLdpTable 1 }

Hh3cMplsExtLdpEntry ::=
    SEQUENCE
    {
        hh3cMplsExtLdpIndex                 Unsigned32,
        hh3cMplsExtLdpCapability            TruthValue,
        hh3cMplsExtLdpRowStatus             RowStatus
    }

hh3cMplsExtLdpIndex     OBJECT-TYPE
    SYNTAX      Unsigned32(1..4294967295)
    MAX-ACCESS  not-accessible
    STATUS      current
    DESCRIPTION
        "Index of LDP interface."
    ::= { hh3cMplsExtLdpEntry 1 }

hh3cMplsExtLdpCapability    OBJECT-TYPE
    SYNTAX      TruthValue
    MAX-ACCESS  read-create
    STATUS      current
    DESCRIPTION
        "The LDP capability of an interface."
    DEFVAL { false }
    ::= { hh3cMplsExtLdpEntry 2 }

hh3cMplsExtLdpRowStatus     OBJECT-TYPE
    SYNTAX      RowStatus
    MAX-ACCESS  read-create
    STATUS      current
    DESCRIPTION
        "Operation status of this table entry.  A row entry cannot
        be modified when the value of this object is 'active'."
    ::= { hh3cMplsExtLdpEntry 3 }
-- =============================================================================
-- End of hh3cMplsExtLdpTable Definition
-- =============================================================================

END
