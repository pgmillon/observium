NBS-META-MIB DEFINITIONS ::= BEGIN

IMPORTS
        OBJECT-TYPE, OBJECT-IDENTITY, MODULE-IDENTITY
            FROM SNMPv2-SMI
        DisplayString
            FROM SNMPv2-TC
        InterfaceIndex, nbs
            FROM NBS-CMMC-MIB
        ;

metaMib MODULE-IDENTITY
        LAST-UPDATED  "200808110000Z"
        ORGANIZATION  "NBS"
        CONTACT-INFO
          "For technical support, please contact your service channel"

        DESCRIPTION
          "MIB for representing NBS FDRNIX private information"

        ::= { nbs 205 }


metaMibGrp OBJECT-IDENTITY
        STATUS      current
        DESCRIPTION "Meta MIB"
        ::= { metaMib 1 }

metaMibFeatureTableSize OBJECT-TYPE
        SYNTAX      INTEGER
        MAX-ACCESS  read-only
        STATUS      current
        DESCRIPTION
          "The number of rows in the metaMibFeature table"
        ::= { metaMibGrp 1 }

metaMibFeatureTable OBJECT-TYPE
        SYNTAX      SEQUENCE OF MetaMibFeatureEntry
        MAX-ACCESS  not-accessible
        STATUS      current
        DESCRIPTION
          "List of features a hardware device might implement."
        ::= { metaMibGrp 2 }

metaMibFeatureEntry OBJECT-TYPE
        SYNTAX      MetaMibFeatureEntry
        MAX-ACCESS  not-accessible
        STATUS      current
        DESCRIPTION
          "A specific feature"

        INDEX { metaMibFeatureID }

        ::= { metaMibFeatureTable 1 }

MetaMibFeatureEntry ::= SEQUENCE {
        metaMibFeatureID               INTEGER,
        metaMibFeatureFamily           DisplayString,
        metaMibFeatureName             DisplayString,
        metaMibFeatureDesc             DisplayString,
        metaMibFeatureUnits            DisplayString,
        metaMibFeatureType             INTEGER
}

metaMibFeatureID OBJECT-TYPE
        SYNTAX      INTEGER
        MAX-ACCESS  not-accessible
        STATUS      current
        DESCRIPTION
          "Unique identifier for this feature"
        ::= { metaMibFeatureEntry 1 }

metaMibFeatureFamily OBJECT-TYPE
        SYNTAX      DisplayString (SIZE(0..32))
        MAX-ACCESS  read-only
        STATUS      current
        DESCRIPTION
          "Family of this feature"
        ::= { metaMibFeatureEntry 2 }

metaMibFeatureName OBJECT-TYPE
        SYNTAX      DisplayString (SIZE(0..32))
        MAX-ACCESS  read-only
        STATUS      current
        DESCRIPTION
          "Name of this feature"
        ::= { metaMibFeatureEntry 3 }

metaMibFeatureDesc OBJECT-TYPE
        SYNTAX      DisplayString
        MAX-ACCESS  read-only
        STATUS      current
        DESCRIPTION
          "Description of this feature and its settings"
        ::= { metaMibFeatureEntry 4 }

metaMibFeatureUnits OBJECT-TYPE
        SYNTAX      DisplayString (SIZE(0..16))
        MAX-ACCESS  read-only
        STATUS      current
        DESCRIPTION
          "The units used in this feature"
        ::= { metaMibFeatureEntry 5 }

metaMibFeatureType OBJECT-TYPE
        SYNTAX      INTEGER {
                enum         (1), -- metaMibVariableCaps contains comma
                                  -- separated list of allowed enums
                string       (2), -- Caps contains (min, max) length
                integer      (3), -- Caps contains (min, max) values
                float        (4)  -- Caps contains (min, max) values
        }
        MAX-ACCESS  read-only
        STATUS      current
        DESCRIPTION
          "Data type"
        ::= { metaMibFeatureEntry 6 }

metaMibVariableTableSize OBJECT-TYPE
        SYNTAX      INTEGER
        MAX-ACCESS  read-only
        STATUS      current
        DESCRIPTION
          "The number of rows in the metaMibVariable table"
        ::= { metaMibGrp 3 }

metaMibVariableTable OBJECT-TYPE
        SYNTAX      SEQUENCE OF MetaMibVariableEntry
        MAX-ACCESS  not-accessible
        STATUS      current
        DESCRIPTION
          "List of variables a specific device implements."
        ::= { metaMibGrp 4 }

metaMibVariableEntry OBJECT-TYPE
        SYNTAX      MetaMibVariableEntry
        MAX-ACCESS  not-accessible
        STATUS      current
        DESCRIPTION
          "A specific feature"

        INDEX { metaMibVariableIfIndex, metaMibVariableID }

        ::= { metaMibVariableTable 1 }

MetaMibVariableEntry ::= SEQUENCE {
        metaMibVariableIfIndex          InterfaceIndex,
        metaMibVariableID               INTEGER,
        metaMibVariableCaps             DisplayString,
        metaMibVariableDefault          DisplayString,
        metaMibVariableJumper           DisplayString,
        metaMibVariableOper             DisplayString,
        metaMibVariableAdmin            DisplayString,
        metaMibVariableStatus           DisplayString
}

metaMibVariableIfIndex OBJECT-TYPE
        SYNTAX      InterfaceIndex
        MAX-ACCESS  not-accessible
        STATUS      current
        DESCRIPTION
          "What CCSSPPP does this belong to? If SS and PPP are zero,
           this belongs to a chassis. If PPP is zero, this belongs to a
           slot."
        ::= { metaMibVariableEntry 1 }

metaMibVariableID OBJECT-TYPE
        SYNTAX      INTEGER
        MAX-ACCESS  not-accessible
        STATUS      current
        DESCRIPTION
          "Index into metaMibFeatureTable (metaMibFeatureID)."
        ::= { metaMibVariableEntry 2 }

metaMibVariableCaps OBJECT-TYPE
        SYNTAX      DisplayString (SIZE(0..128))
        MAX-ACCESS  read-only
        STATUS      current
        DESCRIPTION
          "A list of comma separated strings that indicate what values
           this variable supports. Ranges and string lengths are
           expressed as a two item list (MIN,MAX). A zero length string
           indicates this variable is read only."
        ::= { metaMibVariableEntry 3 }

metaMibVariableDefault OBJECT-TYPE
        SYNTAX      DisplayString (SIZE(0..128))
        MAX-ACCESS  read-only
        STATUS      current
        DESCRIPTION
          "Default value of this variable. It may report a zero length
           string if FeatureType is string."
        ::= { metaMibVariableEntry 4 }

metaMibVariableJumper OBJECT-TYPE
        SYNTAX      DisplayString (SIZE(0..128))
        MAX-ACCESS  read-only
        STATUS      current
        DESCRIPTION
          "Current jumper setting for this variable. If the current
           jumper setting cannot be reported:

               - VariableJumper will report 'N/A' if FeatureType is
                 string.
               - VariableJumper will be zero length otherwise.

           If FeatureType is string, a zero length VariableJumper is
           a valid value."

        ::= { metaMibVariableEntry 5 }

metaMibVariableOper OBJECT-TYPE
        SYNTAX      DisplayString (SIZE(0..128))
        MAX-ACCESS  read-only
        STATUS      current
        DESCRIPTION
          "Current operational value for this variable. If the current
           operational value cannot be reported:

               - VariableOper will report 'N/A' if FeatureType is
                 string.
               - VariableOper will be zero length otherwise.

           If VariableOper reports not supported, but VariableCaps
           reports non-zero length, this variable is write-only due to
           hardware limitations.

           If FeatureType is string, a zero length VariableOper is
           a valid value."

        ::= { metaMibVariableEntry 6 }

metaMibVariableAdmin OBJECT-TYPE
        SYNTAX      DisplayString (SIZE(0..128))
        MAX-ACCESS  read-write
        STATUS      current
        DESCRIPTION
          "Administrative value of this variable. If the administrative
           value cannot be set for this variable, VariableCaps will
           report a zero length string when read.

           Writing zero length values are only permitted if FeatureType
           is string and VariableCaps permits it. Otherwise, zero
           length strings will be rejected.

           If FeatureType is string, a zero length VariableAdmin is
           a valid value."

        ::= { metaMibVariableEntry 7 }

metaMibVariableStatus OBJECT-TYPE
        SYNTAX      DisplayString (SIZE(0..128))
        MAX-ACCESS  read-only
        STATUS      current
        DESCRIPTION
          "Messages relating to this variable"
        ::= { metaMibVariableEntry 8 }

END

--  vim: expandtab
--  vim: ts=8
--  vim: sw=2
--  vim: tw=71
--  vim: nojoinspaces
