NBS-SIGCOND-MIB DEFINITIONS ::= BEGIN

IMPORTS
    Unsigned32, OBJECT-TYPE,
    MODULE-IDENTITY, OBJECT-IDENTITY
        FROM SNMPv2-SMI
    nbs
        FROM NBS-CMMC-MIB;

nbsSigCondMib  MODULE-IDENTITY
    LAST-UPDATED  "201111300000Z"
    ORGANIZATION  "NBS"
    CONTACT-INFO
      "For technical support, please contact your service channel"

    DESCRIPTION
      "Signal Conditioning mib"
    ::= { nbs 227 }

-- *******************************************************************
-- NBS-SIGCOND-MIB local defines
-- *******************************************************************
InterfaceIndex ::= INTEGER

nbsSigCondVoaPortGrp  OBJECT-IDENTITY
    STATUS    current
    DESCRIPTION
      "Variable Optical Attenuation at the port level."
    ::= { nbsSigCondMib 1 }

nbsSigCondVoaFlowGrp  OBJECT-IDENTITY
    STATUS    current
    DESCRIPTION
      "Variable Optical Attenuation at the port.frequency.direction
       level."
    ::= { nbsSigCondMib 2 }

nbsSigCondRamanGrp  OBJECT-IDENTITY
    STATUS    current
    DESCRIPTION
      "Raman amplifier information for the port."
    ::= { nbsSigCondMib 3 }

nbsSigCondPortGrp  OBJECT-IDENTITY
    STATUS    current
    DESCRIPTION
      "Power readings from the port."
    ::= { nbsSigCondMib 100 }


nbsSigCondTraps  OBJECT-IDENTITY
    STATUS      current
    DESCRIPTION "SNMP Traps or Notifications"
    ::= { nbsSigCondMib 200 }

nbsSigCondTrap0  OBJECT-IDENTITY
    STATUS      current
    DESCRIPTION "SNMP Traps or Notifications"
    ::= { nbsSigCondTraps 0 }


-- *******************************************************************
--
-- the nbsSigCondVoaPortTable
--
-- *******************************************************************

nbsSigCondVoaPortTableSize OBJECT-TYPE
        SYNTAX      Unsigned32
        MAX-ACCESS  read-only
        STATUS      current
        DESCRIPTION
          "The number of ports supporting variable optical attenuation
           at the port level."
        ::= { nbsSigCondVoaPortGrp 1 }

nbsSigCondVoaPortTable OBJECT-TYPE
        SYNTAX      SEQUENCE OF NbsSigCondVoaPortEntry
        MAX-ACCESS  not-accessible
        STATUS      current
        DESCRIPTION
          "List of ports supporting variable optical attenuation at the
           port level."
        ::= { nbsSigCondVoaPortGrp 2 }

NbsSigCondVoaPortEntry ::= SEQUENCE {
        nbsSigCondVoaPortIfIndex        InterfaceIndex,
        nbsSigCondVoaPortRxAttenuAdmin  INTEGER,
        nbsSigCondVoaPortRxAttenuOper   INTEGER,
        nbsSigCondVoaPortTxAttenuAdmin  INTEGER,
        nbsSigCondVoaPortTxAttenuOper   INTEGER
}

nbsSigCondVoaPortEntry      OBJECT-TYPE
        SYNTAX      NbsSigCondVoaPortEntry
        MAX-ACCESS  not-accessible
        STATUS      current
        DESCRIPTION
          ""
        INDEX { nbsSigCondVoaPortIfIndex }
        ::= { nbsSigCondVoaPortTable 1 }

nbsSigCondVoaPortIfIndex   OBJECT-TYPE
        SYNTAX      InterfaceIndex
        MAX-ACCESS  not-accessible
        STATUS      current
        DESCRIPTION
          "The Mib2 ifIndex of the attenuable port."
        ::= { nbsSigCondVoaPortEntry 1 }

nbsSigCondVoaPortRxAttenuAdmin OBJECT-TYPE
        SYNTAX      INTEGER (-100000..100000)
        MAX-ACCESS  read-write
        STATUS      current
        DESCRIPTION
          "Persistent and immediately updated.  User-requested
           attenuation to be applied to received signal, expressed in
           millidecibels (mdB).
           Not supported value: -200000"
        DEFVAL { 0 }
        ::= { nbsSigCondVoaPortEntry 2 }

nbsSigCondVoaPortRxAttenuOper OBJECT-TYPE
        SYNTAX      INTEGER
        MAX-ACCESS  read-only
        STATUS      current
        DESCRIPTION
          "Attenuation actually being applied to received signal, in
           millidecibels (mdB).
           Not supported value: -200000"
        DEFVAL { 0 }
        ::= { nbsSigCondVoaPortEntry 3 }

nbsSigCondVoaPortTxAttenuAdmin OBJECT-TYPE
        SYNTAX      INTEGER (-100000..100000)
        MAX-ACCESS  read-write
        STATUS      current
        DESCRIPTION
          "Persistent and immediately updated.  User-requested
           attenuation to be applied before transmitting signal,
           expressed in millidecibels (mdB).
           Not supported value: -200000"
        DEFVAL { 0 }
        ::= { nbsSigCondVoaPortEntry 4 }

nbsSigCondVoaPortTxAttenuOper OBJECT-TYPE
        SYNTAX      INTEGER
        MAX-ACCESS  read-only
        STATUS      current
        DESCRIPTION
          "Attenuation actually being applied before transmitting
           signal, in millidecibels (mdB).
           Not supported value: -200000"
        DEFVAL { 0 }
        ::= { nbsSigCondVoaPortEntry 5}


-- *******************************************************************
--
-- the nbsSigCondVoaFlowTable
--
-- *******************************************************************

nbsSigCondVoaFlowTableSize OBJECT-TYPE
        SYNTAX      Unsigned32
        MAX-ACCESS  read-only
        STATUS      current
        DESCRIPTION
          "The number of attenuable flows in this system."
        ::= { nbsSigCondVoaFlowGrp 1 }

nbsSigCondVoaFlowTable OBJECT-TYPE
        SYNTAX      SEQUENCE OF NbsSigCondVoaFlowEntry
        MAX-ACCESS  not-accessible
        STATUS      current
        DESCRIPTION
          "Table of attenuable flows."
        ::= { nbsSigCondVoaFlowGrp 2 }

NbsSigCondVoaFlowEntry ::= SEQUENCE {
        nbsSigCondVoaFlowIfIndex      InterfaceIndex,
        nbsSigCondVoaFlowWavelength   INTEGER,
        nbsSigCondVoaFlowDirection    INTEGER,
        nbsSigCondVoaFlowAttenuAdmin  INTEGER,
        nbsSigCondVoaFlowAttenuOper   INTEGER
}

nbsSigCondVoaFlowEntry      OBJECT-TYPE
        SYNTAX      NbsSigCondVoaFlowEntry
        MAX-ACCESS  not-accessible
        STATUS      current
        DESCRIPTION
          "Reports status of monitored frequencies."
        INDEX { nbsSigCondVoaFlowIfIndex, nbsSigCondVoaFlowWavelength, nbsSigCondVoaFlowDirection }
        ::= { nbsSigCondVoaFlowTable 1 }

nbsSigCondVoaFlowIfIndex   OBJECT-TYPE
        SYNTAX      InterfaceIndex
        MAX-ACCESS  not-accessible
        STATUS      current
        DESCRIPTION
          "The Mib2 ifIndex of the optical spectrum analyzer port"
        ::= { nbsSigCondVoaFlowEntry 1 }

nbsSigCondVoaFlowWavelength OBJECT-TYPE
        SYNTAX      INTEGER
        MAX-ACCESS  not-accessible
        STATUS      current
        DESCRIPTION
          "The nominal wavelength, in picometers, of this channel."
        ::= { nbsSigCondVoaFlowEntry 2 }

nbsSigCondVoaFlowDirection OBJECT-TYPE
        SYNTAX      INTEGER {
                rx  (1),
                tx  (2)
        }
        MAX-ACCESS  not-accessible
        STATUS      current
        DESCRIPTION
          "Third index of table.  The value rx(1) indicates the
           received signal, and tx(2) indicates the transmitted
           signal."
        ::= { nbsSigCondVoaFlowEntry 3 }

nbsSigCondVoaFlowAttenuAdmin OBJECT-TYPE
        SYNTAX      INTEGER
        MAX-ACCESS  read-write
        STATUS      current
        DESCRIPTION
          "Persistent and immediately updated.  User-requested
           attenuation to be applied to signal, expressed in
           millidecibels (mdB)."
        ::= { nbsSigCondVoaFlowEntry 4 }

nbsSigCondVoaFlowAttenuOper OBJECT-TYPE
        SYNTAX      INTEGER
        MAX-ACCESS  read-only
        STATUS      current
        DESCRIPTION
          "Attenuation actually being applied to signal, in
           millidecibels (mdB)."
        ::= { nbsSigCondVoaFlowEntry 5 }


-- *******************************************************************
--
-- the nbsSigCondRamanTable
--
-- *******************************************************************

nbsSigCondRamanTableSize OBJECT-TYPE
        SYNTAX      Unsigned32
        MAX-ACCESS  read-only
        STATUS      current
        DESCRIPTION
          "The number of raman ports in this system."
        ::= { nbsSigCondRamanGrp 1 }

nbsSigCondRamanTable OBJECT-TYPE
        SYNTAX      SEQUENCE OF NbsSigCondRamanEntry
        MAX-ACCESS  not-accessible
        STATUS      current
        DESCRIPTION
          "Table of Raman readings."
        ::= { nbsSigCondRamanGrp 2 }

NbsSigCondRamanEntry ::= SEQUENCE {
        nbsSigCondRamanIfIndex      InterfaceIndex,
        nbsSigCondRamanPumpPwrAdmin INTEGER,
        nbsSigCondRamanPumpPwrOper  INTEGER
}

nbsSigCondRamanEntry      OBJECT-TYPE
        SYNTAX      NbsSigCondRamanEntry
        MAX-ACCESS  not-accessible
        STATUS      current
        DESCRIPTION
          "Raman readings on an individual port."
        INDEX { nbsSigCondRamanIfIndex }
        ::= { nbsSigCondRamanTable 1 }

nbsSigCondRamanIfIndex   OBJECT-TYPE
        SYNTAX      InterfaceIndex
        MAX-ACCESS  not-accessible
        STATUS      current
        DESCRIPTION
          "The Mib2 ifIndex of the Raman port"
        ::= { nbsSigCondRamanEntry 1 }

nbsSigCondRamanPumpPwrAdmin OBJECT-TYPE
        SYNTAX      INTEGER
        MAX-ACCESS  read-write
        STATUS      current
        DESCRIPTION
          "Persistent and immediately updated.  User-requested pump
           power,  in microwatts (uW).  
           User interfaces should show this in millWatts (mW).
           Not supported value:  -1"
        ::= { nbsSigCondRamanEntry 2 }

nbsSigCondRamanPumpPwrOper OBJECT-TYPE
        SYNTAX      INTEGER
        MAX-ACCESS  read-only
        STATUS      current
        DESCRIPTION
          "Agent reported pump power, in microwatts (uW).
           User interfaces should show this in millWatts (mW).
           Not supported value:  -1"
        ::= { nbsSigCondRamanEntry 3 }


-- *******************************************************************
--
-- the nbsSigCondPortTable
--
-- *******************************************************************

nbsSigCondPortTableSize OBJECT-TYPE
        SYNTAX      Unsigned32
        MAX-ACCESS  read-only
        STATUS      current
        DESCRIPTION
          "The number of entries in nbsSigCondPortTable."
        ::= { nbsSigCondPortGrp 1 }

nbsSigCondPortTable OBJECT-TYPE
        SYNTAX      SEQUENCE OF NbsSigCondPortEntry
        MAX-ACCESS  not-accessible
        STATUS      current
        DESCRIPTION
          "Table of VOA and VGA ports."
        ::= { nbsSigCondPortGrp 2 }

NbsSigCondPortEntry ::= SEQUENCE {
        nbsSigCondPortIfIndex      InterfaceIndex,
        nbsSigCondPortRxPower      INTEGER,
        nbsSigCondPortTxPower      INTEGER,
        nbsSigCondPortReflection   INTEGER
}

nbsSigCondPortEntry      OBJECT-TYPE
        SYNTAX      NbsSigCondPortEntry
        MAX-ACCESS  not-accessible
        STATUS      current
        DESCRIPTION
          ""
        INDEX { nbsSigCondPortIfIndex }
        ::= { nbsSigCondPortTable 1 }

nbsSigCondPortIfIndex   OBJECT-TYPE
        SYNTAX      InterfaceIndex
        MAX-ACCESS  not-accessible
        STATUS      current
        DESCRIPTION
          "The Mib2 ifIndex of the Port port"
        ::= { nbsSigCondPortEntry 1 }

nbsSigCondPortRxPower OBJECT-TYPE
        SYNTAX      INTEGER
        MAX-ACCESS  read-only
        STATUS      current
        DESCRIPTION
          "Measured receiver power, in millidecibels (mdBm).
           User interfaces should show this in decibels (dBm).
           Not supported value:  -100000"
        ::= { nbsSigCondPortEntry 2 }

nbsSigCondPortTxPower OBJECT-TYPE
        SYNTAX      INTEGER
        MAX-ACCESS  read-only
        STATUS      current
        DESCRIPTION
          "Measured transmitter power, in millidecibels (mdBm).
           User interfaces should show this in decibels (dBm).
           Not supported value:  -100000"
        ::= { nbsSigCondPortEntry 3 }

nbsSigCondPortReflection OBJECT-TYPE
        SYNTAX      INTEGER
        MAX-ACCESS  read-only
        STATUS      current
        DESCRIPTION
          "Measured back reflection power, in millidecibels (mdBm).
           User interfaces should show this in decibels (dBm).
           Not supported value:  -100000"
        ::= { nbsSigCondPortEntry 4}


END

--  vim: expandtab
--  vim: ts=8
--  vim: sw=2
--  vim: tw=72
--  vim: nojoinspaces
