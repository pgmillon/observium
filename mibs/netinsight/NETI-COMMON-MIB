NETI-COMMON-MIB DEFINITIONS ::= BEGIN

-- -------------------------------------------------------------
-- The common OIDs and definitions in the Net Insight
-- enterprise MIB
-- -------------------------------------------------------------

IMPORTS
    TEXTUAL-CONVENTION
        FROM SNMPv2-TC
    enterprises, MODULE-IDENTITY
        FROM SNMPv2-SMI;


-- -------------------------------------------------------------
-- The enterprise OID
-- -------------------------------------------------------------

netinsight MODULE-IDENTITY
    LAST-UPDATED
        "201410231300Z"
    ORGANIZATION
        "Net Insight AB"
    CONTACT-INFO
        "Net Insight AB
         Box 42093
         SE-126 14 Stockholm
         Sweden
         Tel +46-8-685 0400
         info@netinsight.net"
    DESCRIPTION
        "Common definitions for the Net Insight MIB tree.
         This in the `root' in the Net Insight MIB tree."

    REVISION
        "201410231300Z"
    DESCRIPTION
        "Added object for new unit Nimbra VA 220: nimbraVA220."

    REVISION
        "201404011000Z"
    DESCRIPTION
        "Added NETI-TRUNK-MIB."

    REVISION
        "201310100900Z"
    DESCRIPTION
        "Added object for new unit: nimbra390."

    REVISION
        "201306031100Z"
    DESCRIPTION
        "Replaced NETI-EVENT-MIB with NETI-EVT-MIB."

    REVISION
        "201301301300Z"
    DESCRIPTION
        "Added object for new units: nimbraVA210.
         Added root for new mib NETI-VA-INET-TRANSPORT-MIB.

         Added object for new unit: nimbra640.

         Added objects for new boards:
         nimbra340ModuleTypesAccess8xSDI,
         nimbra680ModuleTypesSwitch160Gbps,
         nimbra680ModuleTypesAccess8xVideo,
         nimbra680ModuleTypesAccess8xASIAES,
         nimbra680ModuleTypesAccess2x10GbE"

    REVISION
        "201209121100Z"
    DESCRIPTION
        "Added object for new unit: nimbra240."

    REVISION
        "201203220920Z"
    DESCRIPTION
        "Added object for new unit: nimbra310."

    REVISION
        "201203161300Z"
    DESCRIPTION
        "Corrected root object to nimbra230 mibs."

    REVISION
        "201103251400Z"
    DESCRIPTION
        "Added object for new units:
         nimbra230 and nimbra320.

         Added object for new MIB:
         netiNvMIB"

    REVISION
        "201011100800Z"
    DESCRIPTION
        "Added object for new unit:
         nimbra380

         Added object for new board:
         nimbra380ModuleTypesAccess8xGbE"

    REVISION
        "201002041500Z"
    DESCRIPTION
        "Added objects for new units:
         nimbra130,
         nimbra360Gold

         Added objects for new thermometers:
         nimbraOneThermometer,
         nimbra340Thermometer,
         nimbra680Thermometer

         Added objects for new boards:
         nimbraOneModuleTypesAuxGPIO,
         nimbra340ModuleTypesAuxGPIO,
         nimbraOneModuleTypesTrunk3xIP,
         nimbra340ModuleTypesTrunk3xIP,
         nimbra680ModuleTypesIfTrunk6xIP,
         nimbraOneModuleTypesTrunkAccess4xDS3E3,
         nimbra340ModuleTypesTrunkAccess4xDS3E3,
         nimbra680ModuleTypesAccess8xJPEG2000"

    REVISION
        "200812191400Z"
    DESCRIPTION
        "Added Nimbra Vision group nimbravision."

    REVISION
        "200812121300Z"
    DESCRIPTION
        "Updated comments.
         Corrected date on previous revision (wrong year)."

    REVISION
        "200810151200Z"
    DESCRIPTION
        "Added object for new board:
         nimbra680ModuleTypesAccess8x3Gbps"

    REVISION
        "200806191000Z"
    DESCRIPTION
        "Added objects for new unit:
         nimbra688"

    REVISION
        "200707311500Z"
    DESCRIPTION
        "Added objects for new boards:
         nimbraOneModuleTypesAccess8xAESEBU,
         nimbra340ModuleTypesAccess8xAESEBU,
         nimbra680ModuleTypesSwitch80Gbps,
         nimbra680ModuleTypesAccess8xHDSDI,
         nimbra680ModuleTypesAccess8xGbE,
         nimbra680ModuleTypesAccess8xASI,
         nimbra680ModuleTypesAuxGPIO"

    REVISION
        "200701261100Z"
    DESCRIPTION
        "Added object for Nimbra 360 trunk."

    REVISION
        "200608170830Z"
    DESCRIPTION
        "Added objects for Nimbra 340HD:
         nimbra340HD, nimbra340ModuleTypesAccessHDSDI.
         Added object for Nimbra 360."

    REVISION
        "200512150000Z"
    DESCRIPTION
        "Added objects for Nimbra 340.
         Added new PIU objects for Nimbra One.
         Removed of obsoleted and never used objects.
         Reformatted text."

    REVISION
        "200303250000Z"
    DESCRIPTION
        "Added objects that is used by entPhysicalVendorType in ENTITY-MIB
         described in RFC2737:

         nimbraOneModuleTypesDtm622
         nimbraOneModuleTypesAccessGigabitEthernet
         nimbraOneModuleTypesAccessASIRight
         nimbraOneModuleTypesAccessASILeft"
    ::= {enterprises 2928}

-- -------------------------------------------------------------
-- Textual conventions
-- -------------------------------------------------------------

FaultStatus ::= TEXTUAL-CONVENTION
    STATUS  current
    DESCRIPTION
        "Shows the status of a fault that causes an alarm.
         Each fault should have its own variable and this
         OID is used as the identifier of the alarm.

         ok
         The fault is not present and the alarm is not raised.

         fault
         The fault is present and and alarm is raised."
    SYNTAX  INTEGER {
                ok(1),
                fault(2) }


-- -------------------------------------------------------------
-- Product definitions. The OID's are for identifying the agent
-- software and used in sysObjectID in the MIB-II Systems Group.
-- -------------------------------------------------------------
netiReg         OBJECT IDENTIFIER ::= {netinsight 1}

nimbraOne       OBJECT IDENTIFIER ::= {netiReg 1}    -- deprecated
nimbra101       OBJECT IDENTIFIER ::= {netiReg 2}    -- deprecated
nimbra210       OBJECT IDENTIFIER ::= {netiReg 3}    -- deprecated
nimbra220       OBJECT IDENTIFIER ::= {netiReg 4}    -- deprecated
nimbra290       OBJECT IDENTIFIER ::= {netiReg 5}    -- deprecated
nimbraTwo       OBJECT IDENTIFIER ::= {netiReg 6}    -- deprecated
netiRegGeneric  OBJECT IDENTIFIER ::= {netiReg 7}    -- for use as root for objects independent of type
nimbra291       OBJECT IDENTIFIER ::= {netiReg 8}    -- deprecated
nimbra340       OBJECT IDENTIFIER ::= {netiReg 9}
nimbra680       OBJECT IDENTIFIER ::= {netiReg 10}
nimbra340HD     OBJECT IDENTIFIER ::= {netiReg 11}
nimbra360       OBJECT IDENTIFIER ::= {netiReg 12}
nimbra360Gold   OBJECT IDENTIFIER ::= {nimbra360 1}  -- Is subclass of Nimbra 360
nimbra688       OBJECT IDENTIFIER ::= {netiReg 13}
nimbra130       OBJECT IDENTIFIER ::= {netiReg 14}
nimbra380       OBJECT IDENTIFIER ::= {netiReg 15}
nimbra230       OBJECT IDENTIFIER ::= {netiReg 16}
nimbra320       OBJECT IDENTIFIER ::= {netiReg 17}
nimbra140       OBJECT IDENTIFIER ::= {netiReg 18}
nimbra310       OBJECT IDENTIFIER ::= {netiReg 19}
nimbra240       OBJECT IDENTIFIER ::= {netiReg 20}
nimbra640       OBJECT IDENTIFIER ::= {netiReg 21}
nimbraVA210     OBJECT IDENTIFIER ::= {netiReg 22}
nimbraVA210FV     OBJECT IDENTIFIER ::= {nimbraVA210 1}
nimbraVA210DCV1   OBJECT IDENTIFIER ::= {nimbraVA210 2}
nimbraVA210DCV2   OBJECT IDENTIFIER ::= {nimbraVA210 3}
nimbra390       OBJECT IDENTIFIER ::= {netiReg 23}
nimbraVA220     OBJECT IDENTIFIER ::= {netiReg 25}




-- -------------------------------------------------------------
-- Product definitions. The OID's are for identifying the
-- type of physical entity and is used in entPhysicalVendorType
-- in the ENTITY-MIB Physical Table.
-- -------------------------------------------------------------

--
-- NimbraOne
-- (obsoleted since GX4.12.0)
--

nimbraOneChassisTypes     OBJECT IDENTIFIER ::= {nimbraOne 1}
nimbraOneBaseUnit         OBJECT IDENTIFIER ::= {nimbraOneChassisTypes 1}
nimbraOneBackplaneTypes   OBJECT IDENTIFIER ::= {nimbraOne 2}
nimbraOneBackplane        OBJECT IDENTIFIER ::= {nimbraOneBackplaneTypes 1}
nimbraOneContainerTypes   OBJECT IDENTIFIER ::= {nimbraOne 3}
nimbraOneSlot             OBJECT IDENTIFIER ::= {nimbraOneContainerTypes 1}
nimbraOnePowerSupplyTypes OBJECT IDENTIFIER ::= {nimbraOne 4}
nimbraOnePowerSupply      OBJECT IDENTIFIER ::= {nimbraOnePowerSupplyTypes 1}
nimbraOneFanTypes         OBJECT IDENTIFIER ::= {nimbraOne 5}
nimbraOneFan              OBJECT IDENTIFIER ::= {nimbraOneFanTypes 1}
nimbraOneModuleTypes      OBJECT IDENTIFIER ::= {nimbraOne 6}   -- Plug-In Units


-- Management modules (Node Controller)
nimbraOneModuleTypesMgmt OBJECT IDENTIFIER ::= {nimbraOneModuleTypes 1}
nimbraOneModuleTypesMgmtControlModule OBJECT IDENTIFIER ::= {nimbraOneModuleTypesMgmt 1}


-- Trunk modules
nimbraOneModuleTypesDtm OBJECT IDENTIFIER ::= {nimbraOneModuleTypes 2}

-- (obsoleted since GX3.3.2)
nimbraOneModuleTypesDtm850ShortHaulRight  OBJECT IDENTIFIER ::= {nimbraOneModuleTypesDtm 1}   -- MAU850
nimbraOneModuleTypesDtm850ShortHaulLeft   OBJECT IDENTIFIER ::= {nimbraOneModuleTypesDtm 2}   -- MAU850
nimbraOneModuleTypesDtm850LongHaulRight   OBJECT IDENTIFIER ::= {nimbraOneModuleTypesDtm 3}   -- MAU850
nimbraOneModuleTypesDtm850LongHaulLeft    OBJECT IDENTIFIER ::= {nimbraOneModuleTypesDtm 4}   -- MAU850
nimbraOneModuleTypesDtm1000ShortHaulRight OBJECT IDENTIFIER ::= {nimbraOneModuleTypesDtm 5}   -- MAU1000
nimbraOneModuleTypesDtm1000ShortHaulLeft  OBJECT IDENTIFIER ::= {nimbraOneModuleTypesDtm 6}   -- MAU1000
nimbraOneModuleTypesDtm1000LongHaulRight  OBJECT IDENTIFIER ::= {nimbraOneModuleTypesDtm 7}   -- MAU1000
nimbraOneModuleTypesDtm1000LongHaulLeft   OBJECT IDENTIFIER ::= {nimbraOneModuleTypesDtm 8}   -- MAU1000
nimbraOneModuleTypesDtm150Right           OBJECT IDENTIFIER ::= {nimbraOneModuleTypesDtm 9}   -- MAU150
nimbraOneModuleTypesDtm150Left            OBJECT IDENTIFIER ::= {nimbraOneModuleTypesDtm 10}  -- MAU150
nimbraOneModuleTypesDtm622                OBJECT IDENTIFIER ::= {nimbraOneModuleTypesDtm 11}  -- MAU600

-- (obsoleted since GX4.12.0)
nimbraOneModuleTypesTrunk1Gbps            OBJECT IDENTIFIER ::= {nimbraOneModuleTypesDtm 12}  -- MAU1000
nimbraOneModuleTypesTrunkDS3              OBJECT IDENTIFIER ::= {nimbraOneModuleTypesDtm 13}  -- MAU50
nimbraOneModuleTypesTrunkOC3              OBJECT IDENTIFIER ::= {nimbraOneModuleTypesDtm 14}  -- MAU150
nimbraOneModuleTypesTrunk4xOC3            OBJECT IDENTIFIER ::= {nimbraOneModuleTypesDtm 15}  -- MAU155
nimbraOneModuleTypesTrunkOC12             OBJECT IDENTIFIER ::= {nimbraOneModuleTypesDtm 16}  -- MAU600
nimbraOneModuleTypesTrunkOC48             OBJECT IDENTIFIER ::= {nimbraOneModuleTypesDtm 17}  -- MAU2500
nimbraOneModuleTypesTrunk3xIP             OBJECT IDENTIFIER ::= {nimbraOneModuleTypesDtm 18}  -- IP/Ethernet


-- Access modules
nimbraOneModuleTypesAccess OBJECT IDENTIFIER ::= {nimbraOneModuleTypes 3}

-- (obsoleted since GX3.2.2)
nimbraOneModuleTypesAccessE1Right         OBJECT IDENTIFIER ::= {nimbraOneModuleTypesAccess 1}   -- E1
nimbraOneModuleTypesAccessE1Left          OBJECT IDENTIFIER ::= {nimbraOneModuleTypesAccess 2}   -- E1
nimbraOneModuleTypesAccessT1Right         OBJECT IDENTIFIER ::= {nimbraOneModuleTypesAccess 3}   -- T1
nimbraOneModuleTypesAccessT1Left          OBJECT IDENTIFIER ::= {nimbraOneModuleTypesAccess 4}   -- T1
nimbraOneModuleTypesAccessVideo270Right   OBJECT IDENTIFIER ::= {nimbraOneModuleTypesAccess 5}   -- SDI
nimbraOneModuleTypesAccessVideo270Left    OBJECT IDENTIFIER ::= {nimbraOneModuleTypesAccess 6}   -- SDI
nimbraOneModuleTypesAccessEthernet8pRight OBJECT IDENTIFIER ::= {nimbraOneModuleTypesAccess 7}   -- FEC
nimbraOneModuleTypesAccessEthernet8pLeft  OBJECT IDENTIFIER ::= {nimbraOneModuleTypesAccess 8}   -- FEC
nimbraOneModuleTypesAccessGigabitEthernet OBJECT IDENTIFIER ::= {nimbraOneModuleTypesAccess 9}   -- GEC
nimbraOneModuleTypesAccessASIRight        OBJECT IDENTIFIER ::= {nimbraOneModuleTypesAccess 11}  -- ASI
nimbraOneModuleTypesAccessASILeft         OBJECT IDENTIFIER ::= {nimbraOneModuleTypesAccess 12}  -- ASI

-- (obsoleted since GX4.12.0)
nimbraOneModuleTypesAccessGbE             OBJECT IDENTIFIER ::= {nimbraOneModuleTypesAccess 13}  -- GEC
nimbraOneModuleTypesAccess8xEth           OBJECT IDENTIFIER ::= {nimbraOneModuleTypesAccess 14}  -- FEC
nimbraOneModuleTypesAccessASI             OBJECT IDENTIFIER ::= {nimbraOneModuleTypesAccess 15}  -- ASI
nimbraOneModuleTypesAccessSDI             OBJECT IDENTIFIER ::= {nimbraOneModuleTypesAccess 16}  -- SDI
nimbraOneModuleTypesAccess4xOC3           OBJECT IDENTIFIER ::= {nimbraOneModuleTypesAccess 17}  -- SAC155
nimbraOneModuleTypesAccessE1              OBJECT IDENTIFIER ::= {nimbraOneModuleTypesAccess 18}  -- T1
nimbraOneModuleTypesAccessT1              OBJECT IDENTIFIER ::= {nimbraOneModuleTypesAccess 19}  -- E1
nimbraOneModuleTypesAccess8xASI           OBJECT IDENTIFIER ::= {nimbraOneModuleTypesAccess 20}  -- 8x ASI
nimbraOneModuleTypesAccess8xAESEBU        OBJECT IDENTIFIER ::= {nimbraOneModuleTypesAccess 21}  -- 8x AES/EBU


-- Trunk and Access modules
nimbraOneModuleTypesTrunkAccess OBJECT IDENTIFIER ::= {nimbraOneModuleTypes 4}

nimbraOneModuleTypesTrunkAccess4xDS3E3      OBJECT IDENTIFIER ::= {nimbraOneModuleTypesTrunkAccess 1}   -- 4x DS3/E3


-- Auxillary Modules
nimbraOneModuleTypesAux OBJECT IDENTIFIER ::= {nimbraOneModuleTypes 5}

nimbraOneModuleTypesAuxGPIO OBJECT IDENTIFIER ::= {nimbraOneModuleTypesAux 1} -- GPIO Alarm Module


-- Thermometers
nimbraOneThermometerTypes OBJECT IDENTIFIER ::= {nimbraOne 7}
nimbraOneThermometer      OBJECT IDENTIFIER ::= {nimbraOneThermometerTypes 1}


--
-- Nimbra290
-- (obsoleted since GX3.2.8)
--
nimbra290ChassisTypes     OBJECT IDENTIFIER ::= {nimbra290 1}
nimbra290BaseUnit         OBJECT IDENTIFIER ::= {nimbra290ChassisTypes 1}
nimbra290PowerSupplyTypes OBJECT IDENTIFIER ::= {nimbra290 2}
nimbra290PowerUnit        OBJECT IDENTIFIER ::= {nimbra290PowerSupplyTypes 1}
nimbra290FanTypes         OBJECT IDENTIFIER ::= {nimbra290 3}
nimbra290Fan              OBJECT IDENTIFIER ::= {nimbra290FanTypes 1}


--
-- Nimbra340
--

nimbra340ChassisTypes     OBJECT IDENTIFIER ::= {nimbra340 1}
nimbra340ContainerTypes   OBJECT IDENTIFIER ::= {nimbra340 3}
nimbra340PowerSupplyTypes OBJECT IDENTIFIER ::= {nimbra340 4}
nimbra340FanTypes         OBJECT IDENTIFIER ::= {nimbra340 5}
nimbra340ModuleTypes      OBJECT IDENTIFIER ::= {nimbra340 6}  -- Plug-In Units


-- Management modules (Built-in Node Controller)
nimbra340ModuleTypesMgmt              OBJECT IDENTIFIER ::= {nimbra340ModuleTypes 1}
nimbra340ModuleTypesMgmtControlModule OBJECT IDENTIFIER ::= {nimbra340ModuleTypesMgmt 1}


-- Trunk modules for N340, N360 and N380
nimbra340ModuleTypesDtm OBJECT IDENTIFIER ::= {nimbra340ModuleTypes 2}

nimbra340ModuleTypesTrunk1Gbps  OBJECT IDENTIFIER ::= {nimbra340ModuleTypesDtm 1}   -- MAU1000
nimbra340ModuleTypesTrunkDS3    OBJECT IDENTIFIER ::= {nimbra340ModuleTypesDtm 2}   -- MAU50
nimbra340ModuleTypesTrunkOC3    OBJECT IDENTIFIER ::= {nimbra340ModuleTypesDtm 3}   -- MAU150
nimbra340ModuleTypesTrunk4xOC3  OBJECT IDENTIFIER ::= {nimbra340ModuleTypesDtm 4}   -- MAU155
nimbra340ModuleTypesTrunkOC12   OBJECT IDENTIFIER ::= {nimbra340ModuleTypesDtm 5}   -- MAU600
nimbra340ModuleTypesTrunkOC48   OBJECT IDENTIFIER ::= {nimbra340ModuleTypesDtm 6}   -- MAU2500
nimbra340ModuleTypesTrunk3xIP   OBJECT IDENTIFIER ::= {nimbra340ModuleTypesDtm 7}   -- 3xIP/Ethernet


-- Access modules for N340, N360 and N380
nimbra340ModuleTypesAccess OBJECT IDENTIFIER ::= {nimbra340ModuleTypes 3}

nimbra340ModuleTypesAccessGbE      OBJECT IDENTIFIER ::= {nimbra340ModuleTypesAccess 1}   -- GEC
nimbra340ModuleTypesAccess8xEth    OBJECT IDENTIFIER ::= {nimbra340ModuleTypesAccess 2}   -- FEC
nimbra340ModuleTypesAccessASI      OBJECT IDENTIFIER ::= {nimbra340ModuleTypesAccess 3}   -- ASI
nimbra340ModuleTypesAccessSDI      OBJECT IDENTIFIER ::= {nimbra340ModuleTypesAccess 4}   -- SD SDI
nimbra340ModuleTypesAccess4xOC3    OBJECT IDENTIFIER ::= {nimbra340ModuleTypesAccess 5}   -- SAC155
nimbra340ModuleTypesAccessE1       OBJECT IDENTIFIER ::= {nimbra340ModuleTypesAccess 6}   -- T1
nimbra340ModuleTypesAccessT1       OBJECT IDENTIFIER ::= {nimbra340ModuleTypesAccess 7}   -- E1
nimbra340ModuleTypesAccess8xASI    OBJECT IDENTIFIER ::= {nimbra340ModuleTypesAccess 8}   -- 8x ASI
nimbra340ModuleTypesAccessHDSDI    OBJECT IDENTIFIER ::= {nimbra340ModuleTypesAccess 9}   -- HD SDI
nimbra340ModuleTypesAccess8xAESEBU OBJECT IDENTIFIER ::= {nimbra340ModuleTypesAccess 10}  -- 8x AES/EBU
nimbra340ModuleTypesAccess8xSDI    OBJECT IDENTIFIER ::= {nimbra340ModuleTypesAccess 11}  -- 8x SDI



-- Built in modules for N340, N360 and N380. These modules are not
-- plug-in units, but are still modeled as such. Becase the N340, N360
-- and N380 are all variants that differs only on the set of these
-- fixed built-in modules, these fixed modules are grouped together
-- with the N340 modules.

-- Trunk modules
nimbra360ModuleTypesDtm OBJECT IDENTIFIER ::= {nimbra340ModuleTypes 4}
nimbra360ModuleTypesTrunkFunction  OBJECT IDENTIFIER ::= {nimbra360ModuleTypesDtm 1}   -- STM module


-- Auxillary Modules
nimbra340ModuleTypesAux OBJECT IDENTIFIER ::= {nimbra340ModuleTypes 5}
nimbra340ModuleTypesAuxGPIO OBJECT IDENTIFIER ::= {nimbra340ModuleTypesAux 1} -- GPIO Alarm Module


-- Trunk and Access modules
nimbra340ModuleTypesTrunkAccess OBJECT IDENTIFIER ::= {nimbra340ModuleTypes 6}
nimbra340ModuleTypesTrunkAccess4xDS3E3      OBJECT IDENTIFIER ::= {nimbra340ModuleTypesTrunkAccess 1}   -- 4x DS3/E3


-- Access Modules built-in on N380
nimbra380ModuleTypesAccess OBJECT IDENTIFIER ::= {nimbra340ModuleTypes 7 }
nimbra380ModuleTypesAccess8xGbE OBJECT IDENTIFIER ::= {nimbra380ModuleTypesAccess 1}


-- Thermometers built-in
nimbra340ThermometerTypes OBJECT IDENTIFIER ::= {nimbra340 7}
nimbra340Thermometer      OBJECT IDENTIFIER ::= {nimbra340ThermometerTypes 1}




--
-- Nimbra 680
--

nimbra680ChassisTypes     OBJECT IDENTIFIER ::= {nimbra680 1}
nimbra680ContainerTypes   OBJECT IDENTIFIER ::= {nimbra680 3}
nimbra680PowerSupplyTypes OBJECT IDENTIFIER ::= {nimbra680 4}
nimbra680FanTypes         OBJECT IDENTIFIER ::= {nimbra680 5}
nimbra680ModuleTypes      OBJECT IDENTIFIER ::= {nimbra680 6}  -- Plug-In Units


-- Power
nimbra680PowerSupplyTypesPCU  OBJECT IDENTIFIER ::= {nimbra680PowerSupplyTypes 1}   -- DC/DC converter
nimbra680PowerSupplyTypesPSU  OBJECT IDENTIFIER ::= {nimbra680PowerSupplyTypes 2}   -- Rectifier


-- Fans
nimbra680FanTypesFan      OBJECT IDENTIFIER ::= {nimbra680FanTypes 1}


-- Management modules
nimbra680ModuleTypesMgmt              OBJECT IDENTIFIER ::= {nimbra680ModuleTypes 1}

nimbra680ModuleTypesMgmtControlModule OBJECT IDENTIFIER ::= {nimbra680ModuleTypesMgmt 1}


-- Interface modules
nimbra680ModuleTypesIf OBJECT IDENTIFIER ::= {nimbra680ModuleTypes 2}

nimbra680ModuleTypesIfTrunk4xOC3  OBJECT IDENTIFIER ::= {nimbra680ModuleTypesIf 1}
nimbra680ModuleTypesIfTrunk4xOC12 OBJECT IDENTIFIER ::= {nimbra680ModuleTypesIf 2}
nimbra680ModuleTypesIfTrunk2xOC48 OBJECT IDENTIFIER ::= {nimbra680ModuleTypesIf 3}
nimbra680ModuleTypesIfTrunk4xOC48 OBJECT IDENTIFIER ::= {nimbra680ModuleTypesIf 4}
nimbra680ModuleTypesIfTrunkOC192  OBJECT IDENTIFIER ::= {nimbra680ModuleTypesIf 5}
nimbra680ModuleTypesIfTrunk6xIP   OBJECT IDENTIFIER ::= {nimbra680ModuleTypesIf 6}


-- Switch modules
nimbra680ModuleTypesSwitch OBJECT IDENTIFIER ::= {nimbra680ModuleTypes 3}

nimbra680ModuleTypesSwitch40Gbps  OBJECT IDENTIFIER ::= {nimbra680ModuleTypesSwitch 1}
nimbra680ModuleTypesSwitch80Gbps  OBJECT IDENTIFIER ::= {nimbra680ModuleTypesSwitch 2}
nimbra680ModuleTypesSwitch160Gbps  OBJECT IDENTIFIER ::= {nimbra680ModuleTypesSwitch 3}


-- Access Modules
nimbra680ModuleTypesAccess OBJECT IDENTIFIER ::= {nimbra680ModuleTypes 4}

nimbra680ModuleTypesAccess8xHDSDI OBJECT IDENTIFIER ::= {nimbra680ModuleTypesAccess 1} -- 8x HD/SD SDI
nimbra680ModuleTypesAccess8xGbE   OBJECT IDENTIFIER ::= {nimbra680ModuleTypesAccess 2} -- 8x GbE
nimbra680ModuleTypesAccess8xASI   OBJECT IDENTIFIER ::= {nimbra680ModuleTypesAccess 3} -- 8x ASI
nimbra680ModuleTypesAccess8x3Gbps OBJECT IDENTIFIER ::= {nimbra680ModuleTypesAccess 4} -- 8x 3G
nimbra680ModuleTypesAccess8xJPEG2000 OBJECT IDENTIFIER ::= {nimbra680ModuleTypesAccess 5} -- 8x JPEG2000
nimbra680ModuleTypesAccess8xVideo OBJECT IDENTIFIER ::= {nimbra680ModuleTypesAccess 6} -- 8x Video
nimbra680ModuleTypesAccess8xASIAES OBJECT IDENTIFIER ::= {nimbra680ModuleTypesAccess 7} -- 8x ASI/AES
nimbra680ModuleTypesAccess2x10GbE   OBJECT IDENTIFIER ::= {nimbra680ModuleTypesAccess 8} -- 2x 10GbE


-- Auxillary Modules
nimbra680ModuleTypesAux OBJECT IDENTIFIER ::= {nimbra680ModuleTypes 5}

nimbra680ModuleTypesAuxGPIO OBJECT IDENTIFIER ::= {nimbra680ModuleTypesAux 1} -- GPIO Alarm Module


-- Thermometers
nimbra680ThermometerTypes OBJECT IDENTIFIER ::= {nimbra680 7}

nimbra680Thermometer OBJECT IDENTIFIER ::= {nimbra680ThermometerTypes 1}


-- -------------------------------------------------------------
-- The MIB tree
-- -------------------------------------------------------------

-- Mib tree for generic MIBs. Objects and events not associated
-- with a specific product.
netiGeneric OBJECT IDENTIFIER ::= {netinsight 2}
-- MIBs assigned in the generic subtree:
-- NETI-EVENT-MIB   netiEventMIB ::= { netiGeneric 1 }
-- NETI-ETH-MIB     netiEthMIB   ::= { netiGeneric 2 }
-- NETI-TRUNK-MIB   netiTrunkMIB ::= { netiGeneric 3 }
-- NETI-VA-INET-TRANSPORT-MIB   netiVaInetTrspMIB  ::= { netiGeneric 4 }


-- Product specific mibs. Objects and events associated with a
-- specific product.
netiProducts OBJECT IDENTIFIER ::= {netinsight 3}
nimbravision OBJECT IDENTIFIER ::= {netiProducts 1}
-- MIBs assigned in the nimbravision subtree
-- NETI-NV-ALARM-MIB   netiNvAlarmMIB ::= { nimbravision 1 }
-- NETI-NV-MIB         netiNvMIB      ::= { nimbravision 2 }
prodNimbra230 OBJECT IDENTIFIER ::= {netiProducts 2}
-- nimbra230MIB ::= { netiProducts 2 }
-- nimbra140MIB ::= { netiProducts 3 }



-- Agent implementation profiles/capabilities
netiCaps OBJECT IDENTIFIER ::= {netinsight 4}


-- Requirement specifications
netiReqs OBJECT IDENTIFIER ::= {netinsight 5}


-- -------------------------------------------------------------
-- Experimental MIBs, initially for objects and events
-- under development. The structure is the same as for
-- netiGeneric above.
-- -------------------------------------------------------------
-- MIBs assigned in the experimental generic subtree:
-- NETI-ACCOUNTING-MIB             ::= { netiExperimentalGeneric 1 }   - deprecated
-- NETI-ALARM-MIB   netiAlarmMIB   ::= { netiExperimentalGeneric 2 }   - deprecated
-- NETI-DLE-MIB     netiDLEMIB     ::= { netiExperimentalGeneric 3 }   - deprecated
-- NETI-DTM-MIB     netiDTMMIB     ::= { netiExperimentalGeneric 4 }
-- NETI-TUNNEL-MIB  netiTunnelMIB  ::= { netiExperimentalGeneric 5 }   - deprecated
-- NETI-SYSTEM-MIB  netiSystemMIB  ::= { netiExperimentalGeneric 6 }   - deprecated
-- NETI-CONFIG-MIB  netiConfigMIB  ::= { netiExperimentalGeneric 7 }
-- NETI-ALARM-MIB2  netiAlarmMIB2  ::= { netiExperimentalGeneric 8 }   - deprecated
-- NETI-IPOD-MIB    netiIpodMIB    ::= { netiExperimentalGeneric 9 }   - deprecated
-- NETI-ENTITY-MIB  netiEntityMIB  ::= { netiExperimentalGeneric 10 }  - deprecated
-- NETI-ETS-MIB     netiEtsMIB     ::= { netiExperimentalGeneric 11 }  - deprecated
-- NETI-ETHCONF-MIB netiEthConfMIB ::= { netiExperimentalGeneric 12 }  - deprecated
-- NETI-PACKW-MIB   netiPackWMIB   ::= { netiExperimentalGeneric 13 }  - deprecated
-- NETI-CHMGR-MIB   netiChmgrMIB   ::= { netiExperimentalGeneric 14 }
-- NETI-DLT-MIB     netiDltMIB     ::= { netiExperimentalGeneric 15 }  - deprecated
-- NETI-ITS-MIB     netiItsMIB     ::= { netiExperimentalGeneric 16 }
-- NETI-PM-MIB      netiPMMIB      ::= { netiExperimentalGeneric 17 }

netiExperimental         OBJECT IDENTIFIER ::= {netinsight 6}
netiExperimentalReg      OBJECT IDENTIFIER ::= {netiExperimental 1}
netiExperimentalGeneric  OBJECT IDENTIFIER ::= {netiExperimental 2}
netiExperimentalProducts OBJECT IDENTIFIER ::= {netiExperimental 3}
netiExperimentalCaps     OBJECT IDENTIFIER ::= {netiExperimental 4}
netiExperimentalReqs     OBJECT IDENTIFIER ::= {netiExperimental 5}

END
