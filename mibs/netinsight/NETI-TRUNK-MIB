NETI-TRUNK-MIB DEFINITIONS ::= BEGIN

IMPORTS
    MODULE-IDENTITY, OBJECT-TYPE, Counter64, IpAddress,
    Unsigned32, Integer32, Gauge32
        FROM SNMPv2-SMI
    TEXTUAL-CONVENTION, TimeStamp, TruthValue, RowPointer
        FROM SNMPv2-TC
    SnmpAdminString
        FROM SNMP-FRAMEWORK-MIB
    netiGeneric
        FROM NETI-COMMON-MIB;

netiTrunkMIB MODULE-IDENTITY
    LAST-UPDATED
        "201403140800Z"
    ORGANIZATION
        "Net Insight AB"
    CONTACT-INFO
        "Net Insight AB
         Box 42093
         SE-126 14 Stockholm
         Sweden
         Tel +46-8-685 0400
         info@netinsight.se"
    DESCRIPTION
        "MIB for DTM network links (trunks). DTM trunks provide
         transport of DTM data between two DTM networks nodes.  The
         MIB currently includes the DPP-IP group (neti-dppip),
         providing management of DPP-IP encapsulated DTM over
         IP/Ethernet. It includes configuration information and
         status."

    REVISION
        "201403140800Z"
    DESCRIPTION
        "Extended draft. This revision is preliminary. Read-write
         objects have been added to give full managablity to the
         interfaces in the DPP-IP group. Values that limits the
         configuration of the local DPP-IP interfaces have been
         introduced in the dppipLimitsTable. Similarly, limits of the
         peer DPP-IP interfaces have been added in the
         dppipPeerLimitsTable."

    REVISION
        "201308291600Z"
    DESCRIPTION
        "Extended draft. This revision is preliminary. The
         dppipDelayVar01 object has been added to dppipEntry. All
         objects in the MIB are read-only."

    REVISION
        "201301241500Z"
    DESCRIPTION
        "Extended draft. This revision is preliminary. More objects
         have been added to dppipEntry to make the configuration
         information and status more complete. All objects in the MIB
         are read-only."

    REVISION
        "200908261500Z"
    DESCRIPTION
        "Draft. This revision is preliminary. Future revisions are
         likely to be incompatible with this revision."

    ::= { netiGeneric 3 }

trunkObjects  OBJECT IDENTIFIER ::= { netiTrunkMIB 1 }

-- -------------------------------------------------------------
-- Groups in the NETI-TRUNK-MIB
-- -------------------------------------------------------------

dppipGroup  OBJECT IDENTIFIER ::= { trunkObjects 1 }

-- -------------------------------------------------------------
-- Textual conventions
-- -------------------------------------------------------------

FecMode ::= TEXTUAL-CONVENTION
     STATUS      current
     DESCRIPTION
        "The mode of operation of the Forward Error Correction
         function (FEC).  The FEC function may be not used (fecNone),
         used for column correction (fec1D) or used for both row and
         column correction (fec2D)."
     SYNTAX INTEGER {
                fecNone(1),
                fec1D(2),
                fec2D(3)
            }

DppipSupport ::= TEXTUAL-CONVENTION
     DISPLAY-HINT "1d.1d"
     STATUS      current
     DESCRIPTION
        "Represents the support of a specific DPP-IP function:

                    octet    contents
                    1        major version
                    2        minor version

         Any minor version N.x includes support for any minor version
         M.y with major version M<N.  Minor version N.n includes
         support for any minor version N.m with the same major version
         N and m<n."
     SYNTAX      OCTET STRING (SIZE (2))

-- -------------------------------------------------------------
-- The DPP-IP group
-- -------------------------------------------------------------

dppipNumber OBJECT-TYPE
    SYNTAX      Integer32
    MAX-ACCESS  read-only
    STATUS      current
    DESCRIPTION
        "The number of DPP-IP interfaces (regardless of their current
         state) present on this system."
    ::= { dppipGroup 1 }

dppipLastChange OBJECT-TYPE
    SYNTAX      TimeStamp
    MAX-ACCESS  read-only
    STATUS      current
    DESCRIPTION
        "The value of sysUpTime when status or configuration of any
         the objects in the dppipTable was last changed."
     ::= { dppipGroup 2 }

-- The DPP-IP table

-- The DPP-IP table contains information on the system's
-- DPP-IP interfaces.  Each interface is thought of as being
-- attached to a `physical layer interface'.

dppipTable OBJECT-TYPE
     SYNTAX      SEQUENCE OF DppipEntry
     MAX-ACCESS  not-accessible
     STATUS      current
     DESCRIPTION
        "A list of DPP-IP interface entries.  The number of entries is
         given by the value of dppipNumber.  The following objects
         need to be written simultaneously, i.e. as a single write
         operation, while dppipAdminStatus is `up': dppipTxSlots,
         dppipMtu, dppipTxFecMode, dppipTxFecRows, dppipTxFecCols "
     ::= { dppipGroup 3 }

dppipEntry OBJECT-TYPE
     SYNTAX      DppipEntry
     MAX-ACCESS  not-accessible
     STATUS      current
     DESCRIPTION
        "A DPP-IP interface entry containing objects at the subnetwork
         layer and below for a particular interface."
     INDEX { dppipIndex }
     ::= { dppipTable 1 }

DppipEntry ::= SEQUENCE {
    dppipIndex              Unsigned32,
    dppipName               SnmpAdminString,
    dppipAddress            IpAddress,
    dppipNetMask            IpAddress,
    dppipDefaultGateway     IpAddress,
    dppipPeerAddress        IpAddress,
    dppipTxSlots            Unsigned32,
    dppipTxUsedCapacity     Gauge32,
    dppipRxSlots            Gauge32,
    dppipRxUsedCapacity     Gauge32,
    dppipDelayVariation     Unsigned32,
    dppipOperStatus         INTEGER,
    dppipFailure            SnmpAdminString,
    dppipReceivedFrames     Counter64,
    dppipMissingFrames      Counter64,
    dppipDeliveredFrames    Counter64,
    dppipDroppedFrames      Counter64,
    dppipDuplicateFrames    Counter64,
    dppipReorderedFrames    Counter64,
    dppipLostFrames         Counter64,
    dppipRecoveredFrames    Counter64,
    dppipSentFrames           Counter64,
    dppipDelayVarPtp        Unsigned32,
    dppipDelayVar999        Unsigned32,
    dppipAdminStatus        INTEGER,
    dppipVlan               Integer32,
    dppipDelayVar01         Unsigned32,
    dppipPrio               Unsigned32,
    dppipPhysIf             RowPointer,
    dppipMtu                Unsigned32,
    dppipTtl                Unsigned32,
    dppipDscp               Unsigned32,
    dppipRxSlotsPerFrame    Unsigned32,
    dppipAvailTxSlots       Gauge32,
    dppipAvailRxSlots       Gauge32,
    dppipMinUsageRatio      Unsigned32,
    dppipTxTranspSlots      Gauge32,
    dppipRxTranspSlots      Gauge32,
    dppipNomDTDelay         Unsigned32,
    dppipTxFecMode          FecMode,
    dppipTxFecRows          Unsigned32,
    dppipTxFecCols          Unsigned32,
    dppipRxFecMode          FecMode,
    dppipRxFecRows          Unsigned32,
    dppipRxFecCols          Unsigned32,
    dppipCntControl         Integer32,
    dppipSuppressAlarms     TruthValue,
    dppipSigFailFilter      Unsigned32,
    dppipDegThreshold       Unsigned32,
    dppipDegPeriod          Unsigned32,
    dppipTolJitter          Unsigned32 }

dppipIndex OBJECT-TYPE
    SYNTAX      Unsigned32
    MAX-ACCESS  not-accessible
    STATUS      current
    DESCRIPTION
        "A value greater than zero that is unique for each DPP-IP
         interface. The value for each DPP-IP interface must remain
         constant at least from one re-initialization of the entity's
         network management system to the next re-initialization."
    ::= { dppipEntry 1 }

dppipName OBJECT-TYPE
    SYNTAX      SnmpAdminString
    MAX-ACCESS  read-only
    STATUS      current
    DESCRIPTION
        "The textual name of the interface. The value of this object
         should be the name of the DPP-IP interface as assigned by the
         local device."
    ::= { dppipEntry 2 }

dppipAddress OBJECT-TYPE
    SYNTAX      IpAddress
    MAX-ACCESS  read-write
    STATUS      current
    DESCRIPTION
        "The IPv4 address of the DPP-IP interface."
    ::= { dppipEntry 3 }

dppipNetMask OBJECT-TYPE
    SYNTAX      IpAddress
    MAX-ACCESS  read-write
    STATUS      current
    DESCRIPTION
        "The subnet mask associated with the IP address of DPP-IP
         interface.  The value of the mask is an IP address with all
         the network bits set to 1 and all the hosts bits set to 0."
    ::= { dppipEntry 4 }

dppipDefaultGateway OBJECT-TYPE
    SYNTAX      IpAddress
    MAX-ACCESS  read-write
    STATUS      current
    DESCRIPTION
        "The IPv4 address of the default gateway. Packets addressed to
         a destination outside the subnet of the DPP-IP interface are
         by default routed to this gateway. "
    ::= { dppipEntry 5 }

dppipPeerAddress OBJECT-TYPE
    SYNTAX      IpAddress
    MAX-ACCESS  read-write
    STATUS      current
    DESCRIPTION
        "The IPv4 address of the peer DPP-IP interface at the remote
         end of the DTM trunk."
    ::= { dppipEntry 6 }

dppipTxSlots OBJECT-TYPE
    SYNTAX      Unsigned32
    MAX-ACCESS  read-write
    STATUS      current
    DESCRIPTION
        "The DPP-IP interface's current transmit side capacity in
         slots per DTM frame."
    ::= { dppipEntry 7 }

dppipTxUsedCapacity OBJECT-TYPE
    SYNTAX      Gauge32
    MAX-ACCESS  read-only
    STATUS      current
    DESCRIPTION
        "An estimate of the transmit side physical layer capacity used
         by the DPP-IP interface in bits per second. It represents a
         minimum required capacity along the network path."
    ::= { dppipEntry 8 }

dppipRxSlots OBJECT-TYPE
    SYNTAX      Gauge32
    MAX-ACCESS  read-only
    STATUS      current
    DESCRIPTION
        "The DPP-IP interface's current receive side
         capacity in slots per DTM frame."
    ::= { dppipEntry 9 }

dppipRxUsedCapacity OBJECT-TYPE
    SYNTAX      Gauge32
    MAX-ACCESS  read-only
    STATUS      current
    DESCRIPTION
        "An estimate of the receive side physical layer capacity used
         by the DPP-IP interface in bits per second. It represents a
         minimum required capacity along the network path."
    ::= { dppipEntry 10 }

dppipDelayVariation OBJECT-TYPE
    SYNTAX      Unsigned32
    MAX-ACCESS  read-only
    STATUS      current
    DESCRIPTION
        "The RMS (i.e. standard deviation) value of the DPP-IP path
         delay variation in ns. This value represents a momentary
         snapshot of the delay variation."
    ::= { dppipEntry 11 }

dppipOperStatus OBJECT-TYPE
    SYNTAX      INTEGER {
                    up(1),       -- ready to pass data
                    down(2),
                    testing(3),   -- in some test mode
                    unknown(4),
                    dormant(5),
                    notPresent(6),
                    lowerLayerDown(7)
                }
    MAX-ACCESS  read-only
    STATUS      current
    DESCRIPTION
        "The current operational state of the interface.  The
         testing(3) state indicates that no operational frames can be
         passed."
    ::= { dppipEntry 12 }

dppipFailure OBJECT-TYPE
    SYNTAX      SnmpAdminString
    MAX-ACCESS  read-only
    STATUS      current
    DESCRIPTION
        "A textual string describing a fault status on the DPP-IP
         interface. The object presents an empty string if there are
         no faults on the interface."
    ::= { dppipEntry 13 }

dppipReceivedFrames OBJECT-TYPE
    SYNTAX      Counter64
    MAX-ACCESS  read-only
    STATUS      current
    DESCRIPTION
        "The total number of DPP-IP frames that have been received."
    ::= { dppipEntry 14 }

dppipMissingFrames OBJECT-TYPE
    SYNTAX      Counter64
    MAX-ACCESS  read-only
    STATUS      current
    DESCRIPTION
        "The number of DPP-IP frames that were missing in the frame
         sequence, i.e. the expected sequence numbers were not found
         in the DPP-IP framing buffer."
    ::= { dppipEntry 15 }

dppipDeliveredFrames OBJECT-TYPE
    SYNTAX      Counter64
    MAX-ACCESS  read-only
    STATUS      current
    DESCRIPTION
        "The total number of DPP-IP data frames that have been
         delivered to the DTM interface."
    ::= { dppipEntry 16 }

dppipDroppedFrames OBJECT-TYPE
    SYNTAX      Counter64
    MAX-ACCESS  read-only
    STATUS      current
    DESCRIPTION
        "The number of DPP-IP frames that have been received and have
         not been processed since the interface was unable to align
         them to the DPP-IP frame sequence."
    ::= { dppipEntry 17 }

dppipDuplicateFrames OBJECT-TYPE
    SYNTAX      Counter64
    MAX-ACCESS  read-only
    STATUS      current
    DESCRIPTION
        "The number of DPP-IP frames that were received with a
         sequence number of an already processed DPP-IP frame."
    ::= { dppipEntry 18 }

dppipReorderedFrames OBJECT-TYPE
    SYNTAX      Counter64
    MAX-ACCESS  read-only
    STATUS      current
    DESCRIPTION
        "The number of DPP-IP frames that were received out
         of order, but could still be aligned to the DPP-IP
         frame sequence."
    ::= { dppipEntry 19 }

dppipLostFrames OBJECT-TYPE
    SYNTAX      Counter64
    MAX-ACCESS  read-only
    STATUS      current
    DESCRIPTION
        "The number of missing DPP-IP data frames that could not be
         delivered to the DTM interface."
    ::= { dppipEntry 20 }

dppipRecoveredFrames OBJECT-TYPE
    SYNTAX      Counter64
    MAX-ACCESS  read-only
    STATUS      current
    DESCRIPTION
        "The number of missing DPP-IP data frames that were recovered
         by the FEC procedure."
    ::= { dppipEntry 21 }

dppipSentFrames OBJECT-TYPE
    SYNTAX      Counter64
    MAX-ACCESS  read-only
    STATUS      current
    DESCRIPTION
        "The total number of DPP-IP frames that have been sent."
    ::= { dppipEntry 22 }

dppipDelayVarPtp OBJECT-TYPE
    SYNTAX      Unsigned32
    MAX-ACCESS  read-only
    STATUS      current
    DESCRIPTION
        "The point-to-point value of the DPP-IP path delay variation
         in nanoseconds. The special value 0 means that the
         measurement is incomplete"
    ::= { dppipEntry 23 }

dppipDelayVar999 OBJECT-TYPE
    SYNTAX      Unsigned32
    MAX-ACCESS  read-only
    STATUS      current
    DESCRIPTION
        "The 99.9 percentile value of the DPP-IP path delay variation
         given in nanoseconds. The special value 0 means that the
         measurement is incomplete."
    ::= { dppipEntry 24 }

dppipAdminStatus OBJECT-TYPE
    SYNTAX  INTEGER {
                up(1),       -- supposed to pass data
                down(2)
            }
    MAX-ACCESS  read-write
    STATUS      current
    DESCRIPTION
        "The desired state of the interface."
    ::= { dppipEntry 25 }

dppipVlan OBJECT-TYPE
    SYNTAX      Integer32(-1..4095)
    MAX-ACCESS  read-write
    STATUS      current
    DESCRIPTION
        "The VLAN identity associated to the DPP-IP interface.  The
         value 0 indicates that the DPP-IP interface does not belong
         to a VLAN. The value -1 indicates that Ethernet frames from
         the DPP-IP interface are not tagged. "
    ::= { dppipEntry 26 }

dppipDelayVar01 OBJECT-TYPE
    SYNTAX      Unsigned32
    MAX-ACCESS  read-only
    STATUS      current
    DESCRIPTION
        "The 0.1 percentile value of the DPP-IP path delay variation
         given in nanoseconds. The special value 0 means that the
         measurement is incomplete."
    ::= { dppipEntry 27 }

dppipPrio OBJECT-TYPE
    SYNTAX      Unsigned32(0..7)
    MAX-ACCESS  read-write
    STATUS      current
    DESCRIPTION
         "The Ethernet priority for frames sent from the DPP-IP
          interface.  Ignored if frames are untagged (i.e. dppipVlan
          is -1)."
    ::= { dppipEntry 28 }

dppipPhysIf OBJECT-TYPE
    SYNTAX      RowPointer
    MAX-ACCESS  read-only
    STATUS      current
    DESCRIPTION
         "A reference to an object representing the physical interface
          that supports the DPP-IP interface. The special value .0.0
          is used, when no such reference is available."
    ::= { dppipEntry 29 }

dppipMtu OBJECT-TYPE
    SYNTAX      Unsigned32(64..1500)
    MAX-ACCESS  read-write
    STATUS      current
    DESCRIPTION
         "The Maximum Transmission Unit of the DPP-IP interface,
          i.e. the maximum size of the DPP-IP payload, including IP
          header, UDP header and DPP-IP header."
    ::= { dppipEntry 30 }

dppipTtl OBJECT-TYPE
    SYNTAX      Unsigned32(0..127)
    MAX-ACCESS  read-write
    STATUS      current
    DESCRIPTION
         "The Time To Live of frames sent at the DPP-IP interface.
          This value is set in the IP header."
    ::= { dppipEntry 31 }

dppipDscp OBJECT-TYPE
    SYNTAX      Unsigned32(0..63)
    MAX-ACCESS  read-write
    STATUS      current
    DESCRIPTION
        "The Differential Services Coding Point of frames sent at the
         DPP-IP interface.  This value is set in the IP header."
    ::= { dppipEntry 32 }

dppipRxSlotsPerFrame OBJECT-TYPE
    SYNTAX      Unsigned32
    MAX-ACCESS  read-only
    STATUS      current
    DESCRIPTION
         "Number of DTM slots per received DPP-IP data frame."
    ::= { dppipEntry 33 }

dppipAvailTxSlots OBJECT-TYPE
    SYNTAX      Gauge32
    MAX-ACCESS  read-only
    STATUS      current
    DESCRIPTION
         "The maximum transmit slot rate (slots/frame) that can be
          allocated at the DTM switch."
    ::= { dppipEntry 34 }

dppipAvailRxSlots OBJECT-TYPE
    SYNTAX      Gauge32
    MAX-ACCESS  read-only
    STATUS      current
    DESCRIPTION
         "The maximum receive slot rate (slots/frame) that can be
          allocated at the DTM switch."
    ::= { dppipEntry 35 }

dppipMinUsageRatio OBJECT-TYPE
    SYNTAX      Unsigned32
    MAX-ACCESS  read-write
    STATUS      current
    DESCRIPTION
         "The minimum allowed usage ratio (used slots/configured
          slots) in per-mille, when dynamic trunk functionality is
          used.  1000 is default and indicates that the Dynamic Trunk
          function is disabled.

          Requires Dynamic Trunk function support equal to 1.1 or
          higher."
    ::= { dppipEntry 36 }

dppipTxTranspSlots OBJECT-TYPE
    SYNTAX      Gauge32
    MAX-ACCESS  read-only
    STATUS      current
    DESCRIPTION
         "The DPP-IP interface's current transmit side capacity in
          slots per DTM frame that is actually transported over
          the. When Dynamic Trunk functionality is disabled this is
          equal to dppipTxSlots. When Dynamic Trunk functionality is
          enabled this is less or equal to dppipTxSlots, since slots
          that are not used by any channel need not be transported.

          Requires Dynamic Trunk function support equal to 1.1 or
          higher."
    ::= { dppipEntry 37 }

dppipRxTranspSlots OBJECT-TYPE
    SYNTAX      Gauge32
    MAX-ACCESS  read-only
    STATUS      current
    DESCRIPTION
         "The DPP-IP interface's current receive side capacity in
          slots per DTM frame that is actually transported. When
          Dynamic Trunk functionality is disabled this is equal to
          dppipRxSlots. When Dynamic Trunk functionality is enabled
          this is less or equal to dppipRxSlots, since slots that are
          not used by any channel need not be transported.

          Requires Dynamic Trunk function support equal to 1.1 or
          higher."
    ::= { dppipEntry 38 }

dppipNomDTDelay OBJECT-TYPE
    SYNTAX      Unsigned32
    MAX-ACCESS  read-only
    STATUS      current
    DESCRIPTION
         "The nominal extra delay in ns when the Dynamic Trunk
          function is enabled.

          Requires Dynamic Trunk function support equal to 1.1 or
          higher."
    ::= { dppipEntry 39 }

 dppipTxFecMode OBJECT-TYPE
    SYNTAX      FecMode
    MAX-ACCESS  read-write
    STATUS      current
    DESCRIPTION
        "The DPP-IP interface's current mode of operation of the
         transmit side Forward Error Correction function (FEC). The
         FEC function may be not used (fecNone), used for column
         correction (fec1D) or used for both row and column correction
         (fec2D)."
    ::= { dppipEntry 40 }

dppipTxFecRows  OBJECT-TYPE
    SYNTAX      Unsigned32
    MAX-ACCESS  read-write
    STATUS      current
    DESCRIPTION
        "The DPP-IP interface's current number of data rows in the
         transmit side Forward Error Correction (FEC) matrix. This
         object is not applicable when dppipTxFecMode is fecNone."
    ::= { dppipEntry 41 }

dppipTxFecCols OBJECT-TYPE
    SYNTAX      Unsigned32
    MAX-ACCESS  read-write
    STATUS      current
    DESCRIPTION
        "The DPP-IP interface's current number of data columns in the
         transmit side Forward Error Correction (FEC) matrix. This
         object is not applicable when dppipTxFecMode is fecNone."
    ::= { dppipEntry 42 }

dppipRxFecMode OBJECT-TYPE
    SYNTAX     FecMode
    MAX-ACCESS read-only
    STATUS     current
    DESCRIPTION
        "The DPP-IP interface's current mode of operation of the
         receive side Forward Error Correction function (FEC). The FEC
         function may be not used (fecNone), used for column
         correction (fec1D) or used for both row and column correction
         (fec2D)."
    ::= { dppipEntry 43 }

dppipRxFecRows OBJECT-TYPE
    SYNTAX     Unsigned32
    MAX-ACCESS read-only
    STATUS     current
    DESCRIPTION
        "The DPP-IP interface's current number of data rows in the
         receive side Forward Error Correction (FEC) matrix. This
         object is not applicable when dppipRxFecMode is fecNone."
    ::= { dppipEntry 44 }

dppipRxFecCols OBJECT-TYPE
    SYNTAX     Unsigned32
    MAX-ACCESS read-only
    STATUS     current
    DESCRIPTION
        "The DPP-IP interface's current number of data columns in the
         receive side Forward Error Correction (FEC) matrix. This
         object is not applicable when dppipRxFecMode is fecNone."
    ::= { dppipEntry 45 }

dppipCntControl OBJECT-TYPE
    SYNTAX     INTEGER {
                         reset(1)     -- reset statistics counters
               }
    MAX-ACCESS read-write
    STATUS     current
    DESCRIPTION
        "Controls the statistics counter monitoring. The statistics
         monitoring is restarted and all counters set to 0, by writing
         `reset' to this object."
    ::= { dppipEntry 46 }

dppipSuppressAlarms OBJECT-TYPE
    SYNTAX     TruthValue
    MAX-ACCESS read-write
    STATUS     current
    DESCRIPTION
        "Suppression control for alarms from the DPP-IP interface.
         When set to `true', all alarms are suppressed."
    ::= { dppipEntry 47 }

dppipSigFailFilter OBJECT-TYPE
    SYNTAX  Unsigned32(0..2000)
    MAX-ACCESS read-write
    STATUS     current
    DESCRIPTION
        "Signal fail filter hold-off time in milliseconds. Trail
         Signal Fail conditions must be persistent during the hold-off
         time, before operStatus is changed from `up' to `down'."
    ::= { dppipEntry 48 }

dppipDegThreshold OBJECT-TYPE
    SYNTAX  Unsigned32(1..8000)
    MAX-ACCESS read-write
    STATUS     current
    DESCRIPTION
        "The detection threshold for DEG alarm. A bad second is
         declared when the number of errored blocks is equal to or
         greater than the threshold, otherwise a good second is
         declared.  Default is 1200"
    ::= { dppipEntry 49 }

dppipDegPeriod OBJECT-TYPE
    SYNTAX  Unsigned32(2..10)
    MAX-ACCESS read-write
    STATUS     current
    DESCRIPTION
        "The persistence time for detection of DEG alarm as the number
         of consecutive seconds with changed status (bad or good)
         before the alarm is set or cleared."
    ::= { dppipEntry 50 }

dppipTolJitter OBJECT-TYPE
    SYNTAX     Unsigned32
    MAX-ACCESS read-write
    STATUS     current
    DESCRIPTION
        "The tolerated jitter and wander of the DPP-IP interface given
         in microseconds."
    ::= { dppipEntry 51 }

-- End of DPP-IP table


-- The DPP-IP limits table

-- The DPP-IP limits table contains information on the system's
-- DPP-IP interfaces.  The table contains limits that may
-- change due to configuration changes during the uptime of the interface.

dppipLimitsTable OBJECT-TYPE
    SYNTAX     SEQUENCE OF DppipLimitsEntry
    MAX-ACCESS not-accessible
    STATUS     current
    DESCRIPTION
        "A list of DPP-IP interface limits entries.  The number of
         entries is given by the value of dppipNumber."
    ::= { dppipGroup 4 }

dppipLimitsEntry OBJECT-TYPE
    SYNTAX     DppipLimitsEntry
    MAX-ACCESS not-accessible
    STATUS     current
    DESCRIPTION
        "A DPP-IP interface limits entry containing limits for a
         particular interface."
    INDEX { dppipIndex }
    ::= { dppipLimitsTable 1 }

DppipLimitsEntry ::= SEQUENCE {
    dppipMaxFecMode               FecMode,
    dppipMaxFecRows               Unsigned32,
    dppipMinFecRows               Unsigned32,
    dppipMaxFecCols               Unsigned32,
    dppipMinFecCols               Unsigned32,
    dppipMaxFecElems              Unsigned32,
    dppipMaxTxSlots               Unsigned32,
    dppipMinTxSlots               Unsigned32,
    dppipMaxTolJitter             Unsigned32,
    dppipMinTolJitter             Unsigned32,
    dppipDTSupport                DppipSupport,
    dppipTTSupport                DppipSupport }

dppipMaxFecMode OBJECT-TYPE
    SYNTAX     FecMode
    MAX-ACCESS read-only
    STATUS     current
    DESCRIPTION
        "The DPP-IP interface's maximum mode of operation of the
         Forward Error Correction function (FEC).  The FEC function
         may be not used (fecNone), used for column correction (fec1D)
         or used for both row and column correction (fec2D)."
    ::= { dppipLimitsEntry 1 }

dppipMaxFecRows OBJECT-TYPE
    SYNTAX     Unsigned32
    MAX-ACCESS read-only
    STATUS     current
    DESCRIPTION
        "The DPP-IP interface's maximum number of data rows in the
         transmit side Forward Error Correction (FEC) matrix."
    ::= { dppipLimitsEntry 2 }

dppipMinFecRows OBJECT-TYPE
    SYNTAX     Unsigned32
    MAX-ACCESS read-only
    STATUS     current
    DESCRIPTION
        "The DPP-IP interface's minimum number of data rows in the
         transmit side Forward Error Correction (FEC) matrix."
    ::= { dppipLimitsEntry 3 }

dppipMaxFecCols OBJECT-TYPE
    SYNTAX     Unsigned32
    MAX-ACCESS read-only
    STATUS     current
    DESCRIPTION
        "The DPP-IP interface's maximum number of data columns in the
         transmit side Forward Error Correction (FEC) matrix."
    ::= { dppipLimitsEntry 4 }

dppipMinFecCols OBJECT-TYPE
    SYNTAX     Unsigned32
    MAX-ACCESS read-only
    STATUS     current
    DESCRIPTION
        "The DPP-IP interface's minimum number of data columns in the
         transmit side Forward Error Correction (FEC) matrix."
    ::= { dppipLimitsEntry 5 }

dppipMaxFecElems OBJECT-TYPE
    SYNTAX     Unsigned32
    MAX-ACCESS read-only
    STATUS     current
    DESCRIPTION
        "The DPP-IP interface's maximum number of data elements in the
         transmit side Forward Error Correction (FEC) matrix."
    ::= { dppipLimitsEntry 6 }

dppipMaxTxSlots OBJECT-TYPE
    SYNTAX     Unsigned32
    MAX-ACCESS read-only
    STATUS     current
    DESCRIPTION
        "The maximum number of slots per DTM frame that can be
         allocated at the DPP-IP transmit interface."
    ::= { dppipLimitsEntry 7 }

dppipMinTxSlots OBJECT-TYPE
    SYNTAX     Unsigned32
    MAX-ACCESS read-only
    STATUS     current
    DESCRIPTION
        "The minimum number of slots per DTM frame that can be
         allocated at the DPP-IP transmit interface."
    ::= { dppipLimitsEntry 8 }

dppipMaxTolJitter OBJECT-TYPE
    SYNTAX     Unsigned32
    MAX-ACCESS read-only
    STATUS     current
    DESCRIPTION
        "The maximum tolerated jitter that can be configured expressed
         in units of DPP-IP inter-frame intervals.

         The DPP-IP inter-frame interval in microseconds is:
         dppipRxSlotsPerFrame * 125 / dppipRxSlots."
    ::= { dppipLimitsEntry 9 }

dppipMinTolJitter OBJECT-TYPE
    SYNTAX     Unsigned32
    MAX-ACCESS read-only
    STATUS     current
    DESCRIPTION
        "The minimum tolerated jitter that can be configured expressed
         in units of DPP-IP inter-frame intervals.

         The DPP-IP inter-frame interval in microseconds is:
         dppipRxSlotsPerFrame * 125 / dppipRxSlots."
    ::= { dppipLimitsEntry 10 }

dppipDTSupport OBJECT-TYPE
    SYNTAX     DppipSupport
    MAX-ACCESS read-only
    STATUS     current
    DESCRIPTION
        "The local interface's maximum level of support for the
         Dynamic Trunk function."
    ::= { dppipLimitsEntry 11 }

dppipTTSupport OBJECT-TYPE
    SYNTAX     DppipSupport
    MAX-ACCESS read-only
    STATUS     current
    DESCRIPTION
        "The local interface's maximum level of support for the Time
         Transfer function."
    ::= { dppipLimitsEntry 12 }

  -- End of DPP-IP limits table

  -- The DPP-IP peer limits table

  -- The DPP-IP limits table contains information on the system's
  -- DPP-IP interfaces.  The table contains limits that will not
  -- change during the uptime of the peer interface.

dppipPeerLimitsTable OBJECT-TYPE
    SYNTAX     SEQUENCE OF DppipPeerLimitsEntry
    MAX-ACCESS not-accessible
    STATUS     current
    DESCRIPTION
        "A list of DPP-IP interface limits entries.  The number of
         entries is given by the value of dppipNumber."
    ::= { dppipGroup 5 }

dppipPeerLimitsEntry OBJECT-TYPE
    SYNTAX     DppipPeerLimitsEntry
    MAX-ACCESS not-accessible
    STATUS     current
    DESCRIPTION
        "A DPP-IP interface peer limits entry containing limits for the peer
         of a particular interface."
    INDEX { dppipIndex }
    ::= { dppipPeerLimitsTable 1 }

DppipPeerLimitsEntry ::= SEQUENCE {
    dppipPeerMaxFecMode               FecMode,
    dppipPeerMaxFecRows               Unsigned32,
    dppipPeerMinFecRows               Unsigned32,
    dppipPeerMaxFecCols               Unsigned32,
    dppipPeerMinFecCols               Unsigned32,
    dppipPeerMaxFecElems              Unsigned32,
    dppipPeerMaxRxSlots               Unsigned32,
    dppipPeerMinRxSlots               Unsigned32,
    dppipPeerDTSupport                DppipSupport,
    dppipPeerTTSupport                DppipSupport }

dppipPeerMaxFecMode OBJECT-TYPE
    SYNTAX     FecMode
    MAX-ACCESS read-only
    STATUS     current
    DESCRIPTION
        "The peer interface's maximum mode of operation of the Forward
         Error Correction function (FEC).

         The FEC function may be not used (fecNone), used for column
         correction (fec1D) or used for both row and column correction
         (fec2D)."
    ::= { dppipPeerLimitsEntry 1 }

dppipPeerMaxFecRows OBJECT-TYPE
    SYNTAX     Unsigned32
    MAX-ACCESS read-only
    STATUS     current
    DESCRIPTION
        "The peer interface's maximum number of data rows in the
         receive side Forward Error Correction (FEC) matrix."
    ::= { dppipPeerLimitsEntry 2 }

dppipPeerMinFecRows OBJECT-TYPE
    SYNTAX     Unsigned32
    MAX-ACCESS read-only
    STATUS     current
    DESCRIPTION
        "The peer interface's minimum number of data rows in the
         receive side Forward Error Correction (FEC) matrix."
     ::= { dppipPeerLimitsEntry 3 }

dppipPeerMaxFecCols OBJECT-TYPE
    SYNTAX  Unsigned32
    MAX-ACCESS read-only
    STATUS     current
    DESCRIPTION
        "The peer interface's maximum number of data columns in the
         receive side Forward Error Correction (FEC) matrix."
    ::= { dppipPeerLimitsEntry 4 }

dppipPeerMinFecCols OBJECT-TYPE
    SYNTAX     Unsigned32
    MAX-ACCESS read-only
    STATUS     current
    DESCRIPTION
        "The peer interface's minimum number of data columns in the
         receive side Forward Error Correction (FEC) matrix."
    ::= { dppipPeerLimitsEntry 5 }

dppipPeerMaxFecElems OBJECT-TYPE
    SYNTAX     Unsigned32
    MAX-ACCESS read-only
    STATUS     current
    DESCRIPTION
        "The peer interface's maximum number of data elements in the
         receive side Forward Error Correction (FEC) matrix."
     ::= { dppipPeerLimitsEntry 6 }

dppipPeerMaxRxSlots OBJECT-TYPE
    SYNTAX     Unsigned32
    MAX-ACCESS read-only
    STATUS     current
    DESCRIPTION
        "The maximum number of slots per DTM frame that can be
         allocated at the receive interface in the peer."
    ::= { dppipPeerLimitsEntry 7 }

dppipPeerMinRxSlots OBJECT-TYPE
    SYNTAX     Unsigned32
    MAX-ACCESS read-only
    STATUS     current
    DESCRIPTION
        "The minimum number of slots per DTM frame that can be
        allocated at the DPP-IP receive interface of the peer."
    ::= { dppipPeerLimitsEntry 8 }

dppipPeerDTSupport OBJECT-TYPE
    SYNTAX     DppipSupport
    MAX-ACCESS read-only
    STATUS     current
    DESCRIPTION
        "The peer interface's maximum level of support for the Dynamic
         Trunk function."
    ::= { dppipPeerLimitsEntry 9 }

dppipPeerTTSupport OBJECT-TYPE
    SYNTAX     DppipSupport
    MAX-ACCESS read-only
    STATUS     current
    DESCRIPTION
        "The peer interface's maximum level of support for the Time
         Transfer function."
    ::= { dppipPeerLimitsEntry 10 }

-- End of DPP-IP peer limits table

END
