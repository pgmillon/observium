-- =============================================================================
-- Copyright (c) 2004-2010 Hangzhou H3C Tech. Co., Ltd. All rights reserved.
--
-- Description: 802.1ah MAC-in-MAC MIB
-- Reference:
-- Version: V1.0
-- History:
--   V1.0 2009-08-08 Initial version Created by Jianyong Song
--        2010-08-05 Add 'h3cMinmBmac' by Wei Zhang
-- =============================================================================
A3COM-HUAWEI-MINM-MIB DEFINITIONS ::= BEGIN
IMPORTS
        RowStatus,
        TEXTUAL-CONVENTION,
        MacAddress
    FROM SNMPv2-TC
        MODULE-IDENTITY,
        OBJECT-TYPE,
        Integer32,
        Unsigned32
    FROM SNMPv2-SMI
        ifIndex
    FROM RFC1213-MIB
        h3cCommon
    FROM A3COM-HUAWEI-OID-MIB
        h3cVsiIndex
    FROM A3COM-HUAWEI-VSI-MIB;

-- =============================================================================
-- module identity part
-- =============================================================================
h3cMinm MODULE-IDENTITY
    LAST-UPDATED
        "200908081000Z"        -- Aug 08, 2009 at 10:00 GMT
    ORGANIZATION
        "Hangzhou H3C Tech. Co., Ltd."
    CONTACT-INFO
        "Platform Team Hangzhou H3C Tech. Co., Ltd.
         Hai-Dian District Beijing P.R. China
         http://www.h3c.com
         Zip:100085"
    DESCRIPTION
        "802.1ah MAC-in-MAC MIB"
    REVISION
        "200908081000Z"   -- Aug 08, 2009 at 10:00 GMT
    DESCRIPTION
        "The initial version of this MIB."
    ::= { h3cCommon 107 }

-- =============================================================================
-- Textual Conventions
-- =============================================================================
H3cMinmEnabledStatus ::= TEXTUAL-CONVENTION
    STATUS      current
    DESCRIPTION
        "A enumerated value which indicates the state of object."
    SYNTAX  INTEGER
    {
        enabled(1),
        disabled(2)
    }

-- =============================================================================
-- object definition begin
-- =============================================================================

h3cMinmObjects      OBJECT IDENTIFIER ::= { h3cMinm 1 }

h3cMinmScalarGroup OBJECT IDENTIFIER ::= { h3cMinmObjects 1 }

h3cMinmCapabilities    OBJECT-TYPE
    SYNTAX      BITS
    {
        reEncapsulation(0),
        uplink(1),
        vsiShareConnection(2)
    }
    MAX-ACCESS  read-only
    STATUS      current
    DESCRIPTION
        "This object displays the MAC-in-MAC capabilities with respect to
         certain fields. The following values may be supported:
         reEncapsulation:     Support for configuring re-encapsulation (denoted
                              by h3cMinmVsiReEncapsulation).
         uplink:              Support for configuring uplink (denoted
                              by h3cMinmUplinkTable).
         vsiShareConnection:  It indicates that connection entry is shared in
                              all VSIs. h3cVsiIndex is meaningless and must
                              be value 1 in h3cMinmConnectionTable."
    ::= { h3cMinmScalarGroup 1 }

h3cMinmBmac  OBJECT-TYPE
    SYNTAX      MacAddress
    MAX-ACCESS  read-only
    STATUS      current
    DESCRIPTION
        "A MAC address used in creating the MAC header of I-tagged frames
        transmitted across a Provider Backbone Bridged Network. The invalid
        value FF:FF:FF:FF:FF:FF indicates that this node is not supported by
        the device."
    ::= { h3cMinmScalarGroup 2 }

-- =============================================================================
-- h3cMinmVsiTable Definition
-- =============================================================================
h3cMinmVsiTable  OBJECT-TYPE
    SYNTAX      SEQUENCE OF H3cMinmVsiEntry
    MAX-ACCESS  not-accessible
    STATUS      current
    DESCRIPTION
        "A table for configuring MAC-in-MAC service instance parameter."
    ::= { h3cMinmObjects 2 }

h3cMinmVsiEntry  OBJECT-TYPE
    SYNTAX      H3cMinmVsiEntry
    MAX-ACCESS  not-accessible
    STATUS      current
    DESCRIPTION
        "An entry for configuring MAC-in-MAC service instance parameter."
    INDEX
    {
        h3cVsiIndex
    }
    ::= { h3cMinmVsiTable 1 }

H3cMinmVsiEntry ::=
    SEQUENCE
    {
        h3cMinmVsiBvlan               Integer32,
        h3cMinmVsiReEncapsulation     H3cMinmEnabledStatus,
        h3cMinmVsiNextAvailableLinkId Unsigned32
    }

h3cMinmVsiBvlan    OBJECT-TYPE
    SYNTAX      Integer32 (1..4094 | 65535)
    MAX-ACCESS  read-write
    STATUS      current
    DESCRIPTION
        "BVLAN ID. The value 65535 indicates the BVLAN has not been configured
        for get operation, and it indicates deleting the BVLAN configration
        for set operation."
    ::= { h3cMinmVsiEntry 1 }

h3cMinmVsiReEncapsulation    OBJECT-TYPE
    SYNTAX      H3cMinmEnabledStatus
    MAX-ACCESS  read-write
    STATUS      current
    DESCRIPTION
        "Whether the re-encapsulation is enabled. The reEncapsulation field of
        h3cMinmCapabilities denotes whether this node is supported."
    ::= { h3cMinmVsiEntry 2 }

h3cMinmVsiNextAvailableLinkId    OBJECT-TYPE
    SYNTAX      Unsigned32
    MAX-ACCESS  read-only
    STATUS      current
    DESCRIPTION
        "Next available connection entry index for creating a connection entry.
        Its value ranges from 0x1 to 0xFFFFFFFF.The invalid value 0xFFFFFFFF
        indicates that connection entry can not be created. When the
        vsiShareConnection field of h3cMinmCapabilities is set, this node
        returns an invalid value if the value of h3cVsiIndex is not 1."
    ::= { h3cMinmVsiEntry 3 }

-- =============================================================================
-- End of h3cMinmVsiTable Definition
-- =============================================================================

-- =============================================================================
-- h3cMinmUplinkTable Definition
-- =============================================================================
h3cMinmUplinkTable  OBJECT-TYPE
    SYNTAX      SEQUENCE OF H3cMinmUplinkEntry
    MAX-ACCESS  not-accessible
    STATUS      current
    DESCRIPTION
        "A table for uplink ports of the VSI in MAC-in-MAC. The uplink field of
        h3cMinmCapabilities denotes whether this table is supported."
    ::= { h3cMinmObjects 3 }

h3cMinmUplinkEntry  OBJECT-TYPE
    SYNTAX      H3cMinmUplinkEntry
    MAX-ACCESS  not-accessible
    STATUS      current
    DESCRIPTION
        "An entry for uplink ports of the VSI in MAC-in-MAC."
    INDEX
    {
        h3cVsiIndex,
        ifIndex
    }
    ::= { h3cMinmUplinkTable 1 }

H3cMinmUplinkEntry ::=
    SEQUENCE
    {
        h3cMinmUplinkRowStatus      RowStatus
    }

h3cMinmUplinkRowStatus     OBJECT-TYPE
    SYNTAX      RowStatus
    MAX-ACCESS  read-create
    STATUS      current
    DESCRIPTION
        "Operation status of this table entry."
    ::= { h3cMinmUplinkEntry 1 }
-- =============================================================================
-- End of h3cMinmUplinkTable Definition
-- =============================================================================

-- =============================================================================
-- h3cMinmConnectionTable Definition
-- =============================================================================
h3cMinmConnectionTable  OBJECT-TYPE
    SYNTAX      SEQUENCE OF H3cMinmConnectionEntry
    MAX-ACCESS  not-accessible
    STATUS      current
    DESCRIPTION
        "A table for the connection information of BMAC."
    ::= { h3cMinmObjects 4 }

h3cMinmConnectionEntry  OBJECT-TYPE
    SYNTAX      H3cMinmConnectionEntry
    MAX-ACCESS  not-accessible
    STATUS      current
    DESCRIPTION
        "An entry for the connection information of BMAC.
        When the vsiShareConnection field of h3cMinmCapabilities is set,
        connection entry is shared in all VSIs. h3cVsiIndex is meaningless
        and must be value 1 in h3cMinmConnectionTable."
    INDEX
    {
        h3cVsiIndex,
        h3cMinmConnectionLinkId
    }
    ::= { h3cMinmConnectionTable 1 }

H3cMinmConnectionEntry ::=
    SEQUENCE
    {
        h3cMinmConnectionLinkId       Unsigned32,
        h3cMinmConnectionBmac         MacAddress,
        h3cMinmConnectionBvlan        Integer32,
        h3cMinmConnectionPort         Integer32,
        h3cMinmConnectionStatus       INTEGER,
        h3cMinmConnectionAgingStatus  INTEGER,
        h3cMinmConnectionRowStatus    RowStatus
    }

h3cMinmConnectionLinkId    OBJECT-TYPE
    SYNTAX      Unsigned32
    MAX-ACCESS  not-accessible
    STATUS      current
    DESCRIPTION
        "Entry index when the vsiShareConnection bit of h3cMinmCapabilities
        is set(h3cVsiIndex is meaningless and must be value 1),
        else entry index in the VSI of h3cVsiIndex.Its value ranges
        from 0x1 to 0xFFFFFFFE. It should be obtained from
        h3cMinmVsiNextAvailableLinkId for create operation."
    ::= { h3cMinmConnectionEntry 1 }

h3cMinmConnectionBmac    OBJECT-TYPE
    SYNTAX      MacAddress
    MAX-ACCESS  read-create
    STATUS      current
    DESCRIPTION
        "BMAC of an connection entry."
    ::= { h3cMinmConnectionEntry 2 }

h3cMinmConnectionBvlan    OBJECT-TYPE
    SYNTAX      Integer32 (1..4094)
    MAX-ACCESS  read-create
    STATUS      current
    DESCRIPTION
        "BVLAN of an connection entry."
    ::= { h3cMinmConnectionEntry 3 }

h3cMinmConnectionPort   OBJECT-TYPE
    SYNTAX      Integer32
    MAX-ACCESS  read-create
    STATUS      current
    DESCRIPTION
        "Port ifindex of an connection entry."
    ::= { h3cMinmConnectionEntry 4 }

h3cMinmConnectionStatus   OBJECT-TYPE
    SYNTAX      INTEGER
    {
        learned(1),
        configDynamic(2),
        configStatic(3),
        blackhole(4)
    }
    MAX-ACCESS  read-create
    STATUS      current
    DESCRIPTION
        "State of an connection entry."
    ::= { h3cMinmConnectionEntry 5 }

h3cMinmConnectionAgingStatus   OBJECT-TYPE
    SYNTAX      INTEGER
    {
        aging(1),
        noAged(2)
    }
    MAX-ACCESS  read-only
    STATUS      current
    DESCRIPTION
        "Aging time of an connection entry."
    ::= { h3cMinmConnectionEntry 6 }

h3cMinmConnectionRowStatus  OBJECT-TYPE
    SYNTAX      RowStatus
    MAX-ACCESS  read-create
    STATUS      current
    DESCRIPTION
        "Operation status of this table entry."
    ::= { h3cMinmConnectionEntry 7 }
-- =============================================================================
-- End of h3cMinmConnectionTable Definition
-- =============================================================================

END
