-- ====================================================================
-- Copyright (C) 2005 by HUAWEI 3Com TECHNOLOGIES.  All rights reserved
--
-- Description: DLSW HUAWEI 3Com Specific Features MIB
-- Reference: RFC2024
-- Version: V1.0
-- History:
--  V1.0  2005-07-20, LiuYingquan
--    Initial version
-- ====================================================================
A3COM-HUAWEI-SNA-DLSW-EXT-MIB    DEFINITIONS ::= BEGIN
IMPORTS
    MODULE-IDENTITY,
    OBJECT-TYPE,
    TimeTicks,
    Integer32,
    Counter32
        FROM SNMPv2-SMI
    RowStatus
        FROM SNMPv2-TC
    ifIndex
        FROM RFC1213-MIB
    InetAddress,
    InetAddressType
        FROM INET-ADDRESS-MIB
    dlswTConnConfigEntry,
    dlswTConnOperEntry,
    dlswTConnTcpConfigEntry,
    MacAddressNC,
    LFSize,
    TAddress
        FROM DLSW-MIB

    h3cCommon
        FROM A3COM-HUAWEI-OID-MIB;

h3cDlswExt MODULE-IDENTITY
    LAST-UPDATED "200507201900Z"        -- Jul 20, 2005 at 19:00 GMT
    ORGANIZATION
        "Huawei-3com Technologies co.,Ltd."
    CONTACT-INFO
        "R&D Beijing Huawei-3com Technologies Co., Ltd.
         Oriental Electronic Bld., NO.1, Street 8,
         Shang-Di Information Industry Base,
         Hai-Dian District, Beijing, P.R. China
         Zip:100085
         Http://www.huawei-3com.com
         E-mail:support@huawei-3com.com"

    DESCRIPTION
        "The MIB module for management of HUAWEI-3COM specific Data Link
         Switching protocol enhancements. DLSw is described in
         RFC 1795, RFC 2024 and RFC2166."
    REVISION "200507201900Z"   -- Jul 20, 2005 at 19:00 GMT
    DESCRIPTION
            "Initial version of this MIB module."
    ::= { h3cCommon 62 }

h3cDlswExtMIBObjects OBJECT IDENTIFIER ::= { h3cDlswExt 1 }

h3cdeNode           OBJECT IDENTIFIER ::= { h3cDlswExtMIBObjects 1 }
h3cdeTConn          OBJECT IDENTIFIER ::= { h3cDlswExtMIBObjects 2 }
h3cdeBridge         OBJECT IDENTIFIER ::= { h3cDlswExtMIBObjects 3 }
h3cdeQllc           OBJECT IDENTIFIER ::= { h3cDlswExtMIBObjects 4 }
h3cdeSdlc           OBJECT IDENTIFIER ::= { h3cDlswExtMIBObjects 5 }
h3cdeLlc2           OBJECT IDENTIFIER ::= { h3cDlswExtMIBObjects 6 }
h3cdeReachableCache OBJECT IDENTIFIER ::= { h3cDlswExtMIBObjects 7 }
h3cdeEthernetBackup OBJECT IDENTIFIER ::= { h3cDlswExtMIBObjects 8 }


-- ====================================================================
-- H3C DLSw Extension Node Objects
-- ====================================================================

h3cdeNodeVendorID OBJECT-TYPE
    SYNTAX      OCTET STRING (SIZE (3))
    MAX-ACCESS  read-write
    STATUS      current
    DESCRIPTION
        "The value identifies the manufacturer's IEEE-assigned
        Organizationally Unique Identifier (OUI) of this DLSw.
        This information is reported in DLSw Capabilities
        Exchange."
    REFERENCE
        "DLSW: Switch-to-Switch Protocol RFC 1795."
    ::= { h3cdeNode 1 }

h3cdeNodeIpAddrType OBJECT-TYPE
    SYNTAX      InetAddressType
    MAX-ACCESS  read-write
    STATUS      current
    DESCRIPTION
        "The type of ip address: IPv4 or IPv6."
    ::= { h3cdeNode 2 }

h3cdeNodeLocalAddr OBJECT-TYPE
    SYNTAX      InetAddress
    MAX-ACCESS  read-write
    STATUS      current
    DESCRIPTION
        "Local peer ip address. This ip address must have been
        configured for a port on the router. If no local peer
        ip address is configured, then this object will be the
        empty string."
    DEFVAL     { ''H }    -- the empty string
    ::= { h3cdeNode 3 }

h3cdeNodePriority OBJECT-TYPE
    SYNTAX      Integer32 (1..5 | 65535)
    MAX-ACCESS  read-write
    STATUS      current
    DESCRIPTION
        "Peer priority advertised to remote peers in the DLSw Capabilities
        Exchange. If an end station can reach through more
        than one peer, the priority of each peer will be considered when
        a circuit is established.
        A lower priority indicates that peer will be the
        preferred choice if there are more than one path to the
        destination. A value of 65535 indicates the value is meaningless."
    DEFVAL      { 3 }
    ::= { h3cdeNode 4 }

h3cdeNodeInitPacingWindow OBJECT-TYPE
    SYNTAX      Integer32 (1..2000 | 65535)
    UNITS       "packets"
    MAX-ACCESS  read-write
    STATUS      current
    DESCRIPTION
        "Initial pacing window size. This is the starting size of the
        pacing window. DLSw uses an adaptive pacing flow control
        algorithm that automatically adjusts to congestion levels in
        the network. Pacing windows are used to control how many packets
        may be sent to a peer before acknowlegement.
        A value of 65535 indicates the value is meaningless."
    DEFVAL      { 40 }
    ::= { h3cdeNode 5 }

h3cdeNodeMaxPacingWindow OBJECT-TYPE
    SYNTAX      Integer32 (1..2000 | 65535)
    UNITS       "packets"
    MAX-ACCESS  read-write
    STATUS      current
    DESCRIPTION
        "Maximum pacing window size. This is the largest size that
        the pacing window will grow to. DLSw uses an adaptive pacing
        flow control algorithm that automatically adjusts to congestion
        levels in the network. Pacing windows are used to control
        how many packets may be sent to a peer before acknowlegement."
    DEFVAL      { 50 }
    ::= { h3cdeNode 6 }

h3cdeNodeKeepAliveInterval OBJECT-TYPE
    SYNTAX      Integer32 (0..2000 | 65535)
    UNITS       "seconds"
    MAX-ACCESS  read-write
    STATUS      current
    DESCRIPTION
        "Default remote peer keepalive interval in seconds.
        The keepalive parameter refers to how often DLSw peers
        send peer keep alives to each other. These periodic messages
        allow DLSw to keep track of the state of all peers.
        If set to zero, no keepalives are sent.
        A value of 65535 indicates the value is meaningless."
    DEFVAL      { 30 }
    ::= { h3cdeNode 7 }

h3cdeNodePermitDynamic OBJECT-TYPE
    SYNTAX      INTEGER
                {
                permitDynamic(1),
                forbidDynamic(2),
                unknown(65535)
                }
    MAX-ACCESS  read-write
    STATUS      current
    DESCRIPTION
        "To accept connections from non-configured remote peer when
        permitDynamic is specified."
    DEFVAL      { forbidDynamic }
    ::= { h3cdeNode 8 }

h3cdeNodeConnTimeout OBJECT-TYPE
    SYNTAX      Integer32 (1..65535)
    UNITS       "seconds"
    MAX-ACCESS  read-write
    STATUS      current
    DESCRIPTION
        "Define connected state timer."
    DEFVAL      { 300 }
    ::= { h3cdeNode 9 }

h3cdeNodeLocalPendTimeout OBJECT-TYPE
    SYNTAX      Integer32 (1..65535)
    UNITS       "seconds"
    MAX-ACCESS  read-write
    STATUS      current
    DESCRIPTION
        "Define connected state timer."
    DEFVAL      { 30 }
    ::= { h3cdeNode 10 }

h3cdeNodeRemotePendTimeout OBJECT-TYPE
    SYNTAX      Integer32 (1..65535)
    UNITS       "seconds"
    MAX-ACCESS  read-write
    STATUS      current
    DESCRIPTION
        "Define connected state timer."
    DEFVAL      { 30 }
    ::= { h3cdeNode 11 }

h3cdeNodeSnaCacheTimeout OBJECT-TYPE
    SYNTAX      Integer32 (1..65535)
    UNITS       "seconds"
    MAX-ACCESS  read-write
    STATUS      current
    DESCRIPTION
        "Define connected state timer."
    DEFVAL      { 120 }
    ::= { h3cdeNode 12 }

h3cdeNodeExplorerTimeout OBJECT-TYPE
    SYNTAX      Integer32 (1..65535)
    UNITS       "seconds"
    MAX-ACCESS  read-write
    STATUS      current
    DESCRIPTION
        "Define explorer timer."
    DEFVAL      { 30 }
    ::= { h3cdeNode 13 }

h3cdeNodeExplorerWaitTimeout OBJECT-TYPE
    SYNTAX      Integer32 (1..65535)
    UNITS       "seconds"
    MAX-ACCESS  read-write
    STATUS      current
    DESCRIPTION
        "Define explorer waiting timer."
    DEFVAL      { 30 }
    ::= { h3cdeNode 14 }

h3cdeNodeConfigSapList OBJECT-TYPE
    SYNTAX      OCTET STRING (SIZE (16))
    MAX-ACCESS  read-write
    STATUS      current
    DESCRIPTION
        "The SAP list indicates which SAPs are allowed.
        Only SAPs with even numbers are represented,
        in the form of the most significant bit of the first
        octet representing the SAP 0, the next most significant
        bit representing the SAP 2, to the least significant
        bit of the last octet representing the SAP 254. Data
        link switching is allowed for those SAPs which have
        one in its corresponding bit, not allowed otherwise.
        The whole SAP list has to be changed together. Changing
        the SAP list affects only new circuit establishments
        and has no effect on established circuits.

        This list can be used to restrict specific partners
        from knowing about all the SAPs used by DLSw on all its
        interfaces (these are represented in h3cdeIfSapList for
        each interface). For instance, one may want to run NetBIOS
        with some partners but not others.

        If a node supports sending run-time capabilities exchange
        messages, changes to this object should cause that action.
        When to start the run-time capabilities exchange is
        implementation-specific.

        The DEFVAL below indicates support for SAPs 0, 2, 4, 6, 8, A, C and E."
    DEFVAL      { 'FF000000000000000000000000000000'h }
    ::= { h3cdeNode 15 }

h3cdeNodeMaxTransmission OBJECT-TYPE
    SYNTAX      Integer32 (1..10)
    MAX-ACCESS  read-write
    STATUS      current
    DESCRIPTION
        "The maximum retry times for TCP packet.
        Default value is 5."
    DEFVAL      { 5 }
    ::= { h3cdeNode 16 }

h3cdeNodeMulticastStatus OBJECT-TYPE
    SYNTAX      INTEGER
                {
                enabled(1),
                disabled(2)
                }
    MAX-ACCESS  read-write
    STATUS      current
    DESCRIPTION
        "Multicast support status. It is disabled by default."
    DEFVAL      { disabled }
    ::= { h3cdeNode 17 }

h3cdeNodeMulticastAddress OBJECT-TYPE
    SYNTAX      InetAddress
    MAX-ACCESS  read-write
    STATUS      current
    DESCRIPTION
        "Multicast address. Default is 224.0.10.0.
        When the h3cdeNodeMulticastStatus is disabled,
        the multicast address is reset to 0.0.0.0."
    ::= { h3cdeNode 18 }

h3cdeNodeResetTcpAll OBJECT-TYPE
    SYNTAX      INTEGER
                {
                reset(1)
                }
    MAX-ACCESS  read-write
    STATUS      current
    DESCRIPTION
        "Reset all TCP circuit switch.
        Any return value is meaningless."
    ::= { h3cdeNode 19 }

h3cdeNodeStCapTcpNum OBJECT-TYPE
    SYNTAX      Integer32 (0..255)
    MAX-ACCESS  read-write
    STATUS      current
    DESCRIPTION
        "Tcp number reported in DLSw Capabilities Exchange."
    ::= { h3cdeNode 20 }

h3cdeNodeTcpQueueMax OBJECT-TYPE
    SYNTAX      Integer32
    MAX-ACCESS  read-write
    STATUS      current
    DESCRIPTION
        "The max length of TCP queue."
    DEFVAL      { 200 }
    ::= { h3cdeNode 21 }


-- ====================================================================
-- H3C DLSw Extension Transport Connection Configuration Table
-- ====================================================================
h3cdeTConnConfigTable OBJECT-TYPE
    SYNTAX      SEQUENCE OF H3cdeTConnConfigEntry
    MAX-ACCESS  not-accessible
    STATUS      current
    DESCRIPTION
        "This table defines the peer transport connections
        that will be initiated or accepted by this DLSw.

        This table augments dlswTConnConfigTable."
    ::= { h3cdeTConn 1 }

h3cdeTConnConfigEntry OBJECT-TYPE
    SYNTAX      H3cdeTConnConfigEntry
    MAX-ACCESS  not-accessible
    STATUS      current
    DESCRIPTION
        "A list of objects that define specific configuration for
        a DLSw peer transport connection."
    AUGMENTS    { dlswTConnConfigEntry }
    ::= { h3cdeTConnConfigTable 1 }

H3cdeTConnConfigEntry ::=
    SEQUENCE {
        h3cdeTConnConfigVersion              OCTET STRING,
        h3cdeTConnConfigPriority             Integer32,
        h3cdeTConnConfigLfSize               LFSize,
        h3cdeTConnConfigKeepaliveIntval    Integer32,
        h3cdeTConnConfigBackup               INTEGER,
        h3cdeTConnConfigBackupTAddr          TAddress,
        h3cdeTConnConfigBackupLinger         Integer32
    }

h3cdeTConnConfigVersion OBJECT-TYPE
    SYNTAX      OCTET STRING (SIZE (2))
    MAX-ACCESS  read-create
    STATUS      current
    DESCRIPTION
        "This value identifies which version (first octet) and release
        (second octet) of the DLSw standard is supported by this
        partner DLSw. This information is obtained from a DLSw
        Capabilities Exchange message received from the partner DLSw.
        A string of zero length is returned before a Capabilities
        Exchange message is received, or if one is never received.
        A conceptual row with a h3cdeTConnOperState of 'connected' but
        a zero length partner version indicates that the partner is
        a non-standard DLSw partner.

        If an implementation chooses to keep h3cdeTConnOperEntrys in
        the 'disconnected' state, this value should remain unchanged."
    ::= { h3cdeTConnConfigEntry 1 }

h3cdeTConnConfigPriority OBJECT-TYPE
    SYNTAX      Integer32 (1..5)
    MAX-ACCESS  read-create
    STATUS      current
    DESCRIPTION
        "The priority for remote peer."
    DEFVAL      { 3 }
    ::= { h3cdeTConnConfigEntry 2 }

h3cdeTConnConfigLfSize OBJECT-TYPE
    SYNTAX      LFSize
    MAX-ACCESS  read-create
    STATUS      current
    DESCRIPTION
        "The largest frame size."
    ::= { h3cdeTConnConfigEntry 3 }

h3cdeTConnConfigKeepaliveIntval OBJECT-TYPE
    SYNTAX      Integer32 (1..1200)
    UNITS       "seconds"
    MAX-ACCESS  read-create
    STATUS      current
    DESCRIPTION
        "The keepalive interval value."
    DEFVAL      { 30 }
    ::= { h3cdeTConnConfigEntry 4 }

h3cdeTConnConfigBackup OBJECT-TYPE
    SYNTAX      INTEGER
                {
                yes(1),
                no(2)
                }
    MAX-ACCESS  read-create
    STATUS      current
    DESCRIPTION
        "The current remote peer is configured as the
        backup of another configured remote peer."
    DEFVAL      { no }
    ::= { h3cdeTConnConfigEntry 5 }

h3cdeTConnConfigBackupTAddr OBJECT-TYPE
    SYNTAX      TAddress
    MAX-ACCESS  read-create
    STATUS      current
    DESCRIPTION
        "It is the ip address of a configured remote peer of which
        the current remote peer is configrued as backup."
    ::= { h3cdeTConnConfigEntry 6 }

h3cdeTConnConfigBackupLinger OBJECT-TYPE
    SYNTAX      Integer32 (0..1440)
    UNITS       "minutes"
    MAX-ACCESS  read-create
    STATUS      current
    DESCRIPTION
        "Backup peer linger."
    DEFVAL      { 5 }
    ::= { h3cdeTConnConfigEntry 7 }

-- ====================================================================
-- H3C DLSw Extension Transport Connection Operation Table
-- ====================================================================
h3cdeTConnOperTable OBJECT-TYPE
    SYNTAX      SEQUENCE OF H3cdeTConnOperEntry
    MAX-ACCESS  not-accessible
    STATUS      current
    DESCRIPTION
        "A list of peer transport connections.
        Each connected peer will create a conceptual row in the table.
        When the peer disconnects, the row will be deleted from the table.

        This table augments dlswTConnOperTable."
    ::= { h3cdeTConn 2 }

h3cdeTConnOperEntry OBJECT-TYPE
    SYNTAX      H3cdeTConnOperEntry
    MAX-ACCESS  not-accessible
    STATUS      current
    DESCRIPTION
        "A list of objects that contain spefific operational
        information for a DLSw peer transport connection."
    AUGMENTS    { dlswTConnOperEntry }
    ::= { h3cdeTConnOperTable 1 }

H3cdeTConnOperEntry ::=
    SEQUENCE {
        h3cdeTConnOperPeerType         INTEGER,
        h3cdeTConnOperVendorID         OCTET STRING,
        h3cdeTConnOperVersionString    OCTET STRING,
        h3cdeTConnOperUpTime           TimeTicks,
        h3cdeTConnOperMulticastAddress TAddress,
        h3cdeTConnOperStCapTcpNumber   Integer32,
        h3cdeTConnOperRecvPkts         Counter32,
        h3cdeTConnOperSendPkts         Counter32,
        h3cdeTConnOperDropPkts         Counter32
    }

h3cdeTConnOperPeerType OBJECT-TYPE
    SYNTAX      INTEGER
                {
                configured(1),
                learningDynamic(2),
                other(3)
                }
    MAX-ACCESS  read-only
    STATUS      current
    DESCRIPTION
        "The current remote peer is configured when the value is 'configured'."
    ::= { h3cdeTConnOperEntry 1 }

h3cdeTConnOperVendorID OBJECT-TYPE
    SYNTAX      OCTET STRING
    MAX-ACCESS  read-only
    STATUS      current
    DESCRIPTION
        "The value identifies the manufacturer's IEEE-assigned
        Organizationally Unique Identifier (OUI) of remote peer."
    ::= { h3cdeTConnOperEntry 2 }

h3cdeTConnOperVersionString OBJECT-TYPE
    SYNTAX      OCTET STRING
    MAX-ACCESS  read-only
    STATUS      current
    DESCRIPTION
        "Version information of remote peer. The length up to 512 bytes."
    ::= { h3cdeTConnOperEntry 3 }

h3cdeTConnOperUpTime OBJECT-TYPE
    SYNTAX      TimeTicks
    MAX-ACCESS  read-only
    STATUS      current
    DESCRIPTION
        "The amount of time (in seconds) since this transport
        connection last entered the 'connected' state."
    ::= { h3cdeTConnOperEntry 4 }

h3cdeTConnOperMulticastAddress OBJECT-TYPE
    SYNTAX      TAddress
    MAX-ACCESS  read-only
    STATUS      current
    DESCRIPTION
        "When remote peer supports DLSw2.0, this node identifies
        its multicast address."
    ::= { h3cdeTConnOperEntry 5 }

h3cdeTConnOperStCapTcpNumber OBJECT-TYPE
    SYNTAX      Integer32
    MAX-ACCESS  read-only
    STATUS      current
    DESCRIPTION
        "Number of tcp supported when capabilities exchanging."
    ::= { h3cdeTConnOperEntry 6 }

h3cdeTConnOperRecvPkts OBJECT-TYPE
    SYNTAX      Counter32
    MAX-ACCESS  read-only
    STATUS      current
    DESCRIPTION
        "The number of Switch-to-Switch Protocol (SSP) messages
        received on this tcp transport connection."
    ::= { h3cdeTConnOperEntry 7 }

h3cdeTConnOperSendPkts OBJECT-TYPE
    SYNTAX      Counter32
    MAX-ACCESS  read-only
    STATUS      current
    DESCRIPTION
        "The number of SSP messages
        sent on this tcp transport connection."
    ::= { h3cdeTConnOperEntry 8 }

h3cdeTConnOperDropPkts OBJECT-TYPE
    SYNTAX      Counter32
    MAX-ACCESS  read-only
    STATUS      current
    DESCRIPTION
        "The number of SSP messages
        dropped on this tcp transport connection."
    ::= { h3cdeTConnOperEntry 9 }

-- ====================================================================
-- H3C DLSw Extension TCP Transport Connection Specific Configuration
-- ====================================================================
h3cdeTConnTcpConfigTable OBJECT-TYPE
    SYNTAX      SEQUENCE OF H3cdeTConnTcpConfigEntry
    MAX-ACCESS  not-accessible
    STATUS      current
    DESCRIPTION
       "This table defines the TCP transport connections that
        will be either initiated by or accepted by this DSLw.
        It augments the entries in dlswTConnConfigTable whose
        domain is dlswTCPDomain. In other words for each conceptual row
        in the dlswTConnConfigTable, if the dlswTConnConfigTDomain is
        dlswTCPDomain, that conceptual row will be augmented by this
        table.

        dlswTCPDomain, dlswTConnConfigTable, and dlswTConnConfigTDomain
        are all imported from DLSW-MIB (RFC 2024).

        This table augments dlswTConnTcpConfigTable."
    ::= { h3cdeTConn 3 }

h3cdeTConnTcpConfigEntry OBJECT-TYPE
    SYNTAX      H3cdeTConnTcpConfigEntry
    MAX-ACCESS  not-accessible
    STATUS      current
    DESCRIPTION
       "A list of objects that define specific configuration for
        a DLSw peer transport connection within the dlswTCPDomain.
        dlswTCPDomain is imported from DLSW-MIB (RFC 2024)."
    AUGMENTS    { dlswTConnTcpConfigEntry }
    ::= { h3cdeTConnTcpConfigTable 1 }

H3cdeTConnTcpConfigEntry ::=
    SEQUENCE {
        h3cdeTConnTcpConfigQueueMax  Integer32
    }

h3cdeTConnTcpConfigQueueMax  OBJECT-TYPE
    SYNTAX      Integer32 (50..2000)
    MAX-ACCESS  read-create
    STATUS      current
    DESCRIPTION
        "Maximum output TCP queue size for this remote peer.
        For DLSw over TCP encapsulation, packets may be queued
        due to congestion of the TCP network. This variable
        is used to set the output queue maximum of the underlying
        TCP connection for the peer represented by the conceptual row."
    DEFVAL      { 200 }
    ::= { h3cdeTConnTcpConfigEntry 1 }

-- ====================================================================
-- H3C DLSw Bridge MIB-Group
-- ====================================================================
h3cdeBridgeTable OBJECT-TYPE
    SYNTAX      SEQUENCE OF H3cdeBridgeEntry
    MAX-ACCESS  not-accessible
    STATUS      current
    DESCRIPTION
        "A list of bridge group which is serving for DLSw."
    ::= { h3cdeBridge 1 }

h3cdeBridgeEntry OBJECT-TYPE
    SYNTAX      H3cdeBridgeEntry
    MAX-ACCESS  not-accessible
    STATUS      current
    DESCRIPTION
        "A list of bridge information."
    INDEX       { h3cdeBridgeNumIndex }
    ::= { h3cdeBridgeTable 1 }

H3cdeBridgeEntry ::=
    SEQUENCE {
        h3cdeBridgeNumIndex   Integer32,
        h3cdeBridgeRowStatus  RowStatus
    }

h3cdeBridgeNumIndex OBJECT-TYPE
    SYNTAX      Integer32 (1..255)
    MAX-ACCESS  not-accessible
    STATUS      current
    DESCRIPTION
        "This value identifies the bridge number."
    ::= { h3cdeBridgeEntry 1 }

h3cdeBridgeRowStatus OBJECT-TYPE
    SYNTAX      RowStatus
    MAX-ACCESS  read-create
    STATUS      current
    DESCRIPTION
        "RowStatus."
    ::= { h3cdeBridgeEntry 2 }

-- ====================================================================
-- H3C DLSw Bridge group number and interface
-- ====================================================================
h3cdeBridgeIfTable OBJECT-TYPE
    SYNTAX      SEQUENCE OF H3cdeBridgeIfEntry
    MAX-ACCESS  not-accessible
    STATUS      current
    DESCRIPTION
        "The list of interface on which DLSw is active."
    ::= { h3cdeBridge 2 }

h3cdeBridgeIfEntry OBJECT-TYPE
    SYNTAX      H3cdeBridgeIfEntry
    MAX-ACCESS  not-accessible
    STATUS      current
    DESCRIPTION
        "The list of bridge interface information."
    INDEX       { ifIndex }
    ::= { h3cdeBridgeIfTable 1 }

H3cdeBridgeIfEntry ::=
    SEQUENCE {
        h3cdeBridgeIfBrgGrp      Integer32,
        h3cdeBridgeIfRowStatus   RowStatus
    }

h3cdeBridgeIfBrgGrp OBJECT-TYPE
    SYNTAX      Integer32 (1..255)
    MAX-ACCESS  read-create
    STATUS      current
    DESCRIPTION
        "This value identifies the bridge number attached
        to the interface."
    ::= { h3cdeBridgeIfEntry 1 }

h3cdeBridgeIfRowStatus OBJECT-TYPE
    SYNTAX      RowStatus
    MAX-ACCESS  read-create
    STATUS      current
    DESCRIPTION
        "RowStatus."
    ::= { h3cdeBridgeIfEntry 2 }

-- ====================================================================
-- H3C DLSw Extension QLLC Port Configuration Table
-- ====================================================================
h3cdeQllcTable  OBJECT-TYPE
    SYNTAX      SEQUENCE OF H3cdeQllcEntry
    MAX-ACCESS  not-accessible
    STATUS      current
    DESCRIPTION
       "The table defines attributes related for those
        QLLC that participate in data link switching."
    ::= { h3cdeQllc 1 }

h3cdeQllcEntry  OBJECT-TYPE
    SYNTAX      H3cdeQllcEntry
    MAX-ACCESS  not-accessible
    STATUS      current
    DESCRIPTION
       "The ifIndex belongs to the interface which link protocol is x.25."
    INDEX       { ifIndex }
    ::= { h3cdeQllcTable 1 }

H3cdeQllcEntry ::=
    SEQUENCE {
        h3cQllcX121Address  Integer32,
        h3cQllcLocalMac     MacAddressNC,
        h3cQllcLocalSap     OCTET STRING,
        h3cQllcRemoteMac    MacAddressNC,
        h3cQllcRemoteSap    OCTET STRING,
        h3cQllcRowStatus    RowStatus
    }

h3cQllcX121Address  OBJECT-TYPE
    SYNTAX      Integer32
    MAX-ACCESS  read-create
    STATUS      current
    DESCRIPTION
       "X.121 address."
    ::= { h3cdeQllcEntry 1 }

h3cQllcLocalMac  OBJECT-TYPE
    SYNTAX      MacAddressNC
    MAX-ACCESS  read-create
    STATUS      current
    DESCRIPTION
       "The virtual MAC address used to represent the QLLC-attached
        link station to the rest of the DLSw network."
    ::= { h3cdeQllcEntry 2 }

h3cQllcLocalSap  OBJECT-TYPE
    SYNTAX      OCTET STRING (SIZE(1))
    MAX-ACCESS  read-create
    STATUS      current
    DESCRIPTION
       "The SAP used to represent this link station."
    ::= { h3cdeQllcEntry 3 }

h3cQllcRemoteMac  OBJECT-TYPE
    SYNTAX      MacAddressNC
    MAX-ACCESS  read-create
    STATUS      current
    DESCRIPTION
       "The MAC address to which DLSw should attempt to connect
        this link station. If this information is not available,
        a length of zero for this object should be returned."
    DEFVAL      { ''H }
    ::= { h3cdeQllcEntry 4 }

h3cQllcRemoteSap  OBJECT-TYPE
    SYNTAX      OCTET STRING (SIZE (0 | 1))
    MAX-ACCESS  read-create
    STATUS      current
    DESCRIPTION
       "The SAP of the remote station to which this link
        station should be connected. If this information
        is not available, a length of zero for this object
        should be returned."
    DEFVAL      { ''H }
    ::= { h3cdeQllcEntry 5 }

h3cQllcRowStatus  OBJECT-TYPE
    SYNTAX      RowStatus
    MAX-ACCESS  read-create
    STATUS      current
    DESCRIPTION
       "RowStatus."
    ::= { h3cdeQllcEntry 6 }

-- ====================================================================
-- H3C DLSw Extension SDLC Port Configuration Table
-- ====================================================================
h3cdeSdlcPortTable OBJECT-TYPE
    SYNTAX      SEQUENCE OF H3cdeSdlcPortEntry
    MAX-ACCESS  not-accessible
    STATUS      current
    DESCRIPTION
        "The table defines parameters for the interfaces
        whose link protocol is SDLC."
    ::= { h3cdeSdlc 1 }

h3cdeSdlcPortEntry OBJECT-TYPE
    SYNTAX      H3cdeSdlcPortEntry
    MAX-ACCESS  not-accessible
    STATUS      current
    DESCRIPTION
        "Sdlc port entry."
    INDEX       { ifIndex }
    ::= { h3cdeSdlcPortTable 1 }


H3cdeSdlcPortEntry ::=
    SEQUENCE {
        h3cdeSdlcPortRole                INTEGER,
        h3cdeSdlcPortSendWindow          Integer32,
        h3cdeSdlcPortModulo              INTEGER,
        h3cdeSdlcPortMaxPdu              Integer32,
        h3cdeSdlcPortMaxSendQueue        Integer32,
        h3cdeSdlcPortMaxTransmission     Integer32,
        h3cdeSdlcPortSimultaneousEnable  INTEGER,
        h3cdeSdlcPortTimerACK            Integer32,
        h3cdeSdlcPortTimerLifeTime       Integer32,
        h3cdeSdlcPortTimerPollPause      Integer32,
        h3cdeSdlcPortRowStatus           RowStatus
    }

h3cdeSdlcPortRole OBJECT-TYPE
    SYNTAX      INTEGER
                {
                primary(1),
                seconday(2),
                norole(3)
                }
    MAX-ACCESS  read-create
    STATUS      current
    DESCRIPTION
        "The SDLC role of interface."
    DEFVAL      { norole }
    ::= { h3cdeSdlcPortEntry 1 }

h3cdeSdlcPortSendWindow OBJECT-TYPE
    SYNTAX      Integer32 (1..7)
    MAX-ACCESS  read-create
    STATUS      current
    DESCRIPTION
        "Size of local send window."
    DEFVAL      { 7 }
    ::= { h3cdeSdlcPortEntry 2 }

h3cdeSdlcPortModulo OBJECT-TYPE
    SYNTAX      INTEGER
                {
                m8(8),
                m128(128)
                }
    MAX-ACCESS  read-create
    STATUS      current
    DESCRIPTION
        "Size of modulus."
    DEFVAL      { m8 }
    ::= { h3cdeSdlcPortEntry 3 }

h3cdeSdlcPortMaxPdu OBJECT-TYPE
    SYNTAX      Integer32 (1..17600)
    MAX-ACCESS  read-create
    STATUS      current
    DESCRIPTION
        "Maximum bytes for incoming frames."
    DEFVAL      { 265 }
    ::= { h3cdeSdlcPortEntry 4 }

h3cdeSdlcPortMaxSendQueue OBJECT-TYPE
    SYNTAX      Integer32 (20..255)
    MAX-ACCESS  read-create
    STATUS      current
    DESCRIPTION
        "Size of hold queue."
    DEFVAL      { 50 }
    ::= { h3cdeSdlcPortEntry 5 }

h3cdeSdlcPortMaxTransmission OBJECT-TYPE
    SYNTAX      Integer32 (1..255)
    MAX-ACCESS  read-create
    STATUS      current
    DESCRIPTION
        "Number of times to retry an operation."
    DEFVAL      { 20 }
    ::= { h3cdeSdlcPortEntry 6 }

h3cdeSdlcPortSimultaneousEnable OBJECT-TYPE
    SYNTAX      INTEGER
                {
                enabled(1),
                disabled(2)
                }
    MAX-ACCESS  read-create
    STATUS      current
    DESCRIPTION
        "Activate SDLC two-way simultaneous mode."
    DEFVAL      { 1 }
    ::= { h3cdeSdlcPortEntry 7 }

h3cdeSdlcPortTimerACK OBJECT-TYPE
    SYNTAX      Integer32 (1..60000)
    UNITS       "milliseconds"
    MAX-ACCESS  read-create
    STATUS      current
    DESCRIPTION
        "Time to wait for a reply to a frame."
    DEFVAL      { 3000 }
    ::= { h3cdeSdlcPortEntry 8 }

h3cdeSdlcPortTimerLifeTime OBJECT-TYPE
    SYNTAX      Integer32 (1..60000)
    UNITS       "milliseconds"
    MAX-ACCESS  read-create
    STATUS      current
    DESCRIPTION
        "Time to wait for a reply used by secondary station."
    DEFVAL      { 500 }
    ::= { h3cdeSdlcPortEntry 9 }

h3cdeSdlcPortTimerPollPause OBJECT-TYPE
    SYNTAX      Integer32 (1..10000)
    UNITS       "milliseconds"
    MAX-ACCESS  read-create
    STATUS      current
    DESCRIPTION
        "Time between polls for each secondary SDLC station."
    DEFVAL      { 1000 }
    ::= { h3cdeSdlcPortEntry 10 }

h3cdeSdlcPortRowStatus OBJECT-TYPE
    SYNTAX      RowStatus
    MAX-ACCESS  read-create
    STATUS      current
    DESCRIPTION
        "RowStatus."
    ::= { h3cdeSdlcPortEntry 11 }

-- ====================================================================
-- H3C DLSw Extension LLC2 Port Configuration Table
-- ====================================================================
h3cdeLlc2PortTable OBJECT-TYPE
    SYNTAX      SEQUENCE OF H3cdeLlc2PortEntry
    MAX-ACCESS  not-accessible
    STATUS      current
    DESCRIPTION
        "This table defines parameters for the Ethernet interface."
    ::= { h3cdeLlc2 1 }

h3cdeLlc2PortEntry OBJECT-TYPE
    SYNTAX      H3cdeLlc2PortEntry
    MAX-ACCESS  not-accessible
    STATUS      current
    DESCRIPTION
        "LLC2 port entry."
    INDEX       { ifIndex }
    ::= { h3cdeLlc2PortTable 1 }

H3cdeLlc2PortEntry ::=
    SEQUENCE {
        h3cdeLlc2PortMaxAck           Integer32,
        h3cdeLlc2PortMaxPdu           Integer32,
        h3cdeLlc2PortMaxSendQueue     Integer32,
        h3cdeLlc2PortMaxTransmission  Integer32,
        h3cdeLlc2PortModulo           INTEGER,
        h3cdeLlc2PortReceiveWindow    Integer32,
        h3cdeLlc2PortTimerAck         Integer32,
        h3cdeLlc2PortTimerAckDelay    Integer32,
        h3cdeLlc2PortTimerDetect      Integer32,
        h3cdeLlc2PortTimerBusy        Integer32,
        h3cdeLlc2PortTimerPoll        Integer32,
        h3cdeLlc2PortTimerReject      Integer32,
        h3cdeLlc2PortRowStatus        RowStatus
    }

h3cdeLlc2PortMaxAck OBJECT-TYPE
    SYNTAX      Integer32 (1..127)
    MAX-ACCESS  read-create
    STATUS      current
    DESCRIPTION
        "Maximum of I-frames received before ACK."
    DEFVAL      { 3 }
    ::= { h3cdeLlc2PortEntry 1 }

h3cdeLlc2PortMaxPdu OBJECT-TYPE
    SYNTAX      Integer32 (1..1700)
    MAX-ACCESS  read-create
    STATUS      current
    DESCRIPTION
        "Maximum of LLC2 pdu length."
    DEFVAL      { 1493 }
    ::= { h3cdeLlc2PortEntry 2 }

h3cdeLlc2PortMaxSendQueue OBJECT-TYPE
    SYNTAX      Integer32 (20..200)
    MAX-ACCESS  read-create
    STATUS      current
    DESCRIPTION
        "Queue for sending llc2 I-frames."
    DEFVAL      { 50 }
    ::= { h3cdeLlc2PortEntry 3 }

h3cdeLlc2PortMaxTransmission OBJECT-TYPE
    SYNTAX      Integer32 (1..255)
    MAX-ACCESS  read-create
    STATUS      current
    DESCRIPTION
        "Retry times of operations."
    DEFVAL      { 20 }
    ::= { h3cdeLlc2PortEntry 4 }

h3cdeLlc2PortModulo OBJECT-TYPE
    SYNTAX      INTEGER
                {
                m8(8),
                m128(128)
                }
    MAX-ACCESS  read-create
    STATUS      current
    DESCRIPTION
        "Modulus of LLC2."
    DEFVAL      { m128 }
    ::= { h3cdeLlc2PortEntry 5 }

h3cdeLlc2PortReceiveWindow OBJECT-TYPE
    SYNTAX      Integer32 (1..127)
    MAX-ACCESS  read-create
    STATUS      current
    DESCRIPTION
        "Maximum number of I-frames to send before received ACK."
    DEFVAL      { 7 }
    ::= { h3cdeLlc2PortEntry 6 }

h3cdeLlc2PortTimerAck OBJECT-TYPE
    SYNTAX      Integer32 (1..60000)
    UNITS       "milliseconds"
    MAX-ACCESS  read-create
    STATUS      current
    DESCRIPTION
        "Waiting for ACK time after sending an I-frame."
    DEFVAL      { 200 }
    ::= { h3cdeLlc2PortEntry 7 }

h3cdeLlc2PortTimerAckDelay OBJECT-TYPE
    SYNTAX      Integer32 (1..60000)
    UNITS       "milliseconds"
    MAX-ACCESS  read-create
    STATUS      current
    DESCRIPTION
        "Maximum time allows I-frames incoming without replay ACK."
    DEFVAL      { 100 }
    ::= { h3cdeLlc2PortEntry 8 }

h3cdeLlc2PortTimerDetect OBJECT-TYPE
    SYNTAX      Integer32 (1..60000)
    UNITS       "milliseconds"
    MAX-ACCESS  read-create
    STATUS      current
    DESCRIPTION
        "Detect the link status."
    DEFVAL      { 100 }
    ::= { h3cdeLlc2PortEntry 9 }

h3cdeLlc2PortTimerBusy OBJECT-TYPE
    SYNTAX      Integer32 (1..60000)
    UNITS       "milliseconds"
    MAX-ACCESS  read-create
    STATUS      current
    DESCRIPTION
        "Waiting time while other LLC2 station is in busy state."
    DEFVAL      { 300 }
    ::= { h3cdeLlc2PortEntry 10 }

h3cdeLlc2PortTimerPoll OBJECT-TYPE
    SYNTAX      Integer32 (1..60000)
    UNITS       "milliseconds"
    MAX-ACCESS  read-create
    STATUS      current
    DESCRIPTION
        "Waiting time after a P frame is sent."
    DEFVAL      { 5000 }
    ::= { h3cdeLlc2PortEntry 11 }

h3cdeLlc2PortTimerReject OBJECT-TYPE
    SYNTAX      Integer32 (1..60000)
    UNITS       "milliseconds"
    MAX-ACCESS  read-create
    STATUS      current
    DESCRIPTION
        "Waiting time after a REJ frame is sent."
    DEFVAL      { 500 }
    ::= { h3cdeLlc2PortEntry 12 }

h3cdeLlc2PortRowStatus OBJECT-TYPE
    SYNTAX      RowStatus
    MAX-ACCESS  read-create
    STATUS      current
    DESCRIPTION
        "RowStatus."
    ::= { h3cdeLlc2PortEntry 13 }

-- ====================================================================
-- H3C DLSw Reachable Cache MIB-Group
-- ====================================================================
h3cdeRchCacheStat OBJECT IDENTIFIER ::= { h3cdeReachableCache 1 }

h3cdeRchCacheMaxIndex OBJECT-TYPE
    SYNTAX      Integer32
    MAX-ACCESS  read-only
    STATUS      current
    DESCRIPTION
        "Maximum of h3cdeRchCacheIndex."
    ::= { h3cdeRchCacheStat 1 }

h3cdeRchCacheNextIndex OBJECT-TYPE
    SYNTAX      Integer32
    MAX-ACCESS  read-only
    STATUS      current
    DESCRIPTION
        "The next value of h3cdeRchCacheIndex to be assigned by
        the agent. A retrieval of this object atomically reserves
        the returned value for use by the manager to create a row
        in h3cdeRchCacheTable. This makes it possible for the agent
        to control the index space of the MAC address cache, yet
        allows the manager to administratively create new rows."
    ::= { h3cdeRchCacheStat 2 }

h3cdeRchCacheTable OBJECT-TYPE
    SYNTAX      SEQUENCE OF H3cdeRchCacheEntry
    MAX-ACCESS  not-accessible
    STATUS      current
    DESCRIPTION
        "Reachable cache table."
    ::= { h3cdeReachableCache 3 }

h3cdeRchCacheEntry OBJECT-TYPE
    SYNTAX      H3cdeRchCacheEntry
    MAX-ACCESS  not-accessible
    STATUS      current
    DESCRIPTION
        "Reachable cache entry."
    INDEX       { h3cdeRchCacheIndex }
    ::= { h3cdeRchCacheTable 1 }

H3cdeRchCacheEntry ::=
    SEQUENCE {
        h3cdeRchCacheIndex            Integer32,
        h3cdeRchCacheStatus           INTEGER,
        h3cdeRchCacheRemainTime       TimeTicks,
        h3cdeRchCacheMac              MacAddressNC,
        h3cdeRchCacheRemoteIpAddrType InetAddressType,
        h3cdeRchCacheRemoteIp         InetAddress,
        h3cdeRchCacheRowStatus        RowStatus
    }

h3cdeRchCacheIndex OBJECT-TYPE
    SYNTAX      Integer32
    MAX-ACCESS  not-accessible
    STATUS      current
    DESCRIPTION
        "Index of reachable cache entry."
    ::= { h3cdeRchCacheEntry 1 }

h3cdeRchCacheStatus OBJECT-TYPE
    SYNTAX      INTEGER
                {
                found(1),
                verify(2),
                noCacheInfo(3),
                exploring(4),
                waiting(5)
                }
    MAX-ACCESS  read-only
    STATUS      current
    DESCRIPTION
        "Current status of reachable cache entry."
    ::= { h3cdeRchCacheEntry 2 }

h3cdeRchCacheRemainTime OBJECT-TYPE
    SYNTAX      TimeTicks
    MAX-ACCESS  read-only
    STATUS      current
    DESCRIPTION
        "Remain time of reachable cache entry."
    ::= { h3cdeRchCacheEntry 3 }

h3cdeRchCacheMac OBJECT-TYPE
    SYNTAX      MacAddressNC
    MAX-ACCESS  read-create
    STATUS      current
    DESCRIPTION
        "MAC address of reachable cache entry."
    ::= { h3cdeRchCacheEntry 4 }

h3cdeRchCacheRemoteIpAddrType OBJECT-TYPE
    SYNTAX      InetAddressType
    MAX-ACCESS  read-create
    STATUS      current
    DESCRIPTION
        "Remote peer ip address type."
    ::= { h3cdeRchCacheEntry 5 }

h3cdeRchCacheRemoteIp OBJECT-TYPE
    SYNTAX      InetAddress
    MAX-ACCESS  read-create
    STATUS      current
    DESCRIPTION
        "Remote peer ip address of reachable cache entry."
    ::= { h3cdeRchCacheEntry 6 }

h3cdeRchCacheRowStatus OBJECT-TYPE
    SYNTAX      RowStatus
    MAX-ACCESS  read-create
    STATUS      current
    DESCRIPTION
        "RowStatus."
    ::= { h3cdeRchCacheEntry 7 }

-- ====================================================================
-- H3C DLSw Ethernet Backup MIB-Group
-- ====================================================================
h3cdeEBMacMapStat OBJECT IDENTIFIER ::= { h3cdeEthernetBackup 1 }

h3cdeEBMacMapMaxIndex OBJECT-TYPE
    SYNTAX      Integer32
    MAX-ACCESS  read-only
    STATUS      current
    DESCRIPTION
        "Maximum of h3cdeEBMacMapIndex."
    ::= { h3cdeEBMacMapStat 1 }

h3cdeEBMacMapNextIndex OBJECT-TYPE
    SYNTAX      Integer32
    MAX-ACCESS  read-only
    STATUS      current
    DESCRIPTION
        "The next value of h3cdeEBMacMapIndex to be assigned by
        the agent. A retrieval of this object atomically reserves
        the returned value for use by the manager to create a row
        in h3cdeEBMacMapTable. This makes it possible for the agent
        to control the index space of the MAC mapping tables, yet
        allows the manager to administratively create new rows."
    ::= { h3cdeEBMacMapStat 2 }

h3cdeEBIfTable OBJECT-TYPE
    SYNTAX      SEQUENCE OF H3cdeEBIfEntry
    MAX-ACCESS  not-accessible
    STATUS      current
    DESCRIPTION
        "Information of interface which works for DLSw Ethernet redundancy."
    ::= { h3cdeEthernetBackup 3 }

h3cdeEBIfEntry OBJECT-TYPE
    SYNTAX      H3cdeEBIfEntry
    MAX-ACCESS  not-accessible
    STATUS      current
    DESCRIPTION
        "Parameters defined for DLSw Ethernet redundancy interface."
    INDEX       { ifIndex }
    ::= { h3cdeEBIfTable 1 }

H3cdeEBIfEntry ::=
    SEQUENCE {
        h3cdeEBMulticastMac    MacAddressNC,
        h3cdeEBPriority        Integer32,
        h3cdeEBtimer           Integer32,
        h3cdeEBRowStatus       RowStatus
    }

h3cdeEBMulticastMac OBJECT-TYPE
    SYNTAX      MacAddressNC
    MAX-ACCESS  read-create
    STATUS      current
    DESCRIPTION
        "Multicast MAC address configured for the Ethernet
        redundancy of dlsw module. When Ethernet redundancy
        is inactive, its value is '000000000000'H.
        To active Ethernet redundancy, give it a valid multicast MAC address."
    DEFVAL      { '000000000000'h }
    ::= { h3cdeEBIfEntry 1 }

h3cdeEBPriority OBJECT-TYPE
    SYNTAX      Integer32 (1..254)
    MAX-ACCESS  read-create
    STATUS      current
    DESCRIPTION
        "Priority configured for the Ethernet redundancy of DLSw module."
    DEFVAL      { 100 }
    ::= { h3cdeEBIfEntry 2 }

h3cdeEBtimer OBJECT-TYPE
    SYNTAX      Integer32 (100..5000)
    MAX-ACCESS  read-create
    STATUS      current
    DESCRIPTION
        "Timer for the Ethernet redundancy of DLSw module."
    DEFVAL      { 500 }
    ::= { h3cdeEBIfEntry 3 }

h3cdeEBRowStatus OBJECT-TYPE
    SYNTAX      RowStatus
    MAX-ACCESS  read-create
    STATUS      current
    DESCRIPTION
        "RowStatus."
    ::= { h3cdeEBIfEntry 4 }

h3cdeEBMacMapTable OBJECT-TYPE
    SYNTAX      SEQUENCE OF H3cdeEBMacMapEntry
    MAX-ACCESS  not-accessible
    STATUS      current
    DESCRIPTION
        "MAC address mapping table."
    ::= { h3cdeEthernetBackup 4 }

h3cdeEBMacMapEntry OBJECT-TYPE
    SYNTAX      H3cdeEBMacMapEntry
    MAX-ACCESS  not-accessible
    STATUS      current
    DESCRIPTION
        "MAC address mapping entry."
    INDEX       { ifIndex, h3cdeEBMacMapIndex }
    ::= { h3cdeEBMacMapTable 1 }

H3cdeEBMacMapEntry ::=
    SEQUENCE {
        h3cdeEBMacMapIndex         Integer32,
        h3cdeEBMacMapLocalMac      MacAddressNC,
        h3cdeEBMacMapRemoteMac     MacAddressNC,
        h3cdeEBMacMapNeighbour     MacAddressNC,
        h3cdeEBMacMapRowStatus     RowStatus
    }

h3cdeEBMacMapIndex OBJECT-TYPE
    SYNTAX      Integer32
    MAX-ACCESS  not-accessible
    STATUS      current
    DESCRIPTION
        "Index of MAC address mapping entry."
    ::= { h3cdeEBMacMapEntry 1 }

h3cdeEBMacMapLocalMac OBJECT-TYPE
    SYNTAX      MacAddressNC
    MAX-ACCESS  read-create
    STATUS      current
    DESCRIPTION
        "Local MAC address in MAC address mapping.
        When creating a new conceptual row, h3cdeEBMacMapLocalMac
        and h3cdeEBMacMapRemoteMac should be set simultaneously."
    ::= { h3cdeEBMacMapEntry 2 }

h3cdeEBMacMapRemoteMac OBJECT-TYPE
    SYNTAX      MacAddressNC
    MAX-ACCESS  read-create
    STATUS      current
    DESCRIPTION
        "Remote MAC address of MAC address mapping.
        When creating a new conceptual row, h3cdeEBMacMapLocalMac
        and h3cdeEBMacMapRemoteMac should be set simultaneously."
    ::= { h3cdeEBMacMapEntry 3 }

h3cdeEBMacMapNeighbour OBJECT-TYPE
    SYNTAX      MacAddressNC
    MAX-ACCESS  read-create
    STATUS      current
    DESCRIPTION
        "Neighbour of MAC address mapping."
    ::= { h3cdeEBMacMapEntry 4 }

h3cdeEBMacMapRowStatus OBJECT-TYPE
    SYNTAX      RowStatus
    MAX-ACCESS  read-create
    STATUS      current
    DESCRIPTION
        "Status of MAC address mapping entry."
    ::= { h3cdeEBMacMapEntry 5 }


END
