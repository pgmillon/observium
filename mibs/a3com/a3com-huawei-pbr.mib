-- =================================================================
-- Copyright (c) 2004-2011 Hangzhou H3C Tech. Co., Ltd. All rights reserved.
--
-- Description: policy based routing MIB File
-- Reference:
-- Version: V1.0
-- History:
--      V1.0 created by houyefei
--        initial version 2010-12-10
-- =================================================================
A3COM-HUAWEI-PBR-MIB DEFINITIONS ::= BEGIN

IMPORTS
    h3cCommon
        FROM A3COM-HUAWEI-OID-MIB
    OBJECT-TYPE, MODULE-IDENTITY, NOTIFICATION-TYPE
        FROM SNMPv2-SMI
    TruthValue
        FROM SNMPv2-TC
    InetAddress, InetAddressType
        FROM INET-ADDRESS-MIB;

h3cPBR MODULE-IDENTITY
    LAST-UPDATED
        "201012101558Z"
    ORGANIZATION
        "Hangzhou H3C Technologies Co., Ltd."
    CONTACT-INFO
        "Platform Team H3C Technologies Co., Ltd.
         Hai-Dian District Beijing P.R. China
         http://www.h3c.com
         Zip: 100085"
    DESCRIPTION
        "This MIB contains objects to manage the configuration and information
        of policy based routing.  It routes IP packets by user defined policy
        other than normal destination address based routing.
        "
    REVISION
        "201012101558Z"
    DESCRIPTION
        "The initial version of this MIB file."
    ::= { h3cCommon 113 }

-- Objects define
h3cPBRObjects OBJECT IDENTIFIER ::= { h3cPBR 1 }

h3cPBRGlobal OBJECT IDENTIFIER ::= { h3cPBRObjects 1 }

h3cPBRMibTrap OBJECT IDENTIFIER  ::= { h3cPBRObjects 2 }

h3cPBRNexthopTrapEnabled OBJECT-TYPE
    SYNTAX      TruthValue
    MAX-ACCESS  read-write
    STATUS      current
    DESCRIPTION
        "The value is a global setting.  The feature will not work until the
        value is set to 'true'.  If the value is set to 'false', the feature
        will stop working."
    DEFVAL { false }
    ::= { h3cPBRGlobal 1 }

-- PBR trap table
h3cPBRTrapObjects OBJECT IDENTIFIER  ::= { h3cPBRMibTrap 1 }

h3cPBRNexthopAddrType OBJECT-TYPE
    SYNTAX      InetAddressType
    MAX-ACCESS  accessible-for-notify
    STATUS      current
    DESCRIPTION
        "Indicating address type of h3cPBRNexthopAddr, which can be either IPv4
        or IPv6."
    ::= { h3cPBRTrapObjects 1 }

h3cPBRNexthopAddr OBJECT-TYPE
    SYNTAX      InetAddress
    MAX-ACCESS  accessible-for-notify
    STATUS      current
    DESCRIPTION
        "The involved nexthop IP address of trap information."
    ::= { h3cPBRTrapObjects 2 }

h3cPBRTraps OBJECT IDENTIFIER  ::= { h3cPBRMibTrap 2 }

h3cPBRTrapsPrefix OBJECT IDENTIFIER  ::= { h3cPBRTraps 0 }

h3cPBRNexthopFailedTrap NOTIFICATION-TYPE
    OBJECTS
    {
        h3cPBRNexthopAddrType,
        h3cPBRNexthopAddr
    }
    STATUS      current
    DESCRIPTION
        "When the nexthop of policy based routing apply clause became
        unreachable according to routing information, trap is generated
        and is sent to the remote monitoring device."
    ::= { h3cPBRTrapsPrefix 1 }

END
