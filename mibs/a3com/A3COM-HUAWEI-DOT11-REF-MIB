-- =============================================================================
-- Copyright (c) 2004-2011 Hangzhou H3C Tech. Co., Ltd.  All rights reserved.
--
-- Description:
--   The file defines a MIB to provide root node and TC for 802.11 MIB series.
-- Reference:
-- Version: V1.8
-- History:
--   V1.0 created by shiyang (Richard)
--     Initial version 2006-05-10
--   V1.1 2007-04-27 modified by shiyang(Richard)
--        Add "none" and "all" enumerate for H3cDot11AuthenType.
--        Add H3cDot11RFModeType.
--        Add none(1) for H3cDot11AKMType.
--   V1.2 2007-06-21 modified by Vikas K
--        Added H3cDot11AssocFailType.
--        Added H3cDot11AuthorFailType.
--        Added H3cDot11QosAcType.
--   V1.3 2008-8-23 modified by Wang Lu
--        Add H3cDot11RadioElementIndex
--        Add enumerations to H3cDot11RadioType.
--        Remove hyphen in enumerations of H3cDot11QosAcType.
--        Add h3cDot11ElementGroup.
--   V1.4 2008-11-18 modified by Wang Lu
--        Add H3cDot11WorkMode and H3cDot11CirMode
--   V1.5 2009-05-07 modified by Wang Shaojie
--        Modify H3cDot11SSIDEncryptModeType
--   V1.6 2010-01-07 modified by Wang Shaojie
--        Modify H3cDot11SecIEStatusType, H3cDot11CipherType
--        2010-03-18 modified by Wang Lu
--        Modify H3cDot11AKMType and H3cDot11CipherType
--   V1.7 2011-08-10 modified by limingjin
--        Add H3cDot11RadioType2
--   V1.8 2011-08-26 modified by Wang Lu
--        Add H3cDot11SaIntfDevType
-- =============================================================================
A3COM-HUAWEI-DOT11-REF-MIB DEFINITIONS ::= BEGIN

IMPORTS
        TEXTUAL-CONVENTION
    FROM SNMPv2-TC
        MODULE-IDENTITY,
        Integer32, Unsigned32, OBJECT-TYPE
    FROM SNMPv2-SMI
        h3cCommon
    FROM A3COM-HUAWEI-OID-MIB;

h3cDot11 MODULE-IDENTITY
    LAST-UPDATED "201001072000Z"        -- Jan 7, 2009 at 20:00 GMT
    ORGANIZATION
        "Hangzhou H3C Tech. Co., Ltd."
    CONTACT-INFO
        "Platform Team Hangzhou H3C Tech. Co., Ltd.
        Hai-Dian District Beijing P.R. China
        http://www.h3c.com
        Zip:100085
        "
    DESCRIPTION
        "This MIB defines the root node and TC for 802.11 features.
        By this way, the MIB series for 802.11 will be easily maintained.

        GLOSSARY

        IEEE 802.11
        Standard to encourage interoperability among
        wireless networking equipment.

        IEEE 802.11a
        This is a high speed physical layer extension to
        the 802.11 standard on the 5 GHz band.

        IEEE 802.11b
        High-rate wireless LAN standard for wireless
        data transfer at up to 11 Mbps.

        IEEE 802.11g
        Higher Speed Physical Layer (PHY) Extension to
        IEEE 802.11b, will boost wireless LAN speed to 54
        Mbps by using OFDM (orthogonal frequency division
        multiplexing). The IEEE 802.11g specification is
        backward compatible with the widely deployed IEEE
        802.11b standard.
        When configure radio with as bg mode, it means that
        radio will be compatible to 802.11b and 802.11g.
        When configure radio with as g mode, it means that
        radio will be only compatible to 802.11g.

        IEEE 802.11i
        As 802.11 has lot of deficiency in wireless security
        domain, especially for enterprise custom, IEEE defined
        a new standard 802.11i to extend security feature of
        802.11 standard.

        AKM
        The authentication and key management method defined by
        802.11i, and which includes 802.1x and pre-shared key."


    REVISION "201001072000Z"        -- Jan 7, 2010 at 20:00 GMT
    DESCRIPTION
        "Modified for CMCC of GuangDong province."
    REVISION "200905072000Z"        -- May 7, 2009 at 20:00 GMT
    DESCRIPTION
        "Modified for CMCC of GuangDong province."
    REVISION "200706212000Z"        -- Jun 21, 2007 at 20:00 GMT
    DESCRIPTION
        "Modified for CMCC(China Mobile Communication Corporation)
        requirements."
    REVISION "200704272000Z"        -- Apr 27, 2007 at 20:00 GMT
    DESCRIPTION
        "Modified to add new TC."
    REVISION "200605101900Z"        -- May 10, 2006 at 19:00 GMT
    DESCRIPTION
        "The initial revision of this MIB module."
    ::= { h3cCommon 75 }

-- *****************************************************************************
-- *  Textual conventions from 802 definitions
-- *****************************************************************************
--  Common TEXTUAL-CONVENTION
H3cDot11ObjectIDType ::=   TEXTUAL-CONVENTION
    STATUS      current
    DESCRIPTION
        "Represents AP identifier value type."
    SYNTAX      OCTET STRING(SIZE(0..127))

H3cDot11RadioScopeType ::=   TEXTUAL-CONVENTION
    STATUS      current
    DESCRIPTION
        "Represents radio value scope."
    SYNTAX      Integer32

H3cDot11RadioType ::=   TEXTUAL-CONVENTION
    STATUS      current
    DESCRIPTION
        "Represents AP 802.11 radio type of 802.11a/b/g/n as per
        the standard.
        The following values are supported:
        dot11a(1)  - 802.11a
        dot11b(2)  - 802.11b
        dot11g(4)  - 802.11g
        dot11n(8)  - 802.11n
        "
    SYNTAX      INTEGER
        {
            dot11a(1),
            dot11b(2),
            dot11g(4),
            dot11n(8),
            dot11gn(16),
            dot11an(32)
        }

H3cDot11RadioType2 ::=   TEXTUAL-CONVENTION
    STATUS      current
    DESCRIPTION
        "Represents AP 802.11 radio type of 802.11a/b/g/an/gn as per
        the standard.
        The following values are supported:
        dot11a(1)   - 802.11a
        dot11b(2)   - 802.11b
        dot11g(4)   - 802.11g
        dot11an(8)  - 802.11an
        dot11gn(16)  - 802.11gn
        "
    SYNTAX      INTEGER
        {
            dot11a(1),
            dot11b(2),
            dot11g(4),
            dot11an(8),
            dot11gn(16)
        }

H3cDot11MACModeType ::=   TEXTUAL-CONVENTION
    STATUS      current
    DESCRIPTION
        "CAPWAP defines three kinds MAC mode for fit AP.
        The management packet will be exchanged between AP and AC by
        CAPWAP control tunnel.
        For data packet, the following MAC mode are supported:
        split(1)        - AP will tunnel 802.11 data message
        - to AC by CAPWAP,
        localtunnel(2)  - AP will convert data to 802.3, then tunnel
        - it to AC by CAPWAP,
        localbridge(3)  - AP will directly handle data packet without
        - sending to AC to process,
        fatAP           - For fat AP, it will handle all 802.11 frames
        - by itself."
    SYNTAX      INTEGER
        {
            split(1),
            localtunnel(2),
            localbridge(3),
            fatAP(4)
        }

H3cDot11ChannelScopeType ::=   TEXTUAL-CONVENTION
    STATUS      current
    DESCRIPTION
        "Represents the channel scope which consists of 802.11a/b/g."
    SYNTAX      Integer32

H3cDot11NotifyReasonType ::=   TEXTUAL-CONVENTION
    STATUS      current
    DESCRIPTION
        "The explanation string is for the event notification of dot11."
    SYNTAX      OCTET STRING(SIZE(0..255))

H3cDot11SSIDStringType ::=   TEXTUAL-CONVENTION
    STATUS      current
    DESCRIPTION
        "SSID is a string to identify ESS for wireless network."
    SYNTAX      OCTET STRING

H3cDot11ServicePolicyIDType ::=   TEXTUAL-CONVENTION
    STATUS      current
    DESCRIPTION
        "Represents the type of service policy ID."
    SYNTAX      Integer32

H3cDot11SSIDEncryptModeType ::=   TEXTUAL-CONVENTION
    STATUS      current
    DESCRIPTION
        "Represents encryption mode for the specific ESS:
        The following values are supported:
        cleartxt(1)  - clear txt,
        cipher(2)    - WPA and 802.11i
        ext(3)      - ext."
    SYNTAX      INTEGER
        {
            cleartxt(1),
            cipher(2),
            ext(3)
        }

H3cDot11PreambleType ::=   TEXTUAL-CONVENTION
    STATUS      current
    DESCRIPTION
        "Represents the current radio preamble type.
        The following values are supported:
        long(1)  - long preambles,
        short(2) - short preambles."
    SYNTAX      INTEGER
        {
            long(1),
            short(2)
        }

H3cDot11TxPwrLevelScopeType ::=   TEXTUAL-CONVENTION
    STATUS      current
    DESCRIPTION
        "Represents the Tx power level scope for 802.11."
    SYNTAX      Integer32

H3cDot11RFModeType ::=   TEXTUAL-CONVENTION
    STATUS      current
    DESCRIPTION
        "Represents RF management mode.
        The following values are supported:
        manual(1)  - Configure RF parameter by manual,
        auto(2)    - Automaticall configure."
    SYNTAX      INTEGER
        {
            manual(1),
            auto(2)
        }

--  CAPWAP TEXTUAL-CONVENTION
H3cDot11TunnelSecSchemType ::=   TEXTUAL-CONVENTION
    STATUS      current
    DESCRIPTION
        "Represents which security scheme option is available for
        CAPWAP tunnel.
        The following values are supported:
        cleartxt(1)  - No encryption protection,
        dtls(2)      - Encrypted by DTLS,
        ipsec(3)     - Encrypted by IPSEC."
    SYNTAX      INTEGER
        {
            cleartxt(1),
            dtls(2),
            ipsec(3)
        }

--  802.11i TEXTUAL-CONVENTION
H3cDot11SecIEStatusType ::=   TEXTUAL-CONVENTION
    STATUS      current
    DESCRIPTION
        "To enable the WPA Information element in the beacon and probe
        response frames sent by AP.
        The following values are supported:
        none(1) - both wpa and rsn are disabled,
        rsn(2)  - only enable rsn,
        wpa(3)  - only enable wpa,
        all(4)  - both wpa and rsn are enabled,
        ext(5) - only enable ext."
    SYNTAX      INTEGER
        {
            none(1),
            rsn(2),
            wpa(3),
            all(4),
            ext(5)
        }

H3cDot11CipherType ::=   TEXTUAL-CONVENTION
    STATUS      current
    DESCRIPTION
        "Represents the frame encryption cipher types for
        frames on IEEE 802.11 radio interfaces.
        The MIB defines TC by referring to the 802.11i protocol.
        The following values are supported:
        none(1)     - clear text or no cipher method is configure,
        wep40(2)    - 40-bit WEP key,
        tkip(4)     - WPA Temporal Key encryption,
        aesccmp(16) - WPA AES CCMP encryption,
        wep104(32)  - 104-bit WEP key,
        wpisms4(64) - ext encryption,
        wep128(128) - 128-bit WEP key."
    SYNTAX      INTEGER
        {
            none(1),
            wep40(2),
            tkip(4),
            aesccmp(16),
            wep104(32),
            wpisms4(64),
            wep128(128)
        }

H3cDot11AuthenType ::=   TEXTUAL-CONVENTION
    STATUS      current
    DESCRIPTION
        "Represents the Authentication mode defined by 802.11.
        The following values are supported:
        none(1)         - No authentication mode configured,
        opensystem(2)   - In fact,no real authentication happened,
        sharedkey(3)    - System will use challenge message to
        - authenticate the access user,
        all(4)          - both open system and shared key."
    SYNTAX      INTEGER
        {
            none(1),
            opensystem(2),
            sharedkey(3),
            all(4)
        }

H3cDot11AKMType ::=   TEXTUAL-CONVENTION
    STATUS      current
    DESCRIPTION
        "Represents the key management mode defined by 802.11i.
        The following values are supported:
        none(1)         - No key management mode configured,
        psk(2)          - pre-shared key authentication,
        dot1x(3)        - 802.1x authentication,
        ext(4)         - ext."
    SYNTAX      INTEGER
        {
            none(1),
            psk(2),
            dot1x(3),
            ext(4)
        }

H3cDot11AssocFailType ::=   TEXTUAL-CONVENTION
    STATUS      current
    DESCRIPTION
        "Enumeration of the reasons for station association failure.
        including:
        unknownfailure(1)          - unknown failure,
        toomanyassoc(2)            - too many association,
        invalidie(3)               - information element is invalid,
        unsupportedrate(4)         - rate is not supported,
        unsupportedpwrcap(5)       - power capability is not supported
        unsupportedcap(6)          - capability is not supported"
    SYNTAX      INTEGER
        {
            unknownfailure(1),
            toomanyassoc(2),
            invalidie(3),
            unsupportedrate(4),
            unsupportedpwrcap(5),
            unsupportedcap(6)
        }

H3cDot11AuthorFailType ::=   TEXTUAL-CONVENTION
    STATUS      current
    DESCRIPTION
        "Enumeration of the reasons for station authorization failure.
        including:
        unknownfailure(1)           - unknown failure,
        invalidie(2)                - information element is invalid,
        rsnieversionunsupported(3)  - rsn information element version
        is not supported,
        wpaieversionunsupported(4)  - wpa information element version
        is not supported,
        groupcipherinvalid(5)       - group cipher is invalid,
        pairwisecipherinvalid(6)    - pairwise cipher is invalid,
        akminvalid(7)               - akm is invalid"
    SYNTAX      INTEGER
        {
            unknownfailure(1),
            invalidie(2),
            rsnieversionunsupported(3),
            wpaieversionunsupported(4),
            groupcipherinvalid(5),
            pairwisecipherinvalid(6),
            akminvalid(7)
        }

--  802.11e TEXTUAL-CONVENTION
H3cDot11QosAcType ::=   TEXTUAL-CONVENTION
    STATUS      current
    DESCRIPTION
        "802.11e defines four types of access category, including:
        acbk(1)      - for background access category,
        acbe(2)      - for besteffort access category,
        acvi(3)      - for voice access category,
        acvo(4)      - for video access category
        "
    SYNTAX      INTEGER
        {
            acbk(1),
            acbe(2),
            acvi(3),
            acvo(4)
        }

H3cDot11RadioElementIndex ::= TEXTUAL-CONVENTION
    STATUS      current
    DESCRIPTION
    "Represents index of radio.  For split architecture, It comprises two parts.
    The lowest 8 bits mean radio ID.  The highest 8 bits are reserved.  The
    highest 8 bits stand for AP ID.  The meaning is shown as follows:
    31             23                15             7             0
    + + + + + + + + + + + + + + + + + + + + + + + + + + + + + + + +
    |  reserved   |             AP  ID              | radio ID    |
    + + + + + + + + + + + + + + + + + + + + + + + + + + + + + + + +

    For FAT AP, the type represents ifIndex of radio.
    "
    SYNTAX Unsigned32

-- *****************************************************************************
-- *  Major sections
-- *****************************************************************************

H3cDot11WorkMode ::= TEXTUAL-CONVENTION
    STATUS      current
    DESCRIPTION
    "Work mode of device.
    In normal mode, the device will provide WLAN service.
    In monitor mode, the device will monitor the environment.
    In hybrid mode, the device will provide WLAN service while monitoring the
    environment."
    SYNTAX INTEGER
    {
        normal(1),
        monitor(2),
        hybrid(3)
    }

H3cDot11CirMode ::= TEXTUAL-CONVENTION
    STATUS      current
    DESCRIPTION
    "The mode of committed information rate.
    'static' means station will use the configured CIR seperately.
    For example, if the CIR is 1Mbps, every station can enjoy 1Mbps.
    'dynamic' means all stations will share the configured CIR in common."
    SYNTAX INTEGER
    {
        static(1),
        dynamic(2)
    }

H3cDot11SaIntfDevType ::=   TEXTUAL-CONVENTION
    STATUS      current
    DESCRIPTION
        "The type of interference device."
    SYNTAX INTEGER
        {
            microwave(1),
            microwaveInverter(2),
            bluetooth(3),
            fixedFreqOthers(4),
            fixedFreqCordlessPhone(5),
            fixedFreqVideo(6),
            fixedFreqAudio(7),
            freqHopperOthers(8),
            freqHopperCordlessBase(9),
            freqHopperCordlessNetwork(10),
            freqHopperXbox(11),
            genericInterferer(12)
        }

h3cDot11Common OBJECT IDENTIFIER ::= { h3cDot11 12 }

h3cDot11ElementGroup OBJECT IDENTIFIER ::= { h3cDot11Common 1 }

-- *****************************************************************************
-- *  h3cDot11APElementTable Definition
-- *****************************************************************************
h3cDot11APElementTable OBJECT-TYPE
    SYNTAX      SEQUENCE OF H3cDot11APElementEntry
    MAX-ACCESS  not-accessible
    STATUS      current
    DESCRIPTION
        "This table is used to represent fat AP and AP template on AC
        as one kind of AP element."
    ::= { h3cDot11ElementGroup 1 }

h3cDot11APElementEntry OBJECT-TYPE
    SYNTAX      H3cDot11APElementEntry
    MAX-ACCESS  not-accessible
    STATUS      current
    DESCRIPTION
        "Each entry contains information for each AP element."
    INDEX
        {
            h3cDot11APElementIndex
        }
    ::= { h3cDot11APElementTable 1 }

H3cDot11APElementEntry ::= SEQUENCE
    {
        h3cDot11APElementIndex             Integer32,
        h3cDot11APElementTemplateName      OCTET STRING,
        h3cDot11APElementSerialID          OCTET STRING,
        h3cDot11APElementModelAlias        OCTET STRING
    }

h3cDot11APElementIndex OBJECT-TYPE
    SYNTAX      Integer32
    MAX-ACCESS  not-accessible
    STATUS      current
    DESCRIPTION
        "This object represents the index of AP element."
    ::= { h3cDot11APElementEntry 1 }

h3cDot11APElementTemplateName OBJECT-TYPE
    SYNTAX      OCTET STRING
    MAX-ACCESS  read-only
    STATUS      current
    DESCRIPTION
        "This object represents the template name of AP element."
    ::= { h3cDot11APElementEntry 2 }

h3cDot11APElementSerialID OBJECT-TYPE
    SYNTAX      OCTET STRING
    MAX-ACCESS  read-only
    STATUS      current
    DESCRIPTION
        "This object represents the serial ID of AP element."
    ::= { h3cDot11APElementEntry 3 }

h3cDot11APElementModelAlias OBJECT-TYPE
    SYNTAX      OCTET STRING
    MAX-ACCESS  read-only
    STATUS      current
    DESCRIPTION
        "This object represents the alias of AP element model name."
    ::= { h3cDot11APElementEntry 4 }

-- *****************************************************************************
-- *  End of h3cDot11APElementTable Definition
-- *****************************************************************************
-- *****************************************************************************
-- *  h3cDot11RadioElementTable Definition
-- *****************************************************************************
h3cDot11RadioElementTable OBJECT-TYPE
    SYNTAX      SEQUENCE OF H3cDot11RadioElementEntry
    MAX-ACCESS  not-accessible
    STATUS      current
    DESCRIPTION
        "This table is used to represent the radio element of fat AP and AC."
    ::= { h3cDot11ElementGroup 2 }

h3cDot11RadioElementEntry OBJECT-TYPE
    SYNTAX      H3cDot11RadioElementEntry
    MAX-ACCESS  not-accessible
    STATUS      current
    DESCRIPTION
        "Each entry contains information for each radio element."
    INDEX
        {
            h3cDot11APElementIndex,
            h3cDot11RadioElementRadioNum
        }
    ::= { h3cDot11RadioElementTable 1 }

H3cDot11RadioElementEntry ::= SEQUENCE
    {
        h3cDot11RadioElementRadioNum       Unsigned32,
        h3cDot11RadioElementRadioPolicy    OCTET STRING,
        h3cDot11RadioElementRadioIndex     Unsigned32
    }

h3cDot11RadioElementRadioNum OBJECT-TYPE
    SYNTAX      Unsigned32
    MAX-ACCESS  not-accessible
    STATUS      current
    DESCRIPTION
        "This object represents the number of the radio element."
    ::= { h3cDot11RadioElementEntry 1 }

h3cDot11RadioElementRadioPolicy OBJECT-TYPE
    SYNTAX      OCTET STRING
    MAX-ACCESS  read-write
    STATUS      current
    DESCRIPTION
        "This object represents the radio policy of the radio element."
    ::= { h3cDot11RadioElementEntry 2 }

h3cDot11RadioElementRadioIndex OBJECT-TYPE
    SYNTAX      Unsigned32
    MAX-ACCESS  read-only
    STATUS      current
    DESCRIPTION
        "This object represents the index of the radio element.
        On AC, the higher 24 bits stand for the AP index,
        and the last 8 bits stand for the radio index.
        On fat AP, the index stands for the interface index of radio
        interface."
    ::= { h3cDot11RadioElementEntry 3 }

-- *****************************************************************************
-- *  End of h3cDot11RadioElementTable Definition
-- *****************************************************************************
END
