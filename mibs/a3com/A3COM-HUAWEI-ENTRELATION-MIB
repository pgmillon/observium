-- =================================================================
-- Copyright (C) 2001-2002 by  HUAWEI-3COM TECHNOLOGIES. All rights reserved.
--
-- Description:HUAWEI-3COM ENTITY RELATION MIB
-- Version: V1.2
-- History:
--   V1.0(Initial version) 19th Aug 2004
--   V1.1 2004-09-10 Exchange MIB objects' sequence, including h3cEntRelationType 
--                   and h3cEntityIndex.
--                   Change subidentifier of h3cEntRelationConformance from 3 to 2.
--   V1.2 2004-10-12 updated by gaolong
--        Remove h3cEntityIndex, h3cEntRelationType from h3cEntRelationGroup 
--        because they are not-accessible objects.
-- =================================================================
--

	A3COM-HUAWEI-ENTRELATION-MIB DEFINITIONS ::= BEGIN
 
		IMPORTS
			PhysicalIndex			
				FROM ENTITY-MIB			
			h3cCommon			
				FROM A3COM-HUAWEI-OID-MIB			
			OBJECT-GROUP, MODULE-COMPLIANCE			
				FROM SNMPv2-CONF			
			OBJECT-TYPE, MODULE-IDENTITY			
				FROM SNMPv2-SMI			
			TEXTUAL-CONVENTION			
				FROM SNMPv2-TC;
	
	

		h3cEntityRelation MODULE-IDENTITY 
			LAST-UPDATED "200408190000Z"
			ORGANIZATION 
				"Huawei-3com Technologies co.,Ltd."
			CONTACT-INFO 
				"Platform Team Beijing Institute Huawei-3com Tech, Inc.
				Http://www.huawei-3com.com                                       
				E-mail:support@huawei-3com.com "
			DESCRIPTION 
				"The private mib file includes the general relation information
				information of entities.
				Entity MIB is used to express the physical location of the physical
				entities. Other relations, such as stack port pair and combo port 
				pair, are not suitable to be implemented in Entity MIB. So this mib is 
				used to  express these relations. "
			::= { h3cCommon 15 }
		
	
	
--  Textual conventions
-- 
		H3cEntRelationType ::= TEXTUAL-CONVENTION
			STATUS current
			DESCRIPTION 
				"entRelationType describe the relation type of the two entities
				(indicated by entityIndex and relatedEntityIndex) .
				stackport: this port is a stack port. 
				entityIndex is the default uplinkport index, 
				and relatedEntityIndex is the default downlinkport index.
				comboport: this port is a combo port. 
				entityIndex is the default active port index, 
				and relatedEntityIndex is the default inactive port index."
			SYNTAX INTEGER
				{
				stackport(1),
				comboport(2)
				}
			
	

	
--  Node definitions
-- 
		h3cEntRelationObjects OBJECT IDENTIFIER ::= { h3cEntityRelation 1 }
		
--    MIB contains four groups      
		h3cEntRelation OBJECT IDENTIFIER ::= { h3cEntRelationObjects 1 }
		
		h3cEntRelationTable OBJECT-TYPE
			SYNTAX SEQUENCE OF H3cEntRelationEntry
			MAX-ACCESS not-accessible
			STATUS current
			DESCRIPTION
				"Entity MIB is used to express the physical location of 
				the physical entities. Other relations, such as stack 
				port pair and combo port pair, are not suitable to be 
				implemented in Entity MIB. This MIB is used to express 
				these relations. "
			::= { h3cEntRelation 1 }
		
		h3cEntRelationEntry OBJECT-TYPE
			SYNTAX H3cEntRelationEntry
			MAX-ACCESS not-accessible
			STATUS current
			DESCRIPTION
				"The information about a particular physical entity."
			INDEX { h3cEntRelationType, h3cEntityIndex, h3cRelatedEntityIndex }
			::= { h3cEntRelationTable 1 }
		
		H3cEntRelationEntry ::=
			SEQUENCE { 
				h3cEntRelationType
					H3cEntRelationType,
				h3cEntityIndex
					PhysicalIndex,
				h3cRelatedEntityIndex
					PhysicalIndex
			 }

		h3cEntRelationType OBJECT-TYPE
			SYNTAX H3cEntRelationType
			MAX-ACCESS not-accessible
			STATUS current
			DESCRIPTION
				"The index of h3cEntRelationTable.
				entRelationType describe the relation type of the two 
				entities(indicated by entityIndex and relatedEntityIndex) "
			::= { h3cEntRelationEntry 1 }
		
		h3cEntityIndex OBJECT-TYPE
			SYNTAX PhysicalIndex
			MAX-ACCESS not-accessible
			STATUS current
			DESCRIPTION
				"The index of h3cEntRelationTable.
				entityIndex is the index of the entity.
				This index is identical to entPhysicalIndex in ENTITY-MIB"
			::= { h3cEntRelationEntry 2 }
		
		h3cRelatedEntityIndex OBJECT-TYPE
			SYNTAX PhysicalIndex
			MAX-ACCESS read-only
			STATUS current
			DESCRIPTION
				"The index of h3cEntRelationTable.
				relatedEntityIndex is the entity index that entityIndex related to, 
				This index is identical to entPhysicalIndex in ENTITY-MIB"
			::= { h3cEntRelationEntry 3 }
		
--    Conformance and Compliance
		h3cEntRelationConformance OBJECT IDENTIFIER ::= { h3cEntityRelation 2 }
		
		h3cEntRelationCompliances OBJECT IDENTIFIER ::= { h3cEntRelationConformance 1 }
		

-- this module
		h3cEntRelationCompliance MODULE-COMPLIANCE
			STATUS current
			DESCRIPTION 
				"The compliance statement for systems supporting this MIB."
			MODULE -- this module
				MANDATORY-GROUPS { h3cEntRelationGroup }
			::= { h3cEntRelationCompliances 1 }
		
		h3cEntRelationGroups OBJECT IDENTIFIER ::= { h3cEntRelationConformance 2 }
		
		h3cEntRelationGroup OBJECT-GROUP
			OBJECTS { h3cRelatedEntityIndex }
			STATUS current
			DESCRIPTION 
				"Standard HUAWEI Entity Relation group."
			::= { h3cEntRelationGroups 1 }
		
	
	END
