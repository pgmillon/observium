-- =================================================================
-- Copyright (c) 2004-2011 Hangzhou H3C Tech. Co., Ltd. All rights reserved.
--
-- Description: Description Of Portal
-- Reference:
-- Version: V1.4
-- History:
--   V1.0 2008-12-30, Created by d04528
--   V1.1 2009-4-30, Modified by h02978
--        Added node h3cPortalServerPort
--        Added table h3cPortalIfInfoTable, including the following nodes,
--            h3cPortalAuthReqNumber
--            h3cPortalAuthSuccNumber
--            h3cPortalAuthFailNumber
--        Added trap node h3cPortalServerGet
--   V1.2 2010-5-31, Modified by y07111
--        Added table h3cPortalIfServerTable, including the following nodes,
--            h3cPortalIfServerIndex
--            h3cPortalIfServerUrl
--            h3cPortalIfServerRowStatus
--        Added h3cPortalNasId
--   V1.3 2010-11-8, Modified by y07111
--        Added table h3cPortalStatistic,including the following nodes,
--        h3cPortalStatAuthReq
--        h3cPortalStatAckLogout
--        h3cPortalStatNotifyLogout
--        h3cPortalStatChallengeTimeout
--        h3cPortalStatChallengeBusy
--        h3cPortalStatChallengeFail
--        h3cPortalStatAuthTimeout
--        h3cPortalStatAuthFail
--        h3cPortalStatPwdError
--        h3cPortalStatAuthBusy
--        h3cPortalStatAuthDisordered
--        h3cPortalStatAuthUnknownError
--   V1.4 2011-08-18, Added by liqian 04379
--        Added table h3cPortalIfVlanNasIDTable, including the following nodes,
--        h3cPortalIfVlanNasIDIfIndex
--        h3cPortalIfVlanNasIDVlanID
--        h3cPortalIfVlanNasIDNasID
--        Added table h3cPortalSSIDFreeRuleTable, including the following nodes,
--        h3cPortalSSIDFreeRuleIndex
--        h3cPortalSSIDFreeRuleSrcSSID
--        h3cPortalSSIDFreeRuleRowStatus
--        Added table h3cPortalMacTriggerSrvTable, including the following nodes,
--        h3cPortalMacTriggerSrvIndex
--        h3cPortalMacTriggerSrvIPAddrType
--        h3cPortalMacTriggerSrvIP
--        h3cPortalMacTriggerSrvPort
--        h3cPortalMacTriggerSrvRowStatus
--        Added table h3cPortalMacTriggerOnIfTable, including the following nodes,
--        h3cPortalMacTriggerOnIfIfIndex
--        h3cPortalMacTriggerOnIfDetctFlowPeriod
--        h3cPortalMacTriggerOnIfThresholdFlow
--        h3cPortalMacTriggerOnIfRowStatus
--        Added table h3cPortalPktStatistic ,including the following nodes,
--        h3cPortalPktStaReqAuthNum
--        h3cPortalPktStaAckAuthSuccess
--        h3cPortalPktStaAckAuthReject
--        h3cPortalPktStaAckAuthEstablish
--        h3cPortalPktStaAckAuthBusy
--        h3cPortalPktStaAckAuthAuthFail
--        h3cPortalPktStaReqChallengeNum
--        h3cPortalPktStaAckChallengeSuccess
--        h3cPortalPktStaAckChallengeReject
--        h3cPortalPktStaAckChallengeEstablish
--        h3cPortalPktStaAckChallengeBusy
--        h3cPortalPktStaAckChallengeAuthFail
--        2011-11-8, Added by q04356
--        Added table h3cPortalTrapVarObjects, including the following nodes,
--        h3cPortalFirstTrapTime
--        Added table h3cPortalFreeRuleTable, including the following nodes,
--        h3cPortalFreeRuleIndex
--        h3cPortalFreeRuleSrcIfIndex
--        h3cPortalFreeRuleSrcVlanID
--        h3cPortalFreeRuleSrcMac
--        h3cPortalFreeRuleAddrType
--        h3cPortalFreeRuleSrcAddr
--        h3cPortalFreeRuleSrcPrefix
--        h3cPortalFreeRuleDstAddr
--        h3cPortalFreeRuleDstPrefix
--        h3cPortalFreeRuleProtocol
--        h3cPortalFreeRuleSrcPort
--        h3cPortalFreeRuleDstPort
--        h3cPortalFreeRuleRowStatus
--        Added table h3cPortalForbiddenRuleTable, including the following nodes,
--        h3cPortalForbiddenRuleIndex
--        h3cPortalForbiddenRuleSrcIfIndex
--        h3cPortalForbiddenRuleSrcVlanID
--        h3cPortalForbiddenRuleSrcMac
--        h3cPortalForbiddenRuleAddrType
--        h3cPortalForbiddenRuleSrcAddr
--        h3cPortalForbiddenRuleSrcPrefix
--        h3cPortalForbiddenRuleDstAddr
--        h3cPortalForbiddenRuleDstPrefix
--        h3cPortalForbiddenRuleProtocol
--        h3cPortalForbiddenRuleSrcPort
--        h3cPortalForbiddenRuleDstPort
--        h3cPortalForbiddenRuleRowStatus
--        Added node in table h3cPortalStatistic
--        h3cPortalStatAuthResp
--        h3cPortalStatChallengeReq
--        h3cPortalStatChallengeResp
-- =================================================================
A3COM-HUAWEI-PORTAL-MIB DEFINITIONS ::= BEGIN
IMPORTS
    h3cCommon
        FROM A3COM-HUAWEI-OID-MIB
    OBJECT-TYPE, NOTIFICATION-TYPE, MODULE-IDENTITY, Integer32, Counter64, Unsigned32,
    TimeTicks
        FROM SNMPv2-SMI
    RowStatus, TruthValue, MacAddress
        FROM SNMPv2-TC
    ifIndex, InterfaceIndex
        FROM IF-MIB
    InetAddressPrefixLength, InetAddressType, InetAddress
        FROM INET-ADDRESS-MIB;

h3cPortal MODULE-IDENTITY
    LAST-UPDATED "201111080000Z"            -- Nov 8th, 2011 at 00:00 GMT
    ORGANIZATION
        "Hangzhou H3C Tech. Co., Ltd."
    CONTACT-INFO
        "Platform Team Hangzhou H3C Tech. Co., Ltd.
        Hai-Dian District Beijing P.R. China
        http://www.h3c.com
        Zip:100085
        "
    DESCRIPTION
        "The MIB module is used for managing portal."
    ::= { h3cCommon 99 }


h3cPortalConfig OBJECT IDENTIFIER ::= { h3cPortal 1 }

--
-- PORTAL MAX USER NUMBER
--

h3cPortalMaxUserNumber OBJECT-TYPE
    SYNTAX      Integer32
    MAX-ACCESS  read-write
    STATUS      current
    DESCRIPTION
        "Specify the maximum number of online users,
        the value to be set should meet the following two conditions:
        1. Less than or equal to h3cPortalUserNumberUpperLimit.
        2. Greater than or equal to one.

        The default value is equal to h3cPortalUserNumberUpperLimit."
    ::= { h3cPortalConfig 1 }

--
-- PORTAL CURRENT USER NUMBER
--

h3cPortalCurrentUserNumber OBJECT-TYPE
    SYNTAX      Integer32
    MAX-ACCESS  read-only
    STATUS      current
    DESCRIPTION
        "The current number of users connecting to the portal."
    ::= { h3cPortalConfig 2 }

--
-- PORTAL STATUS
--

h3cPortalStatus OBJECT-TYPE
    SYNTAX      INTEGER
    {
         enabled(1),
         disabled(2)
    }
    MAX-ACCESS  read-only
    STATUS      current
    DESCRIPTION
        "It indicates the portal status.
         enabled:
            Portal is enabled on one or more interfaces.
         disabled:
            Portal is not enabled on any interface."
    ::= { h3cPortalConfig 3 }

--
-- PORTAL USER NUMBER_UPPER_LIMIT
--

h3cPortalUserNumberUpperLimit OBJECT-TYPE
    SYNTAX      Integer32
    MAX-ACCESS  read-only
    STATUS      current
    DESCRIPTION
        "The upper limit of h3cPortalMaxUserNumber."
    ::= { h3cPortalConfig 4 }

--
-- PORTAL NAS-ID Config
--
h3cPortalNasId OBJECT-TYPE
    SYNTAX      OCTET STRING
    MAX-ACCESS  read-write
    STATUS      current
    DESCRIPTION
        "The nas id of this device."
    ::= { h3cPortalConfig 5 }

--
-- PORTAL TABLES
--

h3cPortalTables OBJECT IDENTIFIER ::= { h3cPortal 2 }


--
-- PORTAL server table
--
h3cPortalServerTable OBJECT-TYPE
    SYNTAX      SEQUENCE OF H3cPortalServerEntry
    MAX-ACCESS  not-accessible
    STATUS      current
    DESCRIPTION
        "This table defines the name and URL of portal server.
        It can not be created and destroyed by MIB."
    ::= { h3cPortalTables 1 }

h3cPortalServerEntry OBJECT-TYPE
    SYNTAX      H3cPortalServerEntry
    MAX-ACCESS  not-accessible
    STATUS      current
    DESCRIPTION
        "There is a row in this table for each name and URL of portal server.
        It is indexed using the object h3cPortalServerName."
    INDEX
        {
            h3cPortalServerName
        }
    ::= { h3cPortalServerTable 1 }


H3cPortalServerEntry ::= SEQUENCE
    {
        h3cPortalServerName               OCTET STRING,
        h3cPortalServerUrl                OCTET STRING,
        h3cPortalServerPort               Integer32
    }

h3cPortalServerName OBJECT-TYPE
    SYNTAX      OCTET STRING (SIZE (1..32))
    MAX-ACCESS  accessible-for-notify
    STATUS      current
    DESCRIPTION
        "It is the index of the table of h3cPortalServerTable, it shows
        the name of the portal server."
    ::= { h3cPortalServerEntry 1 }

h3cPortalServerUrl OBJECT-TYPE
    SYNTAX      OCTET STRING (SIZE (1..127))
    MAX-ACCESS  read-write
    STATUS      current
    DESCRIPTION
        "It shows the uniform resource locator to the portal server.
        Users which have not logon to portal will be redirected to the
        portal server according to h3cPortalServerUrl.

        The value is consisted of protocol, IP address and relative path.
        For example: HTTP://10.1.1.1/portal

        It is not configurable when the portal server has been enabled."
    ::= { h3cPortalServerEntry 2 }

h3cPortalServerPort OBJECT-TYPE
    SYNTAX      Integer32 (1..65534)
    MAX-ACCESS  read-write
    STATUS      current
    DESCRIPTION
        "It shows the UDP port of the portal server.

        The port will be used when client sends packets to portal server.
        Default value is 50100.

        It is not configurable when the portal server has been enabled."
    ::= { h3cPortalServerEntry 3 }

--
-- PORTAL If Info Table
--
h3cPortalIfInfoTable OBJECT-TYPE
    SYNTAX      SEQUENCE OF H3cPortalIfInfoEntry
    MAX-ACCESS  not-accessible
    STATUS      current
    DESCRIPTION
        "This table describes the portal information on some interface."
    ::= { h3cPortalTables 2 }

h3cPortalIfInfoEntry OBJECT-TYPE
    SYNTAX      H3cPortalIfInfoEntry
    MAX-ACCESS  not-accessible
    STATUS      current
    DESCRIPTION
        "There is a row in this table for a interface on which
        portal has been enabled.
        It is indexed using the object ifIndex."
    INDEX
        {
            ifIndex
        }
    ::= { h3cPortalIfInfoTable 1 }


H3cPortalIfInfoEntry ::= SEQUENCE
    {
        h3cPortalAuthReqNumber            Integer32,
        h3cPortalAuthSuccNumber           Integer32,
        h3cPortalAuthFailNumber           Integer32
    }

h3cPortalAuthReqNumber OBJECT-TYPE
    SYNTAX      Integer32
    MAX-ACCESS  read-only
    STATUS      current
    DESCRIPTION
        "It shows the number of authentication request messages
        which are sent by portal module to AAA module."
    ::= { h3cPortalIfInfoEntry 1 }


h3cPortalAuthSuccNumber OBJECT-TYPE
    SYNTAX      Integer32
    MAX-ACCESS  read-only
    STATUS      current
    DESCRIPTION
        "It shows the number of authentication success response messages
        which are sent by AAA module to portal module."
    ::= { h3cPortalIfInfoEntry 2 }

h3cPortalAuthFailNumber OBJECT-TYPE
    SYNTAX      Integer32
    MAX-ACCESS  read-only
    STATUS      current
    DESCRIPTION
        "It shows the number of authentication failure response messages
        which are sent by AAA module to portal module."
    ::= { h3cPortalIfInfoEntry 3 }

--
-- PORTAL If Config Table
--
h3cPortalIfServerTable OBJECT-TYPE
    SYNTAX      SEQUENCE OF H3cPortalIfServerEntry
    MAX-ACCESS  not-accessible
    STATUS      current
    DESCRIPTION
        "This table describes the portal information on some interface."
    ::= { h3cPortalTables 3 }

h3cPortalIfServerEntry OBJECT-TYPE
    SYNTAX      H3cPortalIfServerEntry
    MAX-ACCESS  not-accessible
    STATUS      current
    DESCRIPTION
        "There is a row in this table for a interface on which
        portal has been enabled.
        It is indexed using the object ifIndex."
    INDEX
        {
            h3cPortalIfServerIndex
        }
    ::= { h3cPortalIfServerTable 1 }

H3cPortalIfServerEntry ::= SEQUENCE
    {
        h3cPortalIfServerIndex                   Integer32,
        h3cPortalIfServerUrl                     OCTET STRING,
        h3cPortalIfServerRowStatus               RowStatus
    }

h3cPortalIfServerIndex  OBJECT-TYPE
    SYNTAX      Integer32 (0..2147483647)
    MAX-ACCESS  not-accessible
    STATUS      current
    DESCRIPTION
        "It is the index of the table of h3cIfPtServerTable, it shows
        the index of the portal server."
    ::={ h3cPortalIfServerEntry 1 }

h3cPortalIfServerUrl OBJECT-TYPE
    SYNTAX      OCTET STRING
    MAX-ACCESS  read-create
    STATUS      current
    DESCRIPTION
        "It shows the uniform resource locator to the portal server.
        Users which have not logon to portal will be redirected to the
        portal server according to h3cPortalServerIfUrl.
        The value is consisted of protocol, IP address and relative path.
        For example: HTTP://10.1.1.1/portal
        It is not configurable when the portal server has been enabled."
    ::= { h3cPortalIfServerEntry 2 }

h3cPortalIfServerRowStatus OBJECT-TYPE
    SYNTAX   RowStatus
    MAX-ACCESS  read-create
    STATUS      current
    DESCRIPTION
        "This object is responsible for managing the creation, deletion and
        modification of rows, which support active status and CreateAndGo,
        Destroy operation.  To create a new row, portal server must be specified.
        To destroy an existent row, the portal server MUST NOT be referred by
        interface."
    ::= { h3cPortalIfServerEntry 3 }

-- PORTAL Vlan Not binding NAS ID Table
h3cPortalIfVlanNasIDTable OBJECT-TYPE
    SYNTAX      SEQUENCE OF H3cPortalIfVlanNasIDEntry
    MAX-ACCESS  not-accessible
    STATUS      current
    DESCRIPTION
        "This table describes the interface on which portal has been enabled,
        the Vlan that the interface belongs to and the NAS ID to which the Vlan
        is bound."
    ::= { h3cPortalTables 4 }

h3cPortalIfVlanNasIDEntry OBJECT-TYPE
    SYNTAX      H3cPortalIfVlanNasIDEntry
    MAX-ACCESS  not-accessible
    STATUS      current
    DESCRIPTION
        "There is a row in this table for a interface on which portal has been
        enabled, the Vlan that the interface belongs to and the NAS ID to which
        the Vlan is bound.
        It is indexed using the object ifIndex and Vlan that the interface
        belongs to."
    INDEX
        {
            h3cPortalIfVlanNasIDIfIndex,
            h3cPortalIfVlanNasIDVlanID
        }
    ::= { h3cPortalIfVlanNasIDTable 1 }

H3cPortalIfVlanNasIDEntry ::= SEQUENCE
    {
        h3cPortalIfVlanNasIDIfIndex         InterfaceIndex,
        h3cPortalIfVlanNasIDVlanID          Integer32,
        h3cPortalIfVlanNasIDNasID           OCTET STRING
    }

h3cPortalIfVlanNasIDIfIndex  OBJECT-TYPE
    SYNTAX      InterfaceIndex
    MAX-ACCESS  not-accessible
    STATUS      current
    DESCRIPTION
        "It is the index of the table of h3cPortalIfVlanNasIDTable, it shows
        the interface on which portal has been enabled."
    ::={ h3cPortalIfVlanNasIDEntry 1 }

h3cPortalIfVlanNasIDVlanID OBJECT-TYPE
    SYNTAX      Integer32 (1..2147483647)
    MAX-ACCESS  not-accessible
    STATUS      current
    DESCRIPTION
        "It is the index of the table of h3cPortalIfVlanNasIDTable, it shows
        the Vlan that the interface belongs to."
    ::= { h3cPortalIfVlanNasIDEntry 2 }

h3cPortalIfVlanNasIDNasID OBJECT-TYPE
    SYNTAX      OCTET STRING (SIZE(0..64))
    MAX-ACCESS  read-only
    STATUS      current
    DESCRIPTION
        "It is the NAS ID to which the Vlan is bound to."
    ::= { h3cPortalIfVlanNasIDEntry 3 }

--
-- PORTAL SSID Free-rule Config Table
--

h3cPortalSSIDFreeRuleTable OBJECT-TYPE
    SYNTAX      SEQUENCE OF H3cPortalSSIDFreeRuleEntry
    MAX-ACCESS  not-accessible
    STATUS      current
    DESCRIPTION
        "This table describes SSID portal-free rule(s) allows specified users
        to access specified external websites without portal authentication."
    ::= { h3cPortalTables 5 }

h3cPortalSSIDFreeRuleEntry OBJECT-TYPE
    SYNTAX      H3cPortalSSIDFreeRuleEntry
    MAX-ACCESS  not-accessible
    STATUS      current
    DESCRIPTION
        "There is a row in this table for SSID portal-free rule.
        It is indexed using the object Index."
    INDEX
        {
            h3cPortalSSIDFreeRuleIndex
        }
    ::= { h3cPortalSSIDFreeRuleTable 1 }

H3cPortalSSIDFreeRuleEntry ::= SEQUENCE
    {
        h3cPortalSSIDFreeRuleIndex                   Integer32,
        h3cPortalSSIDFreeRuleSrcSSID                 OCTET STRING,
        h3cPortalSSIDFreeRuleRowStatus               RowStatus
    }

h3cPortalSSIDFreeRuleIndex  OBJECT-TYPE
    SYNTAX      Integer32 (0..2147483647)
    MAX-ACCESS  not-accessible
    STATUS      current
    DESCRIPTION
        "It is the index of the table of h3cPortalSSIDFreeRuleTable, it shows
        the index of the SSID portal-free rule."
    ::={ h3cPortalSSIDFreeRuleEntry 1 }

h3cPortalSSIDFreeRuleSrcSSID  OBJECT-TYPE
    SYNTAX      OCTET STRING (SIZE(1..128))
    MAX-ACCESS  read-create
    STATUS      current
    DESCRIPTION
        "The SSID match against the packet's source SSID."
    ::={ h3cPortalSSIDFreeRuleEntry 2 }

h3cPortalSSIDFreeRuleRowStatus OBJECT-TYPE
    SYNTAX      RowStatus
    MAX-ACCESS  read-create
    STATUS      current
    DESCRIPTION
        "This object is responsible for managing the creation, deletion and
        modification of rows, which support active status and CreateAndGo,
        Destroy operation."
    ::= { h3cPortalSSIDFreeRuleEntry 3 }

--
-- PORTAL MAC Trigger Server
--

h3cPortalMacTriggerSrvTable OBJECT-TYPE
    SYNTAX      SEQUENCE OF H3cPortalMacTriggerSrvEntry
    MAX-ACCESS  not-accessible
    STATUS      current
    DESCRIPTION
        "This table describes the configration of MAC Trigger Portal server."
    ::= { h3cPortalTables 6 }

h3cPortalMacTriggerSrvEntry OBJECT-TYPE
    SYNTAX      H3cPortalMacTriggerSrvEntry
    MAX-ACCESS  not-accessible
    STATUS      current
    DESCRIPTION
        "There is a row in the table for MAC Trigger Portal server.
        It is indexed using the object Index."
    INDEX
        {
            h3cPortalMacTriggerSrvIndex
        }
    ::= { h3cPortalMacTriggerSrvTable 1 }

H3cPortalMacTriggerSrvEntry ::= SEQUENCE
    {
        h3cPortalMacTriggerSrvIndex              Integer32,
        h3cPortalMacTriggerSrvIPAddrType         InetAddressType,
        h3cPortalMacTriggerSrvIP                 InetAddress,
        h3cPortalMacTriggerSrvPort               Integer32,
        h3cPortalMacTriggerSrvRowStatus          RowStatus
    }

h3cPortalMacTriggerSrvIndex  OBJECT-TYPE
    SYNTAX      Integer32 (0..2147483647)
    MAX-ACCESS  not-accessible
    STATUS      current
    DESCRIPTION
        "It is the index of the table of h3cPortalMacTriggerSrvTable, it shows
        the index of the MAC Trigger Portal server."
    ::={ h3cPortalMacTriggerSrvEntry 1 }

h3cPortalMacTriggerSrvIPAddrType  OBJECT-TYPE
    SYNTAX      InetAddressType
    MAX-ACCESS  read-create
    STATUS      current
    DESCRIPTION
        "The type of MAC Trigger Portal server IP address.  While
       other types of addresses are defined in the InetAddressType
       textual convention, and DNS names, a classifier can only look at
       packets on the wire."
    ::={ h3cPortalMacTriggerSrvEntry 2 }

h3cPortalMacTriggerSrvIP OBJECT-TYPE
    SYNTAX      InetAddress
    MAX-ACCESS  read-create
    STATUS      current
    DESCRIPTION
        "It shows the IP address of MAC Trigger Portal server."
    ::= { h3cPortalMacTriggerSrvEntry 3 }

h3cPortalMacTriggerSrvPort OBJECT-TYPE
    SYNTAX      Integer32 (1..65534)
    MAX-ACCESS  read-create
    STATUS      current
    DESCRIPTION
        "It shows the UDP port of MAC Trigger Portal server.
        The port will be used when client sends packets to MAC Trigger Portal server.
        Default value is 50100."
    ::= { h3cPortalMacTriggerSrvEntry 4 }

h3cPortalMacTriggerSrvRowStatus OBJECT-TYPE
    SYNTAX      RowStatus
    MAX-ACCESS  read-create
    STATUS      current
    DESCRIPTION
        "This object is responsible for managing the creation, deletion and
        modification of rows, which support active status and CreateAndGo,
        Destroy operation."
    ::= { h3cPortalMacTriggerSrvEntry 5 }

--
-- PORTAL Eanble MAC Trigger on interface
--

h3cPortalMacTriggerOnIfTable OBJECT-TYPE
    SYNTAX      SEQUENCE OF H3cPortalMacTriggerOnIfEntry
    MAX-ACCESS  not-accessible
    STATUS      current
    DESCRIPTION
        "This table describes the configration of Portal MAC Trigger on
        interface."
    ::= { h3cPortalTables 7 }

h3cPortalMacTriggerOnIfEntry OBJECT-TYPE
    SYNTAX      H3cPortalMacTriggerOnIfEntry
    MAX-ACCESS  not-accessible
    STATUS      current
    DESCRIPTION
        "There is a row in the table for Portal MAC Trigger configuration on
        interface.  It is indexed using the object Index."
    INDEX
        {
            h3cPortalMacTriggerOnIfIfIndex
        }
    ::= { h3cPortalMacTriggerOnIfTable 1 }

H3cPortalMacTriggerOnIfEntry ::= SEQUENCE
    {
        h3cPortalMacTriggerOnIfIfIndex               InterfaceIndex,
        h3cPortalMacTriggerOnIfDetctFlowPeriod       Integer32,
        h3cPortalMacTriggerOnIfThresholdFlow         Unsigned32,
        h3cPortalMacTriggerOnIfRowStatus             RowStatus
    }

h3cPortalMacTriggerOnIfIfIndex  OBJECT-TYPE
    SYNTAX      InterfaceIndex
    MAX-ACCESS  not-accessible
    STATUS      current
    DESCRIPTION
        "It is the interface index and the index of
        h3cPortalMacTriggerOnIfTable."
    ::={ h3cPortalMacTriggerOnIfEntry 1 }

h3cPortalMacTriggerOnIfDetctFlowPeriod  OBJECT-TYPE
    SYNTAX      Integer32
    MAX-ACCESS  read-create
    STATUS      current
    DESCRIPTION
        "It shows the period of detecting the user flow when
        MAC Trigger and Portal is enabled.  The unit is second."
    ::={ h3cPortalMacTriggerOnIfEntry 2 }

h3cPortalMacTriggerOnIfThresholdFlow  OBJECT-TYPE
    SYNTAX      Unsigned32
    MAX-ACCESS  read-create
    STATUS      current
    DESCRIPTION
        "It shows the threshold flow of the user to triggering authentication
        when MAC Trigger and Portal is enabled.  The unit is byte."
    ::={ h3cPortalMacTriggerOnIfEntry 3 }

h3cPortalMacTriggerOnIfRowStatus OBJECT-TYPE
    SYNTAX      RowStatus
    MAX-ACCESS  read-create
    STATUS      current
    DESCRIPTION
        "This object is responsible for managing the creation, deletion and
        modification of rows, which support active status and CreateAndGo,
        Destroy operation."
    ::= { h3cPortalMacTriggerOnIfEntry 4 }

--
-- PORTAL Free-rule Config Table
--

h3cPortalFreeRuleTable OBJECT-TYPE
    SYNTAX      SEQUENCE OF H3cPortalFreeRuleEntry
    MAX-ACCESS  not-accessible
    STATUS      current
    DESCRIPTION
        "This table describes portal-free rule(s) allows specified users to
         access specified external websites without portal authentication."
    ::= { h3cPortalTables 8 }

h3cPortalFreeRuleEntry OBJECT-TYPE
    SYNTAX      H3cPortalFreeRuleEntry
    MAX-ACCESS  not-accessible
    STATUS      current
    DESCRIPTION
        "There is a row in this table for portal-free rule.
        It is indexed using the object Index."
    INDEX
        {
            h3cPortalFreeRuleIndex
        }
    ::= { h3cPortalFreeRuleTable 1 }

H3cPortalFreeRuleEntry ::= SEQUENCE
    {
	h3cPortalFreeRuleIndex                   Integer32,
        h3cPortalFreeRuleSrcIfIndex              InterfaceIndex,
        h3cPortalFreeRuleSrcVlanID               Integer32,
        h3cPortalFreeRuleSrcMac                  MacAddress,
        h3cPortalFreeRuleAddrType                InetAddressType,
        h3cPortalFreeRuleSrcAddr                 InetAddress,
        h3cPortalFreeRuleSrcPrefix               InetAddressPrefixLength,
        h3cPortalFreeRuleDstAddr                 InetAddress,
        h3cPortalFreeRuleDstPrefix               InetAddressPrefixLength,
        h3cPortalFreeRuleProtocol                INTEGER,
        h3cPortalFreeRuleSrcPort                 Integer32,
        h3cPortalFreeRuleDstPort                 Integer32,
        h3cPortalFreeRuleRowStatus               RowStatus
    }

h3cPortalFreeRuleIndex  OBJECT-TYPE
    SYNTAX      Integer32 (0..2147483647)
    MAX-ACCESS  not-accessible
    STATUS      current
    DESCRIPTION
        "It is the index of the table of h3cPortalFreeRuleTable, it shows
        the index of the portal-free rule."
    ::={ h3cPortalFreeRuleEntry 1 }

h3cPortalFreeRuleSrcIfIndex  OBJECT-TYPE
    SYNTAX      InterfaceIndex
    MAX-ACCESS  read-create
    STATUS      current
    DESCRIPTION
        "The index of source interface."
    ::={ h3cPortalFreeRuleEntry 2 }

h3cPortalFreeRuleSrcVlanID  OBJECT-TYPE
    SYNTAX      Integer32
    MAX-ACCESS  read-create
    STATUS      current
    DESCRIPTION
        "The identification of source vlan."
    ::={ h3cPortalFreeRuleEntry 3 }

h3cPortalFreeRuleSrcMac  OBJECT-TYPE
    SYNTAX      MacAddress
    MAX-ACCESS  read-create
    STATUS      current
    DESCRIPTION
        "The MAC address to match against the packet's source MAC address."
    ::={ h3cPortalFreeRuleEntry 4 }

h3cPortalFreeRuleAddrType  OBJECT-TYPE
    SYNTAX      InetAddressType
    MAX-ACCESS  read-create
    STATUS      current
    DESCRIPTION
        "The type of IP address used by this classifier entry.  While
       other types of addresses are defined in the InetAddressType
       textual convention, and DNS names, a classifier can only look at
       packets on the wire."
    ::={ h3cPortalFreeRuleEntry 5 }

h3cPortalFreeRuleSrcAddr  OBJECT-TYPE
    SYNTAX      InetAddress
    MAX-ACCESS  read-create
    STATUS      current
    DESCRIPTION
        "The IP address to match against the packet's source IP
       address. This may be a DNS name or an IPv4 or IPv6
       prefix.  h3cPortalFreeRuleSrcPrefix indicates the
       number of bits that are relevant."
    ::={ h3cPortalFreeRuleEntry 6 }

h3cPortalFreeRuleSrcPrefix  OBJECT-TYPE
    SYNTAX      InetAddressPrefixLength
    MAX-ACCESS  read-create
    STATUS      current
    DESCRIPTION
        "The length of the CIDR Prefix carried in
       h3cPortalFreeRuleSrcAddr. In IPv4 addresses, a length of 0
       indicates a match of any address; a length of 32 indicates a
       match of a single host address, and a length between 0 and 32
       indicates the use of a CIDR Prefix. IPv6 is similar, except that
       prefix lengths range from 0..128."
    ::={ h3cPortalFreeRuleEntry 7 }

h3cPortalFreeRuleDstAddr  OBJECT-TYPE
    SYNTAX      InetAddress
    MAX-ACCESS  read-create
    STATUS      current
    DESCRIPTION
        "The IP address to match against the packet's destination IP
       address. This may be a DNS name or an IPv4 or IPv6
       prefix.  h3cPortalFreeRuleDstPrefix indicates the
       number of bits that are relevant."
    ::={ h3cPortalFreeRuleEntry 8 }

h3cPortalFreeRuleDstPrefix  OBJECT-TYPE
    SYNTAX      InetAddressPrefixLength
    MAX-ACCESS  read-create
    STATUS      current
    DESCRIPTION
        "The length of the CIDR Prefix carried in
       h3cPortalFreeRuleDstAddr. In IPv4 addresses, a length of 0
       indicates a match of any address; a length of 32 indicates a
       match of a single host address, and a length between 0 and 32
       indicates the use of a CIDR Prefix. IPv6 is similar, except that
       prefix lengths range from 0..128."
    ::={ h3cPortalFreeRuleEntry 9 }

h3cPortalFreeRuleProtocol  OBJECT-TYPE
    SYNTAX      INTEGER
    {
        invalid(0),
        tcp(6),
        udp(17)
    }
    MAX-ACCESS  read-create
    STATUS      current
    DESCRIPTION
        "The protocol-type of port."
    ::={ h3cPortalFreeRuleEntry 10 }

h3cPortalFreeRuleSrcPort  OBJECT-TYPE
    SYNTAX      Integer32
    MAX-ACCESS  read-create
    STATUS      current
    DESCRIPTION
        "The source port allows users to access."
    ::={ h3cPortalFreeRuleEntry 11 }

h3cPortalFreeRuleDstPort  OBJECT-TYPE
    SYNTAX      Integer32
    MAX-ACCESS  read-create
    STATUS      current
    DESCRIPTION
        "The destination port allows users to access."
    ::={ h3cPortalFreeRuleEntry 12 }

h3cPortalFreeRuleRowStatus OBJECT-TYPE
    SYNTAX   RowStatus
    MAX-ACCESS  read-create
    STATUS      current
    DESCRIPTION
        "This object is responsible for managing the creation, deletion and
        modification of rows, which support active status and CreateAndGo,
        Destroy operation."
    ::= { h3cPortalFreeRuleEntry 13 }

--
-- PORTAL Forbidden-rule Config Table
--

h3cPortalForbiddenRuleTable OBJECT-TYPE
    SYNTAX      SEQUENCE OF H3cPortalForbiddenRuleEntry
    MAX-ACCESS  not-accessible
    STATUS      current
    DESCRIPTION
        "This table describes a portal-forbidden rule does not allow specified
         users to access specified external websites."
    ::= { h3cPortalTables 9 }

h3cPortalForbiddenRuleEntry OBJECT-TYPE
    SYNTAX      H3cPortalForbiddenRuleEntry
    MAX-ACCESS  not-accessible
    STATUS      current
    DESCRIPTION
        "There is a row in this table for portal-forbidden rule.
         It is indexed using the object Index."
    INDEX
        {
            h3cPortalForbiddenRuleIndex
        }
    ::= { h3cPortalForbiddenRuleTable 1 }

H3cPortalForbiddenRuleEntry ::= SEQUENCE
    {
	h3cPortalForbiddenRuleIndex                   Integer32,
        h3cPortalForbiddenRuleSrcIfIndex              InterfaceIndex,
        h3cPortalForbiddenRuleSrcVlanID               Integer32,
        h3cPortalForbiddenRuleSrcMac                  MacAddress,
        h3cPortalForbiddenRuleAddrType                InetAddressType,
        h3cPortalForbiddenRuleSrcAddr                 InetAddress,
        h3cPortalForbiddenRuleSrcPrefix               InetAddressPrefixLength,
        h3cPortalForbiddenRuleDstAddr                 InetAddress,
        h3cPortalForbiddenRuleDstPrefix               InetAddressPrefixLength,
        h3cPortalForbiddenRuleProtocol                INTEGER,
        h3cPortalForbiddenRuleSrcPort                 Integer32,
        h3cPortalForbiddenRuleDstPort                 Integer32,
        h3cPortalForbiddenRuleRowStatus               RowStatus
    }

h3cPortalForbiddenRuleIndex  OBJECT-TYPE
    SYNTAX      Integer32 (0..2147483647)
    MAX-ACCESS  not-accessible
    STATUS      current
    DESCRIPTION
        "It is the index of the table of h3cPortalForbiddenRuleTable, it shows
        the index of the portal-forbidden rule."
    ::={ h3cPortalForbiddenRuleEntry 1 }

h3cPortalForbiddenRuleSrcIfIndex  OBJECT-TYPE
    SYNTAX      InterfaceIndex
    MAX-ACCESS  read-create
    STATUS      current
    DESCRIPTION
        "The index of source interface."
    ::={ h3cPortalForbiddenRuleEntry 2 }

h3cPortalForbiddenRuleSrcVlanID  OBJECT-TYPE
    SYNTAX      Integer32
    MAX-ACCESS  read-create
    STATUS      current
    DESCRIPTION
        "The identification of source vlan."
    ::={ h3cPortalForbiddenRuleEntry 3 }

h3cPortalForbiddenRuleSrcMac  OBJECT-TYPE
    SYNTAX      MacAddress
    MAX-ACCESS  read-create
    STATUS      current
    DESCRIPTION
        "The MAC address to match against the packet's source MAC address."
    ::={ h3cPortalForbiddenRuleEntry 4 }

h3cPortalForbiddenRuleAddrType  OBJECT-TYPE
    SYNTAX      InetAddressType
    MAX-ACCESS  read-create
    STATUS      current
    DESCRIPTION
        "The type of IP address used by this classifier entry.  While
       other types of addresses are defined in the InetAddressType
       textual convention, and DNS names, a classifier can only look at
       packets on the wire."
    ::={ h3cPortalForbiddenRuleEntry 5 }

h3cPortalForbiddenRuleSrcAddr  OBJECT-TYPE
    SYNTAX      InetAddress
    MAX-ACCESS  read-create
    STATUS      current
    DESCRIPTION
        "The IP address to match against the packet's source IP
       address. This may be a DNS name or an IPv4 or IPv6
       prefix.  h3cPortalForbiddenRuleSrcPrefix indicates the
       number of bits that are relevant."
    ::={ h3cPortalForbiddenRuleEntry 6 }

h3cPortalForbiddenRuleSrcPrefix  OBJECT-TYPE
    SYNTAX      InetAddressPrefixLength
    MAX-ACCESS  read-create
    STATUS      current
    DESCRIPTION
        "The length of the CIDR Prefix carried in
       h3cPortalFreeRuleSrcAddr. In IPv4 addresses, a length of 0
       indicates a match of any address; a length of 32 indicates a
       match of a single host address, and a length between 0 and 32
       indicates the use of a CIDR Prefix. IPv6 is similar, except that
       prefix lengths range from 0..128."
    ::={ h3cPortalForbiddenRuleEntry 7 }

h3cPortalForbiddenRuleDstAddr  OBJECT-TYPE
    SYNTAX      InetAddress
    MAX-ACCESS  read-create
    STATUS      current
    DESCRIPTION
        "The IP address to match against the packet's destination IP
       address. This may be a DNS name or an IPv4 or IPv6
       prefix.  h3cPortalForbiddenRuleDstPrefix indicates the
       number of bits that are relevant."
    ::={ h3cPortalForbiddenRuleEntry 8 }

h3cPortalForbiddenRuleDstPrefix  OBJECT-TYPE
    SYNTAX      InetAddressPrefixLength
    MAX-ACCESS  read-create
    STATUS      current
    DESCRIPTION
        "The length of the CIDR Prefix carried in
       h3cPortalFreeRuleDstAddr. In IPv4 addresses, a length of 0
       indicates a match of any address; a length of 32 indicates a
       match of a single host address, and a length between 0 and 32
       indicates the use of a CIDR Prefix. IPv6 is similar, except that
       prefix lengths range from 0..128."
    ::={ h3cPortalForbiddenRuleEntry 9 }

h3cPortalForbiddenRuleProtocol  OBJECT-TYPE
    SYNTAX      INTEGER
    {
        invalid(0),
        tcp(6),
        udp(17)
    }
    MAX-ACCESS  read-create
    STATUS      current
    DESCRIPTION
        "The protocol-type of port."
    ::={ h3cPortalForbiddenRuleEntry 10 }

h3cPortalForbiddenRuleSrcPort  OBJECT-TYPE
    SYNTAX      Integer32
    MAX-ACCESS  read-create
    STATUS      current
    DESCRIPTION
        "The source port does not allow users to access."
    ::={ h3cPortalForbiddenRuleEntry 11 }

h3cPortalForbiddenRuleDstPort  OBJECT-TYPE
    SYNTAX      Integer32
    MAX-ACCESS  read-create
    STATUS      current
    DESCRIPTION
        "The destination port does not allow users to access."
    ::={ h3cPortalForbiddenRuleEntry 12 }

h3cPortalForbiddenRuleRowStatus OBJECT-TYPE
    SYNTAX   RowStatus
    MAX-ACCESS  read-create
    STATUS      current
    DESCRIPTION
        "This object is responsible for managing the creation, deletion and
        modification of rows, which support active status and CreateAndGo,
        Destroy operation."
    ::= { h3cPortalForbiddenRuleEntry 13 }

--
-- Define the portal Traps.
--

h3cPortalTraps OBJECT IDENTIFIER ::= { h3cPortal 3 }

h3cPortalTrapPrefix OBJECT IDENTIFIER ::= { h3cPortalTraps 0 }

h3cPortalServerLost NOTIFICATION-TYPE
    OBJECTS
        {
            h3cPortalServerName,
            h3cPortalFirstTrapTime
        }
    STATUS      current
    DESCRIPTION
        "This trap is generated when the device finds that the portal server
        is unreachable, the portal server's name is h3cPortalServerName,
        and the portal server has been enabled."
    ::= { h3cPortalTrapPrefix 1 }

h3cPortalServerGet NOTIFICATION-TYPE
    OBJECTS
        {
            h3cPortalServerName,
            h3cPortalFirstTrapTime
        }
    STATUS      current
    DESCRIPTION
        "This trap is generated when the device finds that the state of portal
        server changes from unreachable state to reachable,
        the portal server's name is h3cPortalServerName,
        and the portal server has been enabled."
    ::= { h3cPortalTrapPrefix 2 }

h3cPortalTrapVarObjects OBJECT IDENTIFIER ::= { h3cPortalTraps 1 }

h3cPortalFirstTrapTime OBJECT-TYPE
    SYNTAX      TimeTicks
    MAX-ACCESS  accessible-for-notify
    STATUS      current
    DESCRIPTION
        "Represents the first trap time."
    ::= { h3cPortalTrapVarObjects 1 }

-- PORTAL STATISTIC

h3cPortalStatistic OBJECT IDENTIFIER ::= { h3cPortal 4 }

-- PORTAL AUTH REQ STATISTIC

h3cPortalStatAuthReq OBJECT-TYPE
    SYNTAX      Counter64
    MAX-ACCESS  read-only
    STATUS      current
    DESCRIPTION
        "It shows the total number of portal authentication requests from the
        portal server."
    ::= { h3cPortalStatistic 1 }

-- PORTAL ACK LOGOUT STATISTIC

h3cPortalStatAckLogout OBJECT-TYPE
    SYNTAX      Counter64
    MAX-ACCESS  read-only
    STATUS      current
    DESCRIPTION
        "It shows the number of logout requests from the portal server."
    ::= { h3cPortalStatistic 2 }

-- PORTAL NOTIFY LOGOUT STATISTIC

h3cPortalStatNotifyLogout OBJECT-TYPE
    SYNTAX      Counter64
    MAX-ACCESS  read-only
    STATUS      current
    DESCRIPTION
        "It shows the number of logout requests from the access device."
    ::= { h3cPortalStatistic 3 }

-- PORTAL CHALLENGE TIMEOUT STATISTIC

h3cPortalStatChallengeTimeout OBJECT-TYPE
    SYNTAX      Counter64
    MAX-ACCESS  read-only
    STATUS      current
    DESCRIPTION
        "It shows the number of challenge from the portal server without
        response."
    ::= { h3cPortalStatistic 4 }

-- PORTAL CHALLENGE BUSY STATISTIC

h3cPortalStatChallengeBusy OBJECT-TYPE
    SYNTAX      Counter64
    MAX-ACCESS  read-only
    STATUS      current
    DESCRIPTION
        "It shows the number of device-busy responses for challenges from
        the portal server."
    ::= { h3cPortalStatistic 5 }

-- PORTAL CHALLENGE FAIL STATISTIC

h3cPortalStatChallengeFail OBJECT-TYPE
    SYNTAX      Counter64
    MAX-ACCESS  read-only
    STATUS      current
    DESCRIPTION
        "It shows the number of challenges from the portal server with
        failure response."
    ::= { h3cPortalStatistic 6 }

-- PORTAL authenticate TIMEOUT STATISTIC

h3cPortalStatAuthTimeout OBJECT-TYPE
    SYNTAX      Counter64
    MAX-ACCESS  read-only
    STATUS      current
    DESCRIPTION
        "It shows the number of authentication requests from the portal
        server without responses."
    ::= { h3cPortalStatistic 7 }

-- PORTAL authenticate FAIL STATISTIC

h3cPortalStatAuthFail OBJECT-TYPE
    SYNTAX      Counter64
    MAX-ACCESS  read-only
    STATUS      current
    DESCRIPTION
        "It shows the number of authentication requests from the portal
        server with failure responses."
    ::= { h3cPortalStatistic 8 }

-- PORTAL PASSWORD ERROR STATISTIC

h3cPortalStatPwdError OBJECT-TYPE
    SYNTAX      Counter64
    MAX-ACCESS  read-only
    STATUS      current
    DESCRIPTION
        "It shows the number of password errors."
    ::= { h3cPortalStatistic 9 }

-- PORTAL authenticate BUSY STATISTIC

h3cPortalStatAuthBusy OBJECT-TYPE
    SYNTAX      Counter64
    MAX-ACCESS  read-only
    STATUS      current
    DESCRIPTION
        "It shows the number of device-busy responses to authentication
        requests from the portal server."
    ::= { h3cPortalStatistic 10 }

-- PORTAL authenticate DISORDER STATISTIC

h3cPortalStatAuthDisordered OBJECT-TYPE
    SYNTAX      Counter64
    MAX-ACCESS  read-only
    STATUS      current
    DESCRIPTION
        "It shows the number of disordered authentication packets from
        the portal server."
    ::= { h3cPortalStatistic 11 }

-- PORTAL authenticate UNKNOWN ERROR STATISTIC

h3cPortalStatAuthUnknownError OBJECT-TYPE
    SYNTAX      Counter64
    MAX-ACCESS  read-only
    STATUS      current
    DESCRIPTION
        "It shows the number of unknown errors."
    ::= { h3cPortalStatistic 12 }
-- PORTAL authenticate response STATISTIC

h3cPortalStatAuthResp OBJECT-TYPE
    SYNTAX      Counter64
    MAX-ACCESS  read-only
    STATUS      current
    DESCRIPTION
        "It shows the number of authentication response messages
        which are sent by AC to portal server."
    ::= { h3cPortalStatistic 13 }

-- PORTAL authenticate challenge request STATISTIC

h3cPortalStatChallengeReq OBJECT-TYPE
    SYNTAX      Counter64
    MAX-ACCESS  read-only
    STATUS      current
    DESCRIPTION
        "It shows the number of challenge request messages
        which are sent by portal server to AC."
    ::= { h3cPortalStatistic 14 }

-- PORTAL authenticate challenge response STATISTIC

h3cPortalStatChallengeResp OBJECT-TYPE
    SYNTAX      Counter64
    MAX-ACCESS  read-only
    STATUS      current
    DESCRIPTION
        "It shows the number of challenge response messages
        which are sent by AC to portal server."
    ::= { h3cPortalStatistic 15 }

-- PORTAL PACKET STATISTIC BY ERROR CODE

h3cPortalPktStatistic OBJECT IDENTIFIER ::= { h3cPortal 5 }

-- PORTAL REQ AUTH STATISTIC

h3cPortalPktStaReqAuthNum OBJECT-TYPE
    SYNTAX      Counter64
    MAX-ACCESS  read-only
    STATUS      current
    DESCRIPTION
        "It shows the total number of portal authentication requests from the
        portal server."
    ::= { h3cPortalPktStatistic 1 }

h3cPortalPktStaAckAuthSuccess OBJECT-TYPE
    SYNTAX      Counter64
    MAX-ACCESS  read-only
    STATUS      current
    DESCRIPTION
        "It shows the total number of the response to REQ-AUTH packet of
        portal server including error code 0 in the packet, that is
        authentication success."
    ::= { h3cPortalPktStatistic 2 }

h3cPortalPktStaAckAuthReject OBJECT-TYPE
    SYNTAX      Counter64
    MAX-ACCESS  read-only
    STATUS      current
    DESCRIPTION
        "It shows the total number of the response to REQ-AUTH packet of
        portal server including error code 1 in the packet, that is rejected
        by server."
    ::= { h3cPortalPktStatistic 3 }

h3cPortalPktStaAckAuthEstablish OBJECT-TYPE
    SYNTAX      Counter64
    MAX-ACCESS  read-only
    STATUS      current
    DESCRIPTION
        "It shows the total number of the response to REQ-AUTH packet of
        portal server including error code 2 in the packet, that is the link
        is already established."
    ::= { h3cPortalPktStatistic 4 }

h3cPortalPktStaAckAuthBusy OBJECT-TYPE
    SYNTAX      Counter64
    MAX-ACCESS  read-only
    STATUS      current
    DESCRIPTION
        "It shows the total number of the response to REQ-AUTH packet of
        portal server including error code 3 in the packet, that is the
        system is busy."
    ::= { h3cPortalPktStatistic 5 }

h3cPortalPktStaAckAuthAuthFail OBJECT-TYPE
    SYNTAX      Counter64
    MAX-ACCESS  read-only
    STATUS      current
    DESCRIPTION
        "It shows the total number of the response to REQ-AUTH packet of
        portal server including error code 4 in the packet, that is
        authentication fail."
    ::= { h3cPortalPktStatistic 6 }

h3cPortalPktStaReqChallengeNum OBJECT-TYPE
    SYNTAX      Counter64
    MAX-ACCESS  read-only
    STATUS      current
    DESCRIPTION
        "It shows the total number of portal challenge requests from the
        portal server."
    ::= { h3cPortalPktStatistic 7 }

h3cPortalPktStaAckChallengeSuccess OBJECT-TYPE
    SYNTAX      Counter64
    MAX-ACCESS  read-only
    STATUS      current
    DESCRIPTION
        "It shows the total number of the response to challenge packet of
        portal server including error code 0 in the packet, that is
        challenge is success."
    ::= { h3cPortalPktStatistic 8 }

h3cPortalPktStaAckChallengeReject OBJECT-TYPE
    SYNTAX      Counter64
    MAX-ACCESS  read-only
    STATUS      current
    DESCRIPTION
        "It shows the total number of the response to challenge packet of
        portal server including error code 1 in the packet, that is
        challenge is rejected by server."
    ::= { h3cPortalPktStatistic 9 }

h3cPortalPktStaAckChallengeEstablish OBJECT-TYPE
    SYNTAX      Counter64
    MAX-ACCESS  read-only
    STATUS      current
    DESCRIPTION
        "It shows the total number of the response to challenge packet of
        portal server including error code 2 in the packet, that is the
        link is alreadys established."
    ::= { h3cPortalPktStatistic 10 }

h3cPortalPktStaAckChallengeBusy OBJECT-TYPE
    SYNTAX      Counter64
    MAX-ACCESS  read-only
    STATUS      current
    DESCRIPTION
        "It shows the total number of the response to challenge packet of
        portal server including error code 3 in the packet, that is the
        system is busy."
    ::= { h3cPortalPktStatistic 11 }

h3cPortalPktStaAckChallengeAuthFail OBJECT-TYPE
    SYNTAX      Counter64
    MAX-ACCESS  read-only
    STATUS      current
    DESCRIPTION
        "It shows the total number of the response to challenge packet of
        portal server including error code 4 in the packet, that is
        authentication fail."
    ::= { h3cPortalPktStatistic 12 }

END
