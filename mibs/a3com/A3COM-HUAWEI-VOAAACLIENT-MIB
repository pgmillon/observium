-- ==========================================================================
-- Copyright (C) 2006 by Huawei-3Com Technologies. All rights reserved.
--
-- Description: The voice AAA client MIB for remote dialing users'
--              Authentication, Authorization and Accounting.
--
-- Reference:
-- Version: V1.0
-- History:
-- V1.0 Initial version
--      Created by XiangZongxin
-- ==========================================================================
A3COM-HUAWEI-VOAAACLIENT-MIB DEFINITIONS ::= BEGIN
    IMPORTS
        OBJECT-TYPE, MODULE-IDENTITY, Integer32
            FROM SNMPv2-SMI
        RowStatus,TruthValue
            FROM SNMPv2-TC
        h3cVoice
            FROM A3COM-HUAWEI-OID-MIB;

    h3cVoiceAAAClient MODULE-IDENTITY
        LAST-UPDATED "200603270000Z"   -- Mar 27, 2006  GMT
        ORGANIZATION
            "Huawei-3Com Technologies Co., Ltd."
        CONTACT-INFO
            "PLAT Team Huawei-3Com Technologies Co.,Ltd.
            Shang-Di Information Industry Base,
            Hai-Dian District Beijing P.R. China
            http://www.huawei-3com.com
            Zip:100085"
        DESCRIPTION
            "This MIB file defines the voice AAA client MIB for remote
            dialing users' Authentication, Authorization and Accounting."
        REVISION "200603270000Z"       -- Mar 27, 2006  GMT
        DESCRIPTION
            "The initial version of this MIB file."
        ::= { h3cVoice 9 }


    h3cVoAAAClientObjects OBJECT IDENTIFIER ::= { h3cVoiceAAAClient 1 }


-- AAA Client Configuration Object Group
--
-- The objects in this group describe and store the configuration parameters
-- on the AAA Client function of this gateway which based on Authentication,
-- Authorization, Accounting protocols.
    h3cVoAAAClientCfgObjects OBJECT IDENTIFIER ::= { h3cVoAAAClientObjects 1 }

    h3cVoAAAGwAuthenDid OBJECT-TYPE
        SYNTAX TruthValue
        MAX-ACCESS read-write
        STATUS current
        DESCRIPTION
            "Enable or disable the function of authentication
            for Direct Inward Dialing."
        DEFVAL { false }
        ::= { h3cVoAAAClientCfgObjects 1 }

    h3cVoAAAGwAuthorDid OBJECT-TYPE
        SYNTAX TruthValue
        MAX-ACCESS read-write
        STATUS current
        DESCRIPTION
            "Enable or disable the function of authorization for Direct
            Inward Dialing on condition that the function of authentication
            is enabled."
        DEFVAL { false }
        ::= { h3cVoAAAClientCfgObjects 2 }

    h3cVoAAAGwAccountingDid OBJECT-TYPE
        SYNTAX TruthValue
        MAX-ACCESS read-write
        STATUS current
        DESCRIPTION
            "Enable or disable the function of accounting for
            Direct Inward Dialing."
        DEFVAL { false }
        ::= { h3cVoAAAClientCfgObjects 3 }

    h3cVoAAAGwAccountMethod OBJECT-TYPE
        SYNTAX INTEGER
            {
                startAck(1),
                startNoAck(2),
                stopOnly(3)
            }
        MAX-ACCESS read-write
        STATUS current
        DESCRIPTION
            "Specify the sending mode of accounting packets of this gateway.
            startAck: send starting and stopping accounting packets and wait
                for the acknowledge of RADIUS server.
            startNoAck: send starting and stopping accounting packets
                without waiting for the acknowledge of RADIUS server.
            stopOnly: send stopping accounting packets and wait
                for the acknowledge of RADIUS server."
        DEFVAL { startNoAck }
        ::= { h3cVoAAAClientCfgObjects 4 }

-- AAA Gateway Access Number Table
--
-- Table to store the AAA access number and the dialing process attribute
-- of this gateway, which includes the access number, the card digits, the
-- password digits,the redialing times and so on.
    h3cVoAAAGwAccessNumberTable OBJECT-TYPE
        SYNTAX SEQUENCE OF H3cVoAAAGwAccessNumberEntry
        MAX-ACCESS not-accessible
        STATUS current
        DESCRIPTION
            "The table contains the information of the AAA access number for
            Two-stage Dialing, which includes the configuration of
            authentication, authorization, accounting, the dialing process,
            the length of card number, the length of password ,
            the redialing times."
        ::= { h3cVoAAAClientObjects 2 }

    h3cVoAAAGwAccessNumberEntry OBJECT-TYPE
        SYNTAX H3cVoAAAGwAccessNumberEntry
        MAX-ACCESS not-accessible
        STATUS current
        DESCRIPTION
            "The information of the access number."
        INDEX { h3cVoAAAGwAccessNumber }
        ::= { h3cVoAAAGwAccessNumberTable 1 }

    H3cVoAAAGwAccessNumberEntry ::=
        SEQUENCE
            {
                h3cVoAAAGwAccessNumber OCTET STRING,
                h3cVoAAAGwAuthentication TruthValue,
                h3cVoAAAGwAuthorization TruthValue,
                h3cVoAAAGwAccounting TruthValue,
                h3cVoAAAGwProcessConfig INTEGER,
                h3cVoAAAGwCardDigit Integer32,
                h3cVoAAAGwPasswordDigit Integer32,
                h3cVoAAAGwRedialTimes Integer32,
                h3cVoAAAGwRowStatus RowStatus
             }

    h3cVoAAAGwAccessNumber OBJECT-TYPE
        SYNTAX OCTET STRING (SIZE (1..31))
        MAX-ACCESS not-accessible
        STATUS current
        DESCRIPTION
            "The access number of the AAA client.
            The access number can be composed of digits, wildcards
            or the letter 'T'.
            If digits, wildcards and the letter 'T'
            are all included in an access number, the wildcards must
            follow digits and appear at the end, and 'T' must be the
            last character and appear only once.
            In addition, an access number can include only wildcards,
            or only one 'T'."
        ::= { h3cVoAAAGwAccessNumberEntry 1 }

    h3cVoAAAGwAuthentication OBJECT-TYPE
        SYNTAX TruthValue
        MAX-ACCESS read-create
        STATUS current
        DESCRIPTION
            "Enable or disable the function of authentication for
            Two-stage Dialing."
        DEFVAL { false }
        ::= { h3cVoAAAGwAccessNumberEntry 2 }

    h3cVoAAAGwAuthorization OBJECT-TYPE
        SYNTAX TruthValue
        MAX-ACCESS read-create
        STATUS current
        DESCRIPTION
            "Enable or disable the function of authorization
            for Two-stage Dialing on condition that the function
            of authentication is enabled."
        DEFVAL { false }
        ::= { h3cVoAAAGwAccessNumberEntry 3 }

    h3cVoAAAGwAccounting OBJECT-TYPE
        SYNTAX TruthValue
        MAX-ACCESS read-create
        STATUS current
        DESCRIPTION
            "Enable or disable the function of accounting for
            Two-stage Dialing."
        DEFVAL { false }
        ::= { h3cVoAAAGwAccessNumberEntry 4 }

    h3cVoAAAGwProcessConfig OBJECT-TYPE
        SYNTAX INTEGER
            {
                callerNumber(1),
                cardNumber(2),
                callerNumIvr(3)
            }
        MAX-ACCESS read-create
        STATUS current
        DESCRIPTION
            "The dialing process type of this access number.
            callerNumber: caller number dialing process without IVR
                (Interactive Voice Reponse), that is, caller number's
                authentication for Two-stage Dialing process
                without IVR.
            cardNumber: card number dialing process with IVR, that is,
                card number and password's authentication for
                Two-stage Dialing process with IVR.
            callerNumIvr: caller number dialing process with IVR,
                that is, caller number's authentication for
                Two-stage Dialing process with IVR."
        DEFVAL { callerNumIvr }
        ::= { h3cVoAAAGwAccessNumberEntry 5 }

    h3cVoAAAGwCardDigit OBJECT-TYPE
        SYNTAX Integer32 (1..31)
        MAX-ACCESS read-create
        STATUS current
        DESCRIPTION
            "The length of card number only for the cardNumber
            dialing process."
        DEFVAL { 12 }
        ::= { h3cVoAAAGwAccessNumberEntry 6 }

    h3cVoAAAGwPasswordDigit OBJECT-TYPE
        SYNTAX Integer32 (1..16)
        MAX-ACCESS read-create
        STATUS current
        DESCRIPTION
            "The length of password only for the cardNumber
            dialing process."
        DEFVAL { 6 }
        ::= { h3cVoAAAGwAccessNumberEntry 7 }

    h3cVoAAAGwRedialTimes OBJECT-TYPE
        SYNTAX Integer32 (0..10)
        MAX-ACCESS read-create
        STATUS current
        DESCRIPTION
            "The redialing times of inputing card number or
            password or called number for the cardNumber dialing process,
            or the redialing times of inputing called number
            for the callerNumIvr dialing process."
        DEFVAL { 2 }
        ::= { h3cVoAAAGwAccessNumberEntry 8 }

    h3cVoAAAGwRowStatus OBJECT-TYPE
        SYNTAX RowStatus
        MAX-ACCESS read-create
        STATUS current
        DESCRIPTION
            "The row status of this table."
        ::= { h3cVoAAAGwAccessNumberEntry 9 }
END
