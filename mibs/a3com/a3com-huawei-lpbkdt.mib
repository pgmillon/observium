-- ==================================================================
-- Copyright (C) 2008 by H3C Technologies. All rights reserved.
--
-- Description: Loopback detection MIB
-- Reference:
-- Version: V1.1
-- History:
-- V1.0 2008-09-27 Created by LuoXuefang
-- V1.1 2009-03-30 Added h3cLpbkdtTrapPerVlanLoopbacked, 
--                 h3cLpbkdtTrapPerVlanRecovered and
--                 h3cLpbkdtObjects by TongWei.
-- ==================================================================
A3COM-HUAWEI-LPBKDT-MIB DEFINITIONS ::= BEGIN

IMPORTS
    h3cCommon
        FROM A3COM-HUAWEI-OID-MIB
    ifIndex, ifDescr
        FROM IF-MIB
    VlanId
        FROM Q-BRIDGE-MIB
    OBJECT-TYPE, MODULE-IDENTITY, NOTIFICATION-TYPE
        FROM SNMPv2-SMI;

h3cLpbkdt MODULE-IDENTITY
    LAST-UPDATED "200903301741Z"        -- March 30, 2009 at 17:41 GMT
    ORGANIZATION "H3C Technologies Co., Ltd."
    CONTACT-INFO
        "Comware Team H3C Technologies Co., Ltd.
        Hai-Dian District Beijing P.R. China
        http://www.h3c.com
        Zip:100085"
    DESCRIPTION
        "Loops may cause broadcast storms.  The purpose of loopback detection
         is to detect loops on the device and to protect the network."

    REVISION "200903301741Z"
    DESCRIPTION
        "To fix bugs in the MIB file."
    REVISION "200809271504Z"
    DESCRIPTION
        "The initial revision of this MIB module."
    ::= { h3cCommon 95 }

-- ==================================================================
--
-- ======================= definition begin =========================
--
-- ==================================================================

h3cLpbkdtNotifications OBJECT IDENTIFIER ::= { h3cLpbkdt 1 }
h3cLpbkdtObjects       OBJECT IDENTIFIER ::= { h3cLpbkdt 2 }
h3cLpbkdtTrapPrefix    OBJECT IDENTIFIER ::= { h3cLpbkdtNotifications 0 }

h3cLpbkdtTrapLoopbacked NOTIFICATION-TYPE
    OBJECTS { ifIndex, ifDescr }
    STATUS current
    DESCRIPTION
        "Trap message is generated when the interface is looped."
    ::= { h3cLpbkdtTrapPrefix 1 }

h3cLpbkdtTrapRecovered NOTIFICATION-TYPE
    OBJECTS { ifIndex, ifDescr }
    STATUS current
    DESCRIPTION
        "Trap message is generated when the loops on the interface
         are eliminated."
    ::= { h3cLpbkdtTrapPrefix 2 }

h3cLpbkdtTrapPerVlanLoopbacked NOTIFICATION-TYPE
    OBJECTS { ifIndex, ifDescr, h3cLpbkdtVlanID }
    STATUS current
    DESCRIPTION
        "Trap message is generated when the interface is looped in the VLAN."
    ::= { h3cLpbkdtTrapPrefix 3 }

h3cLpbkdtTrapPerVlanRecovered NOTIFICATION-TYPE
    OBJECTS { ifIndex, ifDescr, h3cLpbkdtVlanID }
    STATUS current
    DESCRIPTION
        "Trap message is generated when the loop on the interface
         is eliminated in the VLAN."
    ::= { h3cLpbkdtTrapPrefix 4 }

h3cLpbkdtVlanID OBJECT-TYPE
    SYNTAX      VlanId
    MAX-ACCESS  accessible-for-notify
    STATUS      current
    DESCRIPTION
        "The ID of VLAN."
    ::= { h3cLpbkdtObjects 1 }

END
