-- =================================================================
-- Copyright (C) 2005 by HUAWEI-3COM TECHNOLOGIES. All rights reserved.
--
-- Description:  Extended MIB File(extended from DISMAN-PING-MIB RFC2925)
-- Reference:
-- Version: V2.3
-- History:
-- V1.0  Lv zhenfeng, 2003.08, Initial Version
-- V1.1 2004-10-12 updated by gaolong
--      Import OBJECT-IDENTITY, Integer32, Counter32, Gauge32.
-- V1.2 Add new column objects
--      hwNqaResultsMaxDelaySD
--      hwNqaResultsMaxDelayDS
--      hwNqaResultsLostPacketRatio
--      under hwNqaResultsTable table by zhaoyujin, 20041101
--  Add new column objects
--      hwNqaJitterStatsAvePositivesSD
--      hwNqaJitterStatsAveNegativesSD
--      hwNqaJitterStatsAvePositivesDS
--      hwNqaJitterStatsAveNegativesDS
--      hwNqaJitterStatsPktLossUnknown
--  under hwNqaJitterStatsTable table by zhaoyujin, 20041101
--      revise words errors
-- V1.3 2004-12-25 updated by zhaoyujin and weixinzhe
--      Objects description updated
-- V1.4 2005-12-22 Modified by qiuchunxia and liqian
--      add hwNqaCtlHistoryKeptTime
--      add hwNqaCtlHistoryEnable
--      add hwNqaStatisticsResultsTable
--      add hwNqaGroupStatsJitterTable
--      add hwNqaStatisticsCtlTable
--      add hwNqaStatsMaxGroupNumber
--      remove definition of InetAddress, and import from INET-ADDRESS-MIB
-- V1.5 2006-03-03 Modified by jinyi and wangqingfeng
--      modified the description of hwNqaStatResRttSequenceErrors
--      modified the description of hwNqaResultsRttSequenceErrors
--      modified UNITS of some objects by jinyi
--      add hwNqaCtlICPIFAdvFactor, hwNqaCtlCodecType in hwNqaCtlTable
--      add hwNqaResultsPacketLateArrival in hwNqaResultsTable
--      add hwNqaJitterStatsOperOfICPIF and hwNqaJitterStatsOperOfMOS
--      in hwNqaJitterStatsTable
--      add hwNqaStatResPacketLateArrival in hwNqaStatisticsResultsTable
--      add hwNqaStatJitterMaxOfICPIF, hwNqaStatJitterMinOfICPIF
--      hwNqaStatJitterMaxOfMOS and hwNqaStatJitterMinOfMOS
--      in hwNqaGroupStatsJitterTable
--      rename subidentifier 5 of hwNqaStatisticsCtlEntry to
--      hwNqaCtlLifeTime by wangqingfeng
--      rename subidentifier 11 of hwNqaStatisticsResultsEntry to
--      hwNqaStatResInterval by wangqingfeng
-- V1.6 2006-05-12
--      rewrite this MIB with prefix "hwNqa".
-- V2.0 2006-08-14 Modified by zhangjun
--      change the name of root from "hwDismanPing" to "hwNqa"
--      modify some mistakes
-- V2.1  2006-08-22 Modified by qiuchunxia, dupengfei and shenjuanjuan
--      add hwNqaReactionTable and add hwNqaNotifications
-- V2.2 2007-03-08 Modified by zhouwenming
--      add hwNqaResultsRttSum, hwNqaResultsNumOfDelaySD, hwNqaResultsMinDelaySD,
--       hwNqaResultsSumDelaySD, hwNqaResultsSum2DelaySD, hwNqaResultsNumOfDelayDS,
--       hwNqaResultsMinDelayDS, hwNqaResultsSumDelayDS, hwNqaResultsSum2DelayDS
--       in hwNqaResultsTable
--      add hwNqaStatResRttSum, hwNqaStatResNumOfDelaySD, hwNqaStatResMinDelaySD,
--       hwNqaStatResSumDelaySD, hwNqaStatResSum2DelaySD, hwNqaStatResNumOfDelayDS,
--       hwNqaStatResMinDelayDS, hwNqaStatResSumDelayDS, hwNqaStatResSum2DelayDS,
--       hwNqaStatResMaxDelaySD, hwNqaStatResMaxDelayDS
--       in hwNqaStatisticsResultsTable
--      add jitterOwdSD, jitterOwdDS to hwNqaReactCheckedElement
--       in hwNqaReactionTable.
--      add hwNqaReactCheckedNum, hwNqaReactThresholdNum in hwNqaReactionTable
--      add hwNqaStatisticsReactionTable
-- V2.3 2007-04-25 Modified by zhouxingyue and zhouhaifeng
--      add icmpTimestamp in hwNqaCtlCodecType
--      remove size limit and DEFVAL in definition of hwNqaCtlStatisticsInterval.
--      modify type of below from  Unsigned32 to Gauge32:
--       hwNqaStatResMinRtt, hwNqaStatResMaxRtt,hwNqaStatResAverageRtt,
--       hwNqaStatResInterval, hwNqaStatResLostPacketRatio, hwNqaStatResMinDelaySD,
--       hwNqaStatResMaxDelaySD,hwNqaStatResMinDelayDS, hwNqaStatResMaxDelayDS.
--      modify type of below from  Unsigned32 to Counter32:
--       hwNqaStatResProbeResponses, hwNqaStatResSentProbes, hwNqaStatResRttSumOfSquares,
--       hwNqaStatResRttNumDisconnects, hwNqaStatResRttTimeouts, hwNqaStatResRttBusies,
--       hwNqaStatResRttNoConnections, hwNqaStatResRttDrops, hwNqaStatResRttSequenceErrors,
--       hwNqaStatResRttErrors, hwNqaStatResPacketLateArrival, hwNqaStatResRttSum,
--       hwNqaStatResNumOfDelaySD, hwNqaStatResSumDelaySD, hwNqaStatResSum2DelaySD,
--       hwNqaStatResNumOfDelayDS, hwNqaStatResSumDelayDS, hwNqaStatResSum2DelayDS,
--       hwNqaStatReactCheckedNum, hwNqaStatReactThresholdNum.
--      modify type of below from  Gauge32 to Counter32:
--       hwNqaStatJitterNumOfPosSD, hwNqaStatJitterSumOfPosSD, hwNqaStatJitterSumOfSquarePosSD,
--       hwNqaStatJitterNumOfNegSD, hwNqaStatJitterSumOfNegSD, hwNqaStatJitterSumOfSquareNegSD,
--       hwNqaStatJitterNumOfPosDS, hwNqaStatJitterSumOfPosDS, hwNqaStatJitterSumOfSquarePosDS,
--       hwNqaStatJitterNumOfNegDS, hwNqaStatJitterSumOfNegDS, hwNqaStatJitterSumOfSquareNegDS,
--       hwNqaStatJitterPacketLossSD, hwNqaStatJitterPacketLossDS, hwNqaStatJitterPktLossUnknown.
-- =================================================================
A3COM-HUAWEI-NQA-MIB DEFINITIONS ::= BEGIN

        IMPORTS
            MODULE-IDENTITY, OBJECT-TYPE, Unsigned32,
            OBJECT-IDENTITY, NOTIFICATION-TYPE, Integer32, Counter32, Gauge32
                FROM SNMPv2-SMI
            DateAndTime, DisplayString, RowStatus
                FROM SNMPv2-TC
            InetAddressType, InetAddress
                FROM INET-ADDRESS-MIB
            huaweiDatacomm
                FROM A3COM-HUAWEI-OID-MIB
            pingCtlEntry, pingCtlOwnerIndex, pingCtlTestName, pingCtlType,
            pingCtlTargetAddress, pingCtlTargetAddressType, pingCtlDescr
                FROM DISMAN-PING-MIB
            SnmpAdminString
                FROM SNMP-FRAMEWORK-MIB;          -- RFC2571

    hwNqa MODULE-IDENTITY
        LAST-UPDATED "200608140000Z"
        ORGANIZATION "Huawei Technologies Co., Ltd."
            CONTACT-INFO
                " R&D BeiJing, Huawei Technologies Co., Ltd.
                Huawei Bld.,NO.3 Xinxi Rd.,
                Shang-Di Information Industry Base,
                    Hai-Dian District Beijing P.R. China
                Zip:100085
                Http://www.huawei.com
                E-mail:support@huawei.com "
            DESCRIPTION
                "The private mib file includes the test information of the
                device. It is supplementary for rfc2925.txt."
        ::= { huaweiDatacomm 28 }

    hwNqaObjects OBJECT IDENTIFIER ::= { hwNqa 1 }

 -- The registration node (point) for remote NQA(Network Quality Analysis) test
 -- implementation types

hwNqaImplementationTypeDomains  OBJECT IDENTIFIER ::= { hwNqa 2 }

hwNqaUdpEcho OBJECT-IDENTITY
    STATUS      current
    DESCRIPTION
        "Indicates that an implementation is using the UDP based echo server.
        Notes: The hwNqaCtlTargetPort and hwNqaCtlSourcePort need to be set,
        while in the pingUdpEcho Node, hwNqaCtlTargetPort must be set to the
        default value."
    ::= { hwNqaImplementationTypeDomains 1 }

hwNqaTcpconnect OBJECT-IDENTITY
    STATUS      current
    DESCRIPTION
        "Indicates that an implementation is attempting to
        connect to a TCP port in order to calculate a round
        trip time.
        Notes: The hwNqaCtlTargetPort and hwNqaCtlSourcePort need to be set,
        while in the pingTcpConnectionAttempt Node, hwNqaCtlTargetPort must
        be set to the default value."
    ::= { hwNqaImplementationTypeDomains 2 }

hwNqajitter OBJECT-IDENTITY
    STATUS      current
    DESCRIPTION
        "Indicates that an implementation is using udp for packet transfers.
        'jitter' will cause the NQA(Network Quality Analysis) application
        to perform delay variance analysis."
    ::= { hwNqaImplementationTypeDomains 3 }

hwNqaHttp OBJECT-IDENTITY
    STATUS      current
    DESCRIPTION
        "Indicates that an implementation is using udp for name resolution,
        tcp connect and tcp data transfer mechanisms for HTTP data download
        from a particular HTTP Server.
        It causes the NQA application to perform a download of the object
        specified in the URL."
    ::= { hwNqaImplementationTypeDomains 4 }


hwNqadlsw OBJECT-IDENTITY
    STATUS      current
    DESCRIPTION
        "Indicates that an implementation is using tcp for sending keepalives.
        'dlsw' will cause the NQA application to perform a keepalive operation
        to measure the response time of a DLSw peer."
    ::= { hwNqaImplementationTypeDomains 5 }

hwNqadhcp OBJECT-IDENTITY
    STATUS      current
    DESCRIPTION
        "Indicates that an implementation is using udp for sending dhcp
        requests. 'dhcp' will cause the NQA application
        to perform an IP Address lease request/teardown operation."
    ::= { hwNqaImplementationTypeDomains 6 }

hwNqaftp OBJECT-IDENTITY
    STATUS      current
    DESCRIPTION
        "Indicates that an implementation is using tcp packet for ftp connect
         and data transfer."
    ::= { hwNqaImplementationTypeDomains 7 }


-- MIB contains 3 groups

hwNqaMIBVersion OBJECT-TYPE
    SYNTAX      DisplayString
    MAX-ACCESS  read-only
    STATUS      current
    DESCRIPTION
        "Version string of this MIB.
        The format will be: 'Version.Release.Patch: Description'
        An instance likes: '1.0.0: Initial NQA MIB'
        "
    ::= { hwNqaObjects 1 }

hwNqaCtlTable OBJECT-TYPE
    SYNTAX      SEQUENCE OF HwNqaCtlEntry
    MAX-ACCESS  not-accessible
    STATUS      current
    DESCRIPTION
        "Defines the NQA Control Extend Table for providing, via SNMP,
        the capability of performing network analysis operations at a
        remote host."
    ::= { hwNqaObjects 2 }

hwNqaCtlEntry OBJECT-TYPE
    SYNTAX      HwNqaCtlEntry
    MAX-ACCESS  not-accessible
    STATUS      current
    DESCRIPTION
        "Defines an entry in the hwNqaCtlTable. The operation of this
        table is same as that of pingResultsTable."
    AUGMENTS    { pingCtlEntry }
    ::= { hwNqaCtlTable 1 }

HwNqaCtlEntry ::=
    SEQUENCE {
    hwNqaCtlTargetPort               Integer32,
    hwNqaCtlSourcePort               Integer32,
    hwNqaCtlTTL                      Integer32,
    hwNqaCtlJitterAdminInterval      Integer32,
    hwNqaCtlJitterAdminNumPackets    Integer32,
    hwNqaCtlHttpOperationType        INTEGER,
    hwNqaCtlHttpOperationString      DisplayString,
    hwNqaCtlFtpOperationType         INTEGER,
    hwNqaCtlFtpUsername              DisplayString,
    hwNqaCtlFtpPassword              DisplayString,
    hwNqaCtlFtpOperationString       DisplayString,
    hwNqaCtlVPNInstance              DisplayString,
    hwNqaCtlHistoryKeptTime          Integer32,
    hwNqaCtlHistoryEnable            INTEGER,
    hwNqaCtlICPIFAdvFactor           Integer32,
    hwNqaCtlCodecType                INTEGER
    }

hwNqaCtlTargetPort          OBJECT-TYPE
    SYNTAX      Integer32 (0..65536)
    MAX-ACCESS  read-create
    STATUS      current
    DESCRIPTION
        "The destination port that may be used by udpEcho,
        tcpConnect and jitter probes."
    DEFVAL      { 0 }
    ::= { hwNqaCtlEntry 1 }

hwNqaCtlSourcePort          OBJECT-TYPE
    SYNTAX      Integer32 (0..65536)
    MAX-ACCESS  read-create
    STATUS      current
    DESCRIPTION
        "The source port that may be used by all tests except
        for dns and dlsw.
        If no source port is specified, system will create
        a random port as source port."
    DEFVAL      { 0 }
    ::= { hwNqaCtlEntry 2 }

hwNqaCtlTTL OBJECT-TYPE
    SYNTAX      Integer32
    MAX-ACCESS  read-create
    STATUS      current
    DESCRIPTION
        "Specifies the value to store in the TTL Field in the IP packet used to
        encapsulate the NQA probe."
    DEFVAL      { 20 }
    ::= { hwNqaCtlEntry 3 }

hwNqaCtlJitterAdminInterval OBJECT-TYPE
    SYNTAX      Integer32 (0..60000)
    UNITS       "milliseconds"
    MAX-ACCESS  read-create
    STATUS      current
    DESCRIPTION
        "Time value in milliseconds that is an interval between two continuous
        probes in jitter test.

        This object is only used by jitter test."
    DEFVAL      { 20 }
    ::= { hwNqaCtlEntry 4 }

hwNqaCtlJitterAdminNumPackets OBJECT-TYPE
    SYNTAX      Integer32
    MAX-ACCESS  read-create
    STATUS      current
    DESCRIPTION
        "Packet number that specifys how many packets will be sent in
        one jitter test.

        This object is only used by jitter test."
    DEFVAL      { 10 }
    ::= { hwNqaCtlEntry 5 }

hwNqaCtlHttpOperationType OBJECT-TYPE
    SYNTAX      INTEGER{
                get(1),
                post(2)
                }
    MAX-ACCESS  read-create
    STATUS      current
    DESCRIPTION
        "Http operation type: get or post."
    DEFVAL      { get }
    ::= { hwNqaCtlEntry 6 }

hwNqaCtlHttpOperationString OBJECT-TYPE
    SYNTAX      DisplayString(SIZE(0..255))
    MAX-ACCESS  read-create
    STATUS      current
    DESCRIPTION
        "Http operation string. For example, if the http operation type is get,
        the string will be url, home page and http version."
    DEFVAL      { "" }
    ::= { hwNqaCtlEntry 7 }

hwNqaCtlFtpOperationType OBJECT-TYPE
    SYNTAX      INTEGER{
                get(1),
                put(2)
                }
    MAX-ACCESS  read-create
    STATUS      current
    DESCRIPTION
        "Ftp operation type."
    DEFVAL      { get }
    ::= { hwNqaCtlEntry 8 }

hwNqaCtlFtpUsername OBJECT-TYPE
    SYNTAX      DisplayString(SIZE(0..32))
    MAX-ACCESS  read-create
    STATUS      current
    DESCRIPTION
        "Ftp username."
    DEFVAL      { "" }
    ::= { hwNqaCtlEntry 9 }

hwNqaCtlFtpPassword OBJECT-TYPE
    SYNTAX      DisplayString(SIZE(0..32))
    MAX-ACCESS  read-create
    STATUS      current
    DESCRIPTION
        "Ftp password."
    DEFVAL      { "" }
    ::= { hwNqaCtlEntry 10 }

hwNqaCtlFtpOperationString OBJECT-TYPE
    SYNTAX      DisplayString(SIZE(0..255))
    MAX-ACCESS  read-create
    STATUS      current
    DESCRIPTION
        "Ftp operation string. If the ftp operation type is get,
        the string must be the file name which will be gotten from ftp server."
    DEFVAL      { "" }
    ::= { hwNqaCtlEntry 11 }

hwNqaCtlVPNInstance OBJECT-TYPE
    SYNTAX      DisplayString(SIZE(0..255))
    MAX-ACCESS  read-create
    STATUS      current
    DESCRIPTION
        "VPN name by which system finds route in the specified VPN
        to send NQA probe packets."
    DEFVAL      { "" }
    ::= { hwNqaCtlEntry 12 }

hwNqaCtlHistoryKeptTime OBJECT-TYPE
    SYNTAX     Integer32(1..1440)
    UNITS      "minutes"
    MAX-ACCESS read-create
    STATUS     current
    DESCRIPTION
        "To indicate how long the history records will be saved
        in the pingProbeHistoryTable table after the test stopped."
    DEFVAL     { 120 }
    ::= { hwNqaCtlEntry 13 }

hwNqaCtlHistoryEnable OBJECT-TYPE
    SYNTAX      INTEGER
        {
            enabled(1),  --history will be recorded
            disabled(2)  --history will not be recorded
        }
    MAX-ACCESS  read-create
    STATUS      current
    DESCRIPTION
        "To indicate whether the history should be recorded in the
        PingProbeHistoryTable or not.
            enabled(1)   --history will be recorded
            disabled(2)  --history will not be recorded."
    DEFVAL      { disabled }
    ::= { hwNqaCtlEntry 14 }

hwNqaCtlICPIFAdvFactor OBJECT-TYPE
    SYNTAX  Integer32
    MAX-ACCESS read-create
    STATUS  current
    DESCRIPTION
        "The advantage factor depends on the type of access and how the service
        is to be used. This object will be used while calculating the ICPIF
        (Calculated Planning Impairment Factor) values.

        Suggestion values:

        |-----------------------------------|-------|
        |          Service                  |factor |
        |-----------------------------------|-------|
        |conventional wire-line             |  0    |
        |-----------------------------------|-------|
        |mobility within Building           |  5    |
        |-----------------------------------|-------|
        |mobility within geographical area  |  10   |
        |-----------------------------------|-------|
        |access to hard-to-reach location   |  20   |
        |-----------------------------------|-------|
        "
    DEFVAL  {0}
    ::= { hwNqaCtlEntry 15 }

hwNqaCtlCodecType OBJECT-TYPE
    SYNTAX     INTEGER
        {
            notDefined(1),     -- no codec type is defined or codec is unknown
            g711Alaw(2),       -- uses G.711 A-Law
            g711Ulaw(3),       -- uses G.711 muHmm-Law
            g729A(4),          -- uses G.729A
            icmpTimestamp(5)   -- uses icmp timestamp packet type
        }
    MAX-ACCESS read-create
    STATUS     current
    DESCRIPTION
        "To indicate the codec type to be used with jitter probe. This is
        applicable only for the jitter probe."
    DEFVAL     { notDefined }
    ::= { hwNqaCtlEntry 16 }

-- NQA Test Results Table

hwNqaResultsTable OBJECT-TYPE
    SYNTAX      SEQUENCE OF HwNqaResultsEntry
    MAX-ACCESS  not-accessible
    STATUS      current
    DESCRIPTION
        "Defines the NQA Results Extend Table for providing
        the capability of performing NQA operations at a remote
        host. The results of these operations are stored in the
        hwNqaResultsTable. The operation of this table is same
        as that of pingResultsTable."
    ::= { hwNqaObjects 3 }

hwNqaResultsEntry OBJECT-TYPE
    SYNTAX      HwNqaResultsEntry
    MAX-ACCESS  not-accessible
    STATUS      current
    DESCRIPTION
        "The operation of this table is same as that of pingResultsTable."
    INDEX {
             pingCtlOwnerIndex,
             pingCtlTestName
          }
    ::= { hwNqaResultsTable 1 }

HwNqaResultsEntry ::=
    SEQUENCE {
        hwNqaResultsRttNumDisconnects   Unsigned32,
        hwNqaResultsRttTimeouts         Unsigned32,
        hwNqaResultsRttBusies           Unsigned32,
        hwNqaResultsRttNoConnections    Unsigned32,
        hwNqaResultsRttDrops            Unsigned32,
        hwNqaResultsRttSequenceErrors   Unsigned32,
        hwNqaResultsRttStatsErrors      Unsigned32,
        hwNqaResultsMaxDelaySD          Unsigned32,
        hwNqaResultsMaxDelayDS          Unsigned32,
        hwNqaResultsLostPacketRatio     Unsigned32,
        hwNqaResultsPacketLateArrival   Unsigned32,
        hwNqaResultsRttSum              Unsigned32,
        hwNqaResultsNumOfDelaySD        Unsigned32,
        hwNqaResultsMinDelaySD          Unsigned32,
        hwNqaResultsSumDelaySD          Unsigned32,
        hwNqaResultsSum2DelaySD         Unsigned32,
        hwNqaResultsNumOfDelayDS        Unsigned32,
        hwNqaResultsMinDelayDS          Unsigned32,
        hwNqaResultsSumDelayDS          Unsigned32,
        hwNqaResultsSum2DelayDS         Unsigned32
    }

hwNqaResultsRttNumDisconnects OBJECT-TYPE
    SYNTAX      Unsigned32
    MAX-ACCESS  read-only
    STATUS      current
    DESCRIPTION
        "The number of times that a NQA probe failed because
        the destination became disconnected.

        For connectionless protocol pingCtlTypes, this number should be
        zero."
    ::= { hwNqaResultsEntry 1 }


hwNqaResultsRttTimeouts OBJECT-TYPE
    SYNTAX      Unsigned32
    MAX-ACCESS  read-only
    STATUS      current
    DESCRIPTION
        "The number of times that a NQA probe failed because the
        probe timed out."
    ::= { hwNqaResultsEntry 2 }


hwNqaResultsRttBusies OBJECT-TYPE
    SYNTAX      Unsigned32
    MAX-ACCESS  read-only
    STATUS      current
    DESCRIPTION
        "The number of times that a NQA probe failed because all
        NQA tasks have been running.

        If a new probe fails to start, the value of this object
        is incremented. The next test will not start until the
        next Frequency."
    ::= { hwNqaResultsEntry 3 }


hwNqaResultsRttNoConnections OBJECT-TYPE
    SYNTAX      Unsigned32
    MAX-ACCESS  read-only
    STATUS      current
    DESCRIPTION
        "The number of times that a NQA probe failed because the probe
        destination is unavailable.

        For connectionless protocol pingCtlTypes, this number should be
        zero."
    ::= { hwNqaResultsEntry 4 }


hwNqaResultsRttDrops OBJECT-TYPE
    SYNTAX      Unsigned32
    MAX-ACCESS  read-only
    STATUS      current
    DESCRIPTION
        "The number of times that a NQA operation failed to initiated
        for unavailibility of necessary internal resources."
    ::= { hwNqaResultsEntry 5 }


hwNqaResultsRttSequenceErrors OBJECT-TYPE
    SYNTAX      Unsigned32
    MAX-ACCESS  read-only
    STATUS      current
    DESCRIPTION
        "The number of packets arrived out of sequence."
    ::= { hwNqaResultsEntry 6 }

hwNqaResultsRttStatsErrors OBJECT-TYPE
    SYNTAX      Unsigned32
    MAX-ACCESS  read-only
    STATUS      current
    DESCRIPTION
        "The number of some other errors."
    ::= { hwNqaResultsEntry 7 }

hwNqaResultsMaxDelaySD OBJECT-TYPE
    SYNTAX      Unsigned32
    UNITS       "milliseconds"
    MAX-ACCESS  read-only
    STATUS      current
    DESCRIPTION
        "The maximal delay from source device to destination device.
         Currently this value is only used for jitter test, and this
         value must be 0 in other type test. In jitter test, if
         destination system time is not valid, the SD delay may be set 0."
    ::= { hwNqaResultsEntry 8 }

hwNqaResultsMaxDelayDS OBJECT-TYPE
    SYNTAX      Unsigned32
    UNITS       "milliseconds"
    MAX-ACCESS  read-only
    STATUS      current
    DESCRIPTION
        "The maximal delay from destination device to source device.
         Currently this value is only used for jitter test, and this
         value is 0 in other type test. In jitter test, if destination
         system time is not valid, the DS delay may be set 0."
    ::= { hwNqaResultsEntry 9 }

hwNqaResultsLostPacketRatio OBJECT-TYPE
    SYNTAX      Unsigned32
    UNITS       "milliseconds"
    MAX-ACCESS  read-only
    STATUS      current
    DESCRIPTION
        "The value of this object reflects the drop rate of NQA test.
         For example, this value is 30 that means source device only
         had received 70% packets of total sent packets."
    ::= { hwNqaResultsEntry 10 }

hwNqaResultsPacketLateArrival OBJECT-TYPE
    SYNTAX      Unsigned32
    MAX-ACCESS  read-only
    STATUS      current
    DESCRIPTION
        "The value of this object indicates the number of the packets that
        arrived after the timeout."
    ::= { hwNqaResultsEntry 11 }

hwNqaResultsRttSum OBJECT-TYPE
    SYNTAX      Unsigned32
    MAX-ACCESS  read-only
    STATUS      current
    DESCRIPTION
        "The sum of round trip time."
    ::= { hwNqaResultsEntry 12 }

hwNqaResultsNumOfDelaySD OBJECT-TYPE
    SYNTAX      Unsigned32
    MAX-ACCESS  read-only
    STATUS      current
    DESCRIPTION
        "The number of delay from source to destination that are
        successfully measured."
    ::= { hwNqaResultsEntry 13 }

hwNqaResultsMinDelaySD OBJECT-TYPE
    SYNTAX      Unsigned32
    MAX-ACCESS  read-only
    STATUS      current
    DESCRIPTION
        "The minimum of all one way times from source to destination."
    ::= { hwNqaResultsEntry 14 }

hwNqaResultsSumDelaySD OBJECT-TYPE
    SYNTAX      Unsigned32
    MAX-ACCESS  read-only
    STATUS      current
    DESCRIPTION
        "The sum of one way times from source to destination."
    ::= { hwNqaResultsEntry 15 }

hwNqaResultsSum2DelaySD OBJECT-TYPE
    SYNTAX      Unsigned32
    MAX-ACCESS  read-only
    STATUS      current
    DESCRIPTION
        "The sum of squares of one way times from source to  destination."
    ::= { hwNqaResultsEntry 16 }

hwNqaResultsNumOfDelayDS OBJECT-TYPE
    SYNTAX      Unsigned32
    MAX-ACCESS  read-only
    STATUS      current
    DESCRIPTION
        "The number of delay from destination to source that are
        successfully measured."
    ::= { hwNqaResultsEntry 17 }

hwNqaResultsMinDelayDS OBJECT-TYPE
    SYNTAX      Unsigned32
    MAX-ACCESS  read-only
    STATUS      current
    DESCRIPTION
        "The minimum of all one way times from destination to source."
    ::= { hwNqaResultsEntry 18 }

hwNqaResultsSumDelayDS OBJECT-TYPE
    SYNTAX      Unsigned32
    MAX-ACCESS  read-only
    STATUS      current
    DESCRIPTION
        "The sum of one way times from destination to source."
    ::= { hwNqaResultsEntry 19 }

hwNqaResultsSum2DelayDS OBJECT-TYPE
    SYNTAX      Unsigned32
    MAX-ACCESS  read-only
    STATUS      current
    DESCRIPTION
        "The sum of squares of one way times from destination to source."
    ::= { hwNqaResultsEntry 20 }

-- =================================================================
--    Jitter Statistics Table
-- =================================================================


hwNqaJitterStatsTable OBJECT-TYPE
    SYNTAX SEQUENCE OF HwNqaJitterStatsEntry
    MAX-ACCESS  not-accessible
    STATUS      current
    DESCRIPTION
        "Statistics table for latest jitter activity."
    ::= { hwNqaObjects 4 }

hwNqaJitterStatsEntry OBJECT-TYPE
    SYNTAX      HwNqaJitterStatsEntry
    MAX-ACCESS  not-accessible
    STATUS      current
    DESCRIPTION
        "An entry contains the statistics for the latest jitter activity.
        This entry is created only if the pingCtlType is hwNqajitter."
    INDEX {
            pingCtlOwnerIndex,
            pingCtlTestName
          }
    ::= { hwNqaJitterStatsTable 1 }

HwNqaJitterStatsEntry  ::= SEQUENCE
{
    hwNqaJitterStatsNumOfRTT                Counter32,
    hwNqaJitterStatsMinOfPositivesSD        Gauge32,
    hwNqaJitterStatsMaxOfPositivesSD        Gauge32,
    hwNqaJitterStatsNumOfPositivesSD        Gauge32,
    hwNqaJitterStatsSumOfPositivesSD        Gauge32,
    hwNqaJitterStatsSum2PositivesSD         Gauge32,
    hwNqaJitterStatsMinOfNegativesSD        Gauge32,
    hwNqaJitterStatsMaxOfNegativesSD        Gauge32,
    hwNqaJitterStatsNumOfNegativesSD        Gauge32,
    hwNqaJitterStatsSumOfNegativesSD        Gauge32,
    hwNqaJitterStatsSum2NegativesSD         Gauge32,
    hwNqaJitterStatsMinOfPositivesDS        Gauge32,
    hwNqaJitterStatsMaxOfPositivesDS        Gauge32,
    hwNqaJitterStatsNumOfPositivesDS        Gauge32,
    hwNqaJitterStatsSumOfPositivesDS        Gauge32,
    hwNqaJitterStatsSum2PositivesDS         Gauge32,
    hwNqaJitterStatsMinOfNegativesDS        Gauge32,
    hwNqaJitterStatsMaxOfNegativesDS        Gauge32,
    hwNqaJitterStatsNumOfNegativesDS        Gauge32,
    hwNqaJitterStatsSumOfNegativesDS        Gauge32,
    hwNqaJitterStatsSum2NegativesDS         Gauge32,
    hwNqaJitterStatsPacketLossSD            Gauge32,
    hwNqaJitterStatsPacketLossDS            Gauge32,
    hwNqaJitterStatsAvePositivesSD          Gauge32,
    hwNqaJitterStatsAveNegativesSD          Gauge32,
    hwNqaJitterStatsAvePositivesDS          Gauge32,
    hwNqaJitterStatsAveNegativesDS          Gauge32,
    hwNqaJitterStatsPktLossUnknown          Gauge32,
    hwNqaJitterStatsOperOfICPIF             Gauge32,
    hwNqaJitterStatsOperOfMOS               Gauge32
}

hwNqaJitterStatsNumOfRTT OBJECT-TYPE
    SYNTAX      Counter32
    MAX-ACCESS  read-only
    STATUS      current
    DESCRIPTION
        "The number of received destination device responses with which
        jitter test can reach round-trip time."
    ::= { hwNqaJitterStatsEntry 1 }


hwNqaJitterStatsMinOfPositivesSD OBJECT-TYPE
    SYNTAX      Gauge32
    MAX-ACCESS  read-only
    STATUS      current
    DESCRIPTION
        "The value of time that records the minimal positive jitter value from
        source to destination in the jitter test."
    ::= { hwNqaJitterStatsEntry 2 }

hwNqaJitterStatsMaxOfPositivesSD OBJECT-TYPE
    SYNTAX      Gauge32
    MAX-ACCESS  read-only
    STATUS      current
    DESCRIPTION
        "The value of time that records the maximal positive jitter value from
        source to destination in the jitter test."
    ::= { hwNqaJitterStatsEntry 3 }

hwNqaJitterStatsNumOfPositivesSD OBJECT-TYPE
    SYNTAX      Gauge32
    MAX-ACCESS  read-only
    STATUS      current
    DESCRIPTION
        "The number that records positive jitter times from source to
        destination in the jitter test.
        The total number of the value of all positive jitters in packets
        sent from source to destination."
    ::= { hwNqaJitterStatsEntry 4 }

hwNqaJitterStatsSumOfPositivesSD OBJECT-TYPE
    SYNTAX      Gauge32
    MAX-ACCESS  read-only
    STATUS      current
    DESCRIPTION
        "The value of time that records the sum of positive jitter values from
        source to destination in the jitter test."
    ::= { hwNqaJitterStatsEntry 5 }

hwNqaJitterStatsSum2PositivesSD OBJECT-TYPE
    SYNTAX      Gauge32
    MAX-ACCESS  read-only
    STATUS      current
    DESCRIPTION
        "The value of time that records the sum of square of positive jitter
        values from source to destination in the jitter test."
    ::= { hwNqaJitterStatsEntry 6 }

hwNqaJitterStatsMinOfNegativesSD OBJECT-TYPE
    SYNTAX      Gauge32
    MAX-ACCESS  read-only
    STATUS      current
    DESCRIPTION
        "The value of time that records the minimal absolute values of
        negative jitter value from source to destination in the jitter test."
    ::= { hwNqaJitterStatsEntry 7 }

hwNqaJitterStatsMaxOfNegativesSD OBJECT-TYPE
    SYNTAX      Gauge32
    MAX-ACCESS  read-only
    STATUS      current
    DESCRIPTION
        "The value of time that records the maximal absolute values of negative
        jitter value from source to destination in the jitter test."
    ::= { hwNqaJitterStatsEntry 8 }

hwNqaJitterStatsNumOfNegativesSD OBJECT-TYPE
    SYNTAX      Gauge32
    MAX-ACCESS  read-only
    STATUS      current
    DESCRIPTION
        "The number that records negative jitter times from source to
        destination in the jitter test.
        The total number of all negative jitter values in packets
        sent from source to destination."
    ::= { hwNqaJitterStatsEntry 9 }

hwNqaJitterStatsSumOfNegativesSD OBJECT-TYPE
    SYNTAX      Gauge32
    MAX-ACCESS  read-only
    STATUS      current
    DESCRIPTION
        "The value of time that records the sum of negative jitter values from
        source to destination in the jitter test.
        The total number of the value of all negative jitters in packets
        sent from source to destination."
    ::= { hwNqaJitterStatsEntry 10 }

hwNqaJitterStatsSum2NegativesSD OBJECT-TYPE
    SYNTAX      Gauge32
    MAX-ACCESS  read-only
    STATUS      current
    DESCRIPTION
        "The value of time that records the sum of square of negative jitter
        values from source to destination in the jitter test."
    ::= { hwNqaJitterStatsEntry 11 }

hwNqaJitterStatsMinOfPositivesDS OBJECT-TYPE
    SYNTAX      Gauge32
    MAX-ACCESS  read-only
    STATUS      current
    DESCRIPTION
        "The value of time that records the minimal positive jitter value from
        destination to source in the jitter test."
    ::= { hwNqaJitterStatsEntry 12 }

hwNqaJitterStatsMaxOfPositivesDS OBJECT-TYPE
    SYNTAX      Gauge32
    MAX-ACCESS  read-only
    STATUS      current
    DESCRIPTION
        "The value of time that records the maximal positive jitter value from
        destination to source in the jitter test."
    ::= { hwNqaJitterStatsEntry 13 }

hwNqaJitterStatsNumOfPositivesDS OBJECT-TYPE
    SYNTAX      Gauge32
    MAX-ACCESS  read-only
    STATUS      current
    DESCRIPTION
        "The number that records positive jitter times from destination to
        source in the jitter test."
    ::= { hwNqaJitterStatsEntry 14 }

hwNqaJitterStatsSumOfPositivesDS OBJECT-TYPE
    SYNTAX      Gauge32
    MAX-ACCESS  read-only
    STATUS      current
    DESCRIPTION
        "The value of time that records the sum of positive jitter values from
        destination to source in the jitter test."
    ::= { hwNqaJitterStatsEntry 15 }

hwNqaJitterStatsSum2PositivesDS OBJECT-TYPE
    SYNTAX      Gauge32
    MAX-ACCESS  read-only
    STATUS      current
    DESCRIPTION
        "The value of time that records the sum of square of positive jitter
        values from destination to source in the jitter test."
    ::= { hwNqaJitterStatsEntry 16 }

hwNqaJitterStatsMinOfNegativesDS OBJECT-TYPE
    SYNTAX      Gauge32
    MAX-ACCESS  read-only
    STATUS      current
    DESCRIPTION
        "The value of time that records the minimal absolute values of negative
        jitter value from destination to source in the jitter test."
    ::= { hwNqaJitterStatsEntry 17 }

hwNqaJitterStatsMaxOfNegativesDS OBJECT-TYPE
    SYNTAX      Gauge32
    MAX-ACCESS  read-only
    STATUS      current
    DESCRIPTION
        "The value of time that records the maximal absolute values of negative
        jitter value from destination to source in the jitter test."
    ::= { hwNqaJitterStatsEntry 18 }

hwNqaJitterStatsNumOfNegativesDS OBJECT-TYPE
    SYNTAX      Gauge32
    MAX-ACCESS  read-only
    STATUS      current
    DESCRIPTION
        "The number that records negative jitter times from destination to source
        in the jitter test."
    ::= { hwNqaJitterStatsEntry 19 }

hwNqaJitterStatsSumOfNegativesDS OBJECT-TYPE
    SYNTAX      Gauge32
    MAX-ACCESS  read-only
    STATUS      current
    DESCRIPTION
        "The value of time that records the sum of negative jitter values from
        destination to source in the jitter test."
    ::= { hwNqaJitterStatsEntry 20 }

hwNqaJitterStatsSum2NegativesDS OBJECT-TYPE
    SYNTAX      Gauge32
    MAX-ACCESS  read-only
    STATUS      current
    DESCRIPTION
        "The value of time that records the sum of square of negative jitter
        values from destination to source in the jitter test."
    ::= { hwNqaJitterStatsEntry 21 }

hwNqaJitterStatsPacketLossSD OBJECT-TYPE
    SYNTAX      Gauge32
    MAX-ACCESS  read-only
    STATUS      current
    DESCRIPTION
        "The lost packets number sent from source to destination."
    ::= { hwNqaJitterStatsEntry 22 }

hwNqaJitterStatsPacketLossDS OBJECT-TYPE
    SYNTAX      Gauge32
    MAX-ACCESS  read-only
    STATUS      current
    DESCRIPTION
        "The lost packets number sent from destination to source."
    ::= { hwNqaJitterStatsEntry 23 }

hwNqaJitterStatsAvePositivesSD OBJECT-TYPE
    SYNTAX      Gauge32
    MAX-ACCESS  read-only
    STATUS      current
    DESCRIPTION
        "The value of time that records the average positive jitter value
        from source to destination."
    ::= { hwNqaJitterStatsEntry 24 }

hwNqaJitterStatsAveNegativesSD OBJECT-TYPE
    SYNTAX      Gauge32
    MAX-ACCESS  read-only
    STATUS      current
    DESCRIPTION
        "The value of time that records the average negative jitter value
        from source to destination."
    ::= { hwNqaJitterStatsEntry 25 }

hwNqaJitterStatsAvePositivesDS OBJECT-TYPE
    SYNTAX      Gauge32
    MAX-ACCESS  read-only
    STATUS      current
    DESCRIPTION
        "The value of time that records the average positive jitter value
        from destination to source."
    ::= { hwNqaJitterStatsEntry 26 }

hwNqaJitterStatsAveNegativesDS OBJECT-TYPE
    SYNTAX      Gauge32
    MAX-ACCESS  read-only
    STATUS      current
    DESCRIPTION
        "The value of time that records the average negative jitter value
        from destination to source."
    ::= { hwNqaJitterStatsEntry 27 }

hwNqaJitterStatsPktLossUnknown OBJECT-TYPE
    SYNTAX      Gauge32
    UNITS       "milliseconds"
    MAX-ACCESS  read-only
    STATUS      current
    DESCRIPTION
        "The number of packets which is lost with unknown reason."
    ::= { hwNqaJitterStatsEntry 28 }

hwNqaJitterStatsOperOfICPIF OBJECT-TYPE
    SYNTAX      Gauge32
    MAX-ACCESS  read-only
    STATUS      current
    DESCRIPTION
        "The ICPIF (Calculated Planning Impairment Factor) value for the latest
        jitter test."
    ::= { hwNqaJitterStatsEntry 29 }

hwNqaJitterStatsOperOfMOS OBJECT-TYPE
    SYNTAX      Gauge32
    MAX-ACCESS  read-only
    STATUS      current
    DESCRIPTION
        "The MOS (Mean Opinion Score) value for the latest jitter test."
    ::= { hwNqaJitterStatsEntry 30 }

hwNqaAgentEnable OBJECT-TYPE
    SYNTAX      INTEGER{
                enable(1),
                disable(2)
                }
    MAX-ACCESS  read-write
    STATUS      current
    DESCRIPTION
        "Enable NQA agent function."
    DEFVAL { disable }
    ::= { hwNqaObjects 5 }

-- =================================================================
--   Tcp server configuration information Statistics Table
-- =================================================================


hwNqaTcpServerTable OBJECT-TYPE
    SYNTAX SEQUENCE OF HwNqaTcpServerEntry
    MAX-ACCESS  not-accessible
    STATUS      current
    DESCRIPTION
        "A table which contains the status of NQA tcp server
        configuration information."
    ::= { hwNqaObjects 6 }

hwNqaTcpServerEntry OBJECT-TYPE
    SYNTAX      HwNqaTcpServerEntry
    MAX-ACCESS  not-accessible
    STATUS      current
    DESCRIPTION
        "A table which contains the status of NQA tcp server
        configuration information.

        This entry includes not only the tcp server ip address
        but also the tcp server port."
    INDEX {
            hwNqaTcpServerIpAddress,
            hwNqaTcpServerPort
          }
    ::= { hwNqaTcpServerTable 1 }

HwNqaTcpServerEntry  ::= SEQUENCE
{
    hwNqaTcpServerIpAddress                InetAddress,
    hwNqaTcpServerPort                     Integer32,
    hwNqaTcpServerRowStatus                RowStatus
}

hwNqaTcpServerIpAddress          OBJECT-TYPE
    SYNTAX      InetAddress
    MAX-ACCESS  not-accessible
    STATUS      current
    DESCRIPTION
        "Tcp server's ip address."
    DEFVAL { ''H }
    ::= { hwNqaTcpServerEntry 1 }

hwNqaTcpServerPort          OBJECT-TYPE
    SYNTAX      Integer32 (0..65536)
    MAX-ACCESS  not-accessible
    STATUS      current
    DESCRIPTION
        "Tcp server's port number."
    DEFVAL      { 0 }
    ::= { hwNqaTcpServerEntry 2 }

hwNqaTcpServerRowStatus OBJECT-TYPE
    SYNTAX      RowStatus
    MAX-ACCESS  read-create
    STATUS      current
    DESCRIPTION
        "hwNqaTcpServerIpAddress and hwNqaTcpServerPort
        must be set during a creation operation."
    REFERENCE
        "RFC 2579"
    ::= { hwNqaTcpServerEntry 3 }

hwNqaUdpServerTable OBJECT-TYPE
    SYNTAX SEQUENCE OF HwNqaUdpServerEntry
    MAX-ACCESS  not-accessible
    STATUS      current
    DESCRIPTION
        "Status of NQA udp server configuration information."
    ::= { hwNqaObjects 7 }

hwNqaUdpServerEntry OBJECT-TYPE
    SYNTAX      HwNqaUdpServerEntry
    MAX-ACCESS  not-accessible
    STATUS      current
    DESCRIPTION
        "This entry includes not only the udp server ip address
        but also the udp server udp port."
    INDEX {
            hwNqaUdpServerIpAddress,
            hwNqaUdpServerPort
          }
    ::= { hwNqaUdpServerTable 1 }

HwNqaUdpServerEntry  ::= SEQUENCE
{
    hwNqaUdpServerIpAddress                InetAddress,
    hwNqaUdpServerPort                     Integer32,
    hwNqaUdpServerRowStatus                RowStatus
}

hwNqaUdpServerIpAddress          OBJECT-TYPE
    SYNTAX      InetAddress
    MAX-ACCESS  not-accessible
    STATUS      current
    DESCRIPTION
        "Udp server's ip address."
    DEFVAL { ''H }
    ::= { hwNqaUdpServerEntry 1 }

hwNqaUdpServerPort          OBJECT-TYPE
    SYNTAX      Integer32 (0..65536)
    MAX-ACCESS  not-accessible
    STATUS      current
    DESCRIPTION
        "Udp server's port number."
    DEFVAL      { 0 }
    ::= { hwNqaUdpServerEntry 2 }

hwNqaUdpServerRowStatus OBJECT-TYPE
    SYNTAX      RowStatus
    MAX-ACCESS  read-create
    STATUS      current
    DESCRIPTION
        "hwNqaUdpServerIpAddress and hwNqaUdpServerPort
        must be set during a creation operation."
    REFERENCE
        "RFC 2579"
    ::= { hwNqaUdpServerEntry 3 }

hwNqaServerEnable OBJECT-TYPE
    SYNTAX      INTEGER{
                enable(1),
                disable(2)
                }
    MAX-ACCESS  read-write
    STATUS      current
    DESCRIPTION
        "Enable NQA server function."
    DEFVAL { disable }
    ::= { hwNqaObjects 8 }

hwNqaStatsMaxGroupNumber OBJECT-TYPE
    SYNTAX     Integer32
    MAX-ACCESS read-only
    STATUS     current
    DESCRIPTION
        "The maximum number saved per group. The maximum value of
        hwNqaCtlStatisticsGroupNumber can not exceed the value of
        this object."
    ::= { hwNqaObjects 9 }


hwNqaStatisticsCtlTable OBJECT-TYPE
    SYNTAX      SEQUENCE OF HwNqaStatisticsCtlEntry
    MAX-ACCESS  not-accessible
    STATUS      current
    DESCRIPTION
        "Defines the NQA statistics control table for providing, via SNMP,
        the capability of performing NQA operations at a remote host.
        The results of these operations are stored in the
        hwNqaStatisticsResultsTable and the hwNqaGroupStatsJitterTable."
    ::= { hwNqaObjects 10 }

hwNqaStatisticsCtlEntry OBJECT-TYPE
    SYNTAX      HwNqaStatisticsCtlEntry
    MAX-ACCESS  not-accessible
    STATUS      current
    DESCRIPTION
        "Defines an entry in the hwNqaStatisticsCtlTable.
        The hwNqaStatisticsCtlTable has the same index as the
        pingCtlTable in order for a hwNqaStatisticsCtlTable to
        correspond to the pingCtlEntry."
    AUGMENTS    { pingCtlEntry }
    ::= { hwNqaStatisticsCtlTable 1 }

HwNqaStatisticsCtlEntry ::=
    SEQUENCE
        {
            hwNqaCtlStatisticsInterval       Unsigned32,
            hwNqaCtlStatisticsGroupNumber    Unsigned32,
            hwNqaCtlStatisticsKeptTime       Unsigned32,
            hwNqaCtlBeginTime                DateAndTime,
            hwNqaCtlLifeTime                 Unsigned32
        }

hwNqaCtlStatisticsInterval OBJECT-TYPE
    SYNTAX     Unsigned32
    UNITS      "minutes"
    MAX-ACCESS read-create
    STATUS     current
    DESCRIPTION
        "Statistic information will be calculated after the time that is
        the value of hwNqaCtlStatisticsInterval."
    ::= { hwNqaStatisticsCtlEntry 1 }

hwNqaCtlStatisticsGroupNumber OBJECT-TYPE
    SYNTAX     Unsigned32
    MAX-ACCESS read-create
    STATUS     current
    DESCRIPTION
        "The value of this object indicates the number of group saved.
        The length of this object is from 1 to hwNqaStatsMaxGroupNumber."
    DEFVAL     { 2 }
    ::= { hwNqaStatisticsCtlEntry 2 }

hwNqaCtlStatisticsKeptTime OBJECT-TYPE
    SYNTAX     Unsigned32(1..1440)
    UNITS      "minutes"
    MAX-ACCESS read-create
    STATUS     current
    DESCRIPTION
        "To indicate how long the statistic information will be saved after
        the test stops."
    DEFVAL     { 120 }
    ::= { hwNqaStatisticsCtlEntry 3 }

hwNqaCtlBeginTime OBJECT-TYPE
    SYNTAX     DateAndTime
    MAX-ACCESS read-create
    STATUS     current
    DESCRIPTION
        "Time at which the type-specified test will start."
    ::= { hwNqaStatisticsCtlEntry 4 }

hwNqaCtlLifeTime OBJECT-TYPE
    SYNTAX     Unsigned32
    UNITS      "seconds"
    MAX-ACCESS read-create
    STATUS     current
    DESCRIPTION
        "To indicate how long the type-specified test will last."
    DEFVAL     { 0 }
    ::= { hwNqaStatisticsCtlEntry 5 }

hwNqaStatisticsResultsTable OBJECT-TYPE
    SYNTAX      SEQUENCE OF HwNqaStatisticsResultsEntry
    MAX-ACCESS  not-accessible
    STATUS      current
    DESCRIPTION
        "Defines the NQA statistics results table for providing
        the capability of performing NQA operations at a remote
        host. The statistics results of these operations in a statistic cycle
        are stored in the hwNqaStatisticsResultsTable. The statistic cycle is
        the value of hwNqaCtlStatisticsInterval.
        The first two index identify the pingCtlEntry that the probe statistics
        result (HwNqaStatisticsResultsEntry) belongs to."

    ::= { hwNqaObjects 11 }


hwNqaStatisticsResultsEntry OBJECT-TYPE
    SYNTAX       HwNqaStatisticsResultsEntry
    MAX-ACCESS   not-accessible
    STATUS       current
    DESCRIPTION
        "Defines an entry in the hwNqaStatisticsResultsTable. The
        hwNqaStatisticsResultsTable has the same index as the
        pingCtlTable in order for a hwNqaStatisticsResultsEntry to
        correspond to the pingCtlEntry that caused it to be created."
    INDEX
        {
            pingCtlOwnerIndex,
            pingCtlTestName,
            hwNqaStatResIndex
        }
    ::= { hwNqaStatisticsResultsTable 1 }

HwNqaStatisticsResultsEntry ::=
    SEQUENCE
        {
            hwNqaStatResIndex                  Unsigned32,
            hwNqaStatResIpTargetAddressType    InetAddressType,
            hwNqaStatResIpTargetAddress        InetAddress,
            hwNqaStatResMinRtt                 Gauge32,
            hwNqaStatResMaxRtt                 Gauge32,
            hwNqaStatResAverageRtt             Gauge32,
            hwNqaStatResProbeResponses         Counter32,
            hwNqaStatResSentProbes             Counter32,
            hwNqaStatResRttSumOfSquares        Counter32,
            hwNqaStatResStartTime              DateAndTime,
            hwNqaStatResInterval               Gauge32,
            hwNqaStatResRttNumDisconnects      Counter32,
            hwNqaStatResRttTimeouts            Counter32,
            hwNqaStatResRttBusies              Counter32,
            hwNqaStatResRttNoConnections       Counter32,
            hwNqaStatResRttDrops               Counter32,
            hwNqaStatResRttSequenceErrors      Counter32,
            hwNqaStatResRttErrors              Counter32,
            hwNqaStatResLostPacketRatio        Gauge32,
            hwNqaStatResPacketLateArrival      Counter32,
            hwNqaStatResRttSum                 Counter32,
            hwNqaStatResNumOfDelaySD           Counter32,
            hwNqaStatResMinDelaySD             Gauge32,
            hwNqaStatResMaxDelaySD             Gauge32,
            hwNqaStatResSumDelaySD             Counter32,
            hwNqaStatResSum2DelaySD            Counter32,
            hwNqaStatResNumOfDelayDS           Counter32,
            hwNqaStatResMinDelayDS             Gauge32,
            hwNqaStatResMaxDelayDS             Gauge32,
            hwNqaStatResSumDelayDS             Counter32,
            hwNqaStatResSum2DelayDS            Counter32
        }

hwNqaStatResIndex OBJECT-TYPE
    SYNTAX      Unsigned32(1..'ffffffff'h)
    MAX-ACCESS  not-accessible
    STATUS      current
    DESCRIPTION
        "An entry in this table is created when the statistics
        result of a NQA probe is determined.

        An implementation MUST start assigning
        hwNqaStatResIndex values at 1 and wrap after
        exceeding the maximum possible value as defined by
        the limit of this object ('ffffffff'h)."
    ::= { hwNqaStatisticsResultsEntry 1 }

hwNqaStatResIpTargetAddressType OBJECT-TYPE
    SYNTAX      InetAddressType
    MAX-ACCESS  read-only
    STATUS      current
    DESCRIPTION
        "This object indicates the type of address stored
        in the corresponding hwNqaStatResIpTargetAddress
        object."
    DEFVAL { unknown }
    ::= { hwNqaStatisticsResultsEntry 2 }

hwNqaStatResIpTargetAddress OBJECT-TYPE
    SYNTAX      InetAddress
    MAX-ACCESS  read-only
    STATUS      current
    DESCRIPTION
        "This object represent the host address to be used at a remote host for
        performing a network analysis operation."
    DEFVAL { ''H }
    ::= { hwNqaStatisticsResultsEntry 3 }

hwNqaStatResMinRtt  OBJECT-TYPE
    SYNTAX      Gauge32
    UNITS       "milliseconds"
    MAX-ACCESS  read-only
    STATUS      current
    DESCRIPTION
        "The minimum NQA probe round-trip-time (RTT) received. The value
        of 0 for this object implies that no RTT has been received."
    ::= { hwNqaStatisticsResultsEntry 4 }

hwNqaStatResMaxRtt OBJECT-TYPE
    SYNTAX      Gauge32
    UNITS       "milliseconds"
    MAX-ACCESS  read-only
    STATUS      current
    DESCRIPTION
        "The maximum NQA probe round-trip-time (RTT) received. The value
        of 0 for this object implies that no RTT has been received."
    ::= { hwNqaStatisticsResultsEntry 5 }

hwNqaStatResAverageRtt OBJECT-TYPE
    SYNTAX      Gauge32
    UNITS       "milliseconds"
    MAX-ACCESS  read-only
    STATUS      current
    DESCRIPTION
        "The average NQA probe round-trip-time (RTT)."
    ::= { hwNqaStatisticsResultsEntry 6 }

hwNqaStatResProbeResponses OBJECT-TYPE
    SYNTAX      Counter32
    MAX-ACCESS  read-only
    STATUS      current
    DESCRIPTION
        "The number of responses received. The value of this object
        MUST be reported as 0 when no probe responses have been
        received."
    ::= { hwNqaStatisticsResultsEntry 7 }

hwNqaStatResSentProbes OBJECT-TYPE
    SYNTAX      Counter32
    UNITS       "probes"
    MAX-ACCESS  read-only
    STATUS      current
    DESCRIPTION
        "The value of this object reflects the number of probes sent.
        The value of this object MUST be reported as 0 when no probes
        have been sent."
    ::= { hwNqaStatisticsResultsEntry 8 }

hwNqaStatResRttSumOfSquares OBJECT-TYPE
    SYNTAX      Counter32
    UNITS       "milliseconds"
    MAX-ACCESS  read-only
    STATUS      current
    DESCRIPTION
        "This object contains the sum of the squares for all NQA
        responses received. The value of this object MUST
        be reported as 0 when no NQA responses have been
        received."
    ::= { hwNqaStatisticsResultsEntry 9 }

hwNqaStatResStartTime OBJECT-TYPE
    SYNTAX      DateAndTime
    MAX-ACCESS  read-only
    STATUS      current
    DESCRIPTION
        "This object contains the start time of the statistic."
    ::= { hwNqaStatisticsResultsEntry 10 }

hwNqaStatResInterval OBJECT-TYPE
    SYNTAX      Gauge32
    UNITS       "seconds"
    MAX-ACCESS  read-only
    STATUS      current
    DESCRIPTION
        "This object contains the interval between two times of statistic."
    ::= { hwNqaStatisticsResultsEntry 11 }

hwNqaStatResRttNumDisconnects OBJECT-TYPE
    SYNTAX      Counter32
    MAX-ACCESS  read-only
    STATUS      current
    DESCRIPTION
        "The number of times that a NQA probe failed because the destination
        became disconnected.
        For connectionless protocol pingCtlTypes, this number should be
        zero."
    ::= { hwNqaStatisticsResultsEntry 12 }

hwNqaStatResRttTimeouts OBJECT-TYPE
    SYNTAX      Counter32
    MAX-ACCESS  read-only
    STATUS      current
    DESCRIPTION
       "The number of times that a probe failed because the probe timed out."
    ::= { hwNqaStatisticsResultsEntry 13 }

hwNqaStatResRttBusies OBJECT-TYPE
    SYNTAX      Counter32
    MAX-ACCESS  read-only
    STATUS      current
    DESCRIPTION
        "The number of times that a NQA probe failed because
        errors related to sockets."
    ::= { hwNqaStatisticsResultsEntry 14 }

hwNqaStatResRttNoConnections OBJECT-TYPE
    SYNTAX      Counter32
    MAX-ACCESS  read-only
    STATUS      current
    DESCRIPTION
        "The number of times that a NQA probe failed because the
        probe destination is unavailable.
        For connectionless protocol pingCtlTypes, this number should be
        zero."
    ::= { hwNqaStatisticsResultsEntry 15 }

hwNqaStatResRttDrops OBJECT-TYPE
    SYNTAX      Counter32
    MAX-ACCESS  read-only
    STATUS      current
    DESCRIPTION
        "The number of times that a NQA operation failed to initiate
        for unavailibility of necessary internal resources."
    ::= { hwNqaStatisticsResultsEntry 16 }

hwNqaStatResRttSequenceErrors OBJECT-TYPE
    SYNTAX      Counter32
    MAX-ACCESS  read-only
    STATUS      current
    DESCRIPTION
        "The number of packets arrived out of sequence."
    ::= { hwNqaStatisticsResultsEntry 17 }

hwNqaStatResRttErrors OBJECT-TYPE
    SYNTAX      Counter32
    MAX-ACCESS  read-only
    STATUS      current
    DESCRIPTION
        "The number of other errors."
    ::= { hwNqaStatisticsResultsEntry 18 }

hwNqaStatResLostPacketRatio OBJECT-TYPE
    SYNTAX      Gauge32
    MAX-ACCESS  read-only
    STATUS      current
    DESCRIPTION
        "The value of this object reflects the drop rate of NQA
        test packet.
        For example, if the value is 30, that means source device
        only had received 70 percent packets of total sent packets."
    ::= { hwNqaStatisticsResultsEntry 19 }

hwNqaStatResPacketLateArrival OBJECT-TYPE
    SYNTAX      Counter32
    MAX-ACCESS  read-only
    STATUS      current
    DESCRIPTION
        "The value of this object reflects the number of the packets that
        arrived after the timeout."
    ::= { hwNqaStatisticsResultsEntry 20 }

    hwNqaStatResRttSum OBJECT-TYPE
    SYNTAX      Counter32
    MAX-ACCESS  read-only
    STATUS      current
    DESCRIPTION
        "This object contains the sum of the squares for all NQA
        responses received during the test lifetime. The value of this object
        MUST be reported as 0 when no NQA responses have been received."
    ::= { hwNqaStatisticsResultsEntry 21 }

hwNqaStatResNumOfDelaySD OBJECT-TYPE
    SYNTAX      Counter32
    MAX-ACCESS  read-only
    STATUS      current
    DESCRIPTION
        "The number of one way times from source to destination that are
        successfully measured."
    ::= { hwNqaStatisticsResultsEntry 22 }

hwNqaStatResMinDelaySD OBJECT-TYPE
    SYNTAX      Gauge32
    MAX-ACCESS  read-only
    STATUS      current
    DESCRIPTION
        "The minimum one way times from source to destination."
    ::= { hwNqaStatisticsResultsEntry 23 }

hwNqaStatResMaxDelaySD OBJECT-TYPE
    SYNTAX      Gauge32
    MAX-ACCESS  read-only
    STATUS      current
    DESCRIPTION
        "The maximum one way times from source to destination."
    ::= { hwNqaStatisticsResultsEntry 24 }

hwNqaStatResSumDelaySD OBJECT-TYPE
    SYNTAX      Counter32
    MAX-ACCESS  read-only
    STATUS      current
    DESCRIPTION
        "The sum of one way times from source to destination."
    ::= { hwNqaStatisticsResultsEntry 25 }

hwNqaStatResSum2DelaySD OBJECT-TYPE
    SYNTAX      Counter32
    MAX-ACCESS  read-only
    STATUS      current
    DESCRIPTION
        "The sum of squares of one way times from source to destination."
    ::= { hwNqaStatisticsResultsEntry 26 }

hwNqaStatResNumOfDelayDS OBJECT-TYPE
    SYNTAX      Counter32
    MAX-ACCESS  read-only
    STATUS      current
    DESCRIPTION
        "The number of one way times from destination to source that are
        successfully measured."
    ::= { hwNqaStatisticsResultsEntry 27 }

hwNqaStatResMinDelayDS OBJECT-TYPE
    SYNTAX      Gauge32
    MAX-ACCESS  read-only
    STATUS      current
    DESCRIPTION
        "The minimum one way times from destination to source."
    ::= { hwNqaStatisticsResultsEntry 28 }

hwNqaStatResMaxDelayDS OBJECT-TYPE
    SYNTAX      Gauge32
    MAX-ACCESS  read-only
    STATUS      current
    DESCRIPTION
        "The maximum one way times from destination to source."
    ::= { hwNqaStatisticsResultsEntry 29 }

hwNqaStatResSumDelayDS OBJECT-TYPE
    SYNTAX      Counter32
    MAX-ACCESS  read-only
    STATUS      current
    DESCRIPTION
        "The sum of one way times from destination to source."
    ::= { hwNqaStatisticsResultsEntry 30 }

hwNqaStatResSum2DelayDS OBJECT-TYPE
    SYNTAX      Counter32
    MAX-ACCESS  read-only
    STATUS      current
    DESCRIPTION
        "The sum of squares of one way times from destination to source."
    ::= { hwNqaStatisticsResultsEntry 31 }

-- =================================================================
--    hwNqaGroupStatsJitterTable
-- =================================================================
hwNqaGroupStatsJitterTable OBJECT-TYPE
    SYNTAX      SEQUENCE OF HwNqaGroupStatsJitterEntry
    MAX-ACCESS  not-accessible
    STATUS      current
    DESCRIPTION
        "Test Group Statistic table for jitter activity in a statistic cycle.
        The statistic cycle is the value of hwNqaCtlStatisticsInterval.
        The first two index identify the pingCtlEntry that a probe statistics
        result (HwNqaStatisticsResultsEntry) belongs to."
    ::= { hwNqaObjects 12 }

hwNqaGroupStatsJitterEntry OBJECT-TYPE
    SYNTAX      HwNqaGroupStatsJitterEntry
    MAX-ACCESS  not-accessible
    STATUS      current
    DESCRIPTION
        "An entry contains the group statistic information for jitter activity.
        This entry is created only if the pingCtlType is hwNqajitter."
    INDEX
        {
            pingCtlOwnerIndex,
            pingCtlTestName,
            hwNqaStatJitterIndex
        }
    ::= { hwNqaGroupStatsJitterTable 1 }

HwNqaGroupStatsJitterEntry ::=
    SEQUENCE
        {
            hwNqaStatJitterIndex               Unsigned32,
            hwNqaStatJitterMinOfPosSD          Gauge32,
            hwNqaStatJitterMaxOfPosSD          Gauge32,
            hwNqaStatJitterNumOfPosSD          Counter32,
            hwNqaStatJitterSumOfPosSD          Counter32,
            hwNqaStatJitterSumOfSquarePosSD    Counter32,
            hwNqaStatJitterMinOfNegSD          Gauge32,
            hwNqaStatJitterMaxOfNegSD          Gauge32,
            hwNqaStatJitterNumOfNegSD          Counter32,
            hwNqaStatJitterSumOfNegSD          Counter32,
            hwNqaStatJitterSumOfSquareNegSD    Counter32,
            hwNqaStatJitterMinOfPosDS          Gauge32,
            hwNqaStatJitterMaxOfPosDS          Gauge32,
            hwNqaStatJitterNumOfPosDS          Counter32,
            hwNqaStatJitterSumOfPosDS          Counter32,
            hwNqaStatJitterSumOfSquarePosDS    Counter32,
            hwNqaStatJitterMinOfNegDS          Gauge32,
            hwNqaStatJitterMaxOfNegDS          Gauge32,
            hwNqaStatJitterNumOfNegDS          Counter32,
            hwNqaStatJitterSumOfNegDS          Counter32,
            hwNqaStatJitterSumOfSquareNegDS    Counter32,
            hwNqaStatJitterPacketLossSD        Counter32,
            hwNqaStatJitterPacketLossDS        Counter32,
            hwNqaStatJitterAvePosSD            Gauge32,
            hwNqaStatJitterAveNegSD            Gauge32,
            hwNqaStatJitterAvePosDS            Gauge32,
            hwNqaStatJitterAveNegDS            Gauge32,
            hwNqaStatJitterPktLossUnknown      Counter32,
            hwNqaStatJitterMaxOfICPIF          Gauge32,
            hwNqaStatJitterMinOfICPIF          Gauge32,
            hwNqaStatJitterMaxOfMOS            Gauge32,
            hwNqaStatJitterMinOfMOS            Gauge32
        }

hwNqaStatJitterIndex OBJECT-TYPE
    SYNTAX      Unsigned32(1..'ffffffff'h)
    MAX-ACCESS  not-accessible
    STATUS      current
    DESCRIPTION
        "An entry in this table is created when the statistic
        result of a NQA probe in a statistic cycle is determined.

        An implementation MUST start assigning hwNqaStatJitterIndex
        values at 1 and wrap after exceeding the maximum possible
        value as defined by the limit of this object ('ffffffff'h)."
    ::= { hwNqaGroupStatsJitterEntry 1 }

hwNqaStatJitterMinOfPosSD OBJECT-TYPE
    SYNTAX      Gauge32
    UNITS       "milliseconds"
    MAX-ACCESS  read-only
    STATUS      current
    DESCRIPTION
        "The value of time that records the minimal positive jitter value
        from source to destination in jitter test."
    ::= { hwNqaGroupStatsJitterEntry 2 }

hwNqaStatJitterMaxOfPosSD OBJECT-TYPE
    SYNTAX      Gauge32
    UNITS       "milliseconds"
    MAX-ACCESS  read-only
    STATUS      current
    DESCRIPTION
        "The value of time that records the maximal positive jitter value
        from source to destination in the jitter test."
    ::= { hwNqaGroupStatsJitterEntry 3 }

hwNqaStatJitterNumOfPosSD OBJECT-TYPE
    SYNTAX      Counter32
    MAX-ACCESS  read-only
    STATUS      current
    DESCRIPTION
        "The number that records positive jitter times from source to
        destination in the jitter test.
        The total number of all positive jitter values in packets sent
        from source to destination."
    ::= { hwNqaGroupStatsJitterEntry 4 }

hwNqaStatJitterSumOfPosSD OBJECT-TYPE
    SYNTAX      Counter32
    UNITS       "milliseconds"
    MAX-ACCESS  read-only
    STATUS      current
    DESCRIPTION
        "The value of time that records the sum of positive jitter values
        from source to destination in the jitter test."
    ::= { hwNqaGroupStatsJitterEntry 5 }

hwNqaStatJitterSumOfSquarePosSD OBJECT-TYPE
    SYNTAX      Counter32
    UNITS       "milliseconds"
    MAX-ACCESS  read-only
    STATUS      current
    DESCRIPTION
        "The value of time that records the sum of square of positive jitter
        values from source to destination in the jitter test."
    ::= { hwNqaGroupStatsJitterEntry 6 }

hwNqaStatJitterMinOfNegSD OBJECT-TYPE
    SYNTAX      Gauge32
    UNITS       "milliseconds"
    MAX-ACCESS  read-only
    STATUS      current
    DESCRIPTION
        "The value of time that records the minimal absolute values of
        negative jitter value from source to destination in the jitter test."
    ::= { hwNqaGroupStatsJitterEntry 7 }

hwNqaStatJitterMaxOfNegSD OBJECT-TYPE
    SYNTAX      Gauge32
    UNITS       "milliseconds"
    MAX-ACCESS  read-only
    STATUS      current
    DESCRIPTION
        "The value of time that records the maximal absolute values of negative
        jitter value from source to destination in the jitter test."
    ::= { hwNqaGroupStatsJitterEntry 8 }

hwNqaStatJitterNumOfNegSD OBJECT-TYPE
    SYNTAX      Counter32
    MAX-ACCESS  read-only
    STATUS      current
    DESCRIPTION
        "The number that records negative jitter times from source to
        destination in the jitter test.
        The total number of all negative jitter values sent from source to
        destination."
    ::= { hwNqaGroupStatsJitterEntry 9 }

hwNqaStatJitterSumOfNegSD OBJECT-TYPE
    SYNTAX      Counter32
    UNITS       "milliseconds"
    MAX-ACCESS  read-only
    STATUS      current
    DESCRIPTION
        "The value of time that records the sum of negative jitter values
        from source to destination in the jitter test."
    ::= { hwNqaGroupStatsJitterEntry 10 }

hwNqaStatJitterSumOfSquareNegSD OBJECT-TYPE
    SYNTAX      Counter32
    UNITS       "milliseconds"
    MAX-ACCESS  read-only
    STATUS      current
    DESCRIPTION
        "The value of time that records the sum of square of negative jitter
        values from source to destination in the jitter test."
    ::= { hwNqaGroupStatsJitterEntry 11 }

hwNqaStatJitterMinOfPosDS OBJECT-TYPE
    SYNTAX      Gauge32
    UNITS       "milliseconds"
    MAX-ACCESS  read-only
    STATUS      current
    DESCRIPTION
        "The value of time that records the minimal positive jitter value
        from destination to source in the jitter test."
    ::= { hwNqaGroupStatsJitterEntry 12 }

hwNqaStatJitterMaxOfPosDS OBJECT-TYPE
    SYNTAX      Gauge32
    UNITS       "milliseconds"
    MAX-ACCESS  read-only
    STATUS      current
    DESCRIPTION
        "The value of time that records the maximal positive jitter value
        from destination to source in the jitter test."
    ::= { hwNqaGroupStatsJitterEntry 13 }

hwNqaStatJitterNumOfPosDS OBJECT-TYPE
    SYNTAX      Counter32
    MAX-ACCESS  read-only
    STATUS      current
    DESCRIPTION
        "The number that records positive jitter times from destination to
        source in the jitter test."
    ::= { hwNqaGroupStatsJitterEntry 14 }

hwNqaStatJitterSumOfPosDS OBJECT-TYPE
    SYNTAX      Counter32
    UNITS       "milliseconds"
    MAX-ACCESS  read-only
    STATUS      current
    DESCRIPTION
        "The value of time that records the sum of positive jitter values
        from destination to source in the jitter test."
    ::= { hwNqaGroupStatsJitterEntry 15 }

hwNqaStatJitterSumOfSquarePosDS OBJECT-TYPE
    SYNTAX      Counter32
    UNITS       "milliseconds"
    MAX-ACCESS  read-only
    STATUS      current
    DESCRIPTION
        "The value of time that records the sum of square of positive jitter
        values destination to source in the jitter test."
    ::= { hwNqaGroupStatsJitterEntry 16 }

hwNqaStatJitterMinOfNegDS OBJECT-TYPE
    SYNTAX      Gauge32
    UNITS       "milliseconds"
    MAX-ACCESS  read-only
    STATUS      current
    DESCRIPTION
        "The value of time that records the minimal absolute values of negative
        jitter value from destination to source in the jitter test."
    ::= { hwNqaGroupStatsJitterEntry 17 }

hwNqaStatJitterMaxOfNegDS OBJECT-TYPE
    SYNTAX      Gauge32
    UNITS       "milliseconds"
    MAX-ACCESS  read-only
    STATUS      current
    DESCRIPTION
        "The value of time that records the maximal absolute values of negative
        jitter value from destination to source in the jitter test."
    ::= { hwNqaGroupStatsJitterEntry 18 }

hwNqaStatJitterNumOfNegDS OBJECT-TYPE
    SYNTAX      Counter32
    MAX-ACCESS  read-only
    STATUS      current
    DESCRIPTION
        "The number that records negative jitter times from destination to
        source in the jitter test."
    ::= { hwNqaGroupStatsJitterEntry 19 }

hwNqaStatJitterSumOfNegDS OBJECT-TYPE
    SYNTAX      Counter32
    UNITS       "milliseconds"
    MAX-ACCESS  read-only
    STATUS      current
    DESCRIPTION
        "The value of time that records the sum of negative jitter values
        from destination to source in the jitter test."
    ::= { hwNqaGroupStatsJitterEntry 20 }

hwNqaStatJitterSumOfSquareNegDS OBJECT-TYPE
    SYNTAX      Counter32
    UNITS       "milliseconds"
    MAX-ACCESS  read-only
    STATUS      current
    DESCRIPTION
        "The value of time that records the sum of square of negative jitter
        values from destination to source in the jitter test."
    ::= { hwNqaGroupStatsJitterEntry 21 }

hwNqaStatJitterPacketLossSD OBJECT-TYPE
    SYNTAX      Counter32
    MAX-ACCESS  read-only
    STATUS      current
    DESCRIPTION
        "The lost packets number sent from source to destination."
    ::= { hwNqaGroupStatsJitterEntry 22 }

hwNqaStatJitterPacketLossDS OBJECT-TYPE
    SYNTAX      Counter32
    MAX-ACCESS  read-only
    STATUS      current
    DESCRIPTION
        "The lost packets number sent from destination to source."
    ::= { hwNqaGroupStatsJitterEntry 23 }

hwNqaStatJitterAvePosSD OBJECT-TYPE
    SYNTAX      Gauge32
    UNITS       "milliseconds"
    MAX-ACCESS  read-only
    STATUS      current
    DESCRIPTION
        "The value of time that records the average positive jitter value
        from source to destination."
    ::= { hwNqaGroupStatsJitterEntry 24 }

hwNqaStatJitterAveNegSD OBJECT-TYPE
    SYNTAX      Gauge32
    UNITS       "milliseconds"
    MAX-ACCESS  read-only
    STATUS      current
    DESCRIPTION
        "The value of time that records the average negative jitter value
        from source to destination."
    ::= { hwNqaGroupStatsJitterEntry 25 }

hwNqaStatJitterAvePosDS OBJECT-TYPE
    SYNTAX      Gauge32
    UNITS       "milliseconds"
    MAX-ACCESS  read-only
    STATUS      current
    DESCRIPTION
        "The value of time that records the average positive jitter value
        from destination to source."
    ::= { hwNqaGroupStatsJitterEntry 26 }

hwNqaStatJitterAveNegDS OBJECT-TYPE
    SYNTAX      Gauge32
    UNITS       "milliseconds"
    MAX-ACCESS  read-only
    STATUS      current
    DESCRIPTION
        "The value of time that records the average negative jitter value
        from destination to source."
    ::= { hwNqaGroupStatsJitterEntry 27 }

hwNqaStatJitterPktLossUnknown OBJECT-TYPE
    SYNTAX      Counter32
    MAX-ACCESS  read-only
    STATUS      current
    DESCRIPTION
        "The number of packets which is lost with unknown reason."
    ::= { hwNqaGroupStatsJitterEntry 28 }

hwNqaStatJitterMaxOfICPIF OBJECT-TYPE
    SYNTAX      Gauge32
    MAX-ACCESS  read-only
    STATUS      current
    DESCRIPTION
        "The maximum of all ICPIF values in a statistic cycle for jitter test."
    ::= { hwNqaGroupStatsJitterEntry 29 }

hwNqaStatJitterMinOfICPIF OBJECT-TYPE
    SYNTAX      Gauge32
    MAX-ACCESS  read-only
    STATUS      current
    DESCRIPTION
        "The minimum of all ICPIF values in a statistic cycle for jitter test."
    ::= { hwNqaGroupStatsJitterEntry 30 }

hwNqaStatJitterMaxOfMOS OBJECT-TYPE
    SYNTAX      Gauge32
    MAX-ACCESS  read-only
    STATUS      current
    DESCRIPTION
        "The maximum of all MOS values in a statistic cycle for jitter test."
    ::= { hwNqaGroupStatsJitterEntry 31 }

hwNqaStatJitterMinOfMOS OBJECT-TYPE
    SYNTAX      Gauge32
    MAX-ACCESS  read-only
    STATUS      current
    DESCRIPTION
        "The minimum of all MOS values in a statistic cycle for jitter test."
    ::= { hwNqaGroupStatsJitterEntry 32 }

-- Reaction Table
hwNqaReactionTable OBJECT-TYPE
    SYNTAX      SEQUENCE OF HwNqaReactionEntry
    MAX-ACCESS  not-accessible
    STATUS      current
    DESCRIPTION
        "A table of NQA test monitoring notification and
        reaction configuration definitions.

        An entry is removed from this table when its
        corresponding pingCtlEntry is deleted."
  ::= { hwNqaObjects 13 }

hwNqaReactionEntry OBJECT-TYPE
    SYNTAX      HwNqaReactionEntry
    MAX-ACCESS  not-accessible
    STATUS      current
    DESCRIPTION
        "Defines an entry in the hwNqaReactionTable.The first two index
        elements identify the pingCtlEntry that a hwNqaReactItemIndex
        belongs to. The third index element selects a single reaction."
    INDEX
        {
            hwNqaReactOwnerIndex,
            hwNqaReactTestName,
            hwNqaReactItemIndex
        }
    ::= { hwNqaReactionTable 1 }

HwNqaReactionEntry ::=
    SEQUENCE
        {
            hwNqaReactOwnerIndex                   SnmpAdminString,
            hwNqaReactTestName                     SnmpAdminString,
            hwNqaReactItemIndex                    Unsigned32,
            hwNqaReactCheckedElement               INTEGER,
            hwNqaReactThresholdUpperLimit          Unsigned32,
            hwNqaReactThresholdLowerLimit          Unsigned32,
            hwNqaReactThresholdType                INTEGER,
            hwNqaReactThresholdConsecNum           Unsigned32,
            hwNqaReactThresholdAccumNum            Unsigned32,
            hwNqaReactActionType                   INTEGER,
            hwNqaReactCurrentStatus                INTEGER,
            hwNqaReactRowStatus                    RowStatus,
            hwNqaReactCheckedNum                   Unsigned32,
            hwNqaReactThresholdNum                 Unsigned32
        }

hwNqaReactOwnerIndex OBJECT-TYPE
    SYNTAX      SnmpAdminString (SIZE(0..32))
    MAX-ACCESS  accessible-for-notify
    STATUS      current
    DESCRIPTION
        "The first index of hwNqaReactionTable, it is the same as
        pingCtlOwnerIndex in pingCtlTable. hwNqaReactOwnerIndex and
        hwNqaReactTestName identify an existed test."
    ::= { hwNqaReactionEntry 1 }

hwNqaReactTestName OBJECT-TYPE
    SYNTAX      SnmpAdminString (SIZE(0..32))
    MAX-ACCESS  accessible-for-notify
    STATUS      current
    DESCRIPTION
        "The second index of hwNqaReactionTable, it is the same as
        pingCtlTestName in pingCtlTable. hwNqaReactOwnerIndex and
        hwNqaReactTestName identify an existed test."
    ::= { hwNqaReactionEntry 2 }

hwNqaReactItemIndex OBJECT-TYPE
    SYNTAX      Unsigned32 (1..10)
    MAX-ACCESS  accessible-for-notify
    STATUS      current
    DESCRIPTION
        "The third index of hwNqaReactionTable, it definitely
        identifies one of the reaction configurations for a test."
    ::= { hwNqaReactionEntry 3 }

hwNqaReactCheckedElement OBJECT-TYPE
    SYNTAX      INTEGER {
                          probetime(1),
                          probefailure(2),
                          jitterrtt(3),
                          jitterpacketloss(4),
                          jittersd(5),
                          jitterds(6),
                          icpif(7),
                          mos(8),
                          jitterOwdSD(9),
                          jitterOwdDS(10)
                        }
    MAX-ACCESS  read-create
    STATUS      current
    DESCRIPTION
        "A list of reaction condition type.
        'probetime' and 'probefailure' are valid when pingCtlType of
        the test is not hwNqajitter.

        'jitterOwdSD': one way time from source to destination in
                       jitter test.
        'jitterOwdDS': one way time from destination to source in
                       jitter test.

        'jitterrtt', 'jitterpacketloss', 'jittersd', 'jitterds',
        'jitterOwdSD' and 'jitterOwdDS' are valid when pingCtlType
        of the test is hwNqajitter.

        'icpif' and 'mos' are valid when pingCtlType of the test is
        hwNqajitter and hwNqaCtlCodecType is 'g711Alaw' or 'g711Ulaw'
        or 'g729A'."
     ::= { hwNqaReactionEntry 4 }

hwNqaReactThresholdUpperLimit OBJECT-TYPE
    SYNTAX      Unsigned32
    MAX-ACCESS  read-create
    STATUS      current
    DESCRIPTION
        "This object defines an administrative upper-threshold value for
        hwNqaReactCheckedElement.

        The value of this object is zero if hwNqaReactCheckedElement is
        specified as 'jitterpacketloss' and 'probefailure'."

    DEFVAL { 0 }
    ::= { hwNqaReactionEntry 5 }

hwNqaReactThresholdLowerLimit OBJECT-TYPE
    SYNTAX      Unsigned32
    MAX-ACCESS  read-create
    STATUS      current
    DESCRIPTION
        "This object defines an administrative lower-threshold value for
        hwNqaReactCheckedElement.

        The value of hwNqaReactThresholdLowerLimit should be equal or less
        than the value of hwNqaReactThresholdUpperLimit.

        The value of this object is zero if hwNqaReactCheckedElement is
        specified as 'jitterpacketloss' and 'probefailure'."

    DEFVAL { 0 }
    ::= { hwNqaReactionEntry 6 }

hwNqaReactThresholdType OBJECT-TYPE
    SYNTAX      INTEGER {
                           invalid(0),
                           average(1),
                           consecutive(2),
                           accumulative(3)
                       }
    MAX-ACCESS  read-create
    STATUS      current
    DESCRIPTION
        "This object defines the reaction threshold types.

        invalid(0):     Invalid value.

        average(1):     If reaction threshold type is average and the average
                        value of watched operation exceeds threshold limit,
                        an action specified in hwNqaReactActionType is
                        generated when hwNqaReactCurrentStatus changes.


        consecutive(2): If reaction threshold type is consecutive and
                        the times of watched operation consecutively exceeds
                        the limit specified by hwNqaReactThresholdConsecNum,
                        an action specified in hwNqaReactActionType is
                        generated when hwNqaReactCurrentStatus changes.

        accumulative(3): If reaction threshold type is accumulative and
                        the times of watched operation accumulatively exceeds
                        the limit specified by hwNqaReactThresholdAccumNum,
                        an action specified in hwNqaReactActionType is
                        generated when hwNqaReactCurrentStatus changes.

        If reaction threshold type is not configured, the value of this
        object is 'invalid'."
    ::= { hwNqaReactionEntry 7 }

hwNqaReactThresholdConsecNum OBJECT-TYPE
    SYNTAX      Unsigned32
    MAX-ACCESS  read-create
    STATUS      current
    DESCRIPTION
        "This object defines a consecutive threshold limit.

        The value is zero when hwNqaReactThresholdType
        is not 'consecutive'."
    DEFVAL { 0 }
    ::= { hwNqaReactionEntry 8 }

hwNqaReactThresholdAccumNum OBJECT-TYPE
    SYNTAX      Unsigned32
    MAX-ACCESS  read-create
    STATUS      current
    DESCRIPTION
        "This object defines an accumulative threshold limit.

        The value is zero when the hwNqaReactThresholdType
        is not 'accumulative'."
    DEFVAL { 0 }
    ::= { hwNqaReactionEntry 9 }

hwNqaReactActionType OBJECT-TYPE
    SYNTAX      INTEGER {
                           none(0),
                           trapOnly(1),
                           triggerOnly(2),
                           trapAndTrigger(3)
                        }
    MAX-ACCESS  read-create
    STATUS      current
    DESCRIPTION
        "Specifies the type of reaction to generate if the specified
        violation type occurs for the monitored element:

        none               - No reaction is generated
        trapOnly           - A trap is generated
        triggerOnly        - All trigger actions defined for this
                             entry are generated
        trapAndTrigger     - Both a trap and all trigger actions
                             are generated "
    DEFVAL { none }
    ::= { hwNqaReactionEntry 10 }

hwNqaReactCurrentStatus OBJECT-TYPE
    SYNTAX      INTEGER {
                            invalid(1),
                            overThreshold(2),
                            belowThreshold(3)
                        }
    MAX-ACCESS  read-only
    STATUS      current
    DESCRIPTION
        "Specifies the current status of this reaction entry:

        invalid  - Specifies the reaction entry status is uncertain.

        overThreshold   - Specifies the reaction entry has met
                          the hwNqaReactThresholdType and the
                          threshold value.

        belowThreshold  - Specifies the reaction entry has
                          disobeyed the hwNqaReactThresholdType
                          and the threshold value."
    ::= { hwNqaReactionEntry 11 }

hwNqaReactRowStatus OBJECT-TYPE
    SYNTAX      RowStatus
    MAX-ACCESS  read-create
    STATUS      current
    DESCRIPTION
        "This object allows entries to be created and deleted
        in the hwNqaReactionTable.

        Creation of an entry in this table results in a new set of reaction
        configurations which take effect immediately.

        Deletion of an entry in this table results in corresponding reaction
        configurations are being deleted and stop taking effect."
    REFERENCE
        "See definition of RowStatus in RFC 2579, 'Textual
        Conventions for SMIv2.'"
    ::= { hwNqaReactionEntry 12 }

    hwNqaReactCheckedNum OBJECT-TYPE
    SYNTAX      Unsigned32
    MAX-ACCESS  read-only
    STATUS      current
    DESCRIPTION
        "The number of checked element samples that are monitored."
    DEFVAL { 0 }
    ::= { hwNqaReactionEntry 13 }

hwNqaReactThresholdNum OBJECT-TYPE
    SYNTAX      Unsigned32
    MAX-ACCESS  read-only
    STATUS      current
    DESCRIPTION
        "The number of checked element samples that are over threshold."
    DEFVAL { 0 }
    ::= { hwNqaReactionEntry 14 }

-- Statistics Reaction Table
hwNqaStatisticsReactionTable OBJECT-TYPE
    SYNTAX      SEQUENCE OF HwNqaStatisticsReactionEntry
    MAX-ACCESS  not-accessible
    STATUS      current
    DESCRIPTION
        "A table of NQA test monitoring notification and
        reaction configuration definitions.

        An entry is removed from this table when its
        corresponding pingCtlEntry is deleted."
  ::= { hwNqaObjects 14 }

hwNqaStatisticsReactionEntry OBJECT-TYPE
    SYNTAX      HwNqaStatisticsReactionEntry
    MAX-ACCESS  not-accessible
    STATUS      current
    DESCRIPTION
        "Defines an entry in the hwNqaStatisticsReactionTable. The
        first two index elements identify the pingCtlEntry that a
        hwNqaReactItemIndex belongs to. The third index element
        identifies an entry in the hwNqaStatisticsResultsTable.
        The forth index element selects a single reaction."
    INDEX
        {
            hwNqaStatReactOwnerIndex,
            hwNqaStatReactTestName,
            hwNqaStatReactIndex,
            hwNqaStatReactItemIndex
        }
    ::= { hwNqaStatisticsReactionTable 1 }

HwNqaStatisticsReactionEntry ::=
    SEQUENCE
        {
            hwNqaStatReactOwnerIndex               SnmpAdminString,
            hwNqaStatReactTestName                 SnmpAdminString,
            hwNqaStatReactIndex                    Unsigned32,
            hwNqaStatReactItemIndex                Unsigned32,
            hwNqaStatReactCheckedNum               Counter32,
            hwNqaStatReactThresholdNum             Counter32
        }

hwNqaStatReactOwnerIndex OBJECT-TYPE
    SYNTAX      SnmpAdminString (SIZE(0..32))
    MAX-ACCESS  not-accessible
    STATUS      current
    DESCRIPTION
        "The first index of hwNqaStatisticsReactionTable, it is the same
        as pingCtlOwnerIndex in pingCtlTable."
    ::= { hwNqaStatisticsReactionEntry 1 }

hwNqaStatReactTestName OBJECT-TYPE
    SYNTAX      SnmpAdminString (SIZE(0..32))
    MAX-ACCESS  not-accessible
    STATUS      current
    DESCRIPTION
        "The second index of hwNqaStatisticsReactionTable, it is the same
        as pingCtlTestName in pingCtlTable."
    ::= { hwNqaStatisticsReactionEntry 2 }

hwNqaStatReactIndex OBJECT-TYPE
    SYNTAX      Unsigned32
    MAX-ACCESS  not-accessible
    STATUS      current
    DESCRIPTION
        "The third index of hwNqaStatisticsReactionTable. An entry in
        this table is created when the statistics result of a NQA probe
        is determined.

 	An implementation MUST start assigning hwNqaStatResIndex values
 	at 1 and wrap after exceeding the maximum possible value as
 	defined by the limit of this object ('ffffffff'h)."
    DEFVAL { 0 }
    ::= { hwNqaStatisticsReactionEntry 3 }

hwNqaStatReactItemIndex OBJECT-TYPE
    SYNTAX      Unsigned32
    MAX-ACCESS  not-accessible
    STATUS      current
    DESCRIPTION
        "The forth index of hwNqaStatisticsReactionTable, it definitely
 	identifies one of the reaction configurations for a test"
    DEFVAL { 0 }
    ::= { hwNqaStatisticsReactionEntry 4 }

hwNqaStatReactCheckedNum OBJECT-TYPE
    SYNTAX      Counter32
    MAX-ACCESS  read-only
    STATUS      current
    DESCRIPTION
        "The number of checked element samples that are monitored."
    DEFVAL { 0 }
    ::= { hwNqaStatisticsReactionEntry 5 }

hwNqaStatReactThresholdNum OBJECT-TYPE
    SYNTAX      Counter32
    MAX-ACCESS  read-only
    STATUS      current
    DESCRIPTION
        "The number of checked element samples that are over threshold."
    DEFVAL { 0 }
    ::= { hwNqaStatisticsReactionEntry 6 }

-- Notification Definition section
hwNqaNotifications  OBJECT IDENTIFIER ::= { hwNqa 3 }
hwNqaProbeTimeOverThreshold NOTIFICATION-TYPE
    OBJECTS {
            hwNqaReactOwnerIndex,
            hwNqaReactTestName,
            hwNqaReactItemIndex,
            pingCtlTargetAddressType,
            pingCtlTargetAddress,
            pingCtlType,
            pingCtlDescr,
            hwNqaReactThresholdType,
            hwNqaReactCurrentStatus
               }
    STATUS  current
    DESCRIPTION
        "It is generated when the value of hwNqaReactCurrentStatus
        changes.
        The change may occur when the watched condition is over threshold
        or below threshold.

        The over threshold situations is specified as below.
          1. Probe time(equals to RTT for some type of tests) is not in
             the range hwNqaReactThresholdLowerLimit through
             hwNqaReactThresholdUpperLimit.
          2. The probe time is accumulatively not in the range
             hwNqaReactThresholdLowerLimit through
             hwNqaReactThresholdUpperLimit for a number of times
             specified in hwNqaReactThresholdAccumNum.
          3. The probe time is consecutively in the range
             hwNqaReactThresholdLowerLimit through
             hwNqaReactThresholdUpperLimit for a number of times
             specified in hwNqaReactThresholdConsecNum.

        This notification is valid only when hwNqaReactActionType
        is 'trapOnly' or 'trapAndTrigger' and pingCtlType of the test
        is not hwNqajitter."
    ::= { hwNqaNotifications 1 }

hwNqaJitterRTTOverThreshold NOTIFICATION-TYPE
    OBJECTS {
            hwNqaReactOwnerIndex,
            hwNqaReactTestName,
            hwNqaReactItemIndex,
            pingCtlTargetAddressType,
            pingCtlTargetAddress,
            pingCtlType,
            pingCtlDescr,
            hwNqaReactThresholdType,
            hwNqaReactCurrentStatus
               }
    STATUS  current
    DESCRIPTION
        "It is generated when the value of hwNqaReactCurrentStatus
        changes.
        The change may occur when the watched condition is over threshold
        or below threshold.

        The over threshold situations is specified as below.
          1. The average NQA round-trip-time (RTT) of jitter packets
             is not in the range hwNqaReactThresholdLowerLimit through
             hwNqaReactThresholdUpperLimit.
          2. The RTT of jitter packets is accumulatively not in the range
             hwNqaReactThresholdLowerLimit through
             hwNqaReactThresholdUpperLimit for a number of times specified
             in hwNqaReactThresholdAccumNum in one test.

        This notification is valid only when hwNqaReactActionType
        is 'trapOnly' or 'trapAndTrigger' and pingCtlType of the test
        is hwNqajitter."
    ::= { hwNqaNotifications 2 }

hwNqaProbeFailure NOTIFICATION-TYPE
    OBJECTS {
            hwNqaReactOwnerIndex,
            hwNqaReactTestName,
            hwNqaReactItemIndex,
            pingCtlTargetAddressType,
            pingCtlTargetAddress,
            pingCtlType,
            pingCtlDescr,
            hwNqaReactThresholdType,
            hwNqaReactCurrentStatus
              }
    STATUS  current
    DESCRIPTION
        "It is generated when the value of hwNqaReactCurrentStatus
        changes.
        The change may occur when the watched condition is over threshold
        or below threshold.

        The over threshold situations is specified as below.
          1. When the probe test accumulatively failed for a
             number of times specified in hwNqaReactThresholdAccumNum in one
             test while the value of hwNqaReactThresholdType is 'accumulative'.
          2. When the probe test consecutively failed for
             a number of times specified in hwNqaReactThresholdConsecNum in one
             test while the value of hwNqaReactThresholdType is 'consecutive'.

        This notification is valid only when hwNqaReactActionType
        is 'trapOnly' or 'trapAndTrigger' and pingCtlType of the test
        is not hwNqajitter."
    ::= { hwNqaNotifications 3 }

hwNqaJitterPacketLoss NOTIFICATION-TYPE
    OBJECTS {
            hwNqaReactOwnerIndex,
            hwNqaReactTestName,
            hwNqaReactItemIndex,
            pingCtlTargetAddressType,
            pingCtlTargetAddress,
            pingCtlType,
            pingCtlDescr,
            hwNqaReactThresholdType,
            hwNqaReactCurrentStatus
              }
    STATUS  current
    DESCRIPTION
        "It is generated when the value of hwNqaReactCurrentStatus
        changes.
        The change may occur when the watched condition is over threshold
        or below threshold.

        The over threshold situations is specified as below.
          1. When the jitter packets accumulatively lost for a
             number of times specified in hwNqaReactThresholdAccumNum in one
             test while the value of hwNqaReactThresholdType is 'accumulative'.

        This notification is valid only when hwNqaReactActionType
        is 'trapOnly' or 'trapAndTrigger' and pingCtlType of the test
        is hwNqajitter."
    ::= { hwNqaNotifications 4 }

hwNqaJitterSDOverThreshold NOTIFICATION-TYPE
    OBJECTS {
            hwNqaReactOwnerIndex,
            hwNqaReactTestName,
            hwNqaReactItemIndex,
            pingCtlTargetAddressType,
            pingCtlTargetAddress,
            pingCtlType,
            pingCtlDescr,
            hwNqaReactThresholdType,
            hwNqaReactCurrentStatus
             }
    STATUS  current
    DESCRIPTION
        "The SD means the jitter values from source to destination.

        It is generated when the value of hwNqaReactCurrentStatus
        changes.
        The change may occur when the watched condition is over threshold
        or below threshold.

        The over threshold situations is specified as below.
          1. The average of SD in one jitter test is not in the range
             hwNqaReactThresholdLowerLimit through
             hwNqaReactThresholdUpperLimit and the
             hwNqaReactThresholdType is specified as 'average' type.
          2. The average of SD in one jitter test is accumulatively
             not in the range hwNqaReactThresholdLowerLimit through
             hwNqaReactThresholdUpperLimit for a number of times specified
             in hwNqaReactThresholdAccumNum and the
             hwNqaReactThresholdType is specified as 'accumulative' type.

        This notification is valid only when hwNqaReactActionType
        is 'trapOnly' or 'trapAndTrigger' and pingCtlType of the test
        is hwNqajitter."
    ::= { hwNqaNotifications 5 }

hwNqaJitterDSOverThreshold NOTIFICATION-TYPE
    OBJECTS {
            hwNqaReactOwnerIndex,
            hwNqaReactTestName,
            hwNqaReactItemIndex,
            pingCtlTargetAddressType,
            pingCtlTargetAddress,
            pingCtlType,
            pingCtlDescr,
            hwNqaReactThresholdType,
            hwNqaReactCurrentStatus
             }
    STATUS  current
    DESCRIPTION
        "The DS means the jitter values from destination to source.

        It is generated when the value of hwNqaReactCurrentStatus
        changes.
        The change may occur when the watched condition is over threshold
        or below threshold.

        The over threshold situations is specified as below.
          1. The average of DS in one jitter test is not in the range
             hwNqaReactThresholdLowerLimit through
             hwNqaReactThresholdUpperLimit and the
             hwNqaReactThresholdType is specified as 'average' type.
          2. The average of DS in one jitter test is accumulatively not
             in the range hwNqaReactThresholdLowerLimit through
             hwNqaReactThresholdUpperLimit for a number of times specified
             in hwNqaReactThresholdAccumNum and the
             hwNqaReactThresholdType is specified as 'accumulative' type.

        This notification is valid only when hwNqaReactActionType
        is 'trapOnly' or 'trapAndTrigger' and pingCtlType of the test
        is hwNqajitter."
    ::= { hwNqaNotifications 6 }

hwNqaICPIFOverThreshold NOTIFICATION-TYPE
    OBJECTS {
            hwNqaReactOwnerIndex,
            hwNqaReactTestName,
            hwNqaReactItemIndex,
            pingCtlTargetAddressType,
            pingCtlTargetAddress,
            pingCtlType,
            pingCtlDescr,
            hwNqaReactCurrentStatus
              }
    STATUS  current
    DESCRIPTION
        "It is generated when the value of hwNqaReactCurrentStatus
        changes.
        The change may occur when the watched condition is over threshold
        or below threshold.

        The over threshold situations is specified as below.
          1. When the ICPIF value in one jitter test is not in
             the range hwNqaReactThresholdLowerLimit through
             hwNqaReactThresholdUpperLimit.

        This notification is valid only when hwNqaReactActionType
        is 'trapOnly' or 'trapAndTrigger', pingCtlType of the test
        is hwNqajitter and hwNqaCtlCodecType is 'g711Alaw' or 'g711Ulaw'
        or 'g729A'."
    ::= { hwNqaNotifications 7 }

hwNqaMOSOverThreshold NOTIFICATION-TYPE
    OBJECTS {
            hwNqaReactOwnerIndex,
            hwNqaReactTestName,
            hwNqaReactItemIndex,
            pingCtlTargetAddressType,
            pingCtlTargetAddress,
            pingCtlType,
            pingCtlDescr,
            hwNqaReactCurrentStatus
              }
    STATUS  current
    DESCRIPTION
        "It is generated when the value of hwNqaReactCurrentStatus
        changes.
        The change may occur when the watched condition is over threshold
        or below threshold.

        The over threshold situations is specified as below.
          1. When the MOS value in one jitter test is not in
             the range hwNqaReactThresholdLowerLimit through
             hwNqaReactThresholdUpperLimit.

        This notification is valid only when hwNqaReactActionType
        is 'trapOnly' or 'trapAndTrigger' , pingCtlType of the test
        is hwNqajitter and hwNqaCtlCodecType is 'g711Alaw' or 'g711Ulaw'
        or 'g729A'."
    ::= { hwNqaNotifications 8 }

END
