DDN-WOS-MIB DEFINITIONS ::= BEGIN

IMPORTS
    enterprises, MODULE-IDENTITY, NOTIFICATION-TYPE, OBJECT-TYPE,
    Gauge32, Counter64, Unsigned32
        FROM SNMPv2-SMI
    TEXTUAL-CONVENTION, DisplayString, DateAndTime, TruthValue
        FROM SNMPv2-TC
    InetAddressType, InetAddress
        FROM INET-ADDRESS-MIB
    MODULE-COMPLIANCE, OBJECT-GROUP, NOTIFICATION-GROUP
        FROM SNMPv2-CONF;

wosMIB MODULE-IDENTITY
    LAST-UPDATED "201201040000Z"    -- 04 Jan 2012
    ORGANIZATION "DataDirect Networks, Inc."
    CONTACT-INFO
        "DataDirect Networks, Inc.
         Phone: 1 800 TERABYTE
         Email: support@ddn.com"
    DESCRIPTION "SMI v2 MIB module for WOS (Web Object Scalar)."
    REVISION "201201040000Z"        -- 04 Jan 2012
    DESCRIPTION "First release."
    ::= { wos 1 }

datadirect              OBJECT IDENTIFIER ::= { enterprises 6894 }
wos                     OBJECT IDENTIFIER ::= { datadirect 4 }

-- Textual conventions

WosSeverityLevel ::= TEXTUAL-CONVENTION
    STATUS                  current
    DESCRIPTION             "Specifies the severity level of an event:

                             emergency:     A panic condition
                                            - notify all tech staff on call.
                             alert:         Should be corrected immediately
                                            - notify staff who can fix the problem
                                            - e.g. drive down alert.
                             critical:      Should be corrected immediately. Indicates failure in a primary system
                                            - fix CRITICAL problems before ALERT
                             error:         Non-urgent failures
                                            - these should be relayed to developers or admins
                                            - each item must be resolved within a given time.
                             warning:       Warning messages
                                            - not an error, but indication that an error will occur if action is not taken
                                            - e.g. cluster capacity is 70% used
                                            - each item must be resolved within a given time.
                             notice:        Events that are unusual but not error conditions
                                            - might be summarized in an email to developers or admins to spot potential problems
                                            - no immediate action required.
                             informational: Normal operational messages
                                            - may be harvested for reporting, measuring throughput, etc
                                            - no action required.
                             debug:         Info useful to developers for debugging the application
                                            - not useful during operations."
    SYNTAX                  INTEGER { emergency(1),
                                      alert(2),
                                      critical(3),
                                      error(4),
                                      warning(5),
                                      notice(6),
                                      informational(7),
                                      debug(8) }

WosSyslogFacility ::= TEXTUAL-CONVENTION
    STATUS                  current
    DESCRIPTION             "The syslog standard Facilities (from RFC 3164).
                             user (1) - random user-level messages
                             mail (2) - mail system
                             daemon (3) - system daemons
                             auth (4) - security/authorization messages
                             syslog (5) - messages generated internally by syslogd
                             lpr (6) - line printer subsystem
                             news (7) - network news subsystem
                             uucp (8) - UUCP subsystem
                             cron (9) - clock daemon
                             authpriv (10) - security/authorization messages (private)
                             ftp (11) - ftp daemon
                             local0 (16) - reserved for local use
                             local1 (17) - reserved for local use
                             local2 (18) - reserved for local use
                             local3 (19) - reserved for local use
                             local4 (20) - reserved for local use
                             local5 (21) - reserved for local use
                             local6 (22) - reserved for local use
                             local7 (23) - reserved for local use"
    SYNTAX                  INTEGER { user(1),
                                      mail(2),
                                      daemon(3),
                                      auth(4),
                                      syslog(5),
                                      lpr(6),
                                      news(7),
                                      uucp(8),
                                      cron(9),
                                      authpriv(10),
                                      ftp(11),
                                      local0(16),
                                      local1(17),
                                      local2(18),
                                      local3(19),
                                      local4(20),
                                      local5(21),
                                      local6(22),
                                      local7(23) }

-- Top level structure of MIB

wosNotifications        OBJECT IDENTIFIER ::= { wosMIB 0 }
wosObjects              OBJECT IDENTIFIER ::= { wosMIB 1 }
wosConformance          OBJECT IDENTIFIER ::= { wosMIB 2 }

wosNotificationInfo     OBJECT IDENTIFIER ::= { wosObjects 1 }
wosStatsInfo            OBJECT IDENTIFIER ::= { wosObjects 2 }
wosAlertsInfo           OBJECT IDENTIFIER ::= { wosObjects 3 }
wosClusterInfo          OBJECT IDENTIFIER ::= { wosObjects 4 }
wosZonesInfo            OBJECT IDENTIFIER ::= { wosObjects 5 }
wosNodesInfo            OBJECT IDENTIFIER ::= { wosObjects 6 }
wosPoliciesInfo         OBJECT IDENTIFIER ::= { wosObjects 7 }
wosPrefsInfo            OBJECT IDENTIFIER ::= { wosObjects 8 }

-- MIB objects

-- Notification objects

wosTrapDesc         OBJECT-TYPE
    SYNTAX                  DisplayString
    MAX-ACCESS              accessible-for-notify
    STATUS                  current
    DESCRIPTION             "Description of the notification."
    ::= { wosNotificationInfo 1 }

wosTrapSeverity     OBJECT-TYPE
    SYNTAX                  WosSeverityLevel
    MAX-ACCESS              accessible-for-notify
    STATUS                  current
    DESCRIPTION             "Severity of the notification.
                             emergency:     A panic condition
                                            - notify all tech staff on call.
                             alert:         Should be corrected immediately
                                            - notify staff who can fix the problem
                                            - e.g. drive down alert.
                             critical:      Should be corrected immediately. Indicates failure in a primary system
                                            - fix CRITICAL problems before ALERT
                             error:         Non-urgent failures
                                            - these should be relayed to developers or admins
                                            - each item must be resolved within a given time.
                             warning:       Warning messages
                                            - not an error, but indication that an error will occur if action is not taken
                                            - e.g. cluster capacity is 70% used
                                            - each item must be resolved within a given time.
                             notice:        Events that are unusual but not error conditions
                                            - might be summarized in an email to developers or admins to spot potential problems
                                            - no immediate action required.
                             informational: Normal operational messages
                                            - may be harvested for reporting, measuring throughput, etc
                                            - no action required.
                             debug:         Info useful to developers for debugging the application
                                            - not useful during operations."
    ::= { wosNotificationInfo 2 }

wosTrapType         OBJECT-TYPE
    SYNTAX                  DisplayString
    MAX-ACCESS              accessible-for-notify
    STATUS                  current
    DESCRIPTION             "Identifies the type of the notification."
    ::= { wosNotificationInfo 3 }

wosTrapLocation     OBJECT-TYPE
    SYNTAX                  DisplayString
    MAX-ACCESS              accessible-for-notify
    STATUS                  current
    DESCRIPTION             "A location pertaining to the notification (node IP address, cluster name, zone name, etc.)"
    ::= { wosNotificationInfo 4 }

-- Stats objects

wosStatsFRPS         OBJECT-TYPE
    SYNTAX                  Gauge32
    UNITS                   "file reads per second"
    MAX-ACCESS              read-only
    STATUS                  current
    DESCRIPTION             "Object read rate in file reads per second."
    ::= { wosStatsInfo 1 }

wosStatsFWPS         OBJECT-TYPE
    SYNTAX                  Gauge32
    UNITS                   "file writes per second"
    MAX-ACCESS              read-only
    STATUS                  current
    DESCRIPTION             "Object write rate in file writes per second."
    ::= { wosStatsInfo 2 }

wosStatsFDPS         OBJECT-TYPE
    SYNTAX                  Gauge32
    UNITS                   "file deletes per second"
    MAX-ACCESS              read-only
    STATUS                  current
    DESCRIPTION             "Object delete rate in file deletes per second."
    ::= { wosStatsInfo 3 }

wosStatsReadLatency  OBJECT-TYPE
    SYNTAX                  Gauge32
    UNITS                   "milliseconds"
    MAX-ACCESS              read-only
    STATUS                  current
    DESCRIPTION             "Object read latency in milliseconds."
    ::= { wosStatsInfo 4 }

wosStatsWriteLatency OBJECT-TYPE
    SYNTAX                  Gauge32
    UNITS                   "milliseconds"
    MAX-ACCESS              read-only
    STATUS                  current
    DESCRIPTION             "Object write latency in milliseconds."
    ::= { wosStatsInfo 5 }

wosStatsDeleteLatency OBJECT-TYPE
    SYNTAX                  Gauge32
    UNITS                   "milliseconds"
    MAX-ACCESS              read-only
    STATUS                  current
    DESCRIPTION             "Object delete latency in milliseconds."
    ::= { wosStatsInfo 6 }

wosStatsReadThroughput OBJECT-TYPE
    SYNTAX                  Gauge32
    UNITS                   "kilobytes per second"
    MAX-ACCESS              read-only
    STATUS                  current
    DESCRIPTION             "Object read throughput."
    ::= { wosStatsInfo 7 }

wosStatsWriteThroughput OBJECT-TYPE
    SYNTAX                  Gauge32
    UNITS                   "kilobytes per second"
    MAX-ACCESS              read-only
    STATUS                  current
    DESCRIPTION             "Object write throughput."
    ::= { wosStatsInfo 8 }

wosStatsReadCount      OBJECT-TYPE
    SYNTAX                  Counter64
    MAX-ACCESS              read-only
    STATUS                  current
    DESCRIPTION             "Total number of read transactions since the last cluster restart."
    ::= { wosStatsInfo 9 }

wosStatsWriteCount     OBJECT-TYPE
    SYNTAX                  Counter64
    MAX-ACCESS              read-only
    STATUS                  current
    DESCRIPTION             "Total number of write transactions since the last cluster restart."
    ::= { wosStatsInfo 10 }

wosStatsDeleteCount    OBJECT-TYPE
    SYNTAX                  Counter64
    MAX-ACCESS              read-only
    STATUS                  current
    DESCRIPTION             "Total number of delete transactions since the last cluster restart."
    ::= { wosStatsInfo 11 }

-- Alert objects

wosAlertTable OBJECT-TYPE
    SYNTAX                  SEQUENCE OF WosAlertEntry
    MAX-ACCESS              not-accessible
    STATUS                  current
    DESCRIPTION             "Table containing cluster alerts."
    ::= { wosAlertsInfo 1 }

wosAlertEntry OBJECT-TYPE
    SYNTAX                  WosAlertEntry
    MAX-ACCESS              not-accessible
    STATUS                  current
    DESCRIPTION             "An entry in wosAlertTable."
    INDEX                   { wosAlertIndex }
    ::= { wosAlertTable 1 }

WosAlertEntry ::= SEQUENCE {
    wosAlertIndex       Unsigned32,
    wosAlertSeverity    WosSeverityLevel,
    wosAlertTime        DateAndTime,
    wosAlertType        DisplayString,
    wosAlertLocation    DisplayString,
    wosAlertDesc        DisplayString
}

wosAlertIndex OBJECT-TYPE
    SYNTAX                  Unsigned32
    MAX-ACCESS              not-accessible
    STATUS                  current
    DESCRIPTION             "Alert table index. The most recent alert is assigned starting at index 1,
                             and older alerts are assigned indices in ascending order."
    ::= { wosAlertEntry 1 }

wosAlertSeverity OBJECT-TYPE
    SYNTAX                  WosSeverityLevel
    MAX-ACCESS              read-only
    STATUS                  current
    DESCRIPTION             "Severity of the alert.
                             emergency:     A panic condition
                                            - notify all tech staff on call.
                             alert:         Should be corrected immediately
                                            - notify staff who can fix the problem
                                            - e.g. drive down alert.
                             critical:      Should be corrected immediately. Indicates failure in a primary system
                                            - fix CRITICAL problems before ALERT
                             error:         Non-urgent failures
                                            - these should be relayed to developers or admins
                                            - each item must be resolved within a given time.
                             warning:       Warning messages
                                            - not an error, but indication that an error will occur if action is not taken
                                            - e.g. cluster capacity is 70% used
                                            - each item must be resolved within a given time.
                             notice:        Events that are unusual but not error conditions
                                            - might be summarized in an email to developers or admins to spot potential problems
                                            - no immediate action required.
                             informational: Normal operational messages
                                            - may be harvested for reporting, measuring throughput, etc
                                            - no action required.
                             debug:         Info useful to developers for debugging the application
                                            - not useful during operations."
    ::= { wosAlertEntry 2 }

wosAlertTime OBJECT-TYPE
    SYNTAX                  DateAndTime
    MAX-ACCESS              read-only
    STATUS                  current
    DESCRIPTION             "Date and time the alert was generated."
    ::= { wosAlertEntry 3 }

wosAlertType OBJECT-TYPE
    SYNTAX                  DisplayString
    MAX-ACCESS              read-only
    STATUS                  current
    DESCRIPTION             "Identifies the type of the alert."
    ::= { wosAlertEntry 4 }

wosAlertLocation OBJECT-TYPE
    SYNTAX                  DisplayString
    MAX-ACCESS              read-only
    STATUS                  current
    DESCRIPTION             "A location pertaining to the alert (node IP address, cluster name, zone name, etc.)"
    ::= { wosAlertEntry 5 }

wosAlertDesc OBJECT-TYPE
    SYNTAX                  DisplayString
    MAX-ACCESS              read-only
    STATUS                  current
    DESCRIPTION             "Description of the alert."
    ::= { wosAlertEntry 6 }

-- Cluster objects

wosClusterName OBJECT-TYPE
    SYNTAX                  DisplayString
    MAX-ACCESS              read-only
    STATUS                  current
    DESCRIPTION             "The name of the cluster."
    ::= { wosClusterInfo 1 }

wosClusterId OBJECT-TYPE
    SYNTAX                  DisplayString
    MAX-ACCESS              read-only
    STATUS                  current
    DESCRIPTION             "The ID number of the cluster."
    ::= { wosClusterInfo 2 }

wosClusterStatus OBJECT-TYPE
    SYNTAX                  DisplayString
    MAX-ACCESS              read-only
    STATUS                  current
    DESCRIPTION             "The cluster status."
    ::= { wosClusterInfo 3 }

wosClusterPrimaryNodeAddressType OBJECT-TYPE
    SYNTAX                  InetAddressType
    MAX-ACCESS              read-only
    STATUS                  current
    DESCRIPTION             "The IP address type of the primary cluster node."
    ::= { wosClusterInfo 4 }

wosClusterPrimaryNodeAddress OBJECT-TYPE
    SYNTAX                  InetAddress
    MAX-ACCESS              read-only
    STATUS                  current
    DESCRIPTION             "The IP address of the cluster primary node.
                             Refer to wosClusterPrimaryNodeAddress to determine the address type."
    ::= { wosClusterInfo 5 }

wosClusterTotalNodeCount OBJECT-TYPE
    SYNTAX                  Unsigned32
    MAX-ACCESS              read-only
    STATUS                  current
    DESCRIPTION             "The total number of nodes in the cluster."
    ::= { wosClusterInfo 6 }

wosClusterActiveNodeCount OBJECT-TYPE
    SYNTAX                  Unsigned32
    MAX-ACCESS              read-only
    STATUS                  current
    DESCRIPTION             "The number of nodes in the cluster that are active."
    ::= { wosClusterInfo 7 }

wosClusterDisconnectedNodeCount OBJECT-TYPE
    SYNTAX                  Unsigned32
    MAX-ACCESS              read-only
    STATUS                  current
    DESCRIPTION             "Then number of nodes in the cluster that are disconnected."
    ::= { wosClusterInfo 8 }

wosClusterConnectedClientsCount OBJECT-TYPE
    SYNTAX                  Unsigned32
    MAX-ACCESS              read-only
    STATUS                  current
    DESCRIPTION             "The number of active client connections to the cluster."
    ::= { wosClusterInfo 9 }

wosClusterObjectCountLow OBJECT-TYPE
    SYNTAX                  Unsigned32
    MAX-ACCESS              read-only
    STATUS                  current
    DESCRIPTION             "The total number of objects stored in the cluster.
                             Together with wosClusterObjectCountHigh this composes
                             a 64-bit number."
    ::= { wosClusterInfo 10 }

wosClusterObjectCountHigh OBJECT-TYPE
    SYNTAX                  Unsigned32
    MAX-ACCESS              read-only
    STATUS                  current
    DESCRIPTION             "The total number of objects stored in the cluster.
                             Together with wosClusterObjectCountLow this composes
                             a 64-bit number."
    ::= { wosClusterInfo 11 }

wosClusterUsableCapacity OBJECT-TYPE
    SYNTAX                  Unsigned32
    UNITS                   "gigabytes"
    MAX-ACCESS              read-only
    STATUS                  current
    DESCRIPTION             "The usable capacity of the cluster."
    ::= { wosClusterInfo 12 }

wosClusterUsedCapacity OBJECT-TYPE
    SYNTAX                  Unsigned32
    UNITS                   "gigabytes"
    MAX-ACCESS              read-only
    STATUS                  current
    DESCRIPTION             "The used capacity of the cluster."
    ::= { wosClusterInfo 13 }

wosClusterFreeCapacity OBJECT-TYPE
    SYNTAX                  Unsigned32
    UNITS                   "gigabytes"
    MAX-ACCESS              read-only
    STATUS                  current
    DESCRIPTION             "Total free capacity of the cluster."
    ::= { wosClusterInfo 14 }

-- Zone objects

wosZoneTable OBJECT-TYPE
    SYNTAX                  SEQUENCE OF WosZoneEntry
    MAX-ACCESS              not-accessible
    STATUS                  current
    DESCRIPTION             "Table containing cluster zones."
    ::= { wosZonesInfo 1 }

wosZoneEntry OBJECT-TYPE
    SYNTAX                  WosZoneEntry
    MAX-ACCESS              not-accessible
    STATUS                  current
    DESCRIPTION             "An entry in wosZoneTable."
    INDEX                   { wosZoneId }
    ::= { wosZoneTable 1}

WosZoneEntry ::= SEQUENCE {
    wosZoneId               Unsigned32,
    wosZoneName             DisplayString,
    wosZoneNodeCount        Unsigned32
}

wosZoneId OBJECT-TYPE
    SYNTAX                  Unsigned32
    MAX-ACCESS              not-accessible
    STATUS                  current
    DESCRIPTION             "An integer that uniquely identifies the zone in the cluster
                             and is the index value for wosZoneTable entries."
    ::= { wosZoneEntry 1 }

wosZoneName OBJECT-TYPE
    SYNTAX                  DisplayString
    MAX-ACCESS              read-only
    STATUS                  current
    DESCRIPTION             "The name of the zone."
    ::= { wosZoneEntry 2 }

wosZoneNodeCount OBJECT-TYPE
    SYNTAX                  Unsigned32
    MAX-ACCESS              read-only
    STATUS                  current
    DESCRIPTION             "The number of nodes accepted into the zone."
    ::= { wosZoneEntry 3 }

-- Node objects

wosNodeTable OBJECT-TYPE
    SYNTAX                  SEQUENCE OF WosNodeEntry
    MAX-ACCESS              not-accessible
    STATUS                  current
    DESCRIPTION             "Table containing cluster nodes."
    ::= { wosNodesInfo 1 }

wosNodeEntry OBJECT-TYPE
    SYNTAX                  WosNodeEntry
    MAX-ACCESS              not-accessible
    STATUS                  current
    DESCRIPTION             "An entry in wosNodeTable."
    INDEX                   { wosZoneId, wosNodeIndex }
    ::= { wosNodeTable 1 }

WosNodeEntry ::= SEQUENCE {
    wosNodeIndex            Unsigned32,
    wosNodeName             DisplayString,
    wosNodeAddressType      InetAddressType,
    wosNodeAddress          InetAddress,
    wosNodeZoneName         DisplayString,
    wosNodeStatus           DisplayString,
    wosNodeFwVersion        DisplayString,
    wosNodeObjectCountLow   Unsigned32,
    wosNodeObjectCountHigh  Unsigned32,
    wosNodeTotalCapacity    Unsigned32,
    wosNodeUsedCapacity     Unsigned32,
    wosNodePercentFull      Gauge32
}

wosNodeIndex OBJECT-TYPE
    SYNTAX                  Unsigned32
    MAX-ACCESS              not-accessible
    STATUS                  current
    DESCRIPTION             "An arbitrary integer used as the index value for wosNodeTable entries.
                             The index value can change at any time."
    ::= { wosNodeEntry 1 }

wosNodeName OBJECT-TYPE
    SYNTAX                  DisplayString
    MAX-ACCESS              read-only
    STATUS                  current
    DESCRIPTION             "The node name."
    ::= { wosNodeEntry 2 }

wosNodeAddressType OBJECT-TYPE
    SYNTAX                  InetAddressType
    MAX-ACCESS              read-only
    STATUS                  current
    DESCRIPTION             "The IP address type of the node."
    ::= { wosNodeEntry 3 }

wosNodeAddress OBJECT-TYPE
    SYNTAX                  InetAddress
    MAX-ACCESS              read-only
    STATUS                  current
    DESCRIPTION             "The IP address of the node.
                             Refer to wosNodeAddressType to determine the address type."
    ::= { wosNodeEntry 4 }

wosNodeZoneName OBJECT-TYPE
    SYNTAX                  DisplayString
    MAX-ACCESS              read-only
    STATUS                  current
    DESCRIPTION             "The name of the zone that the node belongs to."
    ::= { wosNodeEntry 5 }

wosNodeStatus OBJECT-TYPE
    SYNTAX                  DisplayString
    MAX-ACCESS              read-only
    STATUS                  current
    DESCRIPTION             "The status of the node (e.g. active, connecting, etc.)."
    ::= { wosNodeEntry 6 }

wosNodeFwVersion OBJECT-TYPE
    SYNTAX                  DisplayString
    MAX-ACCESS              read-only
    STATUS                  current
    DESCRIPTION             "The version number of the node's firmware."
    ::= { wosNodeEntry 7 }

wosNodeObjectCountLow OBJECT-TYPE
    SYNTAX                  Unsigned32
    MAX-ACCESS              read-only
    STATUS                  current
    DESCRIPTION             "The total number of objects stored on the node.
                             Together with wosNodeObjectCountHigh this composes
                             a 64-bit number."
    ::= { wosNodeEntry 8 }

wosNodeObjectCountHigh OBJECT-TYPE
    SYNTAX                  Unsigned32
    MAX-ACCESS              read-only
    STATUS                  current
    DESCRIPTION             "The total number of objects stored on the node.
                             Together with wosNodeObjectCountLow this composes
                             a 64-bit number."
    ::= { wosNodeEntry 9 }

wosNodeTotalCapacity OBJECT-TYPE
    SYNTAX                  Unsigned32
    UNITS                   "gigabytes"
    MAX-ACCESS              read-only
    STATUS                  current
    DESCRIPTION             "The total capacity of the node."
    ::= { wosNodeEntry 10 }

wosNodeUsedCapacity OBJECT-TYPE
    SYNTAX                  Unsigned32
    UNITS                   "gigabytes"
    MAX-ACCESS              read-only
    STATUS                  current
    DESCRIPTION             "The used capacity of the node."
    ::= { wosNodeEntry 11 }

wosNodePercentFull OBJECT-TYPE
    SYNTAX                  Gauge32 (0..100)
    MAX-ACCESS              read-only
    STATUS                  current
    DESCRIPTION             "The used capacity of the node as a percentage of the total capacity."
    ::= { wosNodeEntry 12 }

wosPendingNodeTable OBJECT-TYPE
    SYNTAX                  SEQUENCE OF WosPendingNodeEntry
    MAX-ACCESS              not-accessible
    STATUS                  current
    DESCRIPTION             "Table containing pending nodes."
    ::= { wosNodesInfo 2 }

wosPendingNodeEntry OBJECT-TYPE
    SYNTAX                  WosPendingNodeEntry
    MAX-ACCESS              not-accessible
    STATUS                  current
    DESCRIPTION             "An entry in wosPendingNodeTable."
    INDEX                   { wosPendingNodeIndex }
    ::= { wosPendingNodeTable 1 }

WosPendingNodeEntry ::= SEQUENCE {
    wosPendingNodeIndex         Unsigned32,
    wosPendingNodeAddressType   InetAddressType,
    wosPendingNodeAddress       InetAddress,
    wosPendingNodeStatus        DisplayString
}

wosPendingNodeIndex OBJECT-TYPE
    SYNTAX                  Unsigned32
    MAX-ACCESS              not-accessible
    STATUS                  current
    DESCRIPTION             "An arbitrary integer used as the index value for wosPendingNodeTable entries.
                             The index value can change at any time."
    ::= { wosPendingNodeEntry 1 }

wosPendingNodeAddressType OBJECT-TYPE
    SYNTAX                  InetAddressType
    MAX-ACCESS              read-only
    STATUS                  current
    DESCRIPTION             "The IP address type of the pending node."
    ::= { wosPendingNodeEntry 2 }

wosPendingNodeAddress OBJECT-TYPE
    SYNTAX                  InetAddress
    MAX-ACCESS              read-only
    STATUS                  current
    DESCRIPTION             "The IP address of the pending node.
                             Refer to wosPendingNodeAddressType to determine the address type."
    ::= { wosPendingNodeEntry 3 }

wosPendingNodeStatus OBJECT-TYPE
    SYNTAX                  DisplayString
    MAX-ACCESS              read-only
    STATUS                  current
    DESCRIPTION             "The status of the pending node (e.g. pending, pending (upgrading), etc.)."
    ::= { wosPendingNodeEntry 4 }

wosNodeDriveTable OBJECT-TYPE
    SYNTAX                  SEQUENCE OF WosNodeDriveEntry
    MAX-ACCESS              not-accessible
    STATUS                  current
    DESCRIPTION             "Table containing details about a node's disk drives."
    ::= { wosNodesInfo 3 }

wosNodeDriveEntry OBJECT-TYPE
    SYNTAX                  WosNodeDriveEntry
    MAX-ACCESS              not-accessible
    STATUS                  current
    DESCRIPTION             "An entry in wosNodeDriveTable."
    INDEX                   { wosNodeAddressType, wosNodeAddress, wosNodeDriveSlotNbr }
    ::= { wosNodeDriveTable 1 }

WosNodeDriveEntry ::= SEQUENCE {
    wosNodeDriveSlotNbr     Unsigned32,
    wosNodeDriveNodeName    DisplayString,
    wosNodeDriveMfgr        DisplayString,
    wosNodeDriveModel       DisplayString,
    wosNodeDriveSerialNbr   DisplayString,
    wosNodeDriveStatus      DisplayString,
    wosNodeDriveCapacity    Unsigned32
}

wosNodeDriveSlotNbr OBJECT-TYPE
    SYNTAX                  Unsigned32
    MAX-ACCESS              not-accessible
    STATUS                  current
    DESCRIPTION             "The slot number of the node that the drive is installed in."
    ::= { wosNodeDriveEntry 1 }

wosNodeDriveNodeName OBJECT-TYPE
    SYNTAX                  DisplayString
    MAX-ACCESS              read-only
    STATUS                  current
    DESCRIPTION             "The name of the node that the drive is installed in."
    ::= { wosNodeDriveEntry 2 }

wosNodeDriveMfgr OBJECT-TYPE
    SYNTAX                  DisplayString
    MAX-ACCESS              read-only
    STATUS                  current
    DESCRIPTION             "The drive manufacturer."
    ::= { wosNodeDriveEntry 3 }

wosNodeDriveModel OBJECT-TYPE
    SYNTAX                  DisplayString
    MAX-ACCESS              read-only
    STATUS                  current
    DESCRIPTION             "The drive model number."
    ::= { wosNodeDriveEntry 4 }

wosNodeDriveSerialNbr OBJECT-TYPE
    SYNTAX                  DisplayString
    MAX-ACCESS              read-only
    STATUS                  current
    DESCRIPTION             "The drive serial number."
    ::= { wosNodeDriveEntry 5 }

wosNodeDriveStatus OBJECT-TYPE
    SYNTAX                  DisplayString
    MAX-ACCESS              read-only
    STATUS                  current
    DESCRIPTION             "The status of the drive (e.g. down, not present, etc.)."
    ::= { wosNodeDriveEntry 6 }

wosNodeDriveCapacity OBJECT-TYPE
    SYNTAX                  Unsigned32
    UNITS                   "gigabytes"
    MAX-ACCESS              read-only
    STATUS                  current
    DESCRIPTION             "The total capacity of the drive."
    ::= { wosNodeDriveEntry 7 }

-- Policies objects

wosPolicyTable OBJECT-TYPE
    SYNTAX                  SEQUENCE OF WosPolicyEntry
    MAX-ACCESS              not-accessible
    STATUS                  current
    DESCRIPTION             "Table containing policies."
    ::= { wosPoliciesInfo 1 }

wosPolicyEntry OBJECT-TYPE
    SYNTAX                  WosPolicyEntry
    MAX-ACCESS              not-accessible
    STATUS                  current
    DESCRIPTION             "An entry in wosPolicyTable."
    INDEX                   { wosPolicyIndex, wosPolicyReplicaIndex }
    ::= { wosPolicyTable 1 }

WosPolicyEntry ::= SEQUENCE {
    wosPolicyIndex                  Unsigned32,
    wosPolicyReplicaIndex           Unsigned32,
    wosPolicyId                     DisplayString,
    wosPolicyName                   DisplayString,
    wosPolicyReplicaZoneName        DisplayString,
    wosPolicyReplicaCount           Unsigned32,
    wosPolicyReplicationType        DisplayString,
    wosPolicyLocalDataProtection    TruthValue,
    wosPolicyObjCountLow            Unsigned32,
    wosPolicyObjCountHigh           Unsigned32,
    wosPolicyNonComplObjCountLow    Unsigned32,
    wosPolicyNonComplObjCountHigh   Unsigned32,
    wosPolicyUsedCapacity           Unsigned32
}

wosPolicyIndex OBJECT-TYPE
    SYNTAX                  Unsigned32
    MAX-ACCESS              not-accessible
    STATUS                  current
    DESCRIPTION             "An arbitrary integer used as an index value for wosPolicyTable entries.
                             The index value can change at any time."
    ::= { wosPolicyEntry 1 }

wosPolicyReplicaIndex OBJECT-TYPE
    SYNTAX                  Unsigned32
    MAX-ACCESS              not-accessible
    STATUS                  current
    DESCRIPTION             "An integer used as an index value for a zone replica in wosPolicyTable
                             entries. The first zone replica in a policy is assigned starting at
                             index 1 and the remaining zone replicas are assigned indices in
                             ascending order."
    ::= { wosPolicyEntry 2 }

wosPolicyId OBJECT-TYPE
    SYNTAX                  DisplayString
    MAX-ACCESS              read-only
    STATUS                  current
    DESCRIPTION             "The ID number of the policy."
    ::= { wosPolicyEntry 3 }

wosPolicyName OBJECT-TYPE
    SYNTAX                  DisplayString
    MAX-ACCESS              read-only
    STATUS                  current
    DESCRIPTION             "The name of the policy."
    ::= { wosPolicyEntry 4 }

wosPolicyReplicaZoneName OBJECT-TYPE
    SYNTAX                  DisplayString
    MAX-ACCESS              read-only
    STATUS                  current
    DESCRIPTION             "The name of the zone containing replicas for the policy."
    ::= { wosPolicyEntry 5 }

wosPolicyReplicaCount OBJECT-TYPE
    SYNTAX                  Unsigned32
    MAX-ACCESS              read-only
    STATUS                  current
    DESCRIPTION             "The number of replicas in the zone for the policy."
    ::= { wosPolicyEntry 6 }

wosPolicyReplicationType OBJECT-TYPE
    SYNTAX                  DisplayString
    MAX-ACCESS              read-only
    STATUS                  current
    DESCRIPTION             "The replication type of the policy."
    ::= { wosPolicyEntry 7 }

wosPolicyLocalDataProtection OBJECT-TYPE
    SYNTAX                  TruthValue
    MAX-ACCESS              read-only
    STATUS                  current
    DESCRIPTION             "True if local data protection is enabled for the policy."
    ::= { wosPolicyEntry 8 }

wosPolicyObjCountLow OBJECT-TYPE
    SYNTAX                  Unsigned32
    MAX-ACCESS              read-only
    STATUS                  current
    DESCRIPTION             "The total number of objects stored against the policy.
                             Together with wosPolicyObjCountHigh this composes
                             a 64-bit number."
    ::= { wosPolicyEntry 9 }

wosPolicyObjCountHigh OBJECT-TYPE
    SYNTAX                  Unsigned32
    MAX-ACCESS              read-only
    STATUS                  current
    DESCRIPTION             "The total number of objects stored against the policy.
                             Together with wosPolicyObjCountLow this composes
                             a 64-bit number."
    ::= { wosPolicyEntry 10 }

wosPolicyNonComplObjCountLow OBJECT-TYPE
    SYNTAX                  Unsigned32
    MAX-ACCESS              read-only
    STATUS                  current
    DESCRIPTION             "The total number of non-compliant objects stored
                             against the policy. Together with wosPolicyObjCountHigh
                             this composes a 64-bit number."
    ::= { wosPolicyEntry 11 }

wosPolicyNonComplObjCountHigh OBJECT-TYPE
    SYNTAX                  Unsigned32
    MAX-ACCESS              read-only
    STATUS                  current
    DESCRIPTION             "The total number of non-compliant objects stored
                             against the policy. Together with wosPolicyObjCountLow
                             this composes a 64-bit number."
    ::= { wosPolicyEntry 12 }

wosPolicyUsedCapacity OBJECT-TYPE
    SYNTAX                  Unsigned32
    UNITS                   "gigabytes"
    MAX-ACCESS              read-only
    STATUS                  current
    DESCRIPTION             "The total capacity used by the policy."
    ::= { wosPolicyEntry 13 }

-- Preferences objects

wosPrefStoreUnderReplObjs OBJECT-TYPE
    SYNTAX                  TruthValue
    MAX-ACCESS              read-only
    STATUS                  current
    DESCRIPTION             "True if storage of under-replicated objects is allowed."
    ::= { wosPrefsInfo 1 }

wosPrefNodeDownDelay OBJECT-TYPE
    SYNTAX                  Unsigned32
    UNITS                   "minutes"
    MAX-ACCESS              read-only
    STATUS                  current
    DESCRIPTION             "The node down delay time."
    ::= { wosPrefsInfo 2 }

wosPrefEmailAlertNewInterval OBJECT-TYPE
    SYNTAX                  Unsigned32
    UNITS                   "minutes"
    MAX-ACCESS              read-only
    STATUS                  current
    DESCRIPTION             "The minimum delay time between notifications of new alerts."
    ::= { wosPrefsInfo 3 }

wosPrefEmailAlertRmndrInterval OBJECT-TYPE
    SYNTAX                  Unsigned32
    UNITS                   "minutes"
    MAX-ACCESS              read-only
    STATUS                  current
    DESCRIPTION             "The minimum delay time between reminders of existing alerts."
    ::= { wosPrefsInfo 4 }

wosPrefEmailAlertFromAddr OBJECT-TYPE
    SYNTAX                  DisplayString
    MAX-ACCESS              read-only
    STATUS                  current
    DESCRIPTION             "The From address for email alerts."
    ::= { wosPrefsInfo 5 }

wosPrefEmailAlertRecipientTable OBJECT-TYPE
    SYNTAX                  SEQUENCE OF WosPrefEmailAlertRecipientEntry
    MAX-ACCESS              not-accessible
    STATUS                  current
    DESCRIPTION             "Table containing email alert recipients."
    ::= { wosPrefsInfo 6 }

wosPrefEmailAlertRecipientEntry OBJECT-TYPE
    SYNTAX                  WosPrefEmailAlertRecipientEntry
    MAX-ACCESS              not-accessible
    STATUS                  current
    DESCRIPTION             "An entry in wosPrefEmailAlertRecipientTable."
    INDEX                   { wosPrefEmailAlertRecipientIndex }
    ::= { wosPrefEmailAlertRecipientTable 1 }

WosPrefEmailAlertRecipientEntry ::= SEQUENCE {
    wosPrefEmailAlertRecipientIndex    Unsigned32,
    wosPrefEmailAlertRecipient          DisplayString
}

wosPrefEmailAlertRecipientIndex OBJECT-TYPE
    SYNTAX                  Unsigned32
    MAX-ACCESS              not-accessible
    STATUS                  current
    DESCRIPTION             "Email alert table index."
    ::= { wosPrefEmailAlertRecipientEntry 1 }

wosPrefEmailAlertRecipient OBJECT-TYPE
    SYNTAX                  DisplayString
    MAX-ACCESS              read-only
    STATUS                  current
    DESCRIPTION             "The email alert recipient."
    ::= { wosPrefEmailAlertRecipientEntry 2 }

wosPrefEmailAlertServerTable OBJECT-TYPE
    SYNTAX                  SEQUENCE OF WosPrefEmailAlertServerEntry
    MAX-ACCESS              not-accessible
    STATUS                  current
    DESCRIPTION             "Table containing outgoing email servers for email alerts."
    ::= { wosPrefsInfo 7 }

wosPrefEmailAlertServerEntry OBJECT-TYPE
    SYNTAX                  WosPrefEmailAlertServerEntry
    MAX-ACCESS              not-accessible
    STATUS                  current
    DESCRIPTION             "An entry in wosPrefEmailAlertServerTable."
    INDEX                   { wosPrefEmailAlertServerIndex }
    ::= { wosPrefEmailAlertServerTable 1 }

WosPrefEmailAlertServerEntry ::= SEQUENCE {
    wosPrefEmailAlertServerIndex    Unsigned32,
    wosPrefEmailAlertServer         DisplayString
}

wosPrefEmailAlertServerIndex OBJECT-TYPE
    SYNTAX                  Unsigned32
    MAX-ACCESS              not-accessible
    STATUS                  current
    DESCRIPTION             "Email alert server table index."
    ::= { wosPrefEmailAlertServerEntry 1 }

wosPrefEmailAlertServer OBJECT-TYPE
    SYNTAX                  DisplayString
    MAX-ACCESS              read-only
    STATUS                  current
    DESCRIPTION             "The outgoing email server for email alerts."
    ::= { wosPrefEmailAlertServerEntry 2 }

wosPrefSnmpManagerTable OBJECT-TYPE
    SYNTAX                  SEQUENCE OF WosPrefSnmpManagerEntry
    MAX-ACCESS              not-accessible
    STATUS                  current
    DESCRIPTION             "Table containing SNMP managers."
    ::= { wosPrefsInfo 8 }

wosPrefSnmpManagerEntry OBJECT-TYPE
    SYNTAX                  WosPrefSnmpManagerEntry
    MAX-ACCESS              not-accessible
    STATUS                  current
    DESCRIPTION             "An entry in wosPrefSnmpManagerTable."
    INDEX                   { wosPrefSnmpManagerIndex }
    ::= { wosPrefSnmpManagerTable 1 }

WosPrefSnmpManagerEntry ::= SEQUENCE {
    wosPrefSnmpManagerIndex Unsigned32,
    wosPrefSnmpManager      DisplayString
}

wosPrefSnmpManagerIndex OBJECT-TYPE
    SYNTAX                  Unsigned32
    MAX-ACCESS              not-accessible
    STATUS                  current
    DESCRIPTION             "SNMP Manager table index."
    ::= { wosPrefSnmpManagerEntry 1 }

wosPrefSnmpManager OBJECT-TYPE
    SYNTAX                  DisplayString
    MAX-ACCESS              read-only
    STATUS                  current
    DESCRIPTION             "The SNMP manager."
    ::= { wosPrefSnmpManagerEntry 2 }

wosPrefSnmpTrapCommunityName OBJECT-TYPE
    SYNTAX                  DisplayString
    MAX-ACCESS              read-only
    STATUS                  current
    DESCRIPTION             "The community name for the SNMP traps."
    ::= { wosPrefsInfo 9 }

wosPrefMgmtIpFilterTable OBJECT-TYPE
    SYNTAX                  SEQUENCE OF WosPrefMgmtIpFilterEntry
    MAX-ACCESS              not-accessible
    STATUS                  current
    DESCRIPTION             "Table containing management IP filters."
    ::= { wosPrefsInfo 10 }

wosPrefMgmtIpFilterEntry OBJECT-TYPE
    SYNTAX                  WosPrefMgmtIpFilterEntry
    MAX-ACCESS              not-accessible
    STATUS                  current
    DESCRIPTION             "An entry in wosPrefMgmtIpFilterTable."
    INDEX                   { wosPrefMgmtIpFilterIndex }
    ::= { wosPrefMgmtIpFilterTable 1 }

WosPrefMgmtIpFilterEntry ::= SEQUENCE {
    wosPrefMgmtIpFilterIndex    Unsigned32,
    wosPrefMgmtIpFilter         DisplayString
}

wosPrefMgmtIpFilterIndex OBJECT-TYPE
    SYNTAX                  Unsigned32
    MAX-ACCESS              not-accessible
    STATUS                  current
    DESCRIPTION             "Management IP filter table index."
    ::= { wosPrefMgmtIpFilterEntry 1 }

wosPrefMgmtIpFilter OBJECT-TYPE
    SYNTAX                  DisplayString
    MAX-ACCESS              read-only
    STATUS                  current
    DESCRIPTION             "The management IP filter."
    ::= { wosPrefMgmtIpFilterEntry 2 }

wosPrefClientIpFilterTable OBJECT-TYPE
    SYNTAX                  SEQUENCE OF WosPrefClientIpFilterEntry
    MAX-ACCESS              not-accessible
    STATUS                  current
    DESCRIPTION             "Table containing client I/O IP filters."
    ::= { wosPrefsInfo 11 }

wosPrefClientIpFilterEntry OBJECT-TYPE
    SYNTAX                  WosPrefClientIpFilterEntry
    MAX-ACCESS              not-accessible
    STATUS                  current
    DESCRIPTION             "An entry in wosPrefClientIpFilterTable."
    INDEX                   { wosPrefClientIpFilterIndex }
    ::= { wosPrefClientIpFilterTable 1 }

WosPrefClientIpFilterEntry ::= SEQUENCE {
    wosPrefClientIpFilterIndex  Unsigned32,
    wosPrefClientIpFilter         DisplayString
}

wosPrefClientIpFilterIndex OBJECT-TYPE
    SYNTAX                  Unsigned32
    MAX-ACCESS              not-accessible
    STATUS                  current
    DESCRIPTION             "Client I/O IP filter table index."
    ::= { wosPrefClientIpFilterEntry 1 }

wosPrefClientIpFilter OBJECT-TYPE
    SYNTAX                  DisplayString
    MAX-ACCESS              read-only
    STATUS                  current
    DESCRIPTION             "The client I/O IP filter."
    ::= { wosPrefClientIpFilterEntry 2 }

wosPrefSyslogFacility OBJECT-TYPE
    SYNTAX                  WosSyslogFacility
    MAX-ACCESS              read-only
    STATUS                  current
    DESCRIPTION             "The Syslog Facility.
                             user (1) - random user-level messages
                             mail (2) - mail system
                             daemon (3) - system daemons
                             auth (4) - security/authorization messages
                             syslog (5) - messages generated internally by syslogd
                             lpr (6) - line printer subsystem
                             news (7) - network news subsystem
                             uucp (8) - UUCP subsystem
                             cron (9) - clock daemon
                             authpriv (10) - security/authorization messages (private)
                             ftp (11) - ftp daemon
                             local0 (16) - reserved for local use
                             local1 (17) - reserved for local use
                             local2 (18) - reserved for local use
                             local3 (19) - reserved for local use
                             local4 (20) - reserved for local use
                             local5 (21) - reserved for local use
                             local6 (22) - reserved for local use
                             local7 (23) - reserved for local use"
    ::= { wosPrefsInfo 12 }

wosPrefSyslogRemoteHost OBJECT-TYPE
    SYNTAX              DisplayString
    MAX-ACCESS          read-only
    STATUS              current
    DESCRIPTION         "The remote syslog host."
    ::= { wosPrefsInfo 13 }

-- Notifications

wosTrapMessage     NOTIFICATION-TYPE
    OBJECTS                 { wosTrapSeverity, wosTrapType, wosTrapLocation, wosTrapDesc }
    STATUS                  current
    DESCRIPTION             "This notification is sent whenever a cluster alert is generated."
    ::= { wosNotifications 1 }


-- Conformance statements

wosCompliances  OBJECT IDENTIFIER ::= { wosConformance 1 }
wosGroups       OBJECT IDENTIFIER ::= { wosConformance 2 }

-- Compliance statements

wosCompliance MODULE-COMPLIANCE
    STATUS                  current
    DESCRIPTION             "The compliance statement for WOS nodes implementing the DDN-WOS-MIB."
    MODULE                  -- this module
    MANDATORY-GROUPS        { wosEventsGroup,
                              wosNotificationsGroup,
                              wosStatsGroup,
                              wosAlertsGroup,
                              wosClusterGroup,
                              wosZonesGroup,
                              wosNodesGroup,
                              wosPoliciesGroup,
                              wosPrefsGroup }
    ::= { wosCompliances 1 }

-- Group definitions for conformance

wosEventsGroup NOTIFICATION-GROUP
    NOTIFICATIONS           { wosTrapMessage }
    STATUS                  current
    DESCRIPTION             "This groups defines the set of notification types."
    ::= { wosGroups 1 }

wosNotificationsGroup OBJECT-GROUP
    OBJECTS                 { wosTrapDesc,
                              wosTrapSeverity,
                              wosTrapType,
                              wosTrapLocation }
    STATUS                  current
    DESCRIPTION             "This group defines the set of notification objects."
    ::= { wosGroups 2 }

wosStatsGroup OBJECT-GROUP
    OBJECTS                 { wosStatsFRPS,
                              wosStatsFWPS,
                              wosStatsFDPS,
                              wosStatsReadLatency,
                              wosStatsWriteLatency,
                              wosStatsDeleteLatency,
                              wosStatsReadThroughput,
                              wosStatsWriteThroughput,
                              wosStatsReadCount,
                              wosStatsWriteCount,
                              wosStatsDeleteCount }
    STATUS                  current
    DESCRIPTION             "This group defines the set of statistics objects."
    ::= { wosGroups 3 }

wosAlertsGroup OBJECT-GROUP
    OBJECTS                 { wosAlertSeverity,
                              wosAlertTime,
                              wosAlertType,
                              wosAlertLocation,
                              wosAlertDesc }
    STATUS                  current
    DESCRIPTION             "This group defines the set of alert objects."
    ::= { wosGroups 4 }

wosClusterGroup OBJECT-GROUP
    OBJECTS                 { wosClusterName,
                              wosClusterId,
                              wosClusterStatus,
                              wosClusterPrimaryNodeAddressType,
                              wosClusterPrimaryNodeAddress,
                              wosClusterTotalNodeCount,
                              wosClusterActiveNodeCount,
                              wosClusterDisconnectedNodeCount,
                              wosClusterConnectedClientsCount,
                              wosClusterObjectCountLow,
                              wosClusterObjectCountHigh,
                              wosClusterUsableCapacity,
                              wosClusterUsedCapacity,
                              wosClusterFreeCapacity }
    STATUS                  current
    DESCRIPTION             "This group defines the set of cluster objects."
    ::= { wosGroups 5 }

wosZonesGroup OBJECT-GROUP
    OBJECTS                 { wosZoneName,
                              wosZoneNodeCount }
    STATUS                  current
    DESCRIPTION             "This group defines the set of zone objects."
    ::= { wosGroups 6 }

wosNodesGroup OBJECT-GROUP
    OBJECTS                 { wosNodeName,
                              wosNodeAddressType,
                              wosNodeAddress,
                              wosNodeZoneName,
                              wosNodeStatus,
                              wosNodeFwVersion,
                              wosNodeObjectCountLow,
                              wosNodeObjectCountHigh,
                              wosNodeTotalCapacity,
                              wosNodeUsedCapacity,
                              wosNodePercentFull,
                              wosPendingNodeAddressType,
                              wosPendingNodeAddress,
                              wosPendingNodeStatus,
                              wosNodeDriveNodeName,
                              wosNodeDriveMfgr,
                              wosNodeDriveModel,
                              wosNodeDriveSerialNbr,
                              wosNodeDriveStatus,
                              wosNodeDriveCapacity }
    STATUS                  current
    DESCRIPTION             "This group defines the set of node objects."
    ::= { wosGroups 7 }

wosPoliciesGroup OBJECT-GROUP
    OBJECTS                 { wosPolicyId,
                              wosPolicyName,
                              wosPolicyReplicaZoneName,
                              wosPolicyReplicaCount,
                              wosPolicyReplicationType,
                              wosPolicyLocalDataProtection,
                              wosPolicyObjCountLow,
                              wosPolicyObjCountHigh,
                              wosPolicyNonComplObjCountLow,
                              wosPolicyNonComplObjCountHigh,
                              wosPolicyUsedCapacity }
    STATUS                  current
    DESCRIPTION             "This group defines the set of policy objects."
    ::= { wosGroups 8 }

wosPrefsGroup OBJECT-GROUP
    OBJECTS                 { wosPrefStoreUnderReplObjs,
                              wosPrefNodeDownDelay,
                              wosPrefEmailAlertNewInterval,
                              wosPrefEmailAlertRmndrInterval,
                              wosPrefEmailAlertFromAddr,
                              wosPrefEmailAlertRecipient,
                              wosPrefEmailAlertServer,
                              wosPrefSnmpManager,
                              wosPrefSnmpTrapCommunityName,
                              wosPrefMgmtIpFilter,
                              wosPrefClientIpFilter,
                              wosPrefSyslogFacility,
                              wosPrefSyslogRemoteHost }
    STATUS                  current
    DESCRIPTION             "This group defines the set of preferences objects."
    ::= { wosGroups 9 }

END
