GBOS-MIB DEFINITIONS ::= BEGIN

IMPORTS
    MODULE-IDENTITY,
    OBJECT-TYPE,
    Counter32,
    Integer32
    enterprises
            FROM SNMPv2-SMI
    TEXTUAL-CONVENTION,
    DisplayString
            FROM SNMPv2-TC
    MODULE-COMPLIANCE,
    OBJECT-GROUP
            FROM SNMPv2-CONF
    ;

gbos MODULE-IDENTITY
        LAST-UPDATED    "201507181105Z"
        ORGANIZATION    "Observium Limited"
        CONTACT-INFO
                "Adam Armstrong
                Email: adama@observium.org"
        DESCRIPTION
                "Unofficial GTA GB-OS MIB. For Observium use only."
        ::= { enterprises 13559 }

gbObjects        OBJECT IDENTIFIER ::= { gbos 1 }
gbSystem       	 OBJECT IDENTIFIER ::= { gbObjects 1 }
gbSystemInfo	 OBJECT IDENTIFIER ::= { gbSystem 1 }

gbSysSerial OBJECT-TYPE
    SYNTAX      STRING
    MAX-ACCESS  read-only
    STATUS      current
    DESCRIPTION
        "System Serial Number."
    ::= { gbSystemInfo 1 }

gbSysHostname OBJECT-TYPE
    SYNTAX      STRING
    MAX-ACCESS  read-only
    STATUS      current
    DESCRIPTION
        "System configured hostname."
    ::= { gbSystemInfo 2 }

gbSysVersion  OBJECT IDENTIFIER ::= { gbSystem 2 }

gbSysVersionNumber OBJECT-TYPE
    SYNTAX      Gauge32
    MAX-ACCESS  read-only
    STATUS      current
    DESCRIPTION
        "System Version.
         GB-OS version number ((major << 16 ) | (minor << 8) | incremental).
         393730 = 0x60202
         major = 0x6
         minor = 0x02
         incremntal = 0x02"
    ::= { gbSysVersion 1 }

gbSysVersionDescr OBJECT-TYPE
    SYNTAX      STRING
    MAX-ACCESS  read-only
    STATUS      current
    DESCRIPTION
        "GB-OS version description."
    ::= { gbSysVersion 2 }


gbSysVersionL OBJECT-TYPE
    SYNTAX      Gauge32
    MAX-ACCESS  read-only
    STATUS      current
    DESCRIPTION
        "GB-OS lversion (Used Internally)."
    ::= { gbSysVersion 3 }

gbSysProduct  OBJECT IDENTIFIER ::= { gbSystem 3 }

gbSysProductNum OBJECT-TYPE
    SYNTAX      Gauge32
    MAX-ACCESS  read-only
    STATUS      current
    DESCRIPTION
        "Product Type.
	GB-WARE		      	0x01
	GB-WARE Unrestricted   	0x02
	GB-WARE Enterprise   	0x03
	GB-250          	0x13
	GB-300          	0x15
	GB-500          	0x1E
	GB-750          	0x28
	GB-800          	0x29
	GB-DEMO         	0x30
	GB-820          	0x41
	GB-850          	0x42
	GB-1500         	0x46
	GB-2000         	0x5A
	GB-3000         	0x5B
	GB-2100         	0x5C
	GB-2500         	0x5D
	GB-2600         	0x5E"
    ::= { gbSysProduct 1 }

gbSysProductDescr OBJECT-TYPE
    SYNTAX      STRING
    MAX-ACCESS  read-only
    STATUS      current
    DESCRIPTION
        "Product Description."
    ::= { gbSysProduct 2 }

gbSysUpdates  OBJECT IDENTIFIER ::= { gbSystem 4 }

gbSysUpdatesAvail OBJECT-TYPE
    SYNTAX      Gauge32
    MAX-ACCESS  read-only
    STATUS      current
    DESCRIPTION
        "Runtime updates available. (Not implemented)"
    ::= { gbSysUpdates 1 }

gbHighAvailability  OBJECT IDENTIFIER ::= { gbObjects 2 }

gbHighAvailabilityMode OBJECT-TYPE
    SYNTAX      Gauge32
    MAX-ACCESS  read-only
    STATUS      current
    DESCRIPTION
        "HA mode: 0 - disabled
             1 - init mode
             2 - slave mode
             3 - master mode"

    ::= { gbHighAvailability 1 }

gbStatistics  OBJECT IDENTIFIER ::= { gbObjects 3 }

gbStatsCurConns OBJECT-TYPE
    SYNTAX      Gauge32
    MAX-ACCESS  read-only
    STATUS      current
    DESCRIPTION
        "Current number of connections."
    ::= { gbStatistics 1 }

gbStatsPeakConns OBJECT-TYPE
    SYNTAX      Gauge32
    MAX-ACCESS  read-only
    STATUS      current
    DESCRIPTION
        "Peak number of connections."
    ::= { gbStatistics 2 }

gbStatsCurInConns OBJECT-TYPE
    SYNTAX      Gauge32
    MAX-ACCESS  read-only
    STATUS      current
    DESCRIPTION
        "Current number of inbound connections."
    ::= { gbStatistics 3 }

gbStatsCurOutConns OBJECT-TYPE
    SYNTAX      Gauge32
    MAX-ACCESS  read-only
    STATUS      current
    DESCRIPTION
        "Current number of outbound connections."
    ::= { gbStatistics 4 }

gbStatsPeakInConns OBJECT-TYPE
    SYNTAX      Gauge32
    MAX-ACCESS  read-only
    STATUS      current
    DESCRIPTION
        "Peak number of inbound connections."
    ::= { gbStatistics 5 }

gbStatsPeakOutConns OBJECT-TYPE
    SYNTAX      Gauge32
    MAX-ACCESS  read-only
    STATUS      current
    DESCRIPTION
        "Peak number of outbound connections."
    ::= { gbStatistics 6 }



END
