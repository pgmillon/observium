FspR7-LAYER2-MIB DEFINITIONS ::= BEGIN

IMPORTS
    DisplayString,
    TestAndIncr,
    TimeStamp,
    RowStatus,
    DateAndTime,
    TruthValue,
    TEXTUAL-CONVENTION
                                        FROM  SNMPv2-TC
    MODULE-COMPLIANCE,
    NOTIFICATION-GROUP,
    OBJECT-GROUP
                                        FROM  SNMPv2-CONF
    Counter32,
    MODULE-IDENTITY,
    NOTIFICATION-TYPE,
    OBJECT-TYPE,
    OBJECT-IDENTITY,
    TimeTicks,
    mib-2,
    snmpModules,
    enterprises,
    Unsigned32,
    Integer32,
    IpAddress
                                        FROM  SNMPv2-SMI
    SnmpAdminString
                                        FROM  SNMP-FRAMEWORK-MIB
    fspR7,
    TrapAlarmSeverity,
    ServiceImpairment,
    entityIndex,
    entityClass,
    EntityIndex,
    EntityClass,
    neEventLogTimeStamp,
    neEventLogIdentityTranslation,
    LoopConfig,
    ProtectionMech,
    ProtectionMechCaps,
    snmpProxyEntrySingleTargetOutNodeAgentStatus,
    snmpProxyServerSynchroStage,
    Counter64String
                                        FROM  ADVA-MIB
    ApsDirection,
    ApsRevertMode,
    ApsRevertModeCaps,
    ApsType,
    FspR7APSCommand,
    FspR7APSCommandCaps,
    FspR7AdminState,
    FspR7AdminStateCaps,
    FspR7Conn,
    FspR7ConnCaps,
    FspR7ConnectState,
    FspR7EntitySecondaryStates,
    FspR7ForcedStatus,
    FspR7ForcedStatusCaps,
    FspR7Integer32Caps,
    FspR7InterfaceFunction,
    FspR7InterfaceType,
    FspR7InterfaceTypeCaps,
    FspR7OperState,
    FspR7PmReset,
    FspR7PmResetCaps,
    FspR7ProtectionRole,
    FspR7ProtectionType,
    FspR7RowStatusCaps,
    FspR7TypeCrs,
    FspR7TypeCrsCaps,
    FspR7Unsigned32Caps,
    FspR7FunctionCrs,
    FspR7YesNo,
    FspR7YesNoCaps
                                        FROM  FspR7-MIB;
    

layer2MIB MODULE-IDENTITY

    LAST-UPDATED "201102210000Z"

    ORGANIZATION "ADVA Optical Networking"

    CONTACT-INFO "EMEA Support
                  Phone : +49 89 89 0665 848
                  Fax   : +49 89 89 0665 22848
                  Email : support@advaoptical.com

                  North American Support
                  Phone : 886 442 ADVA (2382) (toll-free within the US, Canada and Mexico)
                  Fax   : + 1 806 741 8529 (elsewhere)
                  Email : support-usa@advaoptical.com

                  Asia Pacific Support
                  Phone : + 1 866 442 2382 (other toll-free numbers available in some countries)
                  Email : support-asia@advaoptical.com"

    DESCRIPTION   "This is a MIB definition for L2MUX functionality."

    REVISION      "201102210000Z"
    DESCRIPTION   "FSP3000 F7 Release 10.3 MIB."

    REVISION      "201010290000Z"
    DESCRIPTION   "FSP3000 F7 Release 10.2 MIB."

    REVISION      "201010220000Z"
    DESCRIPTION   "FSP3000 F7 Release 10.2.0 MIB."

    REVISION      "201008310000Z"
    DESCRIPTION   "FSP3000 F7 Release 10.1 MIB."

    REVISION      "201006140000Z"
    DESCRIPTION   "FSP3000 F7 Release 9.4 MIB."

    REVISION      "201003240000Z"
    DESCRIPTION   "FSP3000 F7 Release 9.3 MIB."

    REVISION      "200911200000Z"
    DESCRIPTION   "FSP3000 F7 Release 9.2 MIB."

    REVISION      "200906050000Z"
    DESCRIPTION   "FSP3000 F7 Release 9.1 MIB."
    ::= { fspR7 3 }


layer2EntitiesMIB
    OBJECT IDENTIFIER ::= { layer2MIB 11 }

layer2ProvisioningMIB
    OBJECT IDENTIFIER ::= { layer2MIB 12 }

flowProvisioning
    OBJECT IDENTIFIER ::= { layer2ProvisioningMIB 11 }

ctransProvisioning
    OBJECT IDENTIFIER ::= { layer2ProvisioningMIB 12 }

bridgeProvisioning
    OBJECT IDENTIFIER ::= { layer2ProvisioningMIB 13 }

layer2ConfigurationMIB
    OBJECT IDENTIFIER ::= { layer2MIB 13 }

flowConfiguration
    OBJECT IDENTIFIER ::= { layer2ConfigurationMIB 11 }

bridgeConfiguration
    OBJECT IDENTIFIER ::= { layer2ConfigurationMIB 12 }

queOnBridgeConfiguration
    OBJECT IDENTIFIER ::= { layer2ConfigurationMIB 13 }

layer2StatusMIB
    OBJECT IDENTIFIER ::= { layer2MIB 14 }

flowStatus
    OBJECT IDENTIFIER ::= { layer2StatusMIB 11 }

ctransStatus
    OBJECT IDENTIFIER ::= { layer2StatusMIB 12 }

policerStatus
    OBJECT IDENTIFIER ::= { layer2StatusMIB 13 }

queStatus
    OBJECT IDENTIFIER ::= { layer2StatusMIB 14 }

bridgeStatus
    OBJECT IDENTIFIER ::= { layer2StatusMIB 15 }

layer2CrossConnections
    OBJECT IDENTIFIER ::= { layer2MIB 15 }

layer2PerformanceMonitoring
    OBJECT IDENTIFIER ::= { layer2MIB 16 }

flowPerformanceMonitoring
    OBJECT IDENTIFIER ::= { layer2PerformanceMonitoring 1 }

policerPerformanceMonitoring
    OBJECT IDENTIFIER ::= { layer2PerformanceMonitoring 2 }

quePerformanceMonitoring
    OBJECT IDENTIFIER ::= { layer2PerformanceMonitoring 3 }

layer2Alarms
    OBJECT IDENTIFIER ::= { layer2MIB 17 }

layer2Traps
    OBJECT IDENTIFIER ::= { layer2Alarms 1 }

layer2TrapsPrefix
    OBJECT IDENTIFIER ::= { layer2Traps 0 }

layer2Conditions
    OBJECT IDENTIFIER ::= { layer2Alarms 2 }

layer2FlowProtection
    OBJECT IDENTIFIER ::= { layer2MIB 18 }

BridgeEntityIndex ::= TEXTUAL-CONVENTION
  STATUS        current
  DESCRIPTION
         "The index of a BRIDGE entity." 
  SYNTAX        Integer32 (0..2147483647)

FspR7DisableEnable ::= TEXTUAL-CONVENTION
  STATUS        current
  DESCRIPTION
         "Disable/Enable variable." 
  SYNTAX        INTEGER
                {
                  undefined(0),
                  disable(1),
                  enable(2)
                }

FspR7DisableEnableCaps ::= TEXTUAL-CONVENTION
  STATUS        current
  DESCRIPTION
         "Disable/Enable variable." 
  SYNTAX        BITS
                {
                  capUndefined(0),
                  capDisable(1),
                  capEnable(2)
                }

FspR7Brigde ::= TEXTUAL-CONVENTION
  STATUS        current
  DESCRIPTION
         "To select between diffenrent protection types" 
  SYNTAX        INTEGER                {
                  undefined(0),
                  bridge1plus1(1),  --Permanent Bridge
                  bridge1for1(2),  --No Permanent Bridge
                  bridge1plus1back2back(3),  --Back to Back Protection
                  bridge1for1extra(4)  --Extra traffic
                }

FspR7BrigdeCaps ::= TEXTUAL-CONVENTION
  STATUS        current
  DESCRIPTION
         "To select between diffenrent protection types" 
  SYNTAX        BITS
                {
                  capUndefined(0),
                  capBridge1plus1(1),
                  capBridge1for1(2),
                  capBridge1plus1back2back(3),
                  capBridge1for1extra(4)
                }

FspR7L2Brigde ::= TEXTUAL-CONVENTION
  STATUS        obsolete
  DESCRIPTION
         "To select between diffenrent protection types" 
  SYNTAX        INTEGER                {
                  undefined(0),
                  bridge1plus1(1),  --Permanent Bridge
                  bridge1to1(2)  --No Permanent Bridge
                }

FspR7L2BrigdeCaps ::= TEXTUAL-CONVENTION
  STATUS        obsolete
  DESCRIPTION
         "To select between diffenrent protection types" 
  SYNTAX        BITS
                {
                  capUndefined(0),
                  capBridge1plus1(1),
                  capBridge1to1(2)
                }

FspR7L2FlowType ::= TEXTUAL-CONVENTION
  STATUS        current
  DESCRIPTION
         "EVC type according to MEF" 
  SYNTAX        INTEGER                {
                  undefined(0),
                  eline(1),
                  etree(2),
                  elan(3)
                }

FspR7L2FlowTypeCaps ::= TEXTUAL-CONVENTION
  STATUS        current
  DESCRIPTION
         "EVC type according to MEF" 
  SYNTAX        BITS
                {
                  capUndefined(0),
                  capEline(1),
                  capEtree(2),
                  capElan(3)
                }

FspR7L2LevelDomainMonitored ::= TEXTUAL-CONVENTION
  STATUS        current
  DESCRIPTION
         "Maintenance Domain Level monitored" 
  SYNTAX        INTEGER                {
                  undefined(0),
                  notSupported(1),
                  levelMD0(2),
                  levelMD1(3),
                  levelMD2(4),
                  levelMD3(5),
                  levelMD4(6),
                  levelMD5(7),
                  levelMD6(8),
                  levelMD7(9)
                }

FspR7L2LevelDomainMonitoredCaps ::= TEXTUAL-CONVENTION
  STATUS        current
  DESCRIPTION
         "Maintenance Domain Level monitored" 
  SYNTAX        BITS
                {
                  capUndefined(0),
                  capNotSupported(1),
                  capLevelMD0(2),
                  capLevelMD1(3),
                  capLevelMD2(4),
                  capLevelMD3(5),
                  capLevelMD4(6),
                  capLevelMD5(7),
                  capLevelMD6(8),
                  capLevelMD7(9)
                }

FspR7L2PmMode ::= TEXTUAL-CONVENTION
  STATUS        current
  DESCRIPTION
         "Mode of PM counters" 
  SYNTAX        INTEGER                {
                  undefined(0),
                  enableAll(1),
                  enableCurrent(2),
                  disable(3)
                }

FspR7L2PmModeCaps ::= TEXTUAL-CONVENTION
  STATUS        current
  DESCRIPTION
         "Mode of PM counters" 
  SYNTAX        BITS
                {
                  capUndefined(0),
                  capEnableAll(1),
                  capEnableCurrent(2),
                  capDisable(3)
                }

FspR7L2StandingConditionTypes ::= TEXTUAL-CONVENTION
  STATUS        current
  DESCRIPTION
         "" 
  SYNTAX        INTEGER
                {
                  undefined(0),
                  oosDisabledL2(100000),
                  oosManagementL2(100001),
                  oosMaintenanceL2(100002),
                  oosAinsL2(100003),
                  serverSignalFailL2(100004),
                  mepNotPresentL2(100005),
                  priVidNotEqualExtVidL2(100006),
                  switchtoProtectionInhibitedL2(100007),
                  manswL2(100008),
                  sfCfmLevel0L2 (100009),
                  sfCfmLevel1L2 (100010),
                  sfCfmLevel2L2 (100011),
                  sfCfmLevel3L2 (100012),
                  sfCfmLevel4L2 (100013),
                  sfCfmLevel5L2 (100014),
                  sfCfmLevel6L2 (100015),
                  sfCfmLevel7L2 (100016),
                  switchtoWorkingInhibitedL2(100019)
                }

BridgeStandingConditionTypes ::= TEXTUAL-CONVENTION
  STATUS        current
  DESCRIPTION
         "" 
  SYNTAX        INTEGER
                {
                  undefined(0),
                  bridgeOosManagement(100017),
                  bridgeOosAins(100018)
                }

FspR7RedLinedState ::= TEXTUAL-CONVENTION
  STATUS        current
  DESCRIPTION
         "will be set by higher level software to act as a barrier to deletion" 
  SYNTAX        INTEGER                {
                  undefined(0),
                  yes(1),
                  no(2)
                }

FspR7RedLinedStateCaps ::= TEXTUAL-CONVENTION
  STATUS        current
  DESCRIPTION
         "will be set by higher level software to act as a barrier to deletion" 
  SYNTAX        BITS
                {
                  capUndefined(0),
                  capYes(1),
                  capNo(2)
                }

QueueEntityIndex ::= TEXTUAL-CONVENTION
  STATUS        current
  DESCRIPTION
         "The index of a QUEUE entity. The QUEUE entity may be defined on PORT, FLOW or
         BRIDGE depending on QUEUE type." 
  SYNTAX        Integer32 (0..2147483647)

flowEntityTable OBJECT-TYPE
    SYNTAX      SEQUENCE OF FlowEntityEntry
    MAX-ACCESS  not-accessible
    STATUS      current
    DESCRIPTION   ""
    ::=  { layer2EntitiesMIB 10 }

flowEntityEntry OBJECT-TYPE
    SYNTAX      FlowEntityEntry
    MAX-ACCESS  not-accessible
    STATUS      current
    DESCRIPTION   ""
    INDEX       {
                  flowEntityIndexEth,
                  flowEntityIndexFlow
                }
    ::=  { flowEntityTable 1 }

FlowEntityEntry ::=  SEQUENCE
  { flowEntityIndexEth EntityIndex,
    flowEntityIndexFlow EntityIndex,
    flowEntityClass EntityClass,
    flowEntityClassInstanceNumber Integer32,
    flowEntityIndexAid SnmpAdminString }

flowEntityIndexEth OBJECT-TYPE
    SYNTAX      EntityIndex
    MAX-ACCESS  accessible-for-notify
    STATUS      current
    DESCRIPTION   "First index of a flow entity referencing to eth entity (parent)."
    ::=  { flowEntityEntry 1 }

flowEntityIndexFlow OBJECT-TYPE
    SYNTAX      EntityIndex
    MAX-ACCESS  accessible-for-notify
    STATUS      current
    DESCRIPTION   "Second index of a flow entity referencing to svid value."
    ::=  { flowEntityEntry 2 }

flowEntityClass OBJECT-TYPE
    SYNTAX      EntityClass
    MAX-ACCESS  read-only
    STATUS      current
    DESCRIPTION   "See EntityClass"
    ::=  { flowEntityEntry 3 }

flowEntityClassInstanceNumber OBJECT-TYPE
    SYNTAX      Integer32 (1..2000 | -2147483648)
    MAX-ACCESS  read-only
    STATUS      current
    DESCRIPTION
        "The class instance number of this entity within the module(card)" 
    ::=  { flowEntityEntry 4 }

flowEntityIndexAid OBJECT-TYPE
    SYNTAX      SnmpAdminString
    MAX-ACCESS  read-only
    STATUS      current
    DESCRIPTION
        "Name" 
    ::=  { flowEntityEntry 5 }

ctransEntityTable OBJECT-TYPE
    SYNTAX      SEQUENCE OF CtransEntityEntry
    MAX-ACCESS  not-accessible
    STATUS      current
    DESCRIPTION   ""
    ::=  { layer2EntitiesMIB 11 }

ctransEntityEntry OBJECT-TYPE
    SYNTAX      CtransEntityEntry
    MAX-ACCESS  not-accessible
    STATUS      current
    DESCRIPTION   ""
    INDEX       {
                  ctransEntityIndexEth,
                  ctransEntityIndexCVlanId
                }
    ::=  { ctransEntityTable 1 }

CtransEntityEntry ::=  SEQUENCE
  { ctransEntityIndexEth EntityIndex,
    ctransEntityIndexCVlanId EntityIndex,
    ctransEntityClass EntityClass,
    ctransEntityClassInstanceNumber Integer32,
    ctransEntityIndexAid SnmpAdminString }

ctransEntityIndexEth OBJECT-TYPE
    SYNTAX      EntityIndex
    MAX-ACCESS  accessible-for-notify
    STATUS      current
    DESCRIPTION   "First index of a ctrans entity referencing to eth entity (parent)."
    ::=  { ctransEntityEntry 1 }

ctransEntityIndexCVlanId OBJECT-TYPE
    SYNTAX      EntityIndex
    MAX-ACCESS  accessible-for-notify
    STATUS      current
    DESCRIPTION   "Second index of a ctrans entity referencing to svid value."
    ::=  { ctransEntityEntry 2 }

ctransEntityClass OBJECT-TYPE
    SYNTAX      EntityClass
    MAX-ACCESS  read-only
    STATUS      current
    DESCRIPTION   "See EntityClass"
    ::=  { ctransEntityEntry 3 }

ctransEntityClassInstanceNumber OBJECT-TYPE
    SYNTAX      Integer32 (1..2000 | -2147483648)
    MAX-ACCESS  read-only
    STATUS      current
    DESCRIPTION
        "The class instance number of this entity within the module(card)" 
    ::=  { ctransEntityEntry 4 }

ctransEntityIndexAid OBJECT-TYPE
    SYNTAX      SnmpAdminString
    MAX-ACCESS  read-only
    STATUS      current
    DESCRIPTION
        "Name" 
    ::=  { ctransEntityEntry 5 }

bridgeEntityTable OBJECT-TYPE
    SYNTAX      SEQUENCE OF BridgeEntityEntry
    MAX-ACCESS  not-accessible
    STATUS      current
    DESCRIPTION   "This table contains entries presenting the BRIDGE entities."
    ::=  { layer2EntitiesMIB 12 }

bridgeEntityEntry OBJECT-TYPE
    SYNTAX      BridgeEntityEntry
    MAX-ACCESS  not-accessible
    STATUS      current
    DESCRIPTION   "The BRIDGE entity."
    INDEX       {
                  bridgeEntityContainedIn,
                  bridgeEntitySvid
                }
    ::=  { bridgeEntityTable 1 }

BridgeEntityEntry ::=  SEQUENCE
  { bridgeEntityContainedIn EntityIndex,
    bridgeEntitySvid BridgeEntityIndex,
    bridgeEntityClass EntityClass,
    bridgeEntityClassInstanceNumber Integer32,
    bridgeEntityIndexAid SnmpAdminString }

bridgeEntityContainedIn OBJECT-TYPE
    SYNTAX      EntityIndex
    MAX-ACCESS  not-accessible
    STATUS      current
    DESCRIPTION   "Index of BRIDGE entity pointing to its parent MODULE entity."
    ::=  { bridgeEntityEntry 1 }

bridgeEntitySvid OBJECT-TYPE
    SYNTAX      BridgeEntityIndex
    MAX-ACCESS  not-accessible
    STATUS      current
    DESCRIPTION   "The SVID value for this BRIDGE entity. This index points
         to flow entity with the same SVID."
    ::=  { bridgeEntityEntry 2 }

bridgeEntityClass OBJECT-TYPE
    SYNTAX      EntityClass
    MAX-ACCESS  read-only
    STATUS      current
    DESCRIPTION   "See EntityClass Textual-Convention."
    ::=  { bridgeEntityEntry 3 }

bridgeEntityClassInstanceNumber OBJECT-TYPE
    SYNTAX      Integer32 (1..2000 | -2147483648)
    MAX-ACCESS  read-only
    STATUS      current
    DESCRIPTION   "Order number for the BRIDGE entity present in the system."
    ::=  { bridgeEntityEntry 4 }

bridgeEntityIndexAid OBJECT-TYPE
    SYNTAX      SnmpAdminString
    MAX-ACCESS  read-only
    STATUS      current
    DESCRIPTION   "This column presents a text-based entity address description."
    ::=  { bridgeEntityEntry 5 }

policerOnFlowEntityTable OBJECT-TYPE
    SYNTAX      SEQUENCE OF PolicerOnFlowEntityEntry
    MAX-ACCESS  not-accessible
    STATUS      current
    DESCRIPTION   ""
    ::=  { layer2EntitiesMIB 13 }

policerOnFlowEntityEntry OBJECT-TYPE
    SYNTAX      PolicerOnFlowEntityEntry
    MAX-ACCESS  not-accessible
    STATUS      current
    DESCRIPTION   ""
    INDEX       {
                  policerOnFlowEntityIndexEth,
                  policerOnFlowEntityIndexFlow,
                  policerOnFlowEntityIndexPolicer
                }
    ::=  { policerOnFlowEntityTable 1 }

PolicerOnFlowEntityEntry ::=  SEQUENCE
  { policerOnFlowEntityIndexEth EntityIndex,
    policerOnFlowEntityIndexFlow EntityIndex,
    policerOnFlowEntityIndexPolicer EntityIndex,
    policerOnFlowEntityClass EntityClass,
    policerOnFlowEntityClassInstanceNumber Integer32,
    policerOnFlowEntityIndexAid SnmpAdminString }

policerOnFlowEntityIndexEth OBJECT-TYPE
    SYNTAX      EntityIndex
    MAX-ACCESS  accessible-for-notify
    STATUS      current
    DESCRIPTION   "Index of a policer entity referencing to eth entity (parent)."
    ::=  { policerOnFlowEntityEntry 1 }

policerOnFlowEntityIndexFlow OBJECT-TYPE
    SYNTAX      EntityIndex
    MAX-ACCESS  accessible-for-notify
    STATUS      current
    DESCRIPTION   "Index of a policer entity referencing to svid value."
    ::=  { policerOnFlowEntityEntry 2 }

policerOnFlowEntityIndexPolicer OBJECT-TYPE
    SYNTAX      EntityIndex
    MAX-ACCESS  accessible-for-notify
    STATUS      current
    DESCRIPTION   "Index of a policer entity referencing to prio value."
    ::=  { policerOnFlowEntityEntry 3 }

policerOnFlowEntityClass OBJECT-TYPE
    SYNTAX      EntityClass
    MAX-ACCESS  read-only
    STATUS      current
    DESCRIPTION   "See EntityClass"
    ::=  { policerOnFlowEntityEntry 4 }

policerOnFlowEntityClassInstanceNumber OBJECT-TYPE
    SYNTAX      Integer32 (1..2000 | -2147483648)
    MAX-ACCESS  read-only
    STATUS      current
    DESCRIPTION
        "The class instance number of this entity within the module(card)" 
    ::=  { policerOnFlowEntityEntry 5 }

policerOnFlowEntityIndexAid OBJECT-TYPE
    SYNTAX      SnmpAdminString
    MAX-ACCESS  read-only
    STATUS      current
    DESCRIPTION
        "Name" 
    ::=  { policerOnFlowEntityEntry 6 }

queOnPortEntityTable OBJECT-TYPE
    SYNTAX      SEQUENCE OF QueOnPortEntityEntry
    MAX-ACCESS  not-accessible
    STATUS      current
    DESCRIPTION   ""
    ::=  { layer2EntitiesMIB 15 }

queOnPortEntityEntry OBJECT-TYPE
    SYNTAX      QueOnPortEntityEntry
    MAX-ACCESS  not-accessible
    STATUS      current
    DESCRIPTION   ""
    INDEX       {
                  queOnPortEntityIndexEth,
                  queOnPortEntityIndexPrio
                }
    ::=  { queOnPortEntityTable 1 }

QueOnPortEntityEntry ::=  SEQUENCE
  { queOnPortEntityIndexEth EntityIndex,
    queOnPortEntityIndexPrio EntityIndex,
    queOnPortEntityClass EntityClass,
    queOnPortEntityClassInstanceNumber Integer32,
    queOnPortEntityIndexAid SnmpAdminString }

queOnPortEntityIndexEth OBJECT-TYPE
    SYNTAX      EntityIndex
    MAX-ACCESS  accessible-for-notify
    STATUS      current
    DESCRIPTION   "First index of a que entity referencing to eth entity (parent)."
    ::=  { queOnPortEntityEntry 1 }

queOnPortEntityIndexPrio OBJECT-TYPE
    SYNTAX      EntityIndex
    MAX-ACCESS  accessible-for-notify
    STATUS      current
    DESCRIPTION   "Third index of a que entity referencing to priority value."
    ::=  { queOnPortEntityEntry 2 }

queOnPortEntityClass OBJECT-TYPE
    SYNTAX      EntityClass
    MAX-ACCESS  read-only
    STATUS      current
    DESCRIPTION   "See EntityClass"
    ::=  { queOnPortEntityEntry 3 }

queOnPortEntityClassInstanceNumber OBJECT-TYPE
    SYNTAX      Integer32 (1..2000 | -2147483648)
    MAX-ACCESS  read-only
    STATUS      current
    DESCRIPTION
        "The class instance number of this entity within the module(card)" 
    ::=  { queOnPortEntityEntry 4 }

queOnPortEntityIndexAid OBJECT-TYPE
    SYNTAX      SnmpAdminString
    MAX-ACCESS  read-only
    STATUS      current
    DESCRIPTION
        "Name" 
    ::=  { queOnPortEntityEntry 5 }

queOnFlowEntityTable OBJECT-TYPE
    SYNTAX      SEQUENCE OF QueOnFlowEntityEntry
    MAX-ACCESS  not-accessible
    STATUS      current
    DESCRIPTION   ""
    ::=  { layer2EntitiesMIB 16 }

queOnFlowEntityEntry OBJECT-TYPE
    SYNTAX      QueOnFlowEntityEntry
    MAX-ACCESS  not-accessible
    STATUS      current
    DESCRIPTION   ""
    INDEX       {
                  queOnFlowEntityIndexEth,
                  queOnFlowEntityIndexFlow,
                  queOnFlowEntityIndexPrio
                }
    ::=  { queOnFlowEntityTable 1 }

QueOnFlowEntityEntry ::=  SEQUENCE
  { queOnFlowEntityIndexEth EntityIndex,
    queOnFlowEntityIndexFlow EntityIndex,
    queOnFlowEntityIndexPrio EntityIndex,
    queOnFlowEntityClass EntityClass,
    queOnFlowEntityClassInstanceNumber Integer32,
    queOnFlowEntityIndexAid SnmpAdminString }

queOnFlowEntityIndexEth OBJECT-TYPE
    SYNTAX      EntityIndex
    MAX-ACCESS  accessible-for-notify
    STATUS      current
    DESCRIPTION   "First index of a que entity referencing to eth entity (parent)."
    ::=  { queOnFlowEntityEntry 1 }

queOnFlowEntityIndexFlow OBJECT-TYPE
    SYNTAX      EntityIndex
    MAX-ACCESS  accessible-for-notify
    STATUS      current
    DESCRIPTION   "Third index of a que entity referencing to priority value."
    ::=  { queOnFlowEntityEntry 2 }

queOnFlowEntityIndexPrio OBJECT-TYPE
    SYNTAX      EntityIndex
    MAX-ACCESS  accessible-for-notify
    STATUS      current
    DESCRIPTION   "Third index of a que entity referencing to priority value."
    ::=  { queOnFlowEntityEntry 3 }

queOnFlowEntityClass OBJECT-TYPE
    SYNTAX      EntityClass
    MAX-ACCESS  read-only
    STATUS      current
    DESCRIPTION   "See EntityClass"
    ::=  { queOnFlowEntityEntry 4 }

queOnFlowEntityClassInstanceNumber OBJECT-TYPE
    SYNTAX      Integer32 (1..2000 | -2147483648)
    MAX-ACCESS  read-only
    STATUS      current
    DESCRIPTION
        "The class instance number of this entity within the module(card)" 
    ::=  { queOnFlowEntityEntry 5 }

queOnFlowEntityIndexAid OBJECT-TYPE
    SYNTAX      SnmpAdminString
    MAX-ACCESS  read-only
    STATUS      current
    DESCRIPTION
        "Name" 
    ::=  { queOnFlowEntityEntry 6 }

queOnBridgeEntityTable OBJECT-TYPE
    SYNTAX      SEQUENCE OF QueOnBridgeEntityEntry
    MAX-ACCESS  not-accessible
    STATUS      current
    DESCRIPTION   "This table lists all assigned QUE on BRIDGE entities."
    ::=  { layer2EntitiesMIB 17 }

queOnBridgeEntityEntry OBJECT-TYPE
    SYNTAX      QueOnBridgeEntityEntry
    MAX-ACCESS  not-accessible
    STATUS      current
    DESCRIPTION   "Table entry represents QUE on BRIDGE entity."
    INDEX       {
                  queOnBridgeEntityIndex,
                  queOnBridgeEntitySvid,
                  queOnBridgeEntityPrio
                }
    ::=  { queOnBridgeEntityTable 1 }

QueOnBridgeEntityEntry ::=  SEQUENCE
  { queOnBridgeEntityIndex QueueEntityIndex,
    queOnBridgeEntitySvid QueueEntityIndex,
    queOnBridgeEntityPrio QueueEntityIndex,
    queOnBridgeEntityClass EntityClass,
    queOnBridgeEntityClassInstanceNumber Integer32,
    queOnBridgeEntityIndexAid SnmpAdminString }

queOnBridgeEntityIndex OBJECT-TYPE
    SYNTAX      QueueEntityIndex
    MAX-ACCESS  not-accessible
    STATUS      current
    DESCRIPTION   "First index of a QUE on BRIDGE inherits value from parent entity."
    ::=  { queOnBridgeEntityEntry 1 }

queOnBridgeEntitySvid OBJECT-TYPE
    SYNTAX      QueueEntityIndex
    MAX-ACCESS  not-accessible
    STATUS      current
    DESCRIPTION   "Second index of a QUE on BRIDGE inherits value from parent entity."
    ::=  { queOnBridgeEntityEntry 2 }

queOnBridgeEntityPrio OBJECT-TYPE
    SYNTAX      QueueEntityIndex
    MAX-ACCESS  not-accessible
    STATUS      current
    DESCRIPTION   "Third index of a QUE on BRIDGE points its priority."
    ::=  { queOnBridgeEntityEntry 3 }

queOnBridgeEntityClass OBJECT-TYPE
    SYNTAX      EntityClass
    MAX-ACCESS  read-only
    STATUS      current
    DESCRIPTION   "See EntityClass Textual-Convention."
    ::=  { queOnBridgeEntityEntry 4 }

queOnBridgeEntityClassInstanceNumber OBJECT-TYPE
    SYNTAX      Integer32 (1..2000 | -2147483648)
    MAX-ACCESS  read-only
    STATUS      current
    DESCRIPTION   "System-wide, entity type unique number indicating its position in the system."
    ::=  { queOnBridgeEntityEntry 5 }

queOnBridgeEntityIndexAid OBJECT-TYPE
    SYNTAX      SnmpAdminString
    MAX-ACCESS  read-only
    STATUS      current
    DESCRIPTION   "Printable entity name."
    ::=  { queOnBridgeEntityEntry 6 }

flowEntityProvisionTable OBJECT-TYPE
    SYNTAX      SEQUENCE OF FlowEntityProvisionEntry
    MAX-ACCESS  not-accessible
    STATUS      current
    DESCRIPTION   ""
    ::=  { flowProvisioning 11 }

flowEntityProvisionEntry OBJECT-TYPE
    SYNTAX      FlowEntityProvisionEntry
    MAX-ACCESS  not-accessible
    STATUS      current
    DESCRIPTION   ""
    INDEX       {
                  flowEntityIndexEth,
                  flowEntityIndexFlow
                }
    ::=  { flowEntityProvisionTable 1 }

FlowEntityProvisionEntry ::=  SEQUENCE
  { flowEntityProvisionRowStatus RowStatus,
    flowEntityProvisionType FspR7InterfaceType,
    flowEntityProvisionAdmin FspR7AdminState,
    flowEntityProvisionAlias SnmpAdminString,
    flowEntityProvisionPopCtagRcv Unsigned32,
    flowEntityProvisionPopCtagTrmt Unsigned32,
    flowEntityProvisionCvidRegisteredInFlow SnmpAdminString,
    flowEntityProvisionExternalVid Unsigned32,
    flowEntityProvisionPmMode FspR7L2PmMode,
    flowEntityProvisionShape FspR7DisableEnable,
    flowEntityProvisionPolice FspR7DisableEnable,
    flowEntityProvisionDefaultEvcCos Integer32,
    flowEntityProvisionCirRcv Unsigned32,
    flowEntityProvisionCirTrmt Unsigned32,
    flowEntityProvisionCbsRcv Unsigned32,
    flowEntityProvisionCbsTrmt Unsigned32,
    flowEntityProvisionPushPvidTrmt Unsigned32,
    flowEntityProvisionPrioPvidTrmt Unsigned32,
    flowEntityProvisionRedLineState FspR7RedLinedState,
    flowEntityProvisionTunnelAid SnmpAdminString }

flowEntityProvisionRowStatus OBJECT-TYPE
    SYNTAX      RowStatus
    MAX-ACCESS  read-write
    STATUS      current
    DESCRIPTION   "This object is used to create, or delete a row in this table."
    ::=  { flowEntityProvisionEntry 1 }

flowEntityProvisionType OBJECT-TYPE
    SYNTAX      FspR7InterfaceType
    MAX-ACCESS  read-write
    STATUS      current
    DESCRIPTION   ""
    ::=  { flowEntityProvisionEntry 2 }

flowEntityProvisionAdmin OBJECT-TYPE
    SYNTAX      FspR7AdminState
    MAX-ACCESS  read-write
    STATUS      current
    DESCRIPTION
        "The Adminstrative State will be displayed in the GUI with full
         name values; it will be differently displayed in TL1 syntax according
         to TL1 display rules. The transaction into the UAS state requires
         a special destroy/delete function." 
    ::=  { flowEntityProvisionEntry 3 }

flowEntityProvisionAlias OBJECT-TYPE
    SYNTAX      SnmpAdminString
    MAX-ACCESS  read-write
    STATUS      current
    DESCRIPTION
        "User Applied Descriptor" 
    ::=  { flowEntityProvisionEntry 4 }

flowEntityProvisionPopCtagRcv OBJECT-TYPE
    SYNTAX      Unsigned32 (0..4095 | 4294967295)
    MAX-ACCESS  read-write
    STATUS      current
    DESCRIPTION
        "'c-vid tag is removed in receive to an EVC. This is equivalent to untagged PEP in PB'" 
    ::=  { flowEntityProvisionEntry 5 }

flowEntityProvisionPopCtagTrmt OBJECT-TYPE
    SYNTAX      Unsigned32 (0..4095 | 4294967295)
    MAX-ACCESS  read-write
    STATUS      current
    DESCRIPTION
        "'c-vid tag is removed on transmit from EVC. This is equivalent to the untagged CEP in PB'" 
    ::=  { flowEntityProvisionEntry 6 }

flowEntityProvisionCvidRegisteredInFlow OBJECT-TYPE
    SYNTAX      SnmpAdminString
    MAX-ACCESS  read-write
    STATUS      current
    DESCRIPTION
        "CVLANs Registered with the Flow" 
    ::=  { flowEntityProvisionEntry 7 }

flowEntityProvisionExternalVid OBJECT-TYPE
    SYNTAX      Unsigned32 (1..4095 | 4294967295)
    MAX-ACCESS  read-write
    STATUS      current
    DESCRIPTION
        "External VID" 
    ::=  { flowEntityProvisionEntry 8 }

flowEntityProvisionPmMode OBJECT-TYPE
    SYNTAX      FspR7L2PmMode
    MAX-ACCESS  read-write
    STATUS      current
    DESCRIPTION
        "Mode of PM counters" 
    ::=  { flowEntityProvisionEntry 9 }

flowEntityProvisionShape OBJECT-TYPE
    SYNTAX      FspR7DisableEnable
    MAX-ACCESS  read-write
    STATUS      current
    DESCRIPTION
        "Shape Enablement" 
    ::=  { flowEntityProvisionEntry 10 }

flowEntityProvisionPolice OBJECT-TYPE
    SYNTAX      FspR7DisableEnable
    MAX-ACCESS  read-write
    STATUS      current
    DESCRIPTION
        "Police Enablement" 
    ::=  { flowEntityProvisionEntry 11 }

flowEntityProvisionDefaultEvcCos OBJECT-TYPE
    SYNTAX      Integer32 (7..7 | -2147483648)
    MAX-ACCESS  read-write
    STATUS      current
    DESCRIPTION
        "Default COS for frames not matching classification scheme PCP/DSCP, or used as CoS for EVC based classification." 
    ::=  { flowEntityProvisionEntry 12 }

flowEntityProvisionCirRcv OBJECT-TYPE
    SYNTAX      Unsigned32 
    UNITS       "Mbit/s"
    MAX-ACCESS  read-write
    STATUS      current
    DESCRIPTION
        "CIR (Committed Information Rate ) is used on Ethernet Interfaces with a policing function" 
    ::=  { flowEntityProvisionEntry 13 }

flowEntityProvisionCirTrmt OBJECT-TYPE
    SYNTAX      Unsigned32 
    UNITS       "Mbit/s"
    MAX-ACCESS  read-write
    STATUS      current
    DESCRIPTION
        "CIR (Committed Information Rate ) is used on Ethernet Interfaces with a policing function" 
    ::=  { flowEntityProvisionEntry 14 }

flowEntityProvisionCbsRcv OBJECT-TYPE
    SYNTAX      Unsigned32 (0..26214400 | 4294967295) 
    UNITS       "bytes"
    MAX-ACCESS  read-write
    STATUS      current
    DESCRIPTION
        "Committed Burst Size" 
    ::=  { flowEntityProvisionEntry 15 }

flowEntityProvisionCbsTrmt OBJECT-TYPE
    SYNTAX      Unsigned32 (0..25600 | 4294967295) 
    UNITS       "Kbytes"
    MAX-ACCESS  read-write
    STATUS      current
    DESCRIPTION
        "Committed Burst Size" 
    ::=  { flowEntityProvisionEntry 16 }

flowEntityProvisionPushPvidTrmt OBJECT-TYPE
    SYNTAX      Unsigned32 (0..4095 | 4294967295)
    MAX-ACCESS  read-write
    STATUS      current
    DESCRIPTION
        "C-VID tag is added on transmit from EVC. PEP." 
    ::=  { flowEntityProvisionEntry 17 }

flowEntityProvisionPrioPvidTrmt OBJECT-TYPE
    SYNTAX      Unsigned32 (0..7 | 4294967295)
    MAX-ACCESS  read-write
    STATUS      current
    DESCRIPTION
        "Added PRIO when CTAG is pushed on untagged frame. PEP." 
    ::=  { flowEntityProvisionEntry 18 }

flowEntityProvisionRedLineState OBJECT-TYPE
    SYNTAX      FspR7RedLinedState
    MAX-ACCESS  read-write
    STATUS      current
    DESCRIPTION
        "will be set by higher level software to act as a barrier to deletion" 
    ::=  { flowEntityProvisionEntry 19 }

flowEntityProvisionTunnelAid OBJECT-TYPE
    SYNTAX      SnmpAdminString
    MAX-ACCESS  read-write
    STATUS      current
    DESCRIPTION
        "Tunnel AID" 
    ::=  { flowEntityProvisionEntry 20 }

flowEntityProvisionCapTable OBJECT-TYPE
    SYNTAX      SEQUENCE OF FlowEntityProvisionCapEntry
    MAX-ACCESS  not-accessible
    STATUS      current
    DESCRIPTION   ""
    ::=  { flowProvisioning 12  }

flowEntityProvisionCapEntry OBJECT-TYPE
    SYNTAX      FlowEntityProvisionCapEntry
    MAX-ACCESS  not-accessible
    STATUS      current
    DESCRIPTION   ""
    INDEX       { flowEntityIndexEth,
                  flowEntityIndexFlow }
    ::=  { flowEntityProvisionCapTable 1 }

FlowEntityProvisionCapEntry ::=  SEQUENCE
  { flowEntityProvisionCapRowStatus FspR7RowStatusCaps,
    flowEntityProvisionCapType FspR7InterfaceTypeCaps,
    flowEntityProvisionCapAdmin FspR7AdminStateCaps,
    flowEntityProvisionCapAlias Integer32,
    flowEntityProvisionCapPopCtagRcv Unsigned32,
    flowEntityProvisionCapPopCtagTrmt Unsigned32,
    flowEntityProvisionCapCvidRegisteredInFlow Integer32,
    flowEntityProvisionCapExternalVid Unsigned32,
    flowEntityProvisionCapPmMode FspR7L2PmModeCaps,
    flowEntityProvisionCapShape FspR7DisableEnableCaps,
    flowEntityProvisionCapPolice FspR7DisableEnableCaps,
    flowEntityProvisionCapDefaultEvcCos FspR7Integer32Caps,
    flowEntityProvisionCapCirRcv FspR7Unsigned32Caps,
    flowEntityProvisionCapCirTrmt FspR7Unsigned32Caps,
    flowEntityProvisionCapCbsRcv Unsigned32,
    flowEntityProvisionCapCbsTrmt FspR7Unsigned32Caps,
    flowEntityProvisionCapPushPvidTrmt Unsigned32,
    flowEntityProvisionCapPrioPvidTrmt FspR7Unsigned32Caps,
    flowEntityProvisionCapRedLineState FspR7RedLinedStateCaps,
    flowEntityProvisionCapTunnelAid Integer32 }

flowEntityProvisionCapRowStatus OBJECT-TYPE
    SYNTAX      FspR7RowStatusCaps
    MAX-ACCESS  read-only
    STATUS      current
    DESCRIPTION   "This object is used to create, or delete a row in this table."
    ::=  { flowEntityProvisionCapEntry 1 }

flowEntityProvisionCapType OBJECT-TYPE
    SYNTAX      FspR7InterfaceTypeCaps
    MAX-ACCESS  read-only
    STATUS      current
    DESCRIPTION   ""
    ::=  { flowEntityProvisionCapEntry 2 }

flowEntityProvisionCapAdmin OBJECT-TYPE
    SYNTAX      FspR7AdminStateCaps
    MAX-ACCESS  read-only
    STATUS      current
    DESCRIPTION
        "The Adminstrative State will be displayed in the GUI with full
         name values; it will be differently displayed in TL1 syntax according
         to TL1 display rules. The transaction into the UAS state requires
         a special destroy/delete function." 
    ::=  { flowEntityProvisionCapEntry 3 }

flowEntityProvisionCapAlias OBJECT-TYPE
    SYNTAX      Integer32
    MAX-ACCESS  read-only
    STATUS      current
    DESCRIPTION
        "User Applied Descriptor" 
    ::=  { flowEntityProvisionCapEntry 4 }

flowEntityProvisionCapPopCtagRcv OBJECT-TYPE
    SYNTAX      Unsigned32
    MAX-ACCESS  read-only
    STATUS      current
    DESCRIPTION
        "'c-vid tag is removed in receive to an EVC. This is equivalent to untagged PEP in PB'" 
    ::=  { flowEntityProvisionCapEntry 5 }

flowEntityProvisionCapPopCtagTrmt OBJECT-TYPE
    SYNTAX      Unsigned32
    MAX-ACCESS  read-only
    STATUS      current
    DESCRIPTION
        "'c-vid tag is removed on transmit from EVC. This is equivalent to the untagged CEP in PB'" 
    ::=  { flowEntityProvisionCapEntry 6 }

flowEntityProvisionCapCvidRegisteredInFlow OBJECT-TYPE
    SYNTAX      Integer32
    MAX-ACCESS  read-only
    STATUS      current
    DESCRIPTION
        "CVLANs Registered with the Flow" 
    ::=  { flowEntityProvisionCapEntry 7 }

flowEntityProvisionCapExternalVid OBJECT-TYPE
    SYNTAX      Unsigned32
    MAX-ACCESS  read-only
    STATUS      current
    DESCRIPTION
        "External VID" 
    ::=  { flowEntityProvisionCapEntry 8 }

flowEntityProvisionCapPmMode OBJECT-TYPE
    SYNTAX      FspR7L2PmModeCaps
    MAX-ACCESS  read-only
    STATUS      current
    DESCRIPTION
        "Mode of PM counters" 
    ::=  { flowEntityProvisionCapEntry 9 }

flowEntityProvisionCapShape OBJECT-TYPE
    SYNTAX      FspR7DisableEnableCaps
    MAX-ACCESS  read-only
    STATUS      current
    DESCRIPTION
        "Shape Enablement" 
    ::=  { flowEntityProvisionCapEntry 10 }

flowEntityProvisionCapPolice OBJECT-TYPE
    SYNTAX      FspR7DisableEnableCaps
    MAX-ACCESS  read-only
    STATUS      current
    DESCRIPTION
        "Police Enablement" 
    ::=  { flowEntityProvisionCapEntry 11 }

flowEntityProvisionCapDefaultEvcCos OBJECT-TYPE
    SYNTAX      FspR7Integer32Caps
    MAX-ACCESS  read-only
    STATUS      current
    DESCRIPTION
        "Default COS for frames not matching classification scheme PCP/DSCP, or used as CoS for EVC based classification." 
    ::=  { flowEntityProvisionCapEntry 12 }

flowEntityProvisionCapCirRcv OBJECT-TYPE
    SYNTAX      FspR7Unsigned32Caps
    UNITS       "Mbit/s"
    MAX-ACCESS  read-only
    STATUS      current
    DESCRIPTION
        "CIR (Committed Information Rate ) is used on Ethernet Interfaces with a policing function" 
    ::=  { flowEntityProvisionCapEntry 13 }

flowEntityProvisionCapCirTrmt OBJECT-TYPE
    SYNTAX      FspR7Unsigned32Caps
    UNITS       "Mbit/s"
    MAX-ACCESS  read-only
    STATUS      current
    DESCRIPTION
        "CIR (Committed Information Rate ) is used on Ethernet Interfaces with a policing function" 
    ::=  { flowEntityProvisionCapEntry 14 }

flowEntityProvisionCapCbsRcv OBJECT-TYPE
    SYNTAX      Unsigned32
    UNITS       "bytes"
    MAX-ACCESS  read-only
    STATUS      current
    DESCRIPTION
        "Committed Burst Size" 
    ::=  { flowEntityProvisionCapEntry 15 }

flowEntityProvisionCapCbsTrmt OBJECT-TYPE
    SYNTAX      FspR7Unsigned32Caps
    UNITS       "Kbytes"
    MAX-ACCESS  read-only
    STATUS      current
    DESCRIPTION
        "Committed Burst Size" 
    ::=  { flowEntityProvisionCapEntry 16 }

flowEntityProvisionCapPushPvidTrmt OBJECT-TYPE
    SYNTAX      Unsigned32
    MAX-ACCESS  read-only
    STATUS      current
    DESCRIPTION
        "C-VID tag is added on transmit from EVC. PEP." 
    ::=  { flowEntityProvisionCapEntry 17 }

flowEntityProvisionCapPrioPvidTrmt OBJECT-TYPE
    SYNTAX      FspR7Unsigned32Caps
    MAX-ACCESS  read-only
    STATUS      current
    DESCRIPTION
        "Added PRIO when CTAG is pushed on untagged frame. PEP." 
    ::=  { flowEntityProvisionCapEntry 18 }

flowEntityProvisionCapRedLineState OBJECT-TYPE
    SYNTAX      FspR7RedLinedStateCaps
    MAX-ACCESS  read-only
    STATUS      current
    DESCRIPTION
        "will be set by higher level software to act as a barrier to deletion" 
    ::=  { flowEntityProvisionCapEntry 19 }

flowEntityProvisionCapTunnelAid OBJECT-TYPE
    SYNTAX      Integer32
    MAX-ACCESS  read-only
    STATUS      current
    DESCRIPTION
        "Tunnel AID" 
    ::=  { flowEntityProvisionCapEntry 20 }

flowEntityProvisionDefaultsTable  OBJECT-TYPE
    SYNTAX      SEQUENCE OF FlowEntityProvisionDefaultsEntry
    MAX-ACCESS  not-accessible
    STATUS      current
    DESCRIPTION   ""
    ::=  { flowProvisioning 13  }

flowEntityProvisionDefaultsEntry OBJECT-TYPE
    SYNTAX      FlowEntityProvisionDefaultsEntry
    MAX-ACCESS  not-accessible
    STATUS      current
    DESCRIPTION   ""
    INDEX       { flowEntityIndexEth,
                  flowEntityIndexFlow }
    ::=  { flowEntityProvisionDefaultsTable 1 }

FlowEntityProvisionDefaultsEntry ::=  SEQUENCE
  { flowEntityProvisionDefaultsRowStatus RowStatus,
    flowEntityProvisionDefaultsType FspR7InterfaceType,
    flowEntityProvisionDefaultsAdmin FspR7AdminState,
    flowEntityProvisionDefaultsAlias SnmpAdminString,
    flowEntityProvisionDefaultsPopCtagRcv Unsigned32,
    flowEntityProvisionDefaultsPopCtagTrmt Unsigned32,
    flowEntityProvisionDefaultsCvidRegisteredInFlow SnmpAdminString,
    flowEntityProvisionDefaultsExternalVid Unsigned32,
    flowEntityProvisionDefaultsPmMode FspR7L2PmMode,
    flowEntityProvisionDefaultsShape FspR7DisableEnable,
    flowEntityProvisionDefaultsPolice FspR7DisableEnable,
    flowEntityProvisionDefaultsDefaultEvcCos Integer32,
    flowEntityProvisionDefaultsCirRcv Unsigned32,
    flowEntityProvisionDefaultsCirTrmt Unsigned32,
    flowEntityProvisionDefaultsCbsRcv Unsigned32,
    flowEntityProvisionDefaultsCbsTrmt Unsigned32,
    flowEntityProvisionDefaultsPushPvidTrmt Unsigned32,
    flowEntityProvisionDefaultsPrioPvidTrmt Unsigned32,
    flowEntityProvisionDefaultsRedLineState FspR7RedLinedState,
    flowEntityProvisionDefaultsTunnelAid SnmpAdminString }

flowEntityProvisionDefaultsRowStatus OBJECT-TYPE
    SYNTAX      RowStatus
    MAX-ACCESS  read-only
    STATUS      current
    DESCRIPTION   "This object is used to create, or delete a row in this table."
    ::=  { flowEntityProvisionDefaultsEntry 1 }

flowEntityProvisionDefaultsType OBJECT-TYPE
    SYNTAX      FspR7InterfaceType
    MAX-ACCESS  read-only
    STATUS      current
    DESCRIPTION   ""
    ::=  { flowEntityProvisionDefaultsEntry 2 }

flowEntityProvisionDefaultsAdmin OBJECT-TYPE
    SYNTAX      FspR7AdminState
    MAX-ACCESS  read-only
    STATUS      current
    DESCRIPTION
        "The Adminstrative State will be displayed in the GUI with full
         name values; it will be differently displayed in TL1 syntax according
         to TL1 display rules. The transaction into the UAS state requires
         a special destroy/delete function." 
    ::=  { flowEntityProvisionDefaultsEntry 3 }

flowEntityProvisionDefaultsAlias OBJECT-TYPE
    SYNTAX      SnmpAdminString
    MAX-ACCESS  read-only
    STATUS      current
    DESCRIPTION
        "User Applied Descriptor" 
    ::=  { flowEntityProvisionDefaultsEntry 4 }

flowEntityProvisionDefaultsPopCtagRcv OBJECT-TYPE
    SYNTAX      Unsigned32 (0..4095 | 4294967295)
    MAX-ACCESS  read-only
    STATUS      current
    DESCRIPTION
        "'c-vid tag is removed in receive to an EVC. This is equivalent to untagged PEP in PB'" 
    ::=  { flowEntityProvisionDefaultsEntry 5 }

flowEntityProvisionDefaultsPopCtagTrmt OBJECT-TYPE
    SYNTAX      Unsigned32 (0..4095 | 4294967295)
    MAX-ACCESS  read-only
    STATUS      current
    DESCRIPTION
        "'c-vid tag is removed on transmit from EVC. This is equivalent to the untagged CEP in PB'" 
    ::=  { flowEntityProvisionDefaultsEntry 6 }

flowEntityProvisionDefaultsCvidRegisteredInFlow OBJECT-TYPE
    SYNTAX      SnmpAdminString
    MAX-ACCESS  read-only
    STATUS      current
    DESCRIPTION
        "CVLANs Registered with the Flow" 
    ::=  { flowEntityProvisionDefaultsEntry 7 }

flowEntityProvisionDefaultsExternalVid OBJECT-TYPE
    SYNTAX      Unsigned32 (1..4095 | 4294967295)
    MAX-ACCESS  read-only
    STATUS      current
    DESCRIPTION
        "External VID" 
    ::=  { flowEntityProvisionDefaultsEntry 8 }

flowEntityProvisionDefaultsPmMode OBJECT-TYPE
    SYNTAX      FspR7L2PmMode
    MAX-ACCESS  read-only
    STATUS      current
    DESCRIPTION
        "Mode of PM counters" 
    ::=  { flowEntityProvisionDefaultsEntry 9 }

flowEntityProvisionDefaultsShape OBJECT-TYPE
    SYNTAX      FspR7DisableEnable
    MAX-ACCESS  read-only
    STATUS      current
    DESCRIPTION
        "Shape Enablement" 
    ::=  { flowEntityProvisionDefaultsEntry 10 }

flowEntityProvisionDefaultsPolice OBJECT-TYPE
    SYNTAX      FspR7DisableEnable
    MAX-ACCESS  read-only
    STATUS      current
    DESCRIPTION
        "Police Enablement" 
    ::=  { flowEntityProvisionDefaultsEntry 11 }

flowEntityProvisionDefaultsDefaultEvcCos OBJECT-TYPE
    SYNTAX      Integer32 (7..7 | -2147483648)
    MAX-ACCESS  read-only
    STATUS      current
    DESCRIPTION
        "Default COS for frames not matching classification scheme PCP/DSCP, or used as CoS for EVC based classification." 
    ::=  { flowEntityProvisionDefaultsEntry 12 }

flowEntityProvisionDefaultsCirRcv OBJECT-TYPE
    SYNTAX      Unsigned32 
    UNITS       "Mbit/s"
    MAX-ACCESS  read-only
    STATUS      current
    DESCRIPTION
        "CIR (Committed Information Rate ) is used on Ethernet Interfaces with a policing function" 
    ::=  { flowEntityProvisionDefaultsEntry 13 }

flowEntityProvisionDefaultsCirTrmt OBJECT-TYPE
    SYNTAX      Unsigned32 
    UNITS       "Mbit/s"
    MAX-ACCESS  read-only
    STATUS      current
    DESCRIPTION
        "CIR (Committed Information Rate ) is used on Ethernet Interfaces with a policing function" 
    ::=  { flowEntityProvisionDefaultsEntry 14 }

flowEntityProvisionDefaultsCbsRcv OBJECT-TYPE
    SYNTAX      Unsigned32 (0..26214400 | 4294967295) 
    UNITS       "bytes"
    MAX-ACCESS  read-only
    STATUS      current
    DESCRIPTION
        "Committed Burst Size" 
    ::=  { flowEntityProvisionDefaultsEntry 15 }

flowEntityProvisionDefaultsCbsTrmt OBJECT-TYPE
    SYNTAX      Unsigned32 (0..25600 | 4294967295) 
    UNITS       "Kbytes"
    MAX-ACCESS  read-only
    STATUS      current
    DESCRIPTION
        "Committed Burst Size" 
    ::=  { flowEntityProvisionDefaultsEntry 16 }

flowEntityProvisionDefaultsPushPvidTrmt OBJECT-TYPE
    SYNTAX      Unsigned32 (0..4095 | 4294967295)
    MAX-ACCESS  read-only
    STATUS      current
    DESCRIPTION
        "C-VID tag is added on transmit from EVC. PEP." 
    ::=  { flowEntityProvisionDefaultsEntry 17 }

flowEntityProvisionDefaultsPrioPvidTrmt OBJECT-TYPE
    SYNTAX      Unsigned32 (0..7 | 4294967295)
    MAX-ACCESS  read-only
    STATUS      current
    DESCRIPTION
        "Added PRIO when CTAG is pushed on untagged frame. PEP." 
    ::=  { flowEntityProvisionDefaultsEntry 18 }

flowEntityProvisionDefaultsRedLineState OBJECT-TYPE
    SYNTAX      FspR7RedLinedState
    MAX-ACCESS  read-only
    STATUS      current
    DESCRIPTION
        "will be set by higher level software to act as a barrier to deletion" 
    ::=  { flowEntityProvisionDefaultsEntry 19 }

flowEntityProvisionDefaultsTunnelAid OBJECT-TYPE
    SYNTAX      SnmpAdminString
    MAX-ACCESS  read-only
    STATUS      current
    DESCRIPTION
        "Tunnel AID" 
    ::=  { flowEntityProvisionDefaultsEntry 20 }

flowEntityProvisionCbsRcvCapTable OBJECT-TYPE
    SYNTAX      SEQUENCE OF FlowEntityProvisionCbsRcvCapEntry
    MAX-ACCESS  not-accessible
    STATUS      current
    DESCRIPTION   "This table is used to get capabilities for CBS-RCV parameter. Regular
         cap tables including CBS-RCV show the number of capabilities for a specific entity.
         Value 0 in regular cap tables means 'no capabilities'.
         Each capability for a specific entity has a separate third index."
    ::=  { flowProvisioning 14 }

flowEntityProvisionCbsRcvCapEntry OBJECT-TYPE
    SYNTAX      FlowEntityProvisionCbsRcvCapEntry
    MAX-ACCESS  not-accessible
    STATUS      current
    DESCRIPTION   ""
    INDEX       {
                  flowEntityIndexEth,
                  flowEntityIndexFlow,
                  flowEntityProvisionCbsRcvCapIndexCap
                }
    ::=  { flowEntityProvisionCbsRcvCapTable 1 }

FlowEntityProvisionCbsRcvCapEntry ::=  SEQUENCE
  { flowEntityProvisionCbsRcvCapIndexCap EntityIndex,
    flowEntityProvisionCbsRcvCapCbsRcv Unsigned32 }

flowEntityProvisionCbsRcvCapIndexCap OBJECT-TYPE
    SYNTAX      EntityIndex
    MAX-ACCESS  accessible-for-notify
    STATUS      current
    DESCRIPTION   "Used to display capability value per index. The number of capabilities determines the number of indexes."
    ::=  { flowEntityProvisionCbsRcvCapEntry 1 }

flowEntityProvisionCbsRcvCapCbsRcv OBJECT-TYPE
    SYNTAX      Unsigned32
    UNITS       "bytes"
    MAX-ACCESS  read-only
    STATUS      current
    DESCRIPTION
        "Committed Burst Size" 
    ::=  { flowEntityProvisionCbsRcvCapEntry 2 }

flowEntityProvisionRegisterCapTable OBJECT-TYPE
    SYNTAX      SEQUENCE OF FlowEntityProvisionRegisterCapEntry
    MAX-ACCESS  not-accessible
    STATUS      current
    DESCRIPTION   "This table is used to get capabilities for REGISTER parameter. Regular
         cap tables including REGISTER show the length of output string.
         Value 0 in regular cap tables means 'no capabilities'.
         The third index (n) is used to devide the output string to n string blocks.
         Each block has a maximum of 512 bytes. n = output string / 512."
    ::=  { flowProvisioning 15 }

flowEntityProvisionRegisterCapEntry OBJECT-TYPE
    SYNTAX      FlowEntityProvisionRegisterCapEntry
    MAX-ACCESS  not-accessible
    STATUS      current
    DESCRIPTION   ""
    INDEX       {
                  flowEntityIndexEth,
                  flowEntityIndexFlow,
                  flowEntityProvisionRegisterCapIndexCap
                }
    ::=  { flowEntityProvisionRegisterCapTable 1 }

FlowEntityProvisionRegisterCapEntry ::=  SEQUENCE
  { flowEntityProvisionRegisterCapIndexCap EntityIndex,
    flowEntityProvisionRegisterCapStringCap SnmpAdminString }

flowEntityProvisionRegisterCapIndexCap OBJECT-TYPE
    SYNTAX      EntityIndex
    MAX-ACCESS  accessible-for-notify
    STATUS      current
    DESCRIPTION   "Used to display capability value per index. The number of capabilities determines the number of indexes."
    ::=  { flowEntityProvisionRegisterCapEntry 1 }

flowEntityProvisionRegisterCapStringCap OBJECT-TYPE
    SYNTAX      SnmpAdminString
    MAX-ACCESS  read-only
    STATUS      current
    DESCRIPTION
        "" 
    ::=  { flowEntityProvisionRegisterCapEntry 2 }

flowEntityProvisionExternalVidCapTable OBJECT-TYPE
    SYNTAX      SEQUENCE OF FlowEntityProvisionExternalVidCapEntry
    MAX-ACCESS  not-accessible
    STATUS      current
    DESCRIPTION   "This table is used to get capabilities for EXTVID parameter. Regular
         cap tables including EXTVID show the length of output string.
         Value 0 in regular cap tables means 'no capabilities'.
         The third index (n) is used to devide the output string to n string blocks.
         Each block has a maximum of 512 bytes. n = output string / 512."
    ::=  { flowProvisioning 16 }

flowEntityProvisionExternalVidCapEntry OBJECT-TYPE
    SYNTAX      FlowEntityProvisionExternalVidCapEntry
    MAX-ACCESS  not-accessible
    STATUS      current
    DESCRIPTION   ""
    INDEX       {
                  flowEntityIndexEth,
                  flowEntityIndexFlow,
                  flowEntityProvisionExternalVidCapIndexCap
                }
    ::=  { flowEntityProvisionExternalVidCapTable 1 }

FlowEntityProvisionExternalVidCapEntry ::=  SEQUENCE
  { flowEntityProvisionExternalVidCapIndexCap EntityIndex,
    flowEntityProvisionExternalVidCapStringCap SnmpAdminString }

flowEntityProvisionExternalVidCapIndexCap OBJECT-TYPE
    SYNTAX      EntityIndex
    MAX-ACCESS  accessible-for-notify
    STATUS      current
    DESCRIPTION   "Used to display capability value per index. The number of capabilities determines the number of indexes."
    ::=  { flowEntityProvisionExternalVidCapEntry 1 }

flowEntityProvisionExternalVidCapStringCap OBJECT-TYPE
    SYNTAX      SnmpAdminString
    MAX-ACCESS  read-only
    STATUS      current
    DESCRIPTION
        "" 
    ::=  { flowEntityProvisionExternalVidCapEntry 2 }

flowEntityProvisionPopCtagRcvCapTable OBJECT-TYPE
    SYNTAX      SEQUENCE OF FlowEntityProvisionPopCtagRcvCapEntry
    MAX-ACCESS  not-accessible
    STATUS      current
    DESCRIPTION   "This table is used to get capabilities for POP_RCV parameter. Regular
         cap tables including POP_RCV show the length of output string.
         Value 0 in regular cap tables means 'no capabilities'.
         The third index (n) is used to devide the output string to n string blocks.
         Each block has a maximum of 512 bytes. n = output string / 512."
    ::=  { flowProvisioning 17 }

flowEntityProvisionPopCtagRcvCapEntry OBJECT-TYPE
    SYNTAX      FlowEntityProvisionPopCtagRcvCapEntry
    MAX-ACCESS  not-accessible
    STATUS      current
    DESCRIPTION   ""
    INDEX       {
                  flowEntityIndexEth,
                  flowEntityIndexFlow,
                  flowEntityProvisionPopCtagRcvCapIndexCap
                }
    ::=  { flowEntityProvisionPopCtagRcvCapTable 1 }

FlowEntityProvisionPopCtagRcvCapEntry ::=  SEQUENCE
  { flowEntityProvisionPopCtagRcvCapIndexCap EntityIndex,
    flowEntityProvisionPopCtagRcvCapStringCap SnmpAdminString }

flowEntityProvisionPopCtagRcvCapIndexCap OBJECT-TYPE
    SYNTAX      EntityIndex
    MAX-ACCESS  accessible-for-notify
    STATUS      current
    DESCRIPTION   "Used to display capability value per index. The number of capabilities determines the number of indexes."
    ::=  { flowEntityProvisionPopCtagRcvCapEntry 1 }

flowEntityProvisionPopCtagRcvCapStringCap OBJECT-TYPE
    SYNTAX      SnmpAdminString
    MAX-ACCESS  read-only
    STATUS      current
    DESCRIPTION
        "" 
    ::=  { flowEntityProvisionPopCtagRcvCapEntry 2 }

flowEntityProvisionPopCtagTrmtCapTable OBJECT-TYPE
    SYNTAX      SEQUENCE OF FlowEntityProvisionPopCtagTrmtCapEntry
    MAX-ACCESS  not-accessible
    STATUS      current
    DESCRIPTION   "This table is used to get capabilities for POP_TRMT parameter. Regular
         cap tables including POP_TRMT show the length of output string.
         Value 0 in regular cap tables means 'no capabilities'.
         The third index (n) is used to devide the output string to n string blocks.
         Each block has a maximum of 512 bytes. n = output string / 512."
    ::=  { flowProvisioning 18 }

flowEntityProvisionPopCtagTrmtCapEntry OBJECT-TYPE
    SYNTAX      FlowEntityProvisionPopCtagTrmtCapEntry
    MAX-ACCESS  not-accessible
    STATUS      current
    DESCRIPTION   ""
    INDEX       {
                  flowEntityIndexEth,
                  flowEntityIndexFlow,
                  flowEntityProvisionPopCtagTrmtCapIndexCap
                }
    ::=  { flowEntityProvisionPopCtagTrmtCapTable 1 }

FlowEntityProvisionPopCtagTrmtCapEntry ::=  SEQUENCE
  { flowEntityProvisionPopCtagTrmtCapIndexCap EntityIndex,
    flowEntityProvisionPopCtagTrmtCapStringCap SnmpAdminString }

flowEntityProvisionPopCtagTrmtCapIndexCap OBJECT-TYPE
    SYNTAX      EntityIndex
    MAX-ACCESS  accessible-for-notify
    STATUS      current
    DESCRIPTION   "Used to display capability value per index. The number of capabilities determines the number of indexes."
    ::=  { flowEntityProvisionPopCtagTrmtCapEntry 1 }

flowEntityProvisionPopCtagTrmtCapStringCap OBJECT-TYPE
    SYNTAX      SnmpAdminString
    MAX-ACCESS  read-only
    STATUS      current
    DESCRIPTION
        "" 
    ::=  { flowEntityProvisionPopCtagTrmtCapEntry 2 }

flowEntityProvisionPushTrmtCapTable OBJECT-TYPE
    SYNTAX      SEQUENCE OF FlowEntityProvisionPushTrmtCapEntry
    MAX-ACCESS  not-accessible
    STATUS      current
    DESCRIPTION   "This table is used to get capabilities for PUSH-TRMT parameter. Regular
         cap tables including PUSH-TRMT show the length of output string.
         Value 0 in regular cap tables means 'no capabilities'.
         The third index (n) is used to devide the output string to n string blocks.
         Each block has a maximum of 512 bytes. n = output string / 512."
    ::=  { flowProvisioning 19 }

flowEntityProvisionPushTrmtCapEntry OBJECT-TYPE
    SYNTAX      FlowEntityProvisionPushTrmtCapEntry
    MAX-ACCESS  not-accessible
    STATUS      current
    DESCRIPTION   ""
    INDEX       {
                  flowEntityIndexEth,
                  flowEntityIndexFlow,
                  flowEntityProvisionPushTrmtCapIndexCap
                }
    ::=  { flowEntityProvisionPushTrmtCapTable 1 }

FlowEntityProvisionPushTrmtCapEntry ::=  SEQUENCE
  { flowEntityProvisionPushTrmtCapIndexCap EntityIndex,
    flowEntityProvisionPushTrmtCapStringCap SnmpAdminString }

flowEntityProvisionPushTrmtCapIndexCap OBJECT-TYPE
    SYNTAX      EntityIndex
    MAX-ACCESS  accessible-for-notify
    STATUS      current
    DESCRIPTION   "Used to display capability value per index. The number of capabilities determines the number of indexes."
    ::=  { flowEntityProvisionPushTrmtCapEntry 1 }

flowEntityProvisionPushTrmtCapStringCap OBJECT-TYPE
    SYNTAX      SnmpAdminString
    MAX-ACCESS  read-only
    STATUS      current
    DESCRIPTION
        "" 
    ::=  { flowEntityProvisionPushTrmtCapEntry 2 }

ctransEntityProvisionTable OBJECT-TYPE
    SYNTAX      SEQUENCE OF CtransEntityProvisionEntry
    MAX-ACCESS  not-accessible
    STATUS      current
    DESCRIPTION   ""
    ::=  { ctransProvisioning 11 }

ctransEntityProvisionEntry OBJECT-TYPE
    SYNTAX      CtransEntityProvisionEntry
    MAX-ACCESS  not-accessible
    STATUS      current
    DESCRIPTION   ""
    INDEX       {
                  ctransEntityIndexEth,
                  ctransEntityIndexCVlanId
                }
    ::=  { ctransEntityProvisionTable 1 }

CtransEntityProvisionEntry ::=  SEQUENCE
  { ctransEntityProvisionRowStatus RowStatus,
    ctransEntityProvisionType FspR7InterfaceType,
    ctransEntityProvisionCvidInternal Unsigned32,
    ctransEntityProvisionRange Unsigned32 }

ctransEntityProvisionRowStatus OBJECT-TYPE
    SYNTAX      RowStatus
    MAX-ACCESS  read-write
    STATUS      current
    DESCRIPTION   "This object is used to create, or delete a row in this table."
    ::=  { ctransEntityProvisionEntry 1 }

ctransEntityProvisionType OBJECT-TYPE
    SYNTAX      FspR7InterfaceType
    MAX-ACCESS  read-write
    STATUS      current
    DESCRIPTION   ""
    ::=  { ctransEntityProvisionEntry 2 }

ctransEntityProvisionCvidInternal OBJECT-TYPE
    SYNTAX      Unsigned32 (1..4095 | 4294967295)
    MAX-ACCESS  read-write
    STATUS      current
    DESCRIPTION
        "Internal CVID" 
    ::=  { ctransEntityProvisionEntry 3 }

ctransEntityProvisionRange OBJECT-TYPE
    SYNTAX      Unsigned32 (1..4095 | 4294967295)
    MAX-ACCESS  read-write
    STATUS      current
    DESCRIPTION
        "Range of the translated CVID." 
    ::=  { ctransEntityProvisionEntry 4 }

ctransEntityProvisionCapTable OBJECT-TYPE
    SYNTAX      SEQUENCE OF CtransEntityProvisionCapEntry
    MAX-ACCESS  not-accessible
    STATUS      current
    DESCRIPTION   ""
    ::=  { ctransProvisioning 12  }

ctransEntityProvisionCapEntry OBJECT-TYPE
    SYNTAX      CtransEntityProvisionCapEntry
    MAX-ACCESS  not-accessible
    STATUS      current
    DESCRIPTION   ""
    INDEX       { ctransEntityIndexEth,
                  ctransEntityIndexCVlanId }
    ::=  { ctransEntityProvisionCapTable 1 }

CtransEntityProvisionCapEntry ::=  SEQUENCE
  { ctransEntityProvisionCapRowStatus FspR7RowStatusCaps,
    ctransEntityProvisionCapType FspR7InterfaceTypeCaps,
    ctransEntityProvisionCapCvidInternal Unsigned32,
    ctransEntityProvisionCapRange FspR7Unsigned32Caps }

ctransEntityProvisionCapRowStatus OBJECT-TYPE
    SYNTAX      FspR7RowStatusCaps
    MAX-ACCESS  read-only
    STATUS      current
    DESCRIPTION   "This object is used to create, or delete a row in this table."
    ::=  { ctransEntityProvisionCapEntry 1 }

ctransEntityProvisionCapType OBJECT-TYPE
    SYNTAX      FspR7InterfaceTypeCaps
    MAX-ACCESS  read-only
    STATUS      current
    DESCRIPTION   ""
    ::=  { ctransEntityProvisionCapEntry 2 }

ctransEntityProvisionCapCvidInternal OBJECT-TYPE
    SYNTAX      Unsigned32
    MAX-ACCESS  read-only
    STATUS      current
    DESCRIPTION
        "Internal CVID" 
    ::=  { ctransEntityProvisionCapEntry 3 }

ctransEntityProvisionCapRange OBJECT-TYPE
    SYNTAX      FspR7Unsigned32Caps
    MAX-ACCESS  read-only
    STATUS      current
    DESCRIPTION
        "Range of the translated CVID." 
    ::=  { ctransEntityProvisionCapEntry 4 }

ctransEntityProvisionDefaultsTable  OBJECT-TYPE
    SYNTAX      SEQUENCE OF CtransEntityProvisionDefaultsEntry
    MAX-ACCESS  not-accessible
    STATUS      current
    DESCRIPTION   ""
    ::=  { ctransProvisioning 13  }

ctransEntityProvisionDefaultsEntry OBJECT-TYPE
    SYNTAX      CtransEntityProvisionDefaultsEntry
    MAX-ACCESS  not-accessible
    STATUS      current
    DESCRIPTION   ""
    INDEX       { ctransEntityIndexEth,
                  ctransEntityIndexCVlanId }
    ::=  { ctransEntityProvisionDefaultsTable 1 }

CtransEntityProvisionDefaultsEntry ::=  SEQUENCE
  { ctransEntityProvisionDefaultsRowStatus RowStatus,
    ctransEntityProvisionDefaultsType FspR7InterfaceType,
    ctransEntityProvisionDefaultsCvidInternal Unsigned32,
    ctransEntityProvisionDefaultsRange Unsigned32 }

ctransEntityProvisionDefaultsRowStatus OBJECT-TYPE
    SYNTAX      RowStatus
    MAX-ACCESS  read-only
    STATUS      current
    DESCRIPTION   "This object is used to create, or delete a row in this table."
    ::=  { ctransEntityProvisionDefaultsEntry 1 }

ctransEntityProvisionDefaultsType OBJECT-TYPE
    SYNTAX      FspR7InterfaceType
    MAX-ACCESS  read-only
    STATUS      current
    DESCRIPTION   ""
    ::=  { ctransEntityProvisionDefaultsEntry 2 }

ctransEntityProvisionDefaultsCvidInternal OBJECT-TYPE
    SYNTAX      Unsigned32 (1..4095 | 4294967295)
    MAX-ACCESS  read-only
    STATUS      current
    DESCRIPTION
        "Internal CVID" 
    ::=  { ctransEntityProvisionDefaultsEntry 3 }

ctransEntityProvisionDefaultsRange OBJECT-TYPE
    SYNTAX      Unsigned32 (1..4095 | 4294967295)
    MAX-ACCESS  read-only
    STATUS      current
    DESCRIPTION
        "Range of the translated CVID." 
    ::=  { ctransEntityProvisionDefaultsEntry 4 }

ctransEntityProvisionCvidInternalCapTable OBJECT-TYPE
    SYNTAX      SEQUENCE OF CtransEntityProvisionCvidInternalCapEntry
    MAX-ACCESS  not-accessible
    STATUS      current
    DESCRIPTION   "This table is used to get capabilities for INT_CVID parameter. Regular
         cap tables including INT_CVID show the length of output string.
         Value 0 in regular cap tables means 'no capabilities'.
         The third index (n) is used to devide the output string to n string blocks.
         Each block has a maximum of 512 bytes. n = output string / 512."
    ::=  { ctransProvisioning 14 }

ctransEntityProvisionCvidInternalCapEntry OBJECT-TYPE
    SYNTAX      CtransEntityProvisionCvidInternalCapEntry
    MAX-ACCESS  not-accessible
    STATUS      current
    DESCRIPTION   ""
    INDEX       {
                  ctransEntityIndexEth,
                  ctransEntityIndexCVlanId,
                  ctransEntityProvisionCvidInternalCapIndexCap
                }
    ::=  { ctransEntityProvisionCvidInternalCapTable 1 }

CtransEntityProvisionCvidInternalCapEntry ::=  SEQUENCE
  { ctransEntityProvisionCvidInternalCapIndexCap EntityIndex,
    ctransEntityProvisionCvidInternalCapStringCap SnmpAdminString }

ctransEntityProvisionCvidInternalCapIndexCap OBJECT-TYPE
    SYNTAX      EntityIndex
    MAX-ACCESS  accessible-for-notify
    STATUS      current
    DESCRIPTION   "Used to display capability value per index. The number of capabilities determines the number of indexes."
    ::=  { ctransEntityProvisionCvidInternalCapEntry 1 }

ctransEntityProvisionCvidInternalCapStringCap OBJECT-TYPE
    SYNTAX      SnmpAdminString
    MAX-ACCESS  read-only
    STATUS      current
    DESCRIPTION
        "" 
    ::=  { ctransEntityProvisionCvidInternalCapEntry 2 }

bridgeToAssignEntityTable OBJECT-TYPE
    SYNTAX      SEQUENCE OF BridgeToAssignEntityEntry
    MAX-ACCESS  not-accessible
    STATUS      current
    DESCRIPTION   "This table lists first unusued BRIDGE entity per MODULE."
    ::=  { bridgeProvisioning 11 }

bridgeToAssignEntityEntry OBJECT-TYPE
    SYNTAX      BridgeToAssignEntityEntry
    MAX-ACCESS  not-accessible
    STATUS      current
    DESCRIPTION   "Table entry represents unused BRIDGE placeholder which may be assigned."
    INDEX       {
                  bridgeEntityContainedIn,
                  bridgeEntitySvid
                }
    ::=  { bridgeToAssignEntityTable 1 }

BridgeToAssignEntityEntry ::=  SEQUENCE
  { bridgeToAssignEntityIndexAid SnmpAdminString }

bridgeToAssignEntityIndexAid OBJECT-TYPE
    SYNTAX      SnmpAdminString
    MAX-ACCESS  read-only
    STATUS      current
    DESCRIPTION   "Printable entity name."
    ::=  { bridgeToAssignEntityEntry 1 }

bridgeEntityProvisionTable OBJECT-TYPE
    SYNTAX      SEQUENCE OF BridgeEntityProvisionEntry
    MAX-ACCESS  not-accessible
    STATUS      current
    DESCRIPTION   "This table is used for creating or destroying BRIDGE entities."
    ::=  { bridgeProvisioning 12 }

bridgeEntityProvisionEntry OBJECT-TYPE
    SYNTAX      BridgeEntityProvisionEntry
    MAX-ACCESS  not-accessible
    STATUS      current
    DESCRIPTION   "Entry represents an assigned or unassigned but initiated for creation BRIDGE entity."
    INDEX       {
                  bridgeEntityContainedIn,
                  bridgeEntitySvid
                }
    ::=  { bridgeEntityProvisionTable 1 }

BridgeEntityProvisionEntry ::=  SEQUENCE
  { bridgeEntityProvisionRowStatus RowStatus,
    bridgeEntityProvisionFacilityType FspR7InterfaceType,
    bridgeEntityProvisionAlias SnmpAdminString,
    bridgeEntityProvisionShapeState FspR7DisableEnable,
    bridgeEntityProvisionPmMode FspR7L2PmMode,
    bridgeEntityProvisionCirTrmt Unsigned32,
    bridgeEntityProvisionCbsTrmt Unsigned32,
    bridgeEntityProvisionAdminState FspR7AdminState }

bridgeEntityProvisionRowStatus OBJECT-TYPE
    SYNTAX      RowStatus
    MAX-ACCESS  read-create
    STATUS      current
    DESCRIPTION   "This object is used to create or delete a row in this table."
    ::=  { bridgeEntityProvisionEntry 1 }

bridgeEntityProvisionFacilityType OBJECT-TYPE
    SYNTAX      FspR7InterfaceType
    MAX-ACCESS  read-create
    STATUS      current
    DESCRIPTION   ""
    ::=  { bridgeEntityProvisionEntry 2 }

bridgeEntityProvisionAlias OBJECT-TYPE
    SYNTAX      SnmpAdminString
    MAX-ACCESS  read-create
    STATUS      current
    DESCRIPTION
        "User Applied Descriptor" 
    ::=  { bridgeEntityProvisionEntry 3 }

bridgeEntityProvisionShapeState OBJECT-TYPE
    SYNTAX      FspR7DisableEnable
    MAX-ACCESS  read-create
    STATUS      current
    DESCRIPTION
        "E-LAN Shape Enablement" 
    ::=  { bridgeEntityProvisionEntry 4 }

bridgeEntityProvisionPmMode OBJECT-TYPE
    SYNTAX      FspR7L2PmMode
    MAX-ACCESS  read-create
    STATUS      current
    DESCRIPTION
        "Mode of PM counters" 
    ::=  { bridgeEntityProvisionEntry 5 }

bridgeEntityProvisionCirTrmt OBJECT-TYPE
    SYNTAX      Unsigned32 
    UNITS       "Mbit/s"
    MAX-ACCESS  read-create
    STATUS      current
    DESCRIPTION
        "CIR (Committed Information Rate ) is used on Ethernet Interfaces with a policing function" 
    ::=  { bridgeEntityProvisionEntry 6 }

bridgeEntityProvisionCbsTrmt OBJECT-TYPE
    SYNTAX      Unsigned32 (0..25600 | 4294967295) 
    UNITS       "Kbytes"
    MAX-ACCESS  read-create
    STATUS      current
    DESCRIPTION
        "Committed Burst Size" 
    ::=  { bridgeEntityProvisionEntry 7 }

bridgeEntityProvisionAdminState OBJECT-TYPE
    SYNTAX      FspR7AdminState
    MAX-ACCESS  read-create
    STATUS      current
    DESCRIPTION
        "The Adminstrative State will be displayed in the GUI with full
         name values; it will be differently displayed in TL1 syntax according
         to TL1 display rules. The transaction into the UAS state requires
         a special destroy/delete function." 
    ::=  { bridgeEntityProvisionEntry 8 }

bridgeEntityProvisionCapTable OBJECT-TYPE
    SYNTAX      SEQUENCE OF BridgeEntityProvisionCapEntry
    MAX-ACCESS  not-accessible
    STATUS      current
    DESCRIPTION   "This table is used for creating or destroying BRIDGE entities."
    ::=  { bridgeProvisioning 13  }

bridgeEntityProvisionCapEntry OBJECT-TYPE
    SYNTAX      BridgeEntityProvisionCapEntry
    MAX-ACCESS  not-accessible
    STATUS      current
    DESCRIPTION   "Entry represents an assigned or unassigned but initiated for creation BRIDGE entity."
    INDEX       { bridgeEntityContainedIn,
                  bridgeEntitySvid }
    ::=  { bridgeEntityProvisionCapTable 1 }

BridgeEntityProvisionCapEntry ::=  SEQUENCE
  { bridgeEntityProvisionCapRowStatus FspR7RowStatusCaps,
    bridgeEntityProvisionCapFacilityType FspR7InterfaceTypeCaps,
    bridgeEntityProvisionCapAlias Integer32,
    bridgeEntityProvisionCapShapeState FspR7DisableEnableCaps,
    bridgeEntityProvisionCapPmMode FspR7L2PmModeCaps,
    bridgeEntityProvisionCapCirTrmt FspR7Unsigned32Caps,
    bridgeEntityProvisionCapCbsTrmt FspR7Unsigned32Caps,
    bridgeEntityProvisionCapAdminState FspR7AdminStateCaps }

bridgeEntityProvisionCapRowStatus OBJECT-TYPE
    SYNTAX      FspR7RowStatusCaps
    MAX-ACCESS  read-only
    STATUS      current
    DESCRIPTION   "This object is used to create or delete a row in this table."
    ::=  { bridgeEntityProvisionCapEntry 1 }

bridgeEntityProvisionCapFacilityType OBJECT-TYPE
    SYNTAX      FspR7InterfaceTypeCaps
    MAX-ACCESS  read-only
    STATUS      current
    DESCRIPTION   ""
    ::=  { bridgeEntityProvisionCapEntry 2 }

bridgeEntityProvisionCapAlias OBJECT-TYPE
    SYNTAX      Integer32
    MAX-ACCESS  read-only
    STATUS      current
    DESCRIPTION
        "User Applied Descriptor" 
    ::=  { bridgeEntityProvisionCapEntry 3 }

bridgeEntityProvisionCapShapeState OBJECT-TYPE
    SYNTAX      FspR7DisableEnableCaps
    MAX-ACCESS  read-only
    STATUS      current
    DESCRIPTION
        "E-LAN Shape Enablement" 
    ::=  { bridgeEntityProvisionCapEntry 4 }

bridgeEntityProvisionCapPmMode OBJECT-TYPE
    SYNTAX      FspR7L2PmModeCaps
    MAX-ACCESS  read-only
    STATUS      current
    DESCRIPTION
        "Mode of PM counters" 
    ::=  { bridgeEntityProvisionCapEntry 5 }

bridgeEntityProvisionCapCirTrmt OBJECT-TYPE
    SYNTAX      FspR7Unsigned32Caps
    UNITS       "Mbit/s"
    MAX-ACCESS  read-only
    STATUS      current
    DESCRIPTION
        "CIR (Committed Information Rate ) is used on Ethernet Interfaces with a policing function" 
    ::=  { bridgeEntityProvisionCapEntry 6 }

bridgeEntityProvisionCapCbsTrmt OBJECT-TYPE
    SYNTAX      FspR7Unsigned32Caps
    UNITS       "Kbytes"
    MAX-ACCESS  read-only
    STATUS      current
    DESCRIPTION
        "Committed Burst Size" 
    ::=  { bridgeEntityProvisionCapEntry 7 }

bridgeEntityProvisionCapAdminState OBJECT-TYPE
    SYNTAX      FspR7AdminStateCaps
    MAX-ACCESS  read-only
    STATUS      current
    DESCRIPTION
        "The Adminstrative State will be displayed in the GUI with full
         name values; it will be differently displayed in TL1 syntax according
         to TL1 display rules. The transaction into the UAS state requires
         a special destroy/delete function." 
    ::=  { bridgeEntityProvisionCapEntry 8 }

bridgeEntityProvisionDefaultsTable  OBJECT-TYPE
    SYNTAX      SEQUENCE OF BridgeEntityProvisionDefaultsEntry
    MAX-ACCESS  not-accessible
    STATUS      current
    DESCRIPTION   "This table is used for creating or destroying BRIDGE entities."
    ::=  { bridgeProvisioning 14  }

bridgeEntityProvisionDefaultsEntry OBJECT-TYPE
    SYNTAX      BridgeEntityProvisionDefaultsEntry
    MAX-ACCESS  not-accessible
    STATUS      current
    DESCRIPTION   "Entry represents an assigned or unassigned but initiated for creation BRIDGE entity."
    INDEX       { bridgeEntityContainedIn,
                  bridgeEntitySvid }
    ::=  { bridgeEntityProvisionDefaultsTable 1 }

BridgeEntityProvisionDefaultsEntry ::=  SEQUENCE
  { bridgeEntityProvisionDefaultsRowStatus RowStatus,
    bridgeEntityProvisionDefaultsFacilityType FspR7InterfaceType,
    bridgeEntityProvisionDefaultsAlias SnmpAdminString,
    bridgeEntityProvisionDefaultsShapeState FspR7DisableEnable,
    bridgeEntityProvisionDefaultsPmMode FspR7L2PmMode,
    bridgeEntityProvisionDefaultsCirTrmt Unsigned32,
    bridgeEntityProvisionDefaultsCbsTrmt Unsigned32,
    bridgeEntityProvisionDefaultsAdminState FspR7AdminState }

bridgeEntityProvisionDefaultsRowStatus OBJECT-TYPE
    SYNTAX      RowStatus
    MAX-ACCESS  read-only
    STATUS      current
    DESCRIPTION   "This object is used to create or delete a row in this table."
    ::=  { bridgeEntityProvisionDefaultsEntry 1 }

bridgeEntityProvisionDefaultsFacilityType OBJECT-TYPE
    SYNTAX      FspR7InterfaceType
    MAX-ACCESS  read-only
    STATUS      current
    DESCRIPTION   ""
    ::=  { bridgeEntityProvisionDefaultsEntry 2 }

bridgeEntityProvisionDefaultsAlias OBJECT-TYPE
    SYNTAX      SnmpAdminString
    MAX-ACCESS  read-only
    STATUS      current
    DESCRIPTION
        "User Applied Descriptor" 
    ::=  { bridgeEntityProvisionDefaultsEntry 3 }

bridgeEntityProvisionDefaultsShapeState OBJECT-TYPE
    SYNTAX      FspR7DisableEnable
    MAX-ACCESS  read-only
    STATUS      current
    DESCRIPTION
        "E-LAN Shape Enablement" 
    ::=  { bridgeEntityProvisionDefaultsEntry 4 }

bridgeEntityProvisionDefaultsPmMode OBJECT-TYPE
    SYNTAX      FspR7L2PmMode
    MAX-ACCESS  read-only
    STATUS      current
    DESCRIPTION
        "Mode of PM counters" 
    ::=  { bridgeEntityProvisionDefaultsEntry 5 }

bridgeEntityProvisionDefaultsCirTrmt OBJECT-TYPE
    SYNTAX      Unsigned32 
    UNITS       "Mbit/s"
    MAX-ACCESS  read-only
    STATUS      current
    DESCRIPTION
        "CIR (Committed Information Rate ) is used on Ethernet Interfaces with a policing function" 
    ::=  { bridgeEntityProvisionDefaultsEntry 6 }

bridgeEntityProvisionDefaultsCbsTrmt OBJECT-TYPE
    SYNTAX      Unsigned32 (0..25600 | 4294967295) 
    UNITS       "Kbytes"
    MAX-ACCESS  read-only
    STATUS      current
    DESCRIPTION
        "Committed Burst Size" 
    ::=  { bridgeEntityProvisionDefaultsEntry 7 }

bridgeEntityProvisionDefaultsAdminState OBJECT-TYPE
    SYNTAX      FspR7AdminState
    MAX-ACCESS  read-only
    STATUS      current
    DESCRIPTION
        "The Adminstrative State will be displayed in the GUI with full
         name values; it will be differently displayed in TL1 syntax according
         to TL1 display rules. The transaction into the UAS state requires
         a special destroy/delete function." 
    ::=  { bridgeEntityProvisionDefaultsEntry 8 }

flowEntityConfigTable OBJECT-TYPE
    SYNTAX      SEQUENCE OF FlowEntityConfigEntry
    MAX-ACCESS  not-accessible
    STATUS      current
    DESCRIPTION   ""
    ::=  { flowConfiguration 11 }

flowEntityConfigEntry OBJECT-TYPE
    SYNTAX      FlowEntityConfigEntry
    MAX-ACCESS  not-accessible
    STATUS      current
    DESCRIPTION   ""
    INDEX       {
                  flowEntityIndexEth,
                  flowEntityIndexFlow
                }
    ::=  { flowEntityConfigTable 1 }

FlowEntityConfigEntry ::=  SEQUENCE
  { flowEntityConfigAdmin FspR7AdminState,
    flowEntityConfigAlias SnmpAdminString,
    flowEntityConfigPopCtagRcv Unsigned32,
    flowEntityConfigPopCtagTrmt Unsigned32,
    flowEntityConfigCvidRegisteredInFlow SnmpAdminString,
    flowEntityConfigExternalVid Unsigned32,
    flowEntityConfigPmMode FspR7L2PmMode,
    flowEntityConfigShape FspR7DisableEnable,
    flowEntityConfigPolice FspR7DisableEnable,
    flowEntityConfigDefaultEvcCos Integer32,
    flowEntityConfigCirRcv Unsigned32,
    flowEntityConfigCirTrmt Unsigned32,
    flowEntityConfigCbsRcv Unsigned32,
    flowEntityConfigCbsTrmt Unsigned32,
    flowEntityConfigDataLayerPmReset FspR7PmReset,
    flowEntityConfigPushPvidTrmt Unsigned32,
    flowEntityConfigPrioPvidTrmt Unsigned32,
    flowEntityConfigRedLineState FspR7RedLinedState,
    flowEntityConfigTunnelAid SnmpAdminString,
    flowEntityConfigSwitchCommand FspR7APSCommand,
    flowEntityConfigInhibitSwitchToProt FspR7YesNo,
    flowEntityConfigInhibitSwitchToWork FspR7YesNo }

flowEntityConfigAdmin OBJECT-TYPE
    SYNTAX      FspR7AdminState
    MAX-ACCESS  read-write
    STATUS      current
    DESCRIPTION
        "The Adminstrative State will be displayed in the GUI with full
         name values; it will be differently displayed in TL1 syntax according
         to TL1 display rules. The transaction into the UAS state requires
         a special destroy/delete function." 
    ::=  { flowEntityConfigEntry 1 }

flowEntityConfigAlias OBJECT-TYPE
    SYNTAX      SnmpAdminString
    MAX-ACCESS  read-write
    STATUS      current
    DESCRIPTION
        "User Applied Descriptor" 
    ::=  { flowEntityConfigEntry 2 }

flowEntityConfigPopCtagRcv OBJECT-TYPE
    SYNTAX      Unsigned32 (0..4095 | 4294967295)
    MAX-ACCESS  read-write
    STATUS      current
    DESCRIPTION
        "'c-vid tag is removed in receive to an EVC. This is equivalent to untagged PEP in PB'" 
    ::=  { flowEntityConfigEntry 3 }

flowEntityConfigPopCtagTrmt OBJECT-TYPE
    SYNTAX      Unsigned32 (0..4095 | 4294967295)
    MAX-ACCESS  read-write
    STATUS      current
    DESCRIPTION
        "'c-vid tag is removed on transmit from EVC. This is equivalent to the untagged CEP in PB'" 
    ::=  { flowEntityConfigEntry 4 }

flowEntityConfigCvidRegisteredInFlow OBJECT-TYPE
    SYNTAX      SnmpAdminString
    MAX-ACCESS  read-write
    STATUS      current
    DESCRIPTION
        "CVLANs Registered with the Flow" 
    ::=  { flowEntityConfigEntry 5 }

flowEntityConfigExternalVid OBJECT-TYPE
    SYNTAX      Unsigned32 (1..4095 | 4294967295)
    MAX-ACCESS  read-write
    STATUS      current
    DESCRIPTION
        "External VID" 
    ::=  { flowEntityConfigEntry 6 }

flowEntityConfigPmMode OBJECT-TYPE
    SYNTAX      FspR7L2PmMode
    MAX-ACCESS  read-write
    STATUS      current
    DESCRIPTION
        "Mode of PM counters" 
    ::=  { flowEntityConfigEntry 7 }

flowEntityConfigShape OBJECT-TYPE
    SYNTAX      FspR7DisableEnable
    MAX-ACCESS  read-write
    STATUS      current
    DESCRIPTION
        "Shape Enablement" 
    ::=  { flowEntityConfigEntry 8 }

flowEntityConfigPolice OBJECT-TYPE
    SYNTAX      FspR7DisableEnable
    MAX-ACCESS  read-write
    STATUS      current
    DESCRIPTION
        "Police Enablement" 
    ::=  { flowEntityConfigEntry 9 }

flowEntityConfigDefaultEvcCos OBJECT-TYPE
    SYNTAX      Integer32 (7..7 | -2147483648)
    MAX-ACCESS  read-write
    STATUS      current
    DESCRIPTION
        "Default COS for frames not matching classification scheme PCP/DSCP, or used as CoS for EVC based classification." 
    ::=  { flowEntityConfigEntry 10 }

flowEntityConfigCirRcv OBJECT-TYPE
    SYNTAX      Unsigned32 
    UNITS       "Mbit/s"
    MAX-ACCESS  read-write
    STATUS      current
    DESCRIPTION
        "CIR (Committed Information Rate ) is used on Ethernet Interfaces with a policing function" 
    ::=  { flowEntityConfigEntry 11 }

flowEntityConfigCirTrmt OBJECT-TYPE
    SYNTAX      Unsigned32 
    UNITS       "Mbit/s"
    MAX-ACCESS  read-write
    STATUS      current
    DESCRIPTION
        "CIR (Committed Information Rate ) is used on Ethernet Interfaces with a policing function" 
    ::=  { flowEntityConfigEntry 12 }

flowEntityConfigCbsRcv OBJECT-TYPE
    SYNTAX      Unsigned32 (0..26214400 | 4294967295) 
    UNITS       "bytes"
    MAX-ACCESS  read-write
    STATUS      current
    DESCRIPTION
        "Committed Burst Size" 
    ::=  { flowEntityConfigEntry 13 }

flowEntityConfigCbsTrmt OBJECT-TYPE
    SYNTAX      Unsigned32 (0..25600 | 4294967295) 
    UNITS       "Kbytes"
    MAX-ACCESS  read-write
    STATUS      current
    DESCRIPTION
        "Committed Burst Size" 
    ::=  { flowEntityConfigEntry 14 }

flowEntityConfigDataLayerPmReset OBJECT-TYPE
    SYNTAX      FspR7PmReset
    MAX-ACCESS  read-write
    STATUS      current
    DESCRIPTION
        "Reset data-layer Performance registers" 
    ::=  { flowEntityConfigEntry 15 }

flowEntityConfigPushPvidTrmt OBJECT-TYPE
    SYNTAX      Unsigned32 (0..4095 | 4294967295)
    MAX-ACCESS  read-write
    STATUS      current
    DESCRIPTION
        "C-VID tag is added on transmit from EVC. PEP." 
    ::=  { flowEntityConfigEntry 16 }

flowEntityConfigPrioPvidTrmt OBJECT-TYPE
    SYNTAX      Unsigned32 (0..7 | 4294967295)
    MAX-ACCESS  read-write
    STATUS      current
    DESCRIPTION
        "Added PRIO when CTAG is pushed on untagged frame. PEP." 
    ::=  { flowEntityConfigEntry 17 }

flowEntityConfigRedLineState OBJECT-TYPE
    SYNTAX      FspR7RedLinedState
    MAX-ACCESS  read-write
    STATUS      current
    DESCRIPTION
        "will be set by higher level software to act as a barrier to deletion" 
    ::=  { flowEntityConfigEntry 18 }

flowEntityConfigTunnelAid OBJECT-TYPE
    SYNTAX      SnmpAdminString
    MAX-ACCESS  read-write
    STATUS      current
    DESCRIPTION
        "Tunnel AID" 
    ::=  { flowEntityConfigEntry 19 }

flowEntityConfigSwitchCommand OBJECT-TYPE
    SYNTAX      FspR7APSCommand
    MAX-ACCESS  read-write
    STATUS      current
    DESCRIPTION
        "Protection Switch commands: Manual, Lock or Release.
         The 'Manual Switch' switches manually from addressed facility to
         the partner but does not force the traffic onto a broken fiber and
         it does not block the subsequent automatic functioning of the switch.
         The 'Lock Switch' - ask Gerald for description.......
         The 'Release Switch' releases the current switch command.
         Relevant especially to 'Lock Switch' command. For 'Manual Switch' relevant
         only if revertivity is supported." 
    ::=  { flowEntityConfigEntry 20 }

flowEntityConfigInhibitSwitchToProt OBJECT-TYPE
    SYNTAX      FspR7YesNo
    MAX-ACCESS  read-write
    STATUS      current
    DESCRIPTION
        "Inhibit Switch To PROTN facility. Inhibition blocks
         switch to the PROTN facility (protection path).
         Applicable only for the WKG facility in ACT state." 
    ::=  { flowEntityConfigEntry 21 }

flowEntityConfigInhibitSwitchToWork OBJECT-TYPE
    SYNTAX      FspR7YesNo
    MAX-ACCESS  read-write
    STATUS      current
    DESCRIPTION
        "Inhibit Switch To Working. Inhibition blocks a switch
         to the WKG facility (working path).
         Applicable for the PROTN facility in ACT state." 
    ::=  { flowEntityConfigEntry 22 }

flowEntityConfigCapTable OBJECT-TYPE
    SYNTAX      SEQUENCE OF FlowEntityConfigCapEntry
    MAX-ACCESS  not-accessible
    STATUS      current
    DESCRIPTION   ""
    ::=  { flowConfiguration 12 }

flowEntityConfigCapEntry OBJECT-TYPE
    SYNTAX      FlowEntityConfigCapEntry
    MAX-ACCESS  not-accessible
    STATUS      current
    DESCRIPTION   ""
    INDEX       {
                  flowEntityIndexEth,
                  flowEntityIndexFlow
                }
    ::=  { flowEntityConfigCapTable 1 }

FlowEntityConfigCapEntry ::=  SEQUENCE
  { flowEntityConfigCapAdmin FspR7AdminStateCaps,
    flowEntityConfigCapPmMode FspR7L2PmModeCaps,
    flowEntityConfigCapShape FspR7DisableEnableCaps,
    flowEntityConfigCapPolice FspR7DisableEnableCaps,
    flowEntityConfigCapDefaultEvcCos FspR7Integer32Caps,
    flowEntityConfigCapDataLayerPmReset FspR7PmResetCaps,
    flowEntityConfigCapPopCtagRcv Unsigned32,
    flowEntityConfigCapPopCtagTrmt Unsigned32,
    flowEntityConfigCapCvidRegisteredInFlow Integer32,
    flowEntityConfigCapExternalVid Unsigned32,
    flowEntityConfigCapCbsRcv Unsigned32,
    flowEntityConfigCapPushTrmt Unsigned32,
    flowEntityConfigCapRedLineState FspR7RedLinedStateCaps,
    flowEntityConfigCapSwitchCommand FspR7APSCommandCaps,
    flowEntityConfigCapInhibitSwitchToProt FspR7YesNoCaps,
    flowEntityConfigCapInhibitSwitchToWork FspR7YesNoCaps }

flowEntityConfigCapAdmin OBJECT-TYPE
    SYNTAX      FspR7AdminStateCaps
    MAX-ACCESS  read-only
    STATUS      current
    DESCRIPTION
        "The Adminstrative State will be displayed in the GUI with full
         name values; it will be differently displayed in TL1 syntax according
         to TL1 display rules. The transaction into the UAS state requires
         a special destroy/delete function." 
    ::=  { flowEntityConfigCapEntry 1 }

flowEntityConfigCapPmMode OBJECT-TYPE
    SYNTAX      FspR7L2PmModeCaps
    MAX-ACCESS  read-only
    STATUS      current
    DESCRIPTION
        "Mode of PM counters" 
    ::=  { flowEntityConfigCapEntry 2 }

flowEntityConfigCapShape OBJECT-TYPE
    SYNTAX      FspR7DisableEnableCaps
    MAX-ACCESS  read-only
    STATUS      current
    DESCRIPTION
        "Shape Enablement" 
    ::=  { flowEntityConfigCapEntry 3 }

flowEntityConfigCapPolice OBJECT-TYPE
    SYNTAX      FspR7DisableEnableCaps
    MAX-ACCESS  read-only
    STATUS      current
    DESCRIPTION
        "Police Enablement" 
    ::=  { flowEntityConfigCapEntry 4 }

flowEntityConfigCapDefaultEvcCos OBJECT-TYPE
    SYNTAX      FspR7Integer32Caps
    MAX-ACCESS  read-only
    STATUS      current
    DESCRIPTION
        "Default COS for frames not matching classification scheme PCP/DSCP, or used as CoS for EVC based classification." 
    ::=  { flowEntityConfigCapEntry 5 }

flowEntityConfigCapDataLayerPmReset OBJECT-TYPE
    SYNTAX      FspR7PmResetCaps
    MAX-ACCESS  read-only
    STATUS      current
    DESCRIPTION
        "Reset data-layer Performance registers" 
    ::=  { flowEntityConfigCapEntry 6 }

flowEntityConfigCapPopCtagRcv OBJECT-TYPE
    SYNTAX      Unsigned32
    MAX-ACCESS  read-only
    STATUS      current
    DESCRIPTION
        "'c-vid tag is removed in receive to an EVC. This is equivalent to untagged PEP in PB'" 
    ::=  { flowEntityConfigCapEntry 7 }

flowEntityConfigCapPopCtagTrmt OBJECT-TYPE
    SYNTAX      Unsigned32
    MAX-ACCESS  read-only
    STATUS      current
    DESCRIPTION
        "'c-vid tag is removed on transmit from EVC. This is equivalent to the untagged CEP in PB'" 
    ::=  { flowEntityConfigCapEntry 8 }

flowEntityConfigCapCvidRegisteredInFlow OBJECT-TYPE
    SYNTAX      Integer32
    MAX-ACCESS  read-only
    STATUS      current
    DESCRIPTION
        "CVLANs Registered with the Flow" 
    ::=  { flowEntityConfigCapEntry 9 }

flowEntityConfigCapExternalVid OBJECT-TYPE
    SYNTAX      Unsigned32
    MAX-ACCESS  read-only
    STATUS      current
    DESCRIPTION
        "External VID" 
    ::=  { flowEntityConfigCapEntry 10 }

flowEntityConfigCapCbsRcv OBJECT-TYPE
    SYNTAX      Unsigned32
    UNITS       "bytes"
    MAX-ACCESS  read-only
    STATUS      current
    DESCRIPTION
        "Committed Burst Size" 
    ::=  { flowEntityConfigCapEntry 11 }

flowEntityConfigCapPushTrmt OBJECT-TYPE
    SYNTAX      Unsigned32
    MAX-ACCESS  read-only
    STATUS      current
    DESCRIPTION
        "C-VID tag is added on transmit from EVC. PEP." 
    ::=  { flowEntityConfigCapEntry 12 }

flowEntityConfigCapRedLineState OBJECT-TYPE
    SYNTAX      FspR7RedLinedStateCaps
    MAX-ACCESS  read-only
    STATUS      current
    DESCRIPTION
        "will be set by higher level software to act as a barrier to deletion" 
    ::=  { flowEntityConfigCapEntry 13 }

flowEntityConfigCapSwitchCommand OBJECT-TYPE
    SYNTAX      FspR7APSCommandCaps
    MAX-ACCESS  read-only
    STATUS      current
    DESCRIPTION
        "Protection Switch commands: Manual, Lock or Release.
         The 'Manual Switch' switches manually from addressed facility to
         the partner but does not force the traffic onto a broken fiber and
         it does not block the subsequent automatic functioning of the switch.
         The 'Lock Switch' - ask Gerald for description.......
         The 'Release Switch' releases the current switch command.
         Relevant especially to 'Lock Switch' command. For 'Manual Switch' relevant
         only if revertivity is supported." 
    ::=  { flowEntityConfigCapEntry 14 }

flowEntityConfigCapInhibitSwitchToProt OBJECT-TYPE
    SYNTAX      FspR7YesNoCaps
    MAX-ACCESS  read-only
    STATUS      current
    DESCRIPTION
        "Inhibit Switch To PROTN facility. Inhibition blocks
         switch to the PROTN facility (protection path).
         Applicable only for the WKG facility in ACT state." 
    ::=  { flowEntityConfigCapEntry 15 }

flowEntityConfigCapInhibitSwitchToWork OBJECT-TYPE
    SYNTAX      FspR7YesNoCaps
    MAX-ACCESS  read-only
    STATUS      current
    DESCRIPTION
        "Inhibit Switch To Working. Inhibition blocks a switch
         to the WKG facility (working path).
         Applicable for the PROTN facility in ACT state." 
    ::=  { flowEntityConfigCapEntry 16 }

flowEntityConfigCbsRcvCapTable OBJECT-TYPE
    SYNTAX      SEQUENCE OF FlowEntityConfigCbsRcvCapEntry
    MAX-ACCESS  not-accessible
    STATUS      current
    DESCRIPTION   "This table is used to get capabilities for CBS-RCV parameter. Regular
         cap tables including CBS-RCV show the number of capabilities for a specific entity.
         Value 0 in regular cap tables means 'no capabilities'.
         Each capability for a specific entity has a separate third index."
    ::=  { flowConfiguration 13 }

flowEntityConfigCbsRcvCapEntry OBJECT-TYPE
    SYNTAX      FlowEntityConfigCbsRcvCapEntry
    MAX-ACCESS  not-accessible
    STATUS      current
    DESCRIPTION   ""
    INDEX       {
                  flowEntityIndexEth,
                  flowEntityIndexFlow,
                  flowEntityProvisionCbsRcvCapIndexCap
                }
    ::=  { flowEntityConfigCbsRcvCapTable 1 }

FlowEntityConfigCbsRcvCapEntry ::=  SEQUENCE
  { flowEntityConfigCbsRcvCapCbsRcv Unsigned32 }

flowEntityConfigCbsRcvCapCbsRcv OBJECT-TYPE
    SYNTAX      Unsigned32
    UNITS       "bytes"
    MAX-ACCESS  read-only
    STATUS      current
    DESCRIPTION
        "Committed Burst Size" 
    ::=  { flowEntityConfigCbsRcvCapEntry 1 }

flowEntityConfigRegisterCapTable OBJECT-TYPE
    SYNTAX      SEQUENCE OF FlowEntityConfigRegisterCapEntry
    MAX-ACCESS  not-accessible
    STATUS      current
    DESCRIPTION   "This table is used to get capabilities for REGISTER parameter. Regular
         cap tables including REGISTER show the length of output string.
         Value 0 in regular cap tables means 'no capabilities'.
         The third index (n) is used to devide the output string to n string blocks.
         Each block has a maximum of 512 bytes. n = output string / 512."
    ::=  { flowConfiguration 14 }

flowEntityConfigRegisterCapEntry OBJECT-TYPE
    SYNTAX      FlowEntityConfigRegisterCapEntry
    MAX-ACCESS  not-accessible
    STATUS      current
    DESCRIPTION   ""
    INDEX       {
                  flowEntityIndexEth,
                  flowEntityIndexFlow,
                  flowEntityProvisionRegisterCapIndexCap
                }
    ::=  { flowEntityConfigRegisterCapTable 1 }

FlowEntityConfigRegisterCapEntry ::=  SEQUENCE
  { flowEntityConfigRegisterCapStringCap SnmpAdminString }

flowEntityConfigRegisterCapStringCap OBJECT-TYPE
    SYNTAX      SnmpAdminString
    MAX-ACCESS  read-only
    STATUS      current
    DESCRIPTION
        "" 
    ::=  { flowEntityConfigRegisterCapEntry 1 }

flowEntityConfigExternalVidCapTable OBJECT-TYPE
    SYNTAX      SEQUENCE OF FlowEntityConfigExternalVidCapEntry
    MAX-ACCESS  not-accessible
    STATUS      current
    DESCRIPTION   "This table is used to get capabilities for EXTVID parameter. Regular
         cap tables including EXTVID show the length of output string.
         Value 0 in regular cap tables means 'no capabilities'.
         The third index (n) is used to devide the output string to n string blocks.
         Each block has a maximum of 512 bytes. n = output string / 512."
    ::=  { flowConfiguration 15 }

flowEntityConfigExternalVidCapEntry OBJECT-TYPE
    SYNTAX      FlowEntityConfigExternalVidCapEntry
    MAX-ACCESS  not-accessible
    STATUS      current
    DESCRIPTION   ""
    INDEX       {
                  flowEntityIndexEth,
                  flowEntityIndexFlow,
                  flowEntityProvisionExternalVidCapIndexCap
                }
    ::=  { flowEntityConfigExternalVidCapTable 1 }

FlowEntityConfigExternalVidCapEntry ::=  SEQUENCE
  { flowEntityConfigExternalVidCapStringCap SnmpAdminString }

flowEntityConfigExternalVidCapStringCap OBJECT-TYPE
    SYNTAX      SnmpAdminString
    MAX-ACCESS  read-only
    STATUS      current
    DESCRIPTION
        "" 
    ::=  { flowEntityConfigExternalVidCapEntry 1 }

flowEntityConfigPopCtagRcvCapTable OBJECT-TYPE
    SYNTAX      SEQUENCE OF FlowEntityConfigPopCtagRcvCapEntry
    MAX-ACCESS  not-accessible
    STATUS      current
    DESCRIPTION   "This table is used to get capabilities for POP_RCV parameter. Regular
         cap tables including POP_RCV show the length of output string.
         Value 0 in regular cap tables means 'no capabilities'.
         The third index (n) is used to devide the output string to n string blocks.
         Each block has a maximum of 512 bytes. n = output string / 512."
    ::=  { flowConfiguration 16 }

flowEntityConfigPopCtagRcvCapEntry OBJECT-TYPE
    SYNTAX      FlowEntityConfigPopCtagRcvCapEntry
    MAX-ACCESS  not-accessible
    STATUS      current
    DESCRIPTION   ""
    INDEX       {
                  flowEntityIndexEth,
                  flowEntityIndexFlow,
                  flowEntityProvisionPopCtagRcvCapIndexCap
                }
    ::=  { flowEntityConfigPopCtagRcvCapTable 1 }

FlowEntityConfigPopCtagRcvCapEntry ::=  SEQUENCE
  { flowEntityConfigPopCtagRcvCapStringCap SnmpAdminString }

flowEntityConfigPopCtagRcvCapStringCap OBJECT-TYPE
    SYNTAX      SnmpAdminString
    MAX-ACCESS  read-only
    STATUS      current
    DESCRIPTION
        "" 
    ::=  { flowEntityConfigPopCtagRcvCapEntry 1 }

flowEntityConfigPopCtagTrmtCapTable OBJECT-TYPE
    SYNTAX      SEQUENCE OF FlowEntityConfigPopCtagTrmtCapEntry
    MAX-ACCESS  not-accessible
    STATUS      current
    DESCRIPTION   "This table is used to get capabilities for POP_TRMT parameter. Regular
         cap tables including POP_TRMT show the length of output string.
         Value 0 in regular cap tables means 'no capabilities'.
         The third index (n) is used to devide the output string to n string blocks.
         Each block has a maximum of 512 bytes. n = output string / 512."
    ::=  { flowConfiguration 17 }

flowEntityConfigPopCtagTrmtCapEntry OBJECT-TYPE
    SYNTAX      FlowEntityConfigPopCtagTrmtCapEntry
    MAX-ACCESS  not-accessible
    STATUS      current
    DESCRIPTION   ""
    INDEX       {
                  flowEntityIndexEth,
                  flowEntityIndexFlow,
                  flowEntityProvisionPopCtagTrmtCapIndexCap
                }
    ::=  { flowEntityConfigPopCtagTrmtCapTable 1 }

FlowEntityConfigPopCtagTrmtCapEntry ::=  SEQUENCE
  { flowEntityConfigPopCtagTrmtCapStringCap SnmpAdminString }

flowEntityConfigPopCtagTrmtCapStringCap OBJECT-TYPE
    SYNTAX      SnmpAdminString
    MAX-ACCESS  read-only
    STATUS      current
    DESCRIPTION
        "" 
    ::=  { flowEntityConfigPopCtagTrmtCapEntry 1 }

flowEntityConfigPushTrmtCapTable OBJECT-TYPE
    SYNTAX      SEQUENCE OF FlowEntityConfigPushTrmtCapEntry
    MAX-ACCESS  not-accessible
    STATUS      current
    DESCRIPTION   "This table is used to get capabilities for PUSH-TRMT parameter. Regular
         cap tables including PUSH-TRMT show the length of output string.
         Value 0 in regular cap tables means 'no capabilities'.
         The third index (n) is used to devide the output string to n string blocks.
         Each block has a maximum of 512 bytes. n = output string / 512."
    ::=  { flowConfiguration 18 }

flowEntityConfigPushTrmtCapEntry OBJECT-TYPE
    SYNTAX      FlowEntityConfigPushTrmtCapEntry
    MAX-ACCESS  not-accessible
    STATUS      current
    DESCRIPTION   ""
    INDEX       {
                  flowEntityIndexEth,
                  flowEntityIndexFlow,
                  flowEntityProvisionPushTrmtCapIndexCap
                }
    ::=  { flowEntityConfigPushTrmtCapTable 1 }

FlowEntityConfigPushTrmtCapEntry ::=  SEQUENCE
  { flowEntityConfigPushTrmtCapStringCap SnmpAdminString }

flowEntityConfigPushTrmtCapStringCap OBJECT-TYPE
    SYNTAX      SnmpAdminString
    MAX-ACCESS  read-only
    STATUS      current
    DESCRIPTION
        "" 
    ::=  { flowEntityConfigPushTrmtCapEntry 1 }

bridgeEntityConfigTable OBJECT-TYPE
    SYNTAX      SEQUENCE OF BridgeEntityConfigEntry
    MAX-ACCESS  not-accessible
    STATUS      current
    DESCRIPTION   "This table is used for configuration of BRIDGE entities."
    ::=  { bridgeConfiguration 11 }

bridgeEntityConfigEntry OBJECT-TYPE
    SYNTAX      BridgeEntityConfigEntry
    MAX-ACCESS  not-accessible
    STATUS      current
    DESCRIPTION   "Entry represents an assigned BRIDGE entity."
    INDEX       {
                  bridgeEntityContainedIn,
                  bridgeEntitySvid
                }
    ::=  { bridgeEntityConfigTable 1 }

BridgeEntityConfigEntry ::=  SEQUENCE
  { bridgeEntityConfigAlias SnmpAdminString,
    bridgeEntityConfigShapeState FspR7DisableEnable,
    bridgeEntityConfigPmMode FspR7L2PmMode,
    bridgeEntityConfigCirTrmt Unsigned32,
    bridgeEntityConfigCbsTrmt Unsigned32,
    bridgeEntityConfigAdminState FspR7AdminState }

bridgeEntityConfigAlias OBJECT-TYPE
    SYNTAX      SnmpAdminString
    MAX-ACCESS  read-write
    STATUS      current
    DESCRIPTION
        "User Applied Descriptor" 
    ::=  { bridgeEntityConfigEntry 1 }

bridgeEntityConfigShapeState OBJECT-TYPE
    SYNTAX      FspR7DisableEnable
    MAX-ACCESS  read-write
    STATUS      current
    DESCRIPTION
        "E-LAN Shape Enablement" 
    ::=  { bridgeEntityConfigEntry 2 }

bridgeEntityConfigPmMode OBJECT-TYPE
    SYNTAX      FspR7L2PmMode
    MAX-ACCESS  read-write
    STATUS      current
    DESCRIPTION
        "Mode of PM counters" 
    ::=  { bridgeEntityConfigEntry 3 }

bridgeEntityConfigCirTrmt OBJECT-TYPE
    SYNTAX      Unsigned32 
    UNITS       "Mbit/s"
    MAX-ACCESS  read-write
    STATUS      current
    DESCRIPTION
        "CIR (Committed Information Rate ) is used on Ethernet Interfaces with a policing function" 
    ::=  { bridgeEntityConfigEntry 4 }

bridgeEntityConfigCbsTrmt OBJECT-TYPE
    SYNTAX      Unsigned32 (0..25600 | 4294967295) 
    UNITS       "Kbytes"
    MAX-ACCESS  read-write
    STATUS      current
    DESCRIPTION
        "Committed Burst Size" 
    ::=  { bridgeEntityConfigEntry 5 }

bridgeEntityConfigAdminState OBJECT-TYPE
    SYNTAX      FspR7AdminState
    MAX-ACCESS  read-write
    STATUS      current
    DESCRIPTION
        "The Adminstrative State will be displayed in the GUI with full
         name values; it will be differently displayed in TL1 syntax according
         to TL1 display rules. The transaction into the UAS state requires
         a special destroy/delete function." 
    ::=  { bridgeEntityConfigEntry 6 }

bridgeEntityConfigCapTable OBJECT-TYPE
    SYNTAX      SEQUENCE OF BridgeEntityConfigCapEntry
    MAX-ACCESS  not-accessible
    STATUS      current
    DESCRIPTION   "This table is used for configuration of BRIDGE entities."
    ::=  { bridgeConfiguration 12  }

bridgeEntityConfigCapEntry OBJECT-TYPE
    SYNTAX      BridgeEntityConfigCapEntry
    MAX-ACCESS  not-accessible
    STATUS      current
    DESCRIPTION   "Entry represents an assigned BRIDGE entity."
    INDEX       { bridgeEntityContainedIn,
                  bridgeEntitySvid }
    ::=  { bridgeEntityConfigCapTable 1 }

BridgeEntityConfigCapEntry ::=  SEQUENCE
  { bridgeEntityConfigCapAlias Integer32,
    bridgeEntityConfigCapShapeState FspR7DisableEnableCaps,
    bridgeEntityConfigCapPmMode FspR7L2PmModeCaps,
    bridgeEntityConfigCapCirTrmt FspR7Unsigned32Caps,
    bridgeEntityConfigCapCbsTrmt FspR7Unsigned32Caps,
    bridgeEntityConfigCapAdminState FspR7AdminStateCaps }

bridgeEntityConfigCapAlias OBJECT-TYPE
    SYNTAX      Integer32
    MAX-ACCESS  read-only
    STATUS      current
    DESCRIPTION
        "User Applied Descriptor" 
    ::=  { bridgeEntityConfigCapEntry 1 }

bridgeEntityConfigCapShapeState OBJECT-TYPE
    SYNTAX      FspR7DisableEnableCaps
    MAX-ACCESS  read-only
    STATUS      current
    DESCRIPTION
        "E-LAN Shape Enablement" 
    ::=  { bridgeEntityConfigCapEntry 2 }

bridgeEntityConfigCapPmMode OBJECT-TYPE
    SYNTAX      FspR7L2PmModeCaps
    MAX-ACCESS  read-only
    STATUS      current
    DESCRIPTION
        "Mode of PM counters" 
    ::=  { bridgeEntityConfigCapEntry 3 }

bridgeEntityConfigCapCirTrmt OBJECT-TYPE
    SYNTAX      FspR7Unsigned32Caps
    UNITS       "Mbit/s"
    MAX-ACCESS  read-only
    STATUS      current
    DESCRIPTION
        "CIR (Committed Information Rate ) is used on Ethernet Interfaces with a policing function" 
    ::=  { bridgeEntityConfigCapEntry 4 }

bridgeEntityConfigCapCbsTrmt OBJECT-TYPE
    SYNTAX      FspR7Unsigned32Caps
    UNITS       "Kbytes"
    MAX-ACCESS  read-only
    STATUS      current
    DESCRIPTION
        "Committed Burst Size" 
    ::=  { bridgeEntityConfigCapEntry 5 }

bridgeEntityConfigCapAdminState OBJECT-TYPE
    SYNTAX      FspR7AdminStateCaps
    MAX-ACCESS  read-only
    STATUS      current
    DESCRIPTION
        "The Adminstrative State will be displayed in the GUI with full
         name values; it will be differently displayed in TL1 syntax according
         to TL1 display rules. The transaction into the UAS state requires
         a special destroy/delete function." 
    ::=  { bridgeEntityConfigCapEntry 6 }

queOnBridgeEntityConfigTable OBJECT-TYPE
    SYNTAX      SEQUENCE OF QueOnBridgeEntityConfigEntry
    MAX-ACCESS  not-accessible
    STATUS      current
    DESCRIPTION   "This table is used for configuration of QUE entities."
    ::=  { queOnBridgeConfiguration 11 }

queOnBridgeEntityConfigEntry OBJECT-TYPE
    SYNTAX      QueOnBridgeEntityConfigEntry
    MAX-ACCESS  not-accessible
    STATUS      current
    DESCRIPTION   "Entry represents an assigned QUE entity."
    INDEX       {
                  queOnBridgeEntityIndex,
                  queOnBridgeEntitySvid,
                  queOnBridgeEntityPrio
                }
    ::=  { queOnBridgeEntityConfigTable 1 }

QueOnBridgeEntityConfigEntry ::=  SEQUENCE
  { queOnBridgeEntityConfigDataLayerPmReset FspR7PmReset }

queOnBridgeEntityConfigDataLayerPmReset OBJECT-TYPE
    SYNTAX      FspR7PmReset
    MAX-ACCESS  read-write
    STATUS      current
    DESCRIPTION
        "Reset data-layer Performance registers" 
    ::=  { queOnBridgeEntityConfigEntry 1 }

queOnBridgeEntityConfigCapTable OBJECT-TYPE
    SYNTAX      SEQUENCE OF QueOnBridgeEntityConfigCapEntry
    MAX-ACCESS  not-accessible
    STATUS      current
    DESCRIPTION   "This table is used for configuration of QUE entities."
    ::=  { queOnBridgeConfiguration 12  }

queOnBridgeEntityConfigCapEntry OBJECT-TYPE
    SYNTAX      QueOnBridgeEntityConfigCapEntry
    MAX-ACCESS  not-accessible
    STATUS      current
    DESCRIPTION   "Entry represents an assigned QUE entity."
    INDEX       { queOnBridgeEntityIndex,
                  queOnBridgeEntitySvid,
                  queOnBridgeEntityPrio }
    ::=  { queOnBridgeEntityConfigCapTable 1 }

QueOnBridgeEntityConfigCapEntry ::=  SEQUENCE
  { queOnBridgeEntityConfigCapDataLayerPmReset FspR7PmResetCaps }

queOnBridgeEntityConfigCapDataLayerPmReset OBJECT-TYPE
    SYNTAX      FspR7PmResetCaps
    MAX-ACCESS  read-only
    STATUS      current
    DESCRIPTION
        "Reset data-layer Performance registers" 
    ::=  { queOnBridgeEntityConfigCapEntry 1 }

flowEntityStatusTable OBJECT-TYPE
    SYNTAX      SEQUENCE OF FlowEntityStatusEntry
    MAX-ACCESS  not-accessible
    STATUS      current
    DESCRIPTION   ""
    ::=  { flowStatus 11 }

flowEntityStatusEntry OBJECT-TYPE
    SYNTAX      FlowEntityStatusEntry
    MAX-ACCESS  not-accessible
    STATUS      current
    DESCRIPTION   ""
    INDEX       {
                  flowEntityIndexEth,
                  flowEntityIndexFlow
                }
    ::=  { flowEntityStatusTable 1 }

FlowEntityStatusEntry ::=  SEQUENCE
  { flowEntityStatusOper FspR7OperState,
    flowEntityStatusSecondaryStates FspR7EntitySecondaryStates,
    flowEntityStatusType FspR7InterfaceType,
    flowEntityStatusInternalSvid Unsigned32,
    flowEntityStatusConnectionState FspR7ConnectState,
    flowEntityStatusValidSignalTimer Unsigned32,
    flowEntityStatusProtectionRole FspR7ProtectionRole,
    flowEntityStatusIngressTid SnmpAdminString,
    flowEntityStatusIngressNodeIp IpAddress }

flowEntityStatusOper OBJECT-TYPE
    SYNTAX      FspR7OperState
    MAX-ACCESS  read-only
    STATUS      current
    DESCRIPTION   "The Operational State will be displayed on the GUI with full name values;
         it will be differently displayed in TL1 SYNTAX according to TL1 display rules"
    ::=  { flowEntityStatusEntry 1 }

flowEntityStatusSecondaryStates OBJECT-TYPE
    SYNTAX      FspR7EntitySecondaryStates
    MAX-ACCESS  read-only
    STATUS      current
    DESCRIPTION   "Secondary states of an entity."
    ::=  { flowEntityStatusEntry 2 }

flowEntityStatusType OBJECT-TYPE
    SYNTAX      FspR7InterfaceType
    MAX-ACCESS  read-only
    STATUS      current
    DESCRIPTION   ""
    ::=  { flowEntityStatusEntry 3 }

flowEntityStatusInternalSvid OBJECT-TYPE
    SYNTAX      Unsigned32
    MAX-ACCESS  read-only
    STATUS      current
    DESCRIPTION
        "Index of svid" 
    ::=  { flowEntityStatusEntry 4 }

flowEntityStatusConnectionState OBJECT-TYPE
    SYNTAX      FspR7ConnectState
    MAX-ACCESS  read-only
    STATUS      current
    DESCRIPTION
        "Connection State" 
    ::=  { flowEntityStatusEntry 5 }

flowEntityStatusValidSignalTimer OBJECT-TYPE
    SYNTAX      Unsigned32 (0..5760 | 4294967295) 
    UNITS       "min"
    MAX-ACCESS  read-only
    STATUS      current
    DESCRIPTION
        "AINS state signal quality soak time remaining until transition to IS." 
    ::=  { flowEntityStatusEntry 6 }

flowEntityStatusProtectionRole OBJECT-TYPE
    SYNTAX      FspR7ProtectionRole
    MAX-ACCESS  read-only
    STATUS      current
    DESCRIPTION
        "The Path is Labelled Working or Protection" 
    ::=  { flowEntityStatusEntry 7 }

flowEntityStatusIngressTid OBJECT-TYPE
    SYNTAX      SnmpAdminString
    MAX-ACCESS  read-only
    STATUS      current
    DESCRIPTION
        "Ingress Target ID" 
    ::=  { flowEntityStatusEntry 8 }

flowEntityStatusIngressNodeIp OBJECT-TYPE
    SYNTAX      IpAddress
    MAX-ACCESS  read-only
    STATUS      current
    DESCRIPTION
        "Ingress Node IP" 
    ::=  { flowEntityStatusEntry 9 }

ctransEntityStatusTable OBJECT-TYPE
    SYNTAX      SEQUENCE OF CtransEntityStatusEntry
    MAX-ACCESS  not-accessible
    STATUS      current
    DESCRIPTION   ""
    ::=  { ctransStatus 11 }

ctransEntityStatusEntry OBJECT-TYPE
    SYNTAX      CtransEntityStatusEntry
    MAX-ACCESS  not-accessible
    STATUS      current
    DESCRIPTION   ""
    INDEX       {
                  ctransEntityIndexEth,
                  ctransEntityIndexCVlanId
                }
    ::=  { ctransEntityStatusTable 1 }

CtransEntityStatusEntry ::=  SEQUENCE
  { ctransEntityStatusType FspR7InterfaceType,
    ctransEntityStatusCvidInternal Unsigned32,
    ctransEntityStatusRange Unsigned32 }

ctransEntityStatusType OBJECT-TYPE
    SYNTAX      FspR7InterfaceType
    MAX-ACCESS  read-only
    STATUS      current
    DESCRIPTION   ""
    ::=  { ctransEntityStatusEntry 1 }

ctransEntityStatusCvidInternal OBJECT-TYPE
    SYNTAX      Unsigned32 (1..4095 | 4294967295)
    MAX-ACCESS  read-only
    STATUS      current
    DESCRIPTION
        "Internal CVID" 
    ::=  { ctransEntityStatusEntry 2 }

ctransEntityStatusRange OBJECT-TYPE
    SYNTAX      Unsigned32 (1..4095 | 4294967295)
    MAX-ACCESS  read-only
    STATUS      current
    DESCRIPTION
        "Range of the translated CVID." 
    ::=  { ctransEntityStatusEntry 3 }

policerOnFlowEntityStatusTable OBJECT-TYPE
    SYNTAX      SEQUENCE OF PolicerOnFlowEntityStatusEntry
    MAX-ACCESS  not-accessible
    STATUS      current
    DESCRIPTION   ""
    ::=  { policerStatus 12 }

policerOnFlowEntityStatusEntry OBJECT-TYPE
    SYNTAX      PolicerOnFlowEntityStatusEntry
    MAX-ACCESS  not-accessible
    STATUS      current
    DESCRIPTION   ""
    INDEX       {
                  policerOnFlowEntityIndexEth,
                  policerOnFlowEntityIndexFlow,
                  policerOnFlowEntityIndexPolicer
                }
    ::=  { policerOnFlowEntityStatusTable 1 }

PolicerOnFlowEntityStatusEntry ::=  SEQUENCE
  { policerOnFlowEntityStatusOper FspR7OperState,
    policerOnFlowEntityStatusSecondaryStates FspR7EntitySecondaryStates,
    policerOnFlowEntityStatusType FspR7InterfaceType,
    policerOnFlowEntityStatusAdmin FspR7AdminState,
    policerOnFlowEntityStatusAlias SnmpAdminString,
    policerOnFlowEntityStatusCirRcv Unsigned32,
    policerOnFlowEntityStatusCbsRcv Unsigned32 }

policerOnFlowEntityStatusOper OBJECT-TYPE
    SYNTAX      FspR7OperState
    MAX-ACCESS  read-only
    STATUS      current
    DESCRIPTION   "The Operational State will be displayed on the GUI with full name values;
         it will be differently displayed in TL1 SYNTAX according to TL1 display rules"
    ::=  { policerOnFlowEntityStatusEntry 1 }

policerOnFlowEntityStatusSecondaryStates OBJECT-TYPE
    SYNTAX      FspR7EntitySecondaryStates
    MAX-ACCESS  read-only
    STATUS      current
    DESCRIPTION   "Secondary states of an entity."
    ::=  { policerOnFlowEntityStatusEntry 2 }

policerOnFlowEntityStatusType OBJECT-TYPE
    SYNTAX      FspR7InterfaceType
    MAX-ACCESS  read-only
    STATUS      current
    DESCRIPTION   ""
    ::=  { policerOnFlowEntityStatusEntry 3 }

policerOnFlowEntityStatusAdmin OBJECT-TYPE
    SYNTAX      FspR7AdminState
    MAX-ACCESS  read-only
    STATUS      current
    DESCRIPTION
        "The Adminstrative State will be displayed in the GUI with full
         name values; it will be differently displayed in TL1 syntax according
         to TL1 display rules. The transaction into the UAS state requires
         a special destroy/delete function." 
    ::=  { policerOnFlowEntityStatusEntry 4 }

policerOnFlowEntityStatusAlias OBJECT-TYPE
    SYNTAX      SnmpAdminString
    MAX-ACCESS  read-only
    STATUS      current
    DESCRIPTION
        "User Applied Descriptor" 
    ::=  { policerOnFlowEntityStatusEntry 5 }

policerOnFlowEntityStatusCirRcv OBJECT-TYPE
    SYNTAX      Unsigned32 
    UNITS       "Mbit/s"
    MAX-ACCESS  read-only
    STATUS      current
    DESCRIPTION
        "CIR (Committed Information Rate ) is used on Ethernet Interfaces with a policing function" 
    ::=  { policerOnFlowEntityStatusEntry 6 }

policerOnFlowEntityStatusCbsRcv OBJECT-TYPE
    SYNTAX      Unsigned32 (0..26214400 | 4294967295) 
    UNITS       "bytes"
    MAX-ACCESS  read-only
    STATUS      current
    DESCRIPTION
        "Committed Burst Size" 
    ::=  { policerOnFlowEntityStatusEntry 7 }

queOnPortEntityStatusTable OBJECT-TYPE
    SYNTAX      SEQUENCE OF QueOnPortEntityStatusEntry
    MAX-ACCESS  not-accessible
    STATUS      current
    DESCRIPTION   "This table is used for reading non-configurable parameters of QUE on PORT entities."
    ::=  { queStatus 11 }

queOnPortEntityStatusEntry OBJECT-TYPE
    SYNTAX      QueOnPortEntityStatusEntry
    MAX-ACCESS  not-accessible
    STATUS      current
    DESCRIPTION   "Entry represents an assigned QUE on PORT entity."
    INDEX       {
                  queOnPortEntityIndexEth,
                  queOnPortEntityIndexPrio
                }
    ::=  { queOnPortEntityStatusTable 1 }

QueOnPortEntityStatusEntry ::=  SEQUENCE
  { queOnPortEntityStatusOper FspR7OperState,
    queOnPortEntityStatusSecondaryStates FspR7EntitySecondaryStates,
    queOnPortEntityStatusType FspR7InterfaceType,
    queOnPortEntityStatusAdmin FspR7AdminState,
    queOnPortEntityStatusAlias SnmpAdminString,
    queOnPortEntityStatusCirTrmt Unsigned32,
    queOnPortEntityStatusCbsTrmt Unsigned32 }

queOnPortEntityStatusOper OBJECT-TYPE
    SYNTAX      FspR7OperState
    MAX-ACCESS  read-only
    STATUS      current
    DESCRIPTION   "The Operational State will be displayed on the GUI with full name values;
         it will be differently displayed in TL1 SYNTAX according to TL1 display rules"
    ::=  { queOnPortEntityStatusEntry 1 }

queOnPortEntityStatusSecondaryStates OBJECT-TYPE
    SYNTAX      FspR7EntitySecondaryStates
    MAX-ACCESS  read-only
    STATUS      current
    DESCRIPTION   "Secondary states of an entity."
    ::=  { queOnPortEntityStatusEntry 2 }

queOnPortEntityStatusType OBJECT-TYPE
    SYNTAX      FspR7InterfaceType
    MAX-ACCESS  read-only
    STATUS      current
    DESCRIPTION   ""
    ::=  { queOnPortEntityStatusEntry 3 }

queOnPortEntityStatusAdmin OBJECT-TYPE
    SYNTAX      FspR7AdminState
    MAX-ACCESS  read-only
    STATUS      current
    DESCRIPTION
        "The Adminstrative State will be displayed in the GUI with full
         name values; it will be differently displayed in TL1 syntax according
         to TL1 display rules. The transaction into the UAS state requires
         a special destroy/delete function." 
    ::=  { queOnPortEntityStatusEntry 4 }

queOnPortEntityStatusAlias OBJECT-TYPE
    SYNTAX      SnmpAdminString
    MAX-ACCESS  read-only
    STATUS      current
    DESCRIPTION
        "User Applied Descriptor" 
    ::=  { queOnPortEntityStatusEntry 5 }

queOnPortEntityStatusCirTrmt OBJECT-TYPE
    SYNTAX      Unsigned32 
    UNITS       "Mbit/s"
    MAX-ACCESS  read-only
    STATUS      current
    DESCRIPTION
        "CIR (Committed Information Rate ) is used on Ethernet Interfaces with a policing function" 
    ::=  { queOnPortEntityStatusEntry 6 }

queOnPortEntityStatusCbsTrmt OBJECT-TYPE
    SYNTAX      Unsigned32 (0..25600 | 4294967295) 
    UNITS       "Kbytes"
    MAX-ACCESS  read-only
    STATUS      current
    DESCRIPTION
        "Committed Burst Size" 
    ::=  { queOnPortEntityStatusEntry 7 }

queOnFlowEntityStatusTable OBJECT-TYPE
    SYNTAX      SEQUENCE OF QueOnFlowEntityStatusEntry
    MAX-ACCESS  not-accessible
    STATUS      current
    DESCRIPTION   "This table is used for reading non-configurable parameters of QUE on FLOW entities."
    ::=  { queStatus 12 }

queOnFlowEntityStatusEntry OBJECT-TYPE
    SYNTAX      QueOnFlowEntityStatusEntry
    MAX-ACCESS  not-accessible
    STATUS      current
    DESCRIPTION   "Entry represents an assigned QUE on FLOW entity."
    INDEX       {
                  queOnFlowEntityIndexEth,
                  queOnFlowEntityIndexFlow,
                  queOnFlowEntityIndexPrio
                }
    ::=  { queOnFlowEntityStatusTable 1 }

QueOnFlowEntityStatusEntry ::=  SEQUENCE
  { queOnFlowEntityStatusOper FspR7OperState,
    queOnFlowEntityStatusSecondaryStates FspR7EntitySecondaryStates,
    queOnFlowEntityStatusType FspR7InterfaceType,
    queOnFlowEntityStatusAdmin FspR7AdminState,
    queOnFlowEntityStatusAlias SnmpAdminString,
    queOnFlowEntityStatusCirTrmt Unsigned32,
    queOnFlowEntityStatusCbsTrmt Unsigned32 }

queOnFlowEntityStatusOper OBJECT-TYPE
    SYNTAX      FspR7OperState
    MAX-ACCESS  read-only
    STATUS      current
    DESCRIPTION   "The Operational State will be displayed on the GUI with full name values;
         it will be differently displayed in TL1 SYNTAX according to TL1 display rules"
    ::=  { queOnFlowEntityStatusEntry 1 }

queOnFlowEntityStatusSecondaryStates OBJECT-TYPE
    SYNTAX      FspR7EntitySecondaryStates
    MAX-ACCESS  read-only
    STATUS      current
    DESCRIPTION   "Secondary states of an entity."
    ::=  { queOnFlowEntityStatusEntry 2 }

queOnFlowEntityStatusType OBJECT-TYPE
    SYNTAX      FspR7InterfaceType
    MAX-ACCESS  read-only
    STATUS      current
    DESCRIPTION   ""
    ::=  { queOnFlowEntityStatusEntry 3 }

queOnFlowEntityStatusAdmin OBJECT-TYPE
    SYNTAX      FspR7AdminState
    MAX-ACCESS  read-only
    STATUS      current
    DESCRIPTION
        "The Adminstrative State will be displayed in the GUI with full
         name values; it will be differently displayed in TL1 syntax according
         to TL1 display rules. The transaction into the UAS state requires
         a special destroy/delete function." 
    ::=  { queOnFlowEntityStatusEntry 4 }

queOnFlowEntityStatusAlias OBJECT-TYPE
    SYNTAX      SnmpAdminString
    MAX-ACCESS  read-only
    STATUS      current
    DESCRIPTION
        "User Applied Descriptor" 
    ::=  { queOnFlowEntityStatusEntry 5 }

queOnFlowEntityStatusCirTrmt OBJECT-TYPE
    SYNTAX      Unsigned32 
    UNITS       "Mbit/s"
    MAX-ACCESS  read-only
    STATUS      current
    DESCRIPTION
        "CIR (Committed Information Rate ) is used on Ethernet Interfaces with a policing function" 
    ::=  { queOnFlowEntityStatusEntry 6 }

queOnFlowEntityStatusCbsTrmt OBJECT-TYPE
    SYNTAX      Unsigned32 (0..25600 | 4294967295) 
    UNITS       "Kbytes"
    MAX-ACCESS  read-only
    STATUS      current
    DESCRIPTION
        "Committed Burst Size" 
    ::=  { queOnFlowEntityStatusEntry 7 }

queOnBridgeEntityStatusTable OBJECT-TYPE
    SYNTAX      SEQUENCE OF QueOnBridgeEntityStatusEntry
    MAX-ACCESS  not-accessible
    STATUS      current
    DESCRIPTION   "This table is used for reading non-configurable parameters of QUE on BRIDGE entities."
    ::=  { queStatus 13 }

queOnBridgeEntityStatusEntry OBJECT-TYPE
    SYNTAX      QueOnBridgeEntityStatusEntry
    MAX-ACCESS  not-accessible
    STATUS      current
    DESCRIPTION   "Entry represents an assigned QUE on BRIDGE entity."
    INDEX       {
                  queOnBridgeEntityIndex,
                  queOnBridgeEntitySvid,
                  queOnBridgeEntityPrio
                }
    ::=  { queOnBridgeEntityStatusTable 1 }

QueOnBridgeEntityStatusEntry ::=  SEQUENCE
  { queOnBridgeEntityStatusAdminState FspR7AdminState,
    queOnBridgeEntityStatusFacilityType FspR7InterfaceType,
    queOnBridgeEntityStatusFunction FspR7InterfaceFunction,
    queOnBridgeEntityStatusAlias SnmpAdminString,
    queOnBridgeEntityStatusCirTrmt Unsigned32,
    queOnBridgeEntityStatusCbsTrmt Unsigned32,
    queOnBridgeEntityStatusShapeState FspR7DisableEnable,
    queOnBridgeEntityStatusPmMode FspR7L2PmMode,
    queOnBridgeEntityStatusOper FspR7OperState,
    queOnBridgeEntityStatusSecondaryStates FspR7EntitySecondaryStates }

queOnBridgeEntityStatusAdminState OBJECT-TYPE
    SYNTAX      FspR7AdminState
    MAX-ACCESS  read-only
    STATUS      current
    DESCRIPTION
        "The Adminstrative State will be displayed in the GUI with full
         name values; it will be differently displayed in TL1 syntax according
         to TL1 display rules. The transaction into the UAS state requires
         a special destroy/delete function." 
    ::=  { queOnBridgeEntityStatusEntry 1 }

queOnBridgeEntityStatusFacilityType OBJECT-TYPE
    SYNTAX      FspR7InterfaceType
    MAX-ACCESS  read-only
    STATUS      current
    DESCRIPTION
        "The TYPE defines the transport service type as wrapper with wrapper layer termination OR else as payload" 
    ::=  { queOnBridgeEntityStatusEntry 2 }

queOnBridgeEntityStatusFunction OBJECT-TYPE
    SYNTAX      FspR7InterfaceFunction
    MAX-ACCESS  read-only
    STATUS      current
    DESCRIPTION
        "Interface Function" 
    ::=  { queOnBridgeEntityStatusEntry 3 }

queOnBridgeEntityStatusAlias OBJECT-TYPE
    SYNTAX      SnmpAdminString
    MAX-ACCESS  read-only
    STATUS      current
    DESCRIPTION
        "User Applied Descriptor" 
    ::=  { queOnBridgeEntityStatusEntry 4 }

queOnBridgeEntityStatusCirTrmt OBJECT-TYPE
    SYNTAX      Unsigned32 
    UNITS       "Mbit/s"
    MAX-ACCESS  read-only
    STATUS      current
    DESCRIPTION
        "CIR (Committed Information Rate ) is used on Ethernet Interfaces with a policing function" 
    ::=  { queOnBridgeEntityStatusEntry 5 }

queOnBridgeEntityStatusCbsTrmt OBJECT-TYPE
    SYNTAX      Unsigned32 (0..25600 | 4294967295) 
    UNITS       "Kbytes"
    MAX-ACCESS  read-only
    STATUS      current
    DESCRIPTION
        "Committed Burst Size" 
    ::=  { queOnBridgeEntityStatusEntry 6 }

queOnBridgeEntityStatusShapeState OBJECT-TYPE
    SYNTAX      FspR7DisableEnable
    MAX-ACCESS  read-only
    STATUS      current
    DESCRIPTION
        "Shape Enablement" 
    ::=  { queOnBridgeEntityStatusEntry 7 }

queOnBridgeEntityStatusPmMode OBJECT-TYPE
    SYNTAX      FspR7L2PmMode
    MAX-ACCESS  read-only
    STATUS      current
    DESCRIPTION
        "Mode of PM counters" 
    ::=  { queOnBridgeEntityStatusEntry 8 }

queOnBridgeEntityStatusOper OBJECT-TYPE
    SYNTAX      FspR7OperState
    MAX-ACCESS  read-only
    STATUS      current
    DESCRIPTION   "The Operational State will be displayed on the GUI with full name values;
         it will be differently displayed in TL1 SYNTAX according to TL1 display rules."
    ::=  { queOnBridgeEntityStatusEntry 9 }

queOnBridgeEntityStatusSecondaryStates OBJECT-TYPE
    SYNTAX      FspR7EntitySecondaryStates
    MAX-ACCESS  read-only
    STATUS      current
    DESCRIPTION   "Secondary states."
    ::=  { queOnBridgeEntityStatusEntry 10 }

bridgeEntityStatusTable OBJECT-TYPE
    SYNTAX      SEQUENCE OF BridgeEntityStatusEntry
    MAX-ACCESS  not-accessible
    STATUS      current
    DESCRIPTION   "This table lists all read-only parameters existing on BRIDGE entity."
    ::=  { bridgeStatus 11 }

bridgeEntityStatusEntry OBJECT-TYPE
    SYNTAX      BridgeEntityStatusEntry
    MAX-ACCESS  not-accessible
    STATUS      current
    DESCRIPTION   "Table entry presents BRIDGE entity."
    INDEX       {
                  bridgeEntityContainedIn,
                  bridgeEntitySvid
                }
    ::=  { bridgeEntityStatusTable 1 }

BridgeEntityStatusEntry ::=  SEQUENCE
  { bridgeEntityStatusFacilityType FspR7InterfaceType }

bridgeEntityStatusFacilityType OBJECT-TYPE
    SYNTAX      FspR7InterfaceType
    MAX-ACCESS  read-only
    STATUS      current
    DESCRIPTION   ""
    ::=  { bridgeEntityStatusEntry 1 }

bridgeEntityFlowTable OBJECT-TYPE
    SYNTAX      SEQUENCE OF BridgeEntityFlowEntry
    MAX-ACCESS  not-accessible
    STATUS      current
    DESCRIPTION   "This table lists all FLOW entities associated with particular BRIDGE entity."
    ::=  { bridgeStatus 12 }

bridgeEntityFlowEntry OBJECT-TYPE
    SYNTAX      BridgeEntityFlowEntry
    MAX-ACCESS  not-accessible
    STATUS      current
    DESCRIPTION   "Table entry presents BRIDGE entity. Third table index is the order number."
    INDEX       {
                  bridgeEntityContainedIn,
                  bridgeEntitySvid,
                  bridgeEntityFlowId
                }
    ::=  { bridgeEntityFlowTable 1 }

BridgeEntityFlowEntry ::=  SEQUENCE
  { bridgeEntityFlowId BridgeEntityIndex,
    bridgeEntityFlowIndex EntityIndex }

bridgeEntityFlowId OBJECT-TYPE
    SYNTAX      BridgeEntityIndex
    MAX-ACCESS  not-accessible
    STATUS      current
    DESCRIPTION   "Index of BRIDGE entity."
    ::=  { bridgeEntityFlowEntry 1 }

bridgeEntityFlowIndex OBJECT-TYPE
    SYNTAX      EntityIndex
    MAX-ACCESS  read-only
    STATUS      current
    DESCRIPTION   "First index of a flow entity referencing to eth/veth parent entity."
    ::=  { bridgeEntityFlowEntry 2 }

crossConnectionsProvisioningTable OBJECT-TYPE
    SYNTAX      SEQUENCE OF CrossConnectionsProvisioningEntry
    MAX-ACCESS  not-accessible
    STATUS      current
    DESCRIPTION   ""
    ::=  { layer2CrossConnections 11 }

crossConnectionsProvisioningEntry OBJECT-TYPE
    SYNTAX      CrossConnectionsProvisioningEntry
    MAX-ACCESS  not-accessible
    STATUS      current
    DESCRIPTION   ""
    INDEX       {
                  crossConnectionsProvisioningIndexEthFrom,
                  crossConnectionsProvisioningIndexFlowFrom,
                  crossConnectionsProvisioningIndexEthTo,
                  crossConnectionsProvisioningIndexFlowTo
                }
    ::=  { crossConnectionsProvisioningTable 1 }

CrossConnectionsProvisioningEntry ::=  SEQUENCE
  { crossConnectionsProvisioningIndexEthFrom EntityIndex,
    crossConnectionsProvisioningIndexFlowFrom EntityIndex,
    crossConnectionsProvisioningIndexEthTo EntityIndex,
    crossConnectionsProvisioningIndexFlowTo EntityIndex,
    crossConnectionsProvisioningRowStatus RowStatus,
    crossConnectionsProvisioningAlias SnmpAdminString,
    crossConnectionsProvisioningType FspR7InterfaceType,
    crossConnectionsProvisioningCrsType FspR7TypeCrs,
    crossConnectionsProvisioningConn FspR7Conn }

crossConnectionsProvisioningIndexEthFrom OBJECT-TYPE
    SYNTAX      EntityIndex
    MAX-ACCESS  accessible-for-notify
    STATUS      current
    DESCRIPTION   "First index of the flow entity being a start-point of the given cross-connection (from-point)."
    ::=  { crossConnectionsProvisioningEntry 1 }

crossConnectionsProvisioningIndexFlowFrom OBJECT-TYPE
    SYNTAX      EntityIndex
    MAX-ACCESS  accessible-for-notify
    STATUS      current
    DESCRIPTION   "Second index of the flow entity being a start-point of the given cross-connection (from-point)."
    ::=  { crossConnectionsProvisioningEntry 2 }

crossConnectionsProvisioningIndexEthTo OBJECT-TYPE
    SYNTAX      EntityIndex
    MAX-ACCESS  accessible-for-notify
    STATUS      current
    DESCRIPTION   "First index of the flow entity being an end-point of the given cross-connection (to-point)."
    ::=  { crossConnectionsProvisioningEntry 3 }

crossConnectionsProvisioningIndexFlowTo OBJECT-TYPE
    SYNTAX      EntityIndex
    MAX-ACCESS  accessible-for-notify
    STATUS      current
    DESCRIPTION   "Second index of the flow entity being an end-point of the given cross-connection (to-point)."
    ::=  { crossConnectionsProvisioningEntry 4 }

crossConnectionsProvisioningRowStatus OBJECT-TYPE
    SYNTAX      RowStatus
    MAX-ACCESS  read-write
    STATUS      current
    DESCRIPTION   "This object is used to create, or delete a row in this table."
    ::=  { crossConnectionsProvisioningEntry 5 }

crossConnectionsProvisioningAlias OBJECT-TYPE
    SYNTAX      SnmpAdminString
    MAX-ACCESS  read-write
    STATUS      current
    DESCRIPTION
        "User Applied Descriptor" 
    ::=  { crossConnectionsProvisioningEntry 6 }

crossConnectionsProvisioningType OBJECT-TYPE
    SYNTAX      FspR7InterfaceType
    MAX-ACCESS  read-write
    STATUS      current
    DESCRIPTION
        "The TYPE defines the transport service type as wrapper with wrapper layer termination OR else as payload" 
    ::=  { crossConnectionsProvisioningEntry 7 }

crossConnectionsProvisioningCrsType OBJECT-TYPE
    SYNTAX      FspR7TypeCrs
    MAX-ACCESS  read-write
    STATUS      current
    DESCRIPTION
        "Type of Cross-Connect" 
    ::=  { crossConnectionsProvisioningEntry 8 }

crossConnectionsProvisioningConn OBJECT-TYPE
    SYNTAX      FspR7Conn
    MAX-ACCESS  read-write
    STATUS      current
    DESCRIPTION
        "Bidirectional | Unidirectional" 
    ::=  { crossConnectionsProvisioningEntry 9 }

crossConnectionsProvisioningCapTable OBJECT-TYPE
    SYNTAX      SEQUENCE OF CrossConnectionsProvisioningCapEntry
    MAX-ACCESS  not-accessible
    STATUS      current
    DESCRIPTION   ""
    ::=  { layer2CrossConnections 12  }

crossConnectionsProvisioningCapEntry OBJECT-TYPE
    SYNTAX      CrossConnectionsProvisioningCapEntry
    MAX-ACCESS  not-accessible
    STATUS      current
    DESCRIPTION   ""
    INDEX       { crossConnectionsProvisioningIndexEthFrom,
                  crossConnectionsProvisioningIndexFlowFrom,
                  crossConnectionsProvisioningIndexEthTo,
                  crossConnectionsProvisioningIndexFlowTo }
    ::=  { crossConnectionsProvisioningCapTable 1 }

CrossConnectionsProvisioningCapEntry ::=  SEQUENCE
  { crossConnectionsProvisioningCapIndexEthFrom Integer32,
    crossConnectionsProvisioningCapIndexFlowFrom Integer32,
    crossConnectionsProvisioningCapIndexEthTo Integer32,
    crossConnectionsProvisioningCapIndexFlowTo Integer32,
    crossConnectionsProvisioningCapRowStatus FspR7RowStatusCaps,
    crossConnectionsProvisioningCapAlias Integer32,
    crossConnectionsProvisioningCapType FspR7InterfaceTypeCaps,
    crossConnectionsProvisioningCapCrsType FspR7TypeCrsCaps,
    crossConnectionsProvisioningCapConn FspR7ConnCaps }

crossConnectionsProvisioningCapIndexEthFrom OBJECT-TYPE
    SYNTAX      Integer32
    MAX-ACCESS  read-only
    STATUS      current
    DESCRIPTION   "First index of the flow entity being a start-point of the given cross-connection (from-point)."
    ::=  { crossConnectionsProvisioningCapEntry 1 }

crossConnectionsProvisioningCapIndexFlowFrom OBJECT-TYPE
    SYNTAX      Integer32
    MAX-ACCESS  read-only
    STATUS      current
    DESCRIPTION   "Second index of the flow entity being a start-point of the given cross-connection (from-point)."
    ::=  { crossConnectionsProvisioningCapEntry 2 }

crossConnectionsProvisioningCapIndexEthTo OBJECT-TYPE
    SYNTAX      Integer32
    MAX-ACCESS  read-only
    STATUS      current
    DESCRIPTION   "First index of the flow entity being an end-point of the given cross-connection (to-point)."
    ::=  { crossConnectionsProvisioningCapEntry 3 }

crossConnectionsProvisioningCapIndexFlowTo OBJECT-TYPE
    SYNTAX      Integer32
    MAX-ACCESS  read-only
    STATUS      current
    DESCRIPTION   "Second index of the flow entity being an end-point of the given cross-connection (to-point)."
    ::=  { crossConnectionsProvisioningCapEntry 4 }

crossConnectionsProvisioningCapRowStatus OBJECT-TYPE
    SYNTAX      FspR7RowStatusCaps
    MAX-ACCESS  read-only
    STATUS      current
    DESCRIPTION   "This object is used to create, or delete a row in this table."
    ::=  { crossConnectionsProvisioningCapEntry 5 }

crossConnectionsProvisioningCapAlias OBJECT-TYPE
    SYNTAX      Integer32
    MAX-ACCESS  read-only
    STATUS      current
    DESCRIPTION
        "User Applied Descriptor" 
    ::=  { crossConnectionsProvisioningCapEntry 6 }

crossConnectionsProvisioningCapType OBJECT-TYPE
    SYNTAX      FspR7InterfaceTypeCaps
    MAX-ACCESS  read-only
    STATUS      current
    DESCRIPTION
        "The TYPE defines the transport service type as wrapper with wrapper layer termination OR else as payload" 
    ::=  { crossConnectionsProvisioningCapEntry 7 }

crossConnectionsProvisioningCapCrsType OBJECT-TYPE
    SYNTAX      FspR7TypeCrsCaps
    MAX-ACCESS  read-only
    STATUS      current
    DESCRIPTION
        "Type of Cross-Connect" 
    ::=  { crossConnectionsProvisioningCapEntry 8 }

crossConnectionsProvisioningCapConn OBJECT-TYPE
    SYNTAX      FspR7ConnCaps
    MAX-ACCESS  read-only
    STATUS      current
    DESCRIPTION
        "Bidirectional | Unidirectional" 
    ::=  { crossConnectionsProvisioningCapEntry 9 }

crossConnectionsProvisioningDefaultsTable  OBJECT-TYPE
    SYNTAX      SEQUENCE OF CrossConnectionsProvisioningDefaultsEntry
    MAX-ACCESS  not-accessible
    STATUS      current
    DESCRIPTION   ""
    ::=  { layer2CrossConnections 13  }

crossConnectionsProvisioningDefaultsEntry OBJECT-TYPE
    SYNTAX      CrossConnectionsProvisioningDefaultsEntry
    MAX-ACCESS  not-accessible
    STATUS      current
    DESCRIPTION   ""
    INDEX       { crossConnectionsProvisioningIndexEthFrom,
                  crossConnectionsProvisioningIndexFlowFrom,
                  crossConnectionsProvisioningIndexEthTo,
                  crossConnectionsProvisioningIndexFlowTo }
    ::=  { crossConnectionsProvisioningDefaultsTable 1 }

CrossConnectionsProvisioningDefaultsEntry ::=  SEQUENCE
  { crossConnectionsProvisioningDefaultsIndexEthFrom EntityIndex,
    crossConnectionsProvisioningDefaultsIndexFlowFrom EntityIndex,
    crossConnectionsProvisioningDefaultsIndexEthTo EntityIndex,
    crossConnectionsProvisioningDefaultsIndexFlowTo EntityIndex,
    crossConnectionsProvisioningDefaultsRowStatus RowStatus,
    crossConnectionsProvisioningDefaultsAlias SnmpAdminString,
    crossConnectionsProvisioningDefaultsType FspR7InterfaceType,
    crossConnectionsProvisioningDefaultsCrsType FspR7TypeCrs,
    crossConnectionsProvisioningDefaultsConn FspR7Conn }

crossConnectionsProvisioningDefaultsIndexEthFrom OBJECT-TYPE
    SYNTAX      EntityIndex
    MAX-ACCESS  read-only
    STATUS      current
    DESCRIPTION   "First index of the flow entity being a start-point of the given cross-connection (from-point)."
    ::=  { crossConnectionsProvisioningDefaultsEntry 1 }

crossConnectionsProvisioningDefaultsIndexFlowFrom OBJECT-TYPE
    SYNTAX      EntityIndex
    MAX-ACCESS  read-only
    STATUS      current
    DESCRIPTION   "Second index of the flow entity being a start-point of the given cross-connection (from-point)."
    ::=  { crossConnectionsProvisioningDefaultsEntry 2 }

crossConnectionsProvisioningDefaultsIndexEthTo OBJECT-TYPE
    SYNTAX      EntityIndex
    MAX-ACCESS  read-only
    STATUS      current
    DESCRIPTION   "First index of the flow entity being an end-point of the given cross-connection (to-point)."
    ::=  { crossConnectionsProvisioningDefaultsEntry 3 }

crossConnectionsProvisioningDefaultsIndexFlowTo OBJECT-TYPE
    SYNTAX      EntityIndex
    MAX-ACCESS  read-only
    STATUS      current
    DESCRIPTION   "Second index of the flow entity being an end-point of the given cross-connection (to-point)."
    ::=  { crossConnectionsProvisioningDefaultsEntry 4 }

crossConnectionsProvisioningDefaultsRowStatus OBJECT-TYPE
    SYNTAX      RowStatus
    MAX-ACCESS  read-only
    STATUS      current
    DESCRIPTION   "This object is used to create, or delete a row in this table."
    ::=  { crossConnectionsProvisioningDefaultsEntry 5 }

crossConnectionsProvisioningDefaultsAlias OBJECT-TYPE
    SYNTAX      SnmpAdminString
    MAX-ACCESS  read-only
    STATUS      current
    DESCRIPTION
        "User Applied Descriptor" 
    ::=  { crossConnectionsProvisioningDefaultsEntry 6 }

crossConnectionsProvisioningDefaultsType OBJECT-TYPE
    SYNTAX      FspR7InterfaceType
    MAX-ACCESS  read-only
    STATUS      current
    DESCRIPTION
        "The TYPE defines the transport service type as wrapper with wrapper layer termination OR else as payload" 
    ::=  { crossConnectionsProvisioningDefaultsEntry 7 }

crossConnectionsProvisioningDefaultsCrsType OBJECT-TYPE
    SYNTAX      FspR7TypeCrs
    MAX-ACCESS  read-only
    STATUS      current
    DESCRIPTION
        "Type of Cross-Connect" 
    ::=  { crossConnectionsProvisioningDefaultsEntry 8 }

crossConnectionsProvisioningDefaultsConn OBJECT-TYPE
    SYNTAX      FspR7Conn
    MAX-ACCESS  read-only
    STATUS      current
    DESCRIPTION
        "Bidirectional | Unidirectional" 
    ::=  { crossConnectionsProvisioningDefaultsEntry 9 }

crossConnectionsConfigTable OBJECT-TYPE
    SYNTAX      SEQUENCE OF CrossConnectionsConfigEntry
    MAX-ACCESS  not-accessible
    STATUS      current
    DESCRIPTION   ""
    ::=  { layer2CrossConnections 14 }

crossConnectionsConfigEntry OBJECT-TYPE
    SYNTAX      CrossConnectionsConfigEntry
    MAX-ACCESS  not-accessible
    STATUS      current
    DESCRIPTION   ""
    INDEX       {
                  crossConnectionsProvisioningIndexEthFrom,
                  crossConnectionsProvisioningIndexFlowFrom,
                  crossConnectionsProvisioningIndexEthTo,
                  crossConnectionsProvisioningIndexFlowFrom
                }
    ::=  { crossConnectionsConfigTable 1 }

CrossConnectionsConfigEntry ::=  SEQUENCE
  { crossConnectionsConfigAlias SnmpAdminString }

crossConnectionsConfigAlias OBJECT-TYPE
    SYNTAX      SnmpAdminString
    MAX-ACCESS  read-write
    STATUS      current
    DESCRIPTION
        "User Applied Descriptor" 
    ::=  { crossConnectionsConfigEntry 1 }

crossConnectionsStatusTable OBJECT-TYPE
    SYNTAX      SEQUENCE OF CrossConnectionsStatusEntry
    MAX-ACCESS  not-accessible
    STATUS      current
    DESCRIPTION   ""
    ::=  { layer2CrossConnections 16 }

crossConnectionsStatusEntry OBJECT-TYPE
    SYNTAX      CrossConnectionsStatusEntry
    MAX-ACCESS  not-accessible
    STATUS      current
    DESCRIPTION   ""
    INDEX       {
                  crossConnectionsProvisioningIndexEthFrom,
                  crossConnectionsProvisioningIndexFlowFrom,
                  crossConnectionsProvisioningIndexEthTo,
                  crossConnectionsProvisioningIndexFlowTo
                }
    ::=  { crossConnectionsStatusTable 1 }

CrossConnectionsStatusEntry ::=  SEQUENCE
  { crossConnectionsStatusFromEth EntityIndex,
    crossConnectionsStatusToEth EntityIndex,
    crossConnectionsStatusType FspR7InterfaceType,
    crossConnectionsStatusCrsFunction FspR7FunctionCrs,
    crossConnectionsStatusCrsType FspR7TypeCrs,
    crossConnectionsStatusConn FspR7Conn }

crossConnectionsStatusFromEth OBJECT-TYPE
    SYNTAX      EntityIndex
    MAX-ACCESS  read-only
    STATUS      current
    DESCRIPTION
        "AID of a CH-C# or VCH instance." 
    ::=  { crossConnectionsStatusEntry 1 }

crossConnectionsStatusToEth OBJECT-TYPE
    SYNTAX      EntityIndex
    MAX-ACCESS  read-only
    STATUS      current
    DESCRIPTION
        "AID of a CH-C# or VCH instance." 
    ::=  { crossConnectionsStatusEntry 2 }

crossConnectionsStatusType OBJECT-TYPE
    SYNTAX      FspR7InterfaceType
    MAX-ACCESS  read-only
    STATUS      current
    DESCRIPTION
        "The TYPE defines the transport service type as wrapper with wrapper layer termination OR else as payload" 
    ::=  { crossConnectionsStatusEntry 3 }

crossConnectionsStatusCrsFunction OBJECT-TYPE
    SYNTAX      FspR7FunctionCrs
    MAX-ACCESS  read-only
    STATUS      current
    DESCRIPTION
        "Describes the Cross Connect Functionality" 
    ::=  { crossConnectionsStatusEntry 4 }

crossConnectionsStatusCrsType OBJECT-TYPE
    SYNTAX      FspR7TypeCrs
    MAX-ACCESS  read-only
    STATUS      current
    DESCRIPTION
        "Type of Cross-Connect" 
    ::=  { crossConnectionsStatusEntry 5 }

crossConnectionsStatusConn OBJECT-TYPE
    SYNTAX      FspR7Conn
    MAX-ACCESS  read-only
    STATUS      current
    DESCRIPTION
        "Bidirectional | Unidirectional" 
    ::=  { crossConnectionsStatusEntry 6 }

crossConnectionsPointsFromTable OBJECT-TYPE
    SYNTAX      SEQUENCE OF CrossConnectionsPointsFromEntry
    MAX-ACCESS  not-accessible
    STATUS      current
    DESCRIPTION   "This table contains unused flow startpoints which can be used as an
         element of cross-connection.
        "
    ::=  { layer2CrossConnections 17 }

crossConnectionsPointsFromEntry OBJECT-TYPE
    SYNTAX      CrossConnectionsPointsFromEntry
    MAX-ACCESS  not-accessible
    STATUS      current
    DESCRIPTION   ""
    INDEX       {
                  crossConnectionsProvisioningIndexEthFrom,
                  crossConnectionsProvisioningIndexFlowFrom
                }
    ::=  { crossConnectionsPointsFromTable 1 }

CrossConnectionsPointsFromEntry ::=  SEQUENCE
  { crossConnectionsPointsFromFlow EntityIndex }

crossConnectionsPointsFromFlow OBJECT-TYPE
    SYNTAX      EntityIndex
    MAX-ACCESS  read-only
    STATUS      current
    DESCRIPTION   "Unused flow value which can be used as a start-point
         for creating a cross-connection between two flows.
        "
    ::=  { crossConnectionsPointsFromEntry 1 }

crossConnectionsPointsToTable OBJECT-TYPE
    SYNTAX      SEQUENCE OF CrossConnectionsPointsToEntry
    MAX-ACCESS  not-accessible
    STATUS      current
    DESCRIPTION   "This table contains unused flow endpoints which can be used as an
         element of cross-connection.
        "
    ::=  { layer2CrossConnections 18 }

crossConnectionsPointsToEntry OBJECT-TYPE
    SYNTAX      CrossConnectionsPointsToEntry
    MAX-ACCESS  not-accessible
    STATUS      current
    DESCRIPTION   ""
    INDEX       {
                  crossConnectionsProvisioningIndexEthFrom,
                  crossConnectionsProvisioningIndexFlowFrom,
                  crossConnectionsProvisioningIndexEthTo,
                  crossConnectionsProvisioningIndexFlowTo
                }
    ::=  { crossConnectionsPointsToTable 1 }

CrossConnectionsPointsToEntry ::=  SEQUENCE
  { crossConnectionsPointsToFlow EntityIndex }

crossConnectionsPointsToFlow OBJECT-TYPE
    SYNTAX      EntityIndex
    MAX-ACCESS  read-only
    STATUS      current
    DESCRIPTION   "Unused flow value which can be used as an end-point
         for creating a cross-connection between two flows.
        "
    ::=  { crossConnectionsPointsToEntry 1 }

currentFlowEntityRx15minTable OBJECT-TYPE
    SYNTAX      SEQUENCE OF CurrentFlowEntityRx15minEntry
    MAX-ACCESS  not-accessible
    STATUS      current
    DESCRIPTION   ""
    ::=  { flowPerformanceMonitoring 1 }

currentFlowEntityRx15minEntry OBJECT-TYPE
    SYNTAX      CurrentFlowEntityRx15minEntry
    MAX-ACCESS  not-accessible
    STATUS      current
    DESCRIPTION   ""
    INDEX       {
                  flowEntityIndexEth,
                  flowEntityIndexFlow
                }
    ::=  { currentFlowEntityRx15minTable 1 }

CurrentFlowEntityRx15minEntry ::=  SEQUENCE
  { currentFlowEntityRx15minUnicastFramesPerEvcRcv Counter64String,
    currentFlowEntityRx15minMcBcFramesPerEvcRcv Counter64String,
    currentFlowEntityRx15minElapsedTime Integer32 }

currentFlowEntityRx15minUnicastFramesPerEvcRcv OBJECT-TYPE
    SYNTAX      Counter64String
    MAX-ACCESS  read-only
    STATUS      current
    DESCRIPTION
        "Received Unicast Frames per EVC(prior to policing)" 
    ::=  { currentFlowEntityRx15minEntry 1 }

currentFlowEntityRx15minMcBcFramesPerEvcRcv OBJECT-TYPE
    SYNTAX      Counter64String
    MAX-ACCESS  read-only
    STATUS      current
    DESCRIPTION
        "Received MC/BC Frames per EVC(prior to policing)" 
    ::=  { currentFlowEntityRx15minEntry 2 }

currentFlowEntityRx15minElapsedTime OBJECT-TYPE
    SYNTAX      Integer32 (0..9000 | -2147483648)
    MAX-ACCESS  read-only
    STATUS      current
    DESCRIPTION
        "Elapsed 15Min" 
    ::=  { currentFlowEntityRx15minEntry 3 }

currentFlowEntityRx1dayTable OBJECT-TYPE
    SYNTAX      SEQUENCE OF CurrentFlowEntityRx1dayEntry
    MAX-ACCESS  not-accessible
    STATUS      current
    DESCRIPTION   ""
    ::=  { flowPerformanceMonitoring 2 }

currentFlowEntityRx1dayEntry OBJECT-TYPE
    SYNTAX      CurrentFlowEntityRx1dayEntry
    MAX-ACCESS  not-accessible
    STATUS      current
    DESCRIPTION   ""
    INDEX       {
                  flowEntityIndexEth,
                  flowEntityIndexFlow
                }
    ::=  { currentFlowEntityRx1dayTable 1 }

CurrentFlowEntityRx1dayEntry ::=  SEQUENCE
  { currentFlowEntityRx1dayUnicastFramesPerEvcRcv Counter64String,
    currentFlowEntityRx1dayMcBcFramesPerEvcRcv Counter64String,
    currentFlowEntityRx1dayElapsedTime Integer32 }

currentFlowEntityRx1dayUnicastFramesPerEvcRcv OBJECT-TYPE
    SYNTAX      Counter64String
    MAX-ACCESS  read-only
    STATUS      current
    DESCRIPTION
        "Received Unicast Frames per EVC(prior to policing)" 
    ::=  { currentFlowEntityRx1dayEntry 1 }

currentFlowEntityRx1dayMcBcFramesPerEvcRcv OBJECT-TYPE
    SYNTAX      Counter64String
    MAX-ACCESS  read-only
    STATUS      current
    DESCRIPTION
        "Received MC/BC Frames per EVC(prior to policing)" 
    ::=  { currentFlowEntityRx1dayEntry 2 }

currentFlowEntityRx1dayElapsedTime OBJECT-TYPE
    SYNTAX      Integer32 (0..86400 | -2147483648)
    MAX-ACCESS  read-only
    STATUS      current
    DESCRIPTION
        "Elapsed 1Day" 
    ::=  { currentFlowEntityRx1dayEntry 3 }

intervalFlowEntityRx15minTable OBJECT-TYPE
    SYNTAX      SEQUENCE OF IntervalFlowEntityRx15minEntry
    MAX-ACCESS  not-accessible
    STATUS      current
    DESCRIPTION   ""
    ::=  { flowPerformanceMonitoring 3 }

intervalFlowEntityRx15minEntry OBJECT-TYPE
    SYNTAX      IntervalFlowEntityRx15minEntry
    MAX-ACCESS  not-accessible
    STATUS      current
    DESCRIPTION   ""
    INDEX       {
                  flowEntityIndexEth,
                  flowEntityIndexFlow,
                  intervalFlowEntityRx15minNumber
                }
    ::=  { intervalFlowEntityRx15minTable 1 }

IntervalFlowEntityRx15minEntry ::=  SEQUENCE
  { intervalFlowEntityRx15minNumber Integer32,
    intervalFlowEntityRx15minUnicastFramesPerEvcRcv Counter64String,
    intervalFlowEntityRx15minMcBcFramesPerEvcRcv Counter64String,
    intervalFlowEntityRx15minValidFlag TruthValue,
    intervalFlowEntityRx15minTimeStamp DateAndTime }

intervalFlowEntityRx15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalFlowEntityRx15minEntry 1 }

intervalFlowEntityRx15minUnicastFramesPerEvcRcv OBJECT-TYPE
    SYNTAX      Counter64String
    MAX-ACCESS  read-only
    STATUS      current
    DESCRIPTION
        "Received Unicast Frames per EVC(prior to policing)" 
    ::=  { intervalFlowEntityRx15minEntry 2 }

intervalFlowEntityRx15minMcBcFramesPerEvcRcv OBJECT-TYPE
    SYNTAX      Counter64String
    MAX-ACCESS  read-only
    STATUS      current
    DESCRIPTION
        "Received MC/BC Frames per EVC(prior to policing)" 
    ::=  { intervalFlowEntityRx15minEntry 3 }

intervalFlowEntityRx15minValidFlag OBJECT-TYPE
    SYNTAX      TruthValue
    MAX-ACCESS  read-only
    STATUS      current
    DESCRIPTION
        "Valid Flag" 
    ::=  { intervalFlowEntityRx15minEntry 4 }

intervalFlowEntityRx15minTimeStamp OBJECT-TYPE
    SYNTAX      DateAndTime
    MAX-ACCESS  read-only
    STATUS      current
    DESCRIPTION
        "Timestamp" 
    ::=  { intervalFlowEntityRx15minEntry 5 }

intervalFlowEntityRx1dayTable OBJECT-TYPE
    SYNTAX      SEQUENCE OF IntervalFlowEntityRx1dayEntry
    MAX-ACCESS  not-accessible
    STATUS      current
    DESCRIPTION   ""
    ::=  { flowPerformanceMonitoring 4 }

intervalFlowEntityRx1dayEntry OBJECT-TYPE
    SYNTAX      IntervalFlowEntityRx1dayEntry
    MAX-ACCESS  not-accessible
    STATUS      current
    DESCRIPTION   ""
    INDEX       {
                  flowEntityIndexEth,
                  flowEntityIndexFlow,
                  intervalFlowEntityRx1dayNumber
                }
    ::=  { intervalFlowEntityRx1dayTable 1 }

IntervalFlowEntityRx1dayEntry ::=  SEQUENCE
  { intervalFlowEntityRx1dayNumber Integer32,
    intervalFlowEntityRx1dayUnicastFramesPerEvcRcv Counter64String,
    intervalFlowEntityRx1dayMcBcFramesPerEvcRcv Counter64String,
    intervalFlowEntityRx1dayValidFlag TruthValue,
    intervalFlowEntityRx1dayTimeStamp DateAndTime }

intervalFlowEntityRx1dayNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalFlowEntityRx1dayEntry 1 }

intervalFlowEntityRx1dayUnicastFramesPerEvcRcv OBJECT-TYPE
    SYNTAX      Counter64String
    MAX-ACCESS  read-only
    STATUS      current
    DESCRIPTION
        "Received Unicast Frames per EVC(prior to policing)" 
    ::=  { intervalFlowEntityRx1dayEntry 2 }

intervalFlowEntityRx1dayMcBcFramesPerEvcRcv OBJECT-TYPE
    SYNTAX      Counter64String
    MAX-ACCESS  read-only
    STATUS      current
    DESCRIPTION
        "Received MC/BC Frames per EVC(prior to policing)" 
    ::=  { intervalFlowEntityRx1dayEntry 3 }

intervalFlowEntityRx1dayValidFlag OBJECT-TYPE
    SYNTAX      TruthValue
    MAX-ACCESS  read-only
    STATUS      current
    DESCRIPTION
        "Valid Flag" 
    ::=  { intervalFlowEntityRx1dayEntry 4 }

intervalFlowEntityRx1dayTimeStamp OBJECT-TYPE
    SYNTAX      DateAndTime
    MAX-ACCESS  read-only
    STATUS      current
    DESCRIPTION
        "Timestamp" 
    ::=  { intervalFlowEntityRx1dayEntry 5 }

currentFlowEntityTx15minTable OBJECT-TYPE
    SYNTAX      SEQUENCE OF CurrentFlowEntityTx15minEntry
    MAX-ACCESS  not-accessible
    STATUS      current
    DESCRIPTION   ""
    ::=  { flowPerformanceMonitoring 5 }

currentFlowEntityTx15minEntry OBJECT-TYPE
    SYNTAX      CurrentFlowEntityTx15minEntry
    MAX-ACCESS  not-accessible
    STATUS      current
    DESCRIPTION   ""
    INDEX       {
                  flowEntityIndexEth,
                  flowEntityIndexFlow
                }
    ::=  { currentFlowEntityTx15minTable 1 }

CurrentFlowEntityTx15minEntry ::=  SEQUENCE
  { currentFlowEntityTx15minUnicastFramesPerEvcTrmt Counter64String,
    currentFlowEntityTx15minMcBcFramesPerEvcTrmt Counter64String,
    currentFlowEntityTx15minElapsedTime Integer32 }

currentFlowEntityTx15minUnicastFramesPerEvcTrmt OBJECT-TYPE
    SYNTAX      Counter64String
    MAX-ACCESS  read-only
    STATUS      current
    DESCRIPTION
        "Transmitted Unicast Frames per EVC(prior to policing)" 
    ::=  { currentFlowEntityTx15minEntry 1 }

currentFlowEntityTx15minMcBcFramesPerEvcTrmt OBJECT-TYPE
    SYNTAX      Counter64String
    MAX-ACCESS  read-only
    STATUS      current
    DESCRIPTION
        "Transmitted MC/BC Frames per EVC(prior to policing)" 
    ::=  { currentFlowEntityTx15minEntry 2 }

currentFlowEntityTx15minElapsedTime OBJECT-TYPE
    SYNTAX      Integer32 (0..9000 | -2147483648)
    MAX-ACCESS  read-only
    STATUS      current
    DESCRIPTION
        "Elapsed 15Min" 
    ::=  { currentFlowEntityTx15minEntry 3 }

currentFlowEntityTx1dayTable OBJECT-TYPE
    SYNTAX      SEQUENCE OF CurrentFlowEntityTx1dayEntry
    MAX-ACCESS  not-accessible
    STATUS      current
    DESCRIPTION   ""
    ::=  { flowPerformanceMonitoring 6 }

currentFlowEntityTx1dayEntry OBJECT-TYPE
    SYNTAX      CurrentFlowEntityTx1dayEntry
    MAX-ACCESS  not-accessible
    STATUS      current
    DESCRIPTION   ""
    INDEX       {
                  flowEntityIndexEth,
                  flowEntityIndexFlow
                }
    ::=  { currentFlowEntityTx1dayTable 1 }

CurrentFlowEntityTx1dayEntry ::=  SEQUENCE
  { currentFlowEntityTx1dayUnicastFramesPerEvcTrmt Counter64String,
    currentFlowEntityTx1dayMcBcFramesPerEvcTrmt Counter64String,
    currentFlowEntityTx1dayElapsedTime Integer32 }

currentFlowEntityTx1dayUnicastFramesPerEvcTrmt OBJECT-TYPE
    SYNTAX      Counter64String
    MAX-ACCESS  read-only
    STATUS      current
    DESCRIPTION
        "Transmitted Unicast Frames per EVC(prior to policing)" 
    ::=  { currentFlowEntityTx1dayEntry 1 }

currentFlowEntityTx1dayMcBcFramesPerEvcTrmt OBJECT-TYPE
    SYNTAX      Counter64String
    MAX-ACCESS  read-only
    STATUS      current
    DESCRIPTION
        "Transmitted MC/BC Frames per EVC(prior to policing)" 
    ::=  { currentFlowEntityTx1dayEntry 2 }

currentFlowEntityTx1dayElapsedTime OBJECT-TYPE
    SYNTAX      Integer32 (0..86400 | -2147483648)
    MAX-ACCESS  read-only
    STATUS      current
    DESCRIPTION
        "Elapsed 1Day" 
    ::=  { currentFlowEntityTx1dayEntry 3 }

intervalFlowEntityTx15minTable OBJECT-TYPE
    SYNTAX      SEQUENCE OF IntervalFlowEntityTx15minEntry
    MAX-ACCESS  not-accessible
    STATUS      current
    DESCRIPTION   ""
    ::=  { flowPerformanceMonitoring 7 }

intervalFlowEntityTx15minEntry OBJECT-TYPE
    SYNTAX      IntervalFlowEntityTx15minEntry
    MAX-ACCESS  not-accessible
    STATUS      current
    DESCRIPTION   ""
    INDEX       {
                  flowEntityIndexEth,
                  flowEntityIndexFlow,
                  intervalFlowEntityTx15minNumber
                }
    ::=  { intervalFlowEntityTx15minTable 1 }

IntervalFlowEntityTx15minEntry ::=  SEQUENCE
  { intervalFlowEntityTx15minNumber Integer32,
    intervalFlowEntityTx15minUnicastFramesPerEvcTrmt Counter64String,
    intervalFlowEntityTx15minMcBcFramesPerEvcTrmt Counter64String,
    intervalFlowEntityTx15minValidFlag TruthValue,
    intervalFlowEntityTx15minTimeStamp DateAndTime }

intervalFlowEntityTx15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalFlowEntityTx15minEntry 1 }

intervalFlowEntityTx15minUnicastFramesPerEvcTrmt OBJECT-TYPE
    SYNTAX      Counter64String
    MAX-ACCESS  read-only
    STATUS      current
    DESCRIPTION
        "Transmitted Unicast Frames per EVC(prior to policing)" 
    ::=  { intervalFlowEntityTx15minEntry 2 }

intervalFlowEntityTx15minMcBcFramesPerEvcTrmt OBJECT-TYPE
    SYNTAX      Counter64String
    MAX-ACCESS  read-only
    STATUS      current
    DESCRIPTION
        "Transmitted MC/BC Frames per EVC(prior to policing)" 
    ::=  { intervalFlowEntityTx15minEntry 3 }

intervalFlowEntityTx15minValidFlag OBJECT-TYPE
    SYNTAX      TruthValue
    MAX-ACCESS  read-only
    STATUS      current
    DESCRIPTION
        "Valid Flag" 
    ::=  { intervalFlowEntityTx15minEntry 4 }

intervalFlowEntityTx15minTimeStamp OBJECT-TYPE
    SYNTAX      DateAndTime
    MAX-ACCESS  read-only
    STATUS      current
    DESCRIPTION
        "Timestamp" 
    ::=  { intervalFlowEntityTx15minEntry 5 }

intervalFlowEntityTx1dayTable OBJECT-TYPE
    SYNTAX      SEQUENCE OF IntervalFlowEntityTx1dayEntry
    MAX-ACCESS  not-accessible
    STATUS      current
    DESCRIPTION   ""
    ::=  { flowPerformanceMonitoring 8 }

intervalFlowEntityTx1dayEntry OBJECT-TYPE
    SYNTAX      IntervalFlowEntityTx1dayEntry
    MAX-ACCESS  not-accessible
    STATUS      current
    DESCRIPTION   ""
    INDEX       {
                  flowEntityIndexEth,
                  flowEntityIndexFlow,
                  intervalFlowEntityTx15minNumber
                }
    ::=  { intervalFlowEntityTx1dayTable 1 }

IntervalFlowEntityTx1dayEntry ::=  SEQUENCE
  { intervalFlowEntityTx1dayNumber Integer32,
    intervalFlowEntityTx1dayUnicastFramesPerEvcTrmt Counter64String,
    intervalFlowEntityTx1dayMcBcFramesPerEvcTrmt Counter64String,
    intervalFlowEntityTx1dayValidFlag TruthValue,
    intervalFlowEntityTx1dayTimeStamp DateAndTime }

intervalFlowEntityTx1dayNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalFlowEntityTx1dayEntry 1 }

intervalFlowEntityTx1dayUnicastFramesPerEvcTrmt OBJECT-TYPE
    SYNTAX      Counter64String
    MAX-ACCESS  read-only
    STATUS      current
    DESCRIPTION
        "Transmitted Unicast Frames per EVC(prior to policing)" 
    ::=  { intervalFlowEntityTx1dayEntry 2 }

intervalFlowEntityTx1dayMcBcFramesPerEvcTrmt OBJECT-TYPE
    SYNTAX      Counter64String
    MAX-ACCESS  read-only
    STATUS      current
    DESCRIPTION
        "Transmitted MC/BC Frames per EVC(prior to policing)" 
    ::=  { intervalFlowEntityTx1dayEntry 3 }

intervalFlowEntityTx1dayValidFlag OBJECT-TYPE
    SYNTAX      TruthValue
    MAX-ACCESS  read-only
    STATUS      current
    DESCRIPTION
        "Valid Flag" 
    ::=  { intervalFlowEntityTx1dayEntry 4 }

intervalFlowEntityTx1dayTimeStamp OBJECT-TYPE
    SYNTAX      DateAndTime
    MAX-ACCESS  read-only
    STATUS      current
    DESCRIPTION
        "Timestamp" 
    ::=  { intervalFlowEntityTx1dayEntry 5 }

currentpolicerOnFlowEntity15minTable OBJECT-TYPE
    SYNTAX      SEQUENCE OF CurrentpolicerOnFlowEntity15minEntry
    MAX-ACCESS  not-accessible
    STATUS      current
    DESCRIPTION   ""
    ::=  { policerPerformanceMonitoring 5 }

currentpolicerOnFlowEntity15minEntry OBJECT-TYPE
    SYNTAX      CurrentpolicerOnFlowEntity15minEntry
    MAX-ACCESS  not-accessible
    STATUS      current
    DESCRIPTION   ""
    INDEX       {
                  policerOnFlowEntityIndexEth,
                  policerOnFlowEntityIndexFlow,
                  policerOnFlowEntityIndexPolicer
                }
    ::=  { currentpolicerOnFlowEntity15minTable 1 }

CurrentpolicerOnFlowEntity15minEntry ::=  SEQUENCE
  { currentpolicerOnFlowEntity15minBytesMarkedGreen Counter64String,
    currentpolicerOnFlowEntity15minFramesMarkedGreen Counter64String,
    currentpolicerOnFlowEntity15minBytesMarkedRed Counter64String,
    currentpolicerOnFlowEntity15minFramesMarkedRed Counter64String,
    currentpolicerOnFlowEntity15minElapsedTime Integer32 }

currentpolicerOnFlowEntity15minBytesMarkedGreen OBJECT-TYPE
    SYNTAX      Counter64String
    MAX-ACCESS  read-only
    STATUS      current
    DESCRIPTION
        "Bytes marked green per EVC COS" 
    ::=  { currentpolicerOnFlowEntity15minEntry 1 }

currentpolicerOnFlowEntity15minFramesMarkedGreen OBJECT-TYPE
    SYNTAX      Counter64String
    MAX-ACCESS  read-only
    STATUS      current
    DESCRIPTION
        "Frames marked green per EVC COS" 
    ::=  { currentpolicerOnFlowEntity15minEntry 2 }

currentpolicerOnFlowEntity15minBytesMarkedRed OBJECT-TYPE
    SYNTAX      Counter64String
    MAX-ACCESS  read-only
    STATUS      current
    DESCRIPTION
        "Bytes marked red per EVC COS" 
    ::=  { currentpolicerOnFlowEntity15minEntry 3 }

currentpolicerOnFlowEntity15minFramesMarkedRed OBJECT-TYPE
    SYNTAX      Counter64String
    MAX-ACCESS  read-only
    STATUS      current
    DESCRIPTION
        "Frames marked red per EVC COS" 
    ::=  { currentpolicerOnFlowEntity15minEntry 4 }

currentpolicerOnFlowEntity15minElapsedTime OBJECT-TYPE
    SYNTAX      Integer32 (0..9000 | -2147483648)
    MAX-ACCESS  read-only
    STATUS      current
    DESCRIPTION
        "Elapsed 15Min" 
    ::=  { currentpolicerOnFlowEntity15minEntry 5 }

currentpolicerOnFlowEntity1dayTable OBJECT-TYPE
    SYNTAX      SEQUENCE OF CurrentpolicerOnFlowEntity1dayEntry
    MAX-ACCESS  not-accessible
    STATUS      current
    DESCRIPTION   ""
    ::=  { policerPerformanceMonitoring 6 }

currentpolicerOnFlowEntity1dayEntry OBJECT-TYPE
    SYNTAX      CurrentpolicerOnFlowEntity1dayEntry
    MAX-ACCESS  not-accessible
    STATUS      current
    DESCRIPTION   ""
    INDEX       {
                  policerOnFlowEntityIndexEth,
                  policerOnFlowEntityIndexFlow,
                  policerOnFlowEntityIndexPolicer
                }
    ::=  { currentpolicerOnFlowEntity1dayTable 1 }

CurrentpolicerOnFlowEntity1dayEntry ::=  SEQUENCE
  { currentpolicerOnFlowEntity1dayBytesMarkedGreen Counter64String,
    currentpolicerOnFlowEntity1dayFramesMarkedGreen Counter64String,
    currentpolicerOnFlowEntity1dayBytesMarkedRed Counter64String,
    currentpolicerOnFlowEntity1dayFramesMarkedRed Counter64String,
    currentpolicerOnFlowEntity1dayElapsedTime Integer32 }

currentpolicerOnFlowEntity1dayBytesMarkedGreen OBJECT-TYPE
    SYNTAX      Counter64String
    MAX-ACCESS  read-only
    STATUS      current
    DESCRIPTION
        "Bytes marked green per EVC COS" 
    ::=  { currentpolicerOnFlowEntity1dayEntry 1 }

currentpolicerOnFlowEntity1dayFramesMarkedGreen OBJECT-TYPE
    SYNTAX      Counter64String
    MAX-ACCESS  read-only
    STATUS      current
    DESCRIPTION
        "Frames marked green per EVC COS" 
    ::=  { currentpolicerOnFlowEntity1dayEntry 2 }

currentpolicerOnFlowEntity1dayBytesMarkedRed OBJECT-TYPE
    SYNTAX      Counter64String
    MAX-ACCESS  read-only
    STATUS      current
    DESCRIPTION
        "Bytes marked red per EVC COS" 
    ::=  { currentpolicerOnFlowEntity1dayEntry 3 }

currentpolicerOnFlowEntity1dayFramesMarkedRed OBJECT-TYPE
    SYNTAX      Counter64String
    MAX-ACCESS  read-only
    STATUS      current
    DESCRIPTION
        "Frames marked red per EVC COS" 
    ::=  { currentpolicerOnFlowEntity1dayEntry 4 }

currentpolicerOnFlowEntity1dayElapsedTime OBJECT-TYPE
    SYNTAX      Integer32 (0..86400 | -2147483648)
    MAX-ACCESS  read-only
    STATUS      current
    DESCRIPTION
        "Elapsed 1Day" 
    ::=  { currentpolicerOnFlowEntity1dayEntry 5 }

intervalpolicerOnFlowEntity15minTable OBJECT-TYPE
    SYNTAX      SEQUENCE OF IntervalpolicerOnFlowEntity15minEntry
    MAX-ACCESS  not-accessible
    STATUS      current
    DESCRIPTION   ""
    ::=  { policerPerformanceMonitoring 7 }

intervalpolicerOnFlowEntity15minEntry OBJECT-TYPE
    SYNTAX      IntervalpolicerOnFlowEntity15minEntry
    MAX-ACCESS  not-accessible
    STATUS      current
    DESCRIPTION   ""
    INDEX       {
                  policerOnFlowEntityIndexEth,
                  policerOnFlowEntityIndexFlow,
                  policerOnFlowEntityIndexPolicer,
                  intervalpolicerOnFlowEntity15minNumber
                }
    ::=  { intervalpolicerOnFlowEntity15minTable 1 }

IntervalpolicerOnFlowEntity15minEntry ::=  SEQUENCE
  { intervalpolicerOnFlowEntity15minNumber Integer32,
    intervalpolicerOnFlowEntity15minBytesMarkedGreen Counter64String,
    intervalpolicerOnFlowEntity15minFramesMarkedGreen Counter64String,
    intervalpolicerOnFlowEntity15minBytesMarkedRed Counter64String,
    intervalpolicerOnFlowEntity15minFramesMarkedRed Counter64String,
    intervalpolicerOnFlowEntity15minValidFlag TruthValue,
    intervalpolicerOnFlowEntity15minTimeStamp DateAndTime }

intervalpolicerOnFlowEntity15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalpolicerOnFlowEntity15minEntry 1 }

intervalpolicerOnFlowEntity15minBytesMarkedGreen OBJECT-TYPE
    SYNTAX      Counter64String
    MAX-ACCESS  read-only
    STATUS      current
    DESCRIPTION
        "Bytes marked green per EVC COS" 
    ::=  { intervalpolicerOnFlowEntity15minEntry 2 }

intervalpolicerOnFlowEntity15minFramesMarkedGreen OBJECT-TYPE
    SYNTAX      Counter64String
    MAX-ACCESS  read-only
    STATUS      current
    DESCRIPTION
        "Frames marked green per EVC COS" 
    ::=  { intervalpolicerOnFlowEntity15minEntry 3 }

intervalpolicerOnFlowEntity15minBytesMarkedRed OBJECT-TYPE
    SYNTAX      Counter64String
    MAX-ACCESS  read-only
    STATUS      current
    DESCRIPTION
        "Bytes marked red per EVC COS" 
    ::=  { intervalpolicerOnFlowEntity15minEntry 4 }

intervalpolicerOnFlowEntity15minFramesMarkedRed OBJECT-TYPE
    SYNTAX      Counter64String
    MAX-ACCESS  read-only
    STATUS      current
    DESCRIPTION
        "Frames marked red per EVC COS" 
    ::=  { intervalpolicerOnFlowEntity15minEntry 5 }

intervalpolicerOnFlowEntity15minValidFlag OBJECT-TYPE
    SYNTAX      TruthValue
    MAX-ACCESS  read-only
    STATUS      current
    DESCRIPTION
        "Valid Flag" 
    ::=  { intervalpolicerOnFlowEntity15minEntry 6 }

intervalpolicerOnFlowEntity15minTimeStamp OBJECT-TYPE
    SYNTAX      DateAndTime
    MAX-ACCESS  read-only
    STATUS      current
    DESCRIPTION
        "Timestamp" 
    ::=  { intervalpolicerOnFlowEntity15minEntry 7 }

intervalpolicerOnFlowEntity1dayTable OBJECT-TYPE
    SYNTAX      SEQUENCE OF IntervalpolicerOnFlowEntity1dayEntry
    MAX-ACCESS  not-accessible
    STATUS      current
    DESCRIPTION   ""
    ::=  { policerPerformanceMonitoring 8 }

intervalpolicerOnFlowEntity1dayEntry OBJECT-TYPE
    SYNTAX      IntervalpolicerOnFlowEntity1dayEntry
    MAX-ACCESS  not-accessible
    STATUS      current
    DESCRIPTION   ""
    INDEX       {
                  policerOnFlowEntityIndexEth,
                  policerOnFlowEntityIndexFlow,
                  policerOnFlowEntityIndexPolicer,
                  intervalpolicerOnFlowEntity1dayNumber
                }
    ::=  { intervalpolicerOnFlowEntity1dayTable 1 }

IntervalpolicerOnFlowEntity1dayEntry ::=  SEQUENCE
  { intervalpolicerOnFlowEntity1dayNumber Integer32,
    intervalpolicerOnFlowEntity1dayBytesMarkedGreen Counter64String,
    intervalpolicerOnFlowEntity1dayFramesMarkedGreen Counter64String,
    intervalpolicerOnFlowEntity1dayBytesMarkedRed Counter64String,
    intervalpolicerOnFlowEntity1dayFramesMarkedRed Counter64String,
    intervalpolicerOnFlowEntity1dayValidFlag TruthValue,
    intervalpolicerOnFlowEntity1dayTimeStamp DateAndTime }

intervalpolicerOnFlowEntity1dayNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalpolicerOnFlowEntity1dayEntry 1 }

intervalpolicerOnFlowEntity1dayBytesMarkedGreen OBJECT-TYPE
    SYNTAX      Counter64String
    MAX-ACCESS  read-only
    STATUS      current
    DESCRIPTION
        "Bytes marked green per EVC COS" 
    ::=  { intervalpolicerOnFlowEntity1dayEntry 2 }

intervalpolicerOnFlowEntity1dayFramesMarkedGreen OBJECT-TYPE
    SYNTAX      Counter64String
    MAX-ACCESS  read-only
    STATUS      current
    DESCRIPTION
        "Frames marked green per EVC COS" 
    ::=  { intervalpolicerOnFlowEntity1dayEntry 3 }

intervalpolicerOnFlowEntity1dayBytesMarkedRed OBJECT-TYPE
    SYNTAX      Counter64String
    MAX-ACCESS  read-only
    STATUS      current
    DESCRIPTION
        "Bytes marked red per EVC COS" 
    ::=  { intervalpolicerOnFlowEntity1dayEntry 4 }

intervalpolicerOnFlowEntity1dayFramesMarkedRed OBJECT-TYPE
    SYNTAX      Counter64String
    MAX-ACCESS  read-only
    STATUS      current
    DESCRIPTION
        "Frames marked red per EVC COS" 
    ::=  { intervalpolicerOnFlowEntity1dayEntry 5 }

intervalpolicerOnFlowEntity1dayValidFlag OBJECT-TYPE
    SYNTAX      TruthValue
    MAX-ACCESS  read-only
    STATUS      current
    DESCRIPTION
        "Valid Flag" 
    ::=  { intervalpolicerOnFlowEntity1dayEntry 6 }

intervalpolicerOnFlowEntity1dayTimeStamp OBJECT-TYPE
    SYNTAX      DateAndTime
    MAX-ACCESS  read-only
    STATUS      current
    DESCRIPTION
        "Timestamp" 
    ::=  { intervalpolicerOnFlowEntity1dayEntry 7 }

currentQueOnPortEntity15minTable OBJECT-TYPE
    SYNTAX      SEQUENCE OF CurrentQueOnPortEntity15minEntry
    MAX-ACCESS  not-accessible
    STATUS      current
    DESCRIPTION   ""
    ::=  { quePerformanceMonitoring 1 }

currentQueOnPortEntity15minEntry OBJECT-TYPE
    SYNTAX      CurrentQueOnPortEntity15minEntry
    MAX-ACCESS  not-accessible
    STATUS      current
    DESCRIPTION   ""
    INDEX       {
                  queOnPortEntityIndexEth,
                  queOnPortEntityIndexPrio
                }
    ::=  { currentQueOnPortEntity15minTable 1 }

CurrentQueOnPortEntity15minEntry ::=  SEQUENCE
  { currentQueOnPortEntity15minBytesDroppedBufOverflow Counter64String,
    currentQueOnPortEntity15minFramesDroppedBufOverflow Counter64String,
    currentQueOnPortEntity15minElapsedTime Integer32 }

currentQueOnPortEntity15minBytesDroppedBufOverflow OBJECT-TYPE
    SYNTAX      Counter64String
    MAX-ACCESS  read-only
    STATUS      current
    DESCRIPTION
        "Bytes dropped due to buffer overflow" 
    ::=  { currentQueOnPortEntity15minEntry 1 }

currentQueOnPortEntity15minFramesDroppedBufOverflow OBJECT-TYPE
    SYNTAX      Counter64String
    MAX-ACCESS  read-only
    STATUS      current
    DESCRIPTION
        "Frames dropped due to buffer overflow" 
    ::=  { currentQueOnPortEntity15minEntry 2 }

currentQueOnPortEntity15minElapsedTime OBJECT-TYPE
    SYNTAX      Integer32 (0..9000 | -2147483648)
    MAX-ACCESS  read-only
    STATUS      current
    DESCRIPTION
        "Elapsed 15Min" 
    ::=  { currentQueOnPortEntity15minEntry 3 }

currentQueOnPortEntity1dayTable OBJECT-TYPE
    SYNTAX      SEQUENCE OF CurrentQueOnPortEntity1dayEntry
    MAX-ACCESS  not-accessible
    STATUS      current
    DESCRIPTION   ""
    ::=  { quePerformanceMonitoring 2 }

currentQueOnPortEntity1dayEntry OBJECT-TYPE
    SYNTAX      CurrentQueOnPortEntity1dayEntry
    MAX-ACCESS  not-accessible
    STATUS      current
    DESCRIPTION   ""
    INDEX       {
                  queOnPortEntityIndexEth,
                  queOnPortEntityIndexPrio
                }
    ::=  { currentQueOnPortEntity1dayTable 1 }

CurrentQueOnPortEntity1dayEntry ::=  SEQUENCE
  { currentQueOnPortEntity1dayBytesDroppedBufOverflow Counter64String,
    currentQueOnPortEntity1dayFramesDroppedBufOverflow Counter64String,
    currentQueOnPortEntity1dayElapsedTime Integer32 }

currentQueOnPortEntity1dayBytesDroppedBufOverflow OBJECT-TYPE
    SYNTAX      Counter64String
    MAX-ACCESS  read-only
    STATUS      current
    DESCRIPTION
        "Bytes dropped due to buffer overflow" 
    ::=  { currentQueOnPortEntity1dayEntry 1 }

currentQueOnPortEntity1dayFramesDroppedBufOverflow OBJECT-TYPE
    SYNTAX      Counter64String
    MAX-ACCESS  read-only
    STATUS      current
    DESCRIPTION
        "Frames dropped due to buffer overflow" 
    ::=  { currentQueOnPortEntity1dayEntry 2 }

currentQueOnPortEntity1dayElapsedTime OBJECT-TYPE
    SYNTAX      Integer32 (0..86400 | -2147483648)
    MAX-ACCESS  read-only
    STATUS      current
    DESCRIPTION
        "Elapsed 1Day" 
    ::=  { currentQueOnPortEntity1dayEntry 3 }

intervalQueOnPortEntity15minTable OBJECT-TYPE
    SYNTAX      SEQUENCE OF IntervalQueOnPortEntity15minEntry
    MAX-ACCESS  not-accessible
    STATUS      current
    DESCRIPTION   ""
    ::=  { quePerformanceMonitoring 3 }

intervalQueOnPortEntity15minEntry OBJECT-TYPE
    SYNTAX      IntervalQueOnPortEntity15minEntry
    MAX-ACCESS  not-accessible
    STATUS      current
    DESCRIPTION   ""
    INDEX       {
                  queOnPortEntityIndexEth,
                  queOnPortEntityIndexPrio,
                  intervalQueOnPortEntity15minNumber
                }
    ::=  { intervalQueOnPortEntity15minTable 1 }

IntervalQueOnPortEntity15minEntry ::=  SEQUENCE
  { intervalQueOnPortEntity15minNumber Integer32,
    intervalQueOnPortEntity15minBytesDroppedBufOverflow Counter64String,
    intervalQueOnPortEntity15minFramesDroppedBufOverflow Counter64String,
    intervalQueOnPortEntity15minValidFlag TruthValue,
    intervalQueOnPortEntity15minTimeStamp DateAndTime }

intervalQueOnPortEntity15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalQueOnPortEntity15minEntry 1 }

intervalQueOnPortEntity15minBytesDroppedBufOverflow OBJECT-TYPE
    SYNTAX      Counter64String
    MAX-ACCESS  read-only
    STATUS      current
    DESCRIPTION
        "Bytes dropped due to buffer overflow" 
    ::=  { intervalQueOnPortEntity15minEntry 2 }

intervalQueOnPortEntity15minFramesDroppedBufOverflow OBJECT-TYPE
    SYNTAX      Counter64String
    MAX-ACCESS  read-only
    STATUS      current
    DESCRIPTION
        "Frames dropped due to buffer overflow" 
    ::=  { intervalQueOnPortEntity15minEntry 3 }

intervalQueOnPortEntity15minValidFlag OBJECT-TYPE
    SYNTAX      TruthValue
    MAX-ACCESS  read-only
    STATUS      current
    DESCRIPTION
        "Valid Flag" 
    ::=  { intervalQueOnPortEntity15minEntry 4 }

intervalQueOnPortEntity15minTimeStamp OBJECT-TYPE
    SYNTAX      DateAndTime
    MAX-ACCESS  read-only
    STATUS      current
    DESCRIPTION
        "Timestamp" 
    ::=  { intervalQueOnPortEntity15minEntry 5 }

intervalQueOnPortEntity1dayTable OBJECT-TYPE
    SYNTAX      SEQUENCE OF IntervalQueOnPortEntity1dayEntry
    MAX-ACCESS  not-accessible
    STATUS      current
    DESCRIPTION   ""
    ::=  { quePerformanceMonitoring 4 }

intervalQueOnPortEntity1dayEntry OBJECT-TYPE
    SYNTAX      IntervalQueOnPortEntity1dayEntry
    MAX-ACCESS  not-accessible
    STATUS      current
    DESCRIPTION   ""
    INDEX       {
                  queOnPortEntityIndexEth,
                  queOnPortEntityIndexPrio,
                  intervalQueOnPortEntity1dayNumber
                }
    ::=  { intervalQueOnPortEntity1dayTable 1 }

IntervalQueOnPortEntity1dayEntry ::=  SEQUENCE
  { intervalQueOnPortEntity1dayNumber Integer32,
    intervalQueOnPortEntity1dayBytesDroppedBufOverflow Counter64String,
    intervalQueOnPortEntity1dayFramesDroppedBufOverflow Counter64String,
    intervalQueOnPortEntity1dayValidFlag TruthValue,
    intervalQueOnPortEntity1dayTimeStamp DateAndTime }

intervalQueOnPortEntity1dayNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalQueOnPortEntity1dayEntry 1 }

intervalQueOnPortEntity1dayBytesDroppedBufOverflow OBJECT-TYPE
    SYNTAX      Counter64String
    MAX-ACCESS  read-only
    STATUS      current
    DESCRIPTION
        "Bytes dropped due to buffer overflow" 
    ::=  { intervalQueOnPortEntity1dayEntry 2 }

intervalQueOnPortEntity1dayFramesDroppedBufOverflow OBJECT-TYPE
    SYNTAX      Counter64String
    MAX-ACCESS  read-only
    STATUS      current
    DESCRIPTION
        "Frames dropped due to buffer overflow" 
    ::=  { intervalQueOnPortEntity1dayEntry 3 }

intervalQueOnPortEntity1dayValidFlag OBJECT-TYPE
    SYNTAX      TruthValue
    MAX-ACCESS  read-only
    STATUS      current
    DESCRIPTION
        "Valid Flag" 
    ::=  { intervalQueOnPortEntity1dayEntry 4 }

intervalQueOnPortEntity1dayTimeStamp OBJECT-TYPE
    SYNTAX      DateAndTime
    MAX-ACCESS  read-only
    STATUS      current
    DESCRIPTION
        "Timestamp" 
    ::=  { intervalQueOnPortEntity1dayEntry 5 }

currentQueOnFlowEntity15minTable OBJECT-TYPE
    SYNTAX      SEQUENCE OF CurrentQueOnFlowEntity15minEntry
    MAX-ACCESS  not-accessible
    STATUS      current
    DESCRIPTION   ""
    ::=  { quePerformanceMonitoring 5 }

currentQueOnFlowEntity15minEntry OBJECT-TYPE
    SYNTAX      CurrentQueOnFlowEntity15minEntry
    MAX-ACCESS  not-accessible
    STATUS      current
    DESCRIPTION   ""
    INDEX       {
                  queOnFlowEntityIndexEth,
                  queOnFlowEntityIndexFlow,
                  queOnFlowEntityIndexPrio
                }
    ::=  { currentQueOnFlowEntity15minTable 1 }

CurrentQueOnFlowEntity15minEntry ::=  SEQUENCE
  { currentQueOnFlowEntity15minBytesDroppedBufOverflow Counter64String,
    currentQueOnFlowEntity15minFramesDroppedBufOverflow Counter64String,
    currentQueOnFlowEntity15minElapsedTime Integer32 }

currentQueOnFlowEntity15minBytesDroppedBufOverflow OBJECT-TYPE
    SYNTAX      Counter64String
    MAX-ACCESS  read-only
    STATUS      current
    DESCRIPTION
        "Bytes dropped due to buffer overflow" 
    ::=  { currentQueOnFlowEntity15minEntry 1 }

currentQueOnFlowEntity15minFramesDroppedBufOverflow OBJECT-TYPE
    SYNTAX      Counter64String
    MAX-ACCESS  read-only
    STATUS      current
    DESCRIPTION
        "Frames dropped due to buffer overflow" 
    ::=  { currentQueOnFlowEntity15minEntry 2 }

currentQueOnFlowEntity15minElapsedTime OBJECT-TYPE
    SYNTAX      Integer32 (0..9000 | -2147483648)
    MAX-ACCESS  read-only
    STATUS      current
    DESCRIPTION
        "Elapsed 15Min" 
    ::=  { currentQueOnFlowEntity15minEntry 3 }

currentQueOnFlowEntity1dayTable OBJECT-TYPE
    SYNTAX      SEQUENCE OF CurrentQueOnFlowEntity1dayEntry
    MAX-ACCESS  not-accessible
    STATUS      current
    DESCRIPTION   ""
    ::=  { quePerformanceMonitoring 6 }

currentQueOnFlowEntity1dayEntry OBJECT-TYPE
    SYNTAX      CurrentQueOnFlowEntity1dayEntry
    MAX-ACCESS  not-accessible
    STATUS      current
    DESCRIPTION   ""
    INDEX       {
                  queOnFlowEntityIndexEth,
                  queOnFlowEntityIndexFlow,
                  queOnFlowEntityIndexPrio
                }
    ::=  { currentQueOnFlowEntity1dayTable 1 }

CurrentQueOnFlowEntity1dayEntry ::=  SEQUENCE
  { currentQueOnFlowEntity1dayBytesDroppedBufOverflow Counter64String,
    currentQueOnFlowEntity1dayFramesDroppedBufOverflow Counter64String,
    currentQueOnFlowEntity1dayElapsedTime Integer32 }

currentQueOnFlowEntity1dayBytesDroppedBufOverflow OBJECT-TYPE
    SYNTAX      Counter64String
    MAX-ACCESS  read-only
    STATUS      current
    DESCRIPTION
        "Bytes dropped due to buffer overflow" 
    ::=  { currentQueOnFlowEntity1dayEntry 1 }

currentQueOnFlowEntity1dayFramesDroppedBufOverflow OBJECT-TYPE
    SYNTAX      Counter64String
    MAX-ACCESS  read-only
    STATUS      current
    DESCRIPTION
        "Frames dropped due to buffer overflow" 
    ::=  { currentQueOnFlowEntity1dayEntry 2 }

currentQueOnFlowEntity1dayElapsedTime OBJECT-TYPE
    SYNTAX      Integer32 (0..86400 | -2147483648)
    MAX-ACCESS  read-only
    STATUS      current
    DESCRIPTION
        "Elapsed 1Day" 
    ::=  { currentQueOnFlowEntity1dayEntry 3 }

intervalQueOnFlowEntity15minTable OBJECT-TYPE
    SYNTAX      SEQUENCE OF IntervalQueOnFlowEntity15minEntry
    MAX-ACCESS  not-accessible
    STATUS      current
    DESCRIPTION   ""
    ::=  { quePerformanceMonitoring 7 }

intervalQueOnFlowEntity15minEntry OBJECT-TYPE
    SYNTAX      IntervalQueOnFlowEntity15minEntry
    MAX-ACCESS  not-accessible
    STATUS      current
    DESCRIPTION   ""
    INDEX       {
                  queOnFlowEntityIndexEth,
                  queOnFlowEntityIndexFlow,
                  queOnFlowEntityIndexPrio,
                  intervalQueOnFlowEntity15minNumber
                }
    ::=  { intervalQueOnFlowEntity15minTable 1 }

IntervalQueOnFlowEntity15minEntry ::=  SEQUENCE
  { intervalQueOnFlowEntity15minNumber Integer32,
    intervalQueOnFlowEntity15minBytesDroppedBufOverflow Counter64String,
    intervalQueOnFlowEntity15minFramesDroppedBufOverflow Counter64String,
    intervalQueOnFlowEntity15minValidFlag TruthValue,
    intervalQueOnFlowEntity15minTimeStamp DateAndTime }

intervalQueOnFlowEntity15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalQueOnFlowEntity15minEntry 1 }

intervalQueOnFlowEntity15minBytesDroppedBufOverflow OBJECT-TYPE
    SYNTAX      Counter64String
    MAX-ACCESS  read-only
    STATUS      current
    DESCRIPTION
        "Bytes dropped due to buffer overflow" 
    ::=  { intervalQueOnFlowEntity15minEntry 2 }

intervalQueOnFlowEntity15minFramesDroppedBufOverflow OBJECT-TYPE
    SYNTAX      Counter64String
    MAX-ACCESS  read-only
    STATUS      current
    DESCRIPTION
        "Frames dropped due to buffer overflow" 
    ::=  { intervalQueOnFlowEntity15minEntry 3 }

intervalQueOnFlowEntity15minValidFlag OBJECT-TYPE
    SYNTAX      TruthValue
    MAX-ACCESS  read-only
    STATUS      current
    DESCRIPTION
        "Valid Flag" 
    ::=  { intervalQueOnFlowEntity15minEntry 4 }

intervalQueOnFlowEntity15minTimeStamp OBJECT-TYPE
    SYNTAX      DateAndTime
    MAX-ACCESS  read-only
    STATUS      current
    DESCRIPTION
        "Timestamp" 
    ::=  { intervalQueOnFlowEntity15minEntry 5 }

intervalQueOnFlowEntity1dayTable OBJECT-TYPE
    SYNTAX      SEQUENCE OF IntervalQueOnFlowEntity1dayEntry
    MAX-ACCESS  not-accessible
    STATUS      current
    DESCRIPTION   ""
    ::=  { quePerformanceMonitoring 8 }

intervalQueOnFlowEntity1dayEntry OBJECT-TYPE
    SYNTAX      IntervalQueOnFlowEntity1dayEntry
    MAX-ACCESS  not-accessible
    STATUS      current
    DESCRIPTION   ""
    INDEX       {
                  queOnFlowEntityIndexEth,
                  queOnFlowEntityIndexFlow,
                  queOnFlowEntityIndexPrio,
                  intervalQueOnFlowEntity1dayNumber
                }
    ::=  { intervalQueOnFlowEntity1dayTable 1 }

IntervalQueOnFlowEntity1dayEntry ::=  SEQUENCE
  { intervalQueOnFlowEntity1dayNumber Integer32,
    intervalQueOnFlowEntity1dayBytesDroppedBufOverflow Counter64String,
    intervalQueOnFlowEntity1dayFramesDroppedBufOverflow Counter64String,
    intervalQueOnFlowEntity1dayValidFlag TruthValue,
    intervalQueOnFlowEntity1dayTimeStamp DateAndTime }

intervalQueOnFlowEntity1dayNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalQueOnFlowEntity1dayEntry 1 }

intervalQueOnFlowEntity1dayBytesDroppedBufOverflow OBJECT-TYPE
    SYNTAX      Counter64String
    MAX-ACCESS  read-only
    STATUS      current
    DESCRIPTION
        "Bytes dropped due to buffer overflow" 
    ::=  { intervalQueOnFlowEntity1dayEntry 2 }

intervalQueOnFlowEntity1dayFramesDroppedBufOverflow OBJECT-TYPE
    SYNTAX      Counter64String
    MAX-ACCESS  read-only
    STATUS      current
    DESCRIPTION
        "Frames dropped due to buffer overflow" 
    ::=  { intervalQueOnFlowEntity1dayEntry 3 }

intervalQueOnFlowEntity1dayValidFlag OBJECT-TYPE
    SYNTAX      TruthValue
    MAX-ACCESS  read-only
    STATUS      current
    DESCRIPTION
        "Valid Flag" 
    ::=  { intervalQueOnFlowEntity1dayEntry 4 }

intervalQueOnFlowEntity1dayTimeStamp OBJECT-TYPE
    SYNTAX      DateAndTime
    MAX-ACCESS  read-only
    STATUS      current
    DESCRIPTION
        "Timestamp" 
    ::=  { intervalQueOnFlowEntity1dayEntry 5 }

currentQueOnBridgeEntity15minTable OBJECT-TYPE
    SYNTAX      SEQUENCE OF CurrentQueOnBridgeEntity15minEntry
    MAX-ACCESS  not-accessible
    STATUS      current
    DESCRIPTION   "This table contains for QUE on BRIDGE entities. It is used for reading
         non-configurable, currently counted performance monitoring parameters with
         1-day counting period."
    ::=  { quePerformanceMonitoring 9 }

currentQueOnBridgeEntity15minEntry OBJECT-TYPE
    SYNTAX      CurrentQueOnBridgeEntity15minEntry
    MAX-ACCESS  not-accessible
    STATUS      current
    DESCRIPTION   ""
    INDEX       {
                  queOnBridgeEntityIndex,
                  queOnBridgeEntitySvid,
                  queOnBridgeEntityPrio
                }
    ::=  { currentQueOnBridgeEntity15minTable 1 }

CurrentQueOnBridgeEntity15minEntry ::=  SEQUENCE
  { currentQueOnBridgeEntity15minBytesDroppedBufOverflow Counter64String,
    currentQueOnBridgeEntity15minFramesDroppedBufOverflow Counter64String,
    currentQueOnBridgeEntity15minElapsedTime Integer32 }

currentQueOnBridgeEntity15minBytesDroppedBufOverflow OBJECT-TYPE
    SYNTAX      Counter64String
    MAX-ACCESS  read-only
    STATUS      current
    DESCRIPTION
        "Bytes dropped due to buffer overflow" 
    ::=  { currentQueOnBridgeEntity15minEntry 1 }

currentQueOnBridgeEntity15minFramesDroppedBufOverflow OBJECT-TYPE
    SYNTAX      Counter64String
    MAX-ACCESS  read-only
    STATUS      current
    DESCRIPTION
        "Frames dropped due to buffer overflow" 
    ::=  { currentQueOnBridgeEntity15minEntry 2 }

currentQueOnBridgeEntity15minElapsedTime OBJECT-TYPE
    SYNTAX      Integer32 (0..9000 | -2147483648)
    MAX-ACCESS  read-only
    STATUS      current
    DESCRIPTION
        "Elapsed 15Min" 
    ::=  { currentQueOnBridgeEntity15minEntry 3 }

currentQueOnBridgeEntity1dayTable OBJECT-TYPE
    SYNTAX      SEQUENCE OF CurrentQueOnBridgeEntity1dayEntry
    MAX-ACCESS  not-accessible
    STATUS      current
    DESCRIPTION   "This table contains for QUE on BRIDGE entities. It is used for reading
         non-configurable, currently counted performance monitoring parameters with
         1-day counting period."
    ::=  { quePerformanceMonitoring 10 }

currentQueOnBridgeEntity1dayEntry OBJECT-TYPE
    SYNTAX      CurrentQueOnBridgeEntity1dayEntry
    MAX-ACCESS  not-accessible
    STATUS      current
    DESCRIPTION   "Entry represents an assigned QUE on BRIDGE entity."
    INDEX       {
                  queOnBridgeEntityIndex,
                  queOnBridgeEntitySvid,
                  queOnBridgeEntityPrio
                }
    ::=  { currentQueOnBridgeEntity1dayTable 1 }

CurrentQueOnBridgeEntity1dayEntry ::=  SEQUENCE
  { currentQueOnBridgeEntity1dayBytesDroppedBufOverflow Counter64String,
    currentQueOnBridgeEntity1dayFramesDroppedBufOverflow Counter64String,
    currentQueOnBridgeEntity1dayElapsedTime Integer32 }

currentQueOnBridgeEntity1dayBytesDroppedBufOverflow OBJECT-TYPE
    SYNTAX      Counter64String
    MAX-ACCESS  read-only
    STATUS      current
    DESCRIPTION
        "Bytes dropped due to buffer overflow" 
    ::=  { currentQueOnBridgeEntity1dayEntry 1 }

currentQueOnBridgeEntity1dayFramesDroppedBufOverflow OBJECT-TYPE
    SYNTAX      Counter64String
    MAX-ACCESS  read-only
    STATUS      current
    DESCRIPTION
        "Frames dropped due to buffer overflow" 
    ::=  { currentQueOnBridgeEntity1dayEntry 2 }

currentQueOnBridgeEntity1dayElapsedTime OBJECT-TYPE
    SYNTAX      Integer32 (0..86400 | -2147483648)
    MAX-ACCESS  read-only
    STATUS      current
    DESCRIPTION
        "Elapsed 1Day" 
    ::=  { currentQueOnBridgeEntity1dayEntry 3 }

intervalQueOnBridgeEntity15minTable OBJECT-TYPE
    SYNTAX      SEQUENCE OF IntervalQueOnBridgeEntity15minEntry
    MAX-ACCESS  not-accessible
    STATUS      current
    DESCRIPTION   "This table contains for QUE on BRIDGE entities. It is used for reading
         non-configurable, already counted performance monitoring parameters with
         15-minutes counting period."
    ::=  { quePerformanceMonitoring 11 }

intervalQueOnBridgeEntity15minEntry OBJECT-TYPE
    SYNTAX      IntervalQueOnBridgeEntity15minEntry
    MAX-ACCESS  not-accessible
    STATUS      current
    DESCRIPTION   "Entry represents an assigned QUE on BRIDGE entity."
    INDEX       {
                  queOnBridgeEntityIndex,
                  queOnBridgeEntitySvid,
                  queOnBridgeEntityPrio,
                  intervalQueOnBridgeEntity15minNumber
                }
    ::=  { intervalQueOnBridgeEntity15minTable 1 }

IntervalQueOnBridgeEntity15minEntry ::=  SEQUENCE
  { intervalQueOnBridgeEntity15minNumber Integer32,
    intervalQueOnBridgeEntity15minBytesDroppedBufOverflow Counter64String,
    intervalQueOnBridgeEntity15minFramesDroppedBufOverflow Counter64String,
    intervalQueOnBridgeEntity15minValidFlag TruthValue,
    intervalQueOnBridgeEntity15minTimeStamp DateAndTime }

intervalQueOnBridgeEntity15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1." 
    ::=  { intervalQueOnBridgeEntity15minEntry 1 }

intervalQueOnBridgeEntity15minBytesDroppedBufOverflow OBJECT-TYPE
    SYNTAX      Counter64String
    MAX-ACCESS  read-only
    STATUS      current
    DESCRIPTION
        "Bytes dropped due to buffer overflow" 
    ::=  { intervalQueOnBridgeEntity15minEntry 2 }

intervalQueOnBridgeEntity15minFramesDroppedBufOverflow OBJECT-TYPE
    SYNTAX      Counter64String
    MAX-ACCESS  read-only
    STATUS      current
    DESCRIPTION
        "Frames dropped due to buffer overflow" 
    ::=  { intervalQueOnBridgeEntity15minEntry 3 }

intervalQueOnBridgeEntity15minValidFlag OBJECT-TYPE
    SYNTAX      TruthValue
    MAX-ACCESS  read-only
    STATUS      current
    DESCRIPTION
        "Valid Flag" 
    ::=  { intervalQueOnBridgeEntity15minEntry 4 }

intervalQueOnBridgeEntity15minTimeStamp OBJECT-TYPE
    SYNTAX      DateAndTime
    MAX-ACCESS  read-only
    STATUS      current
    DESCRIPTION
        "Timestamp" 
    ::=  { intervalQueOnBridgeEntity15minEntry 5 }

intervalQueOnBridgeEntity1dayTable OBJECT-TYPE
    SYNTAX      SEQUENCE OF IntervalQueOnBridgeEntity1dayEntry
    MAX-ACCESS  not-accessible
    STATUS      current
    DESCRIPTION   "This table contains for QUE on BRIDGE entities. It is used for reading
         non-configurable, already counted performance monitoring parameters with
         1-day counting period."
    ::=  { quePerformanceMonitoring 12 }

intervalQueOnBridgeEntity1dayEntry OBJECT-TYPE
    SYNTAX      IntervalQueOnBridgeEntity1dayEntry
    MAX-ACCESS  not-accessible
    STATUS      current
    DESCRIPTION   "Entry represents an assigned QUE on BRIDGE entity."
    INDEX       {
                  queOnBridgeEntityIndex,
                  queOnBridgeEntitySvid,
                  queOnBridgeEntityPrio,
                  intervalQueOnBridgeEntity1dayNumber
                }
    ::=  { intervalQueOnBridgeEntity1dayTable 1 }

IntervalQueOnBridgeEntity1dayEntry ::=  SEQUENCE
  { intervalQueOnBridgeEntity1dayNumber Integer32,
    intervalQueOnBridgeEntity1dayBytesDroppedBufOverflow Counter64String,
    intervalQueOnBridgeEntity1dayFramesDroppedBufOverflow Counter64String,
    intervalQueOnBridgeEntity1dayValidFlag TruthValue,
    intervalQueOnBridgeEntity1dayTimeStamp DateAndTime }

intervalQueOnBridgeEntity1dayNumber OBJECT-TYPE
    SYNTAX      Integer32 (1..31)
    MAX-ACCESS  not-accessible
    STATUS      current
    DESCRIPTION
        "A number, which identifies the interval for
         which the set of statistics is available. The interval
         identified by 1 is the most recently completed 1 day
         interval." 
    ::=  { intervalQueOnBridgeEntity1dayEntry 1 }

intervalQueOnBridgeEntity1dayBytesDroppedBufOverflow OBJECT-TYPE
    SYNTAX      Counter64String
    MAX-ACCESS  read-only
    STATUS      current
    DESCRIPTION
        "Bytes dropped due to buffer overflow" 
    ::=  { intervalQueOnBridgeEntity1dayEntry 2 }

intervalQueOnBridgeEntity1dayFramesDroppedBufOverflow OBJECT-TYPE
    SYNTAX      Counter64String
    MAX-ACCESS  read-only
    STATUS      current
    DESCRIPTION
        "Frames dropped due to buffer overflow" 
    ::=  { intervalQueOnBridgeEntity1dayEntry 3 }

intervalQueOnBridgeEntity1dayValidFlag OBJECT-TYPE
    SYNTAX      TruthValue
    MAX-ACCESS  read-only
    STATUS      current
    DESCRIPTION
        "Valid Flag" 
    ::=  { intervalQueOnBridgeEntity1dayEntry 4 }

intervalQueOnBridgeEntity1dayTimeStamp OBJECT-TYPE
    SYNTAX      DateAndTime
    MAX-ACCESS  read-only
    STATUS      current
    DESCRIPTION
        "Timestamp" 
    ::=  { intervalQueOnBridgeEntity1dayEntry 5 }


alarmOosDisabledL2 NOTIFICATION-TYPE 
    OBJECTS     { flowCurrentConditionSeverity,flowCurrentConditionAffect,neEventLogTimeStamp,neEventLogIdentityTranslation } 
    STATUS      current
    DESCRIPTION   "Non-Specific Disablement of Management Access"
    ::=  { layer2TrapsPrefix 100000 }


alarmOosManagementL2 NOTIFICATION-TYPE 
    OBJECTS     { flowCurrentConditionSeverity,flowCurrentConditionAffect,neEventLogTimeStamp,neEventLogIdentityTranslation } 
    STATUS      current
    DESCRIPTION   "Alarms are logged but not notified, service affecting changes are permitted"
    ::=  { layer2TrapsPrefix 100001 }


alarmOosMaintenanceL2 NOTIFICATION-TYPE 
    OBJECTS     { flowCurrentConditionSeverity,flowCurrentConditionAffect,neEventLogTimeStamp,neEventLogIdentityTranslation } 
    STATUS      current
    DESCRIPTION   "Alarms are logged but not notified, service affecting changes and operations are permitted"
    ::=  { layer2TrapsPrefix 100002 }


alarmOosAinsL2 NOTIFICATION-TYPE 
    OBJECTS     { flowCurrentConditionSeverity,flowCurrentConditionAffect,neEventLogTimeStamp,neEventLogIdentityTranslation } 
    STATUS      current
    DESCRIPTION   "Automatic In Service"
    ::=  { layer2TrapsPrefix 100003 }


alarmServerSignalFailL2 NOTIFICATION-TYPE 
    OBJECTS     { flowCurrentConditionSeverity,flowCurrentConditionAffect,neEventLogTimeStamp,neEventLogIdentityTranslation } 
    STATUS      current
    DESCRIPTION   "All member ports signals have failed"
    ::=  { layer2TrapsPrefix 100004 }


alarmMepNotPresentL2 NOTIFICATION-TYPE 
    OBJECTS     { flowCurrentConditionSeverity,flowCurrentConditionAffect,neEventLogTimeStamp,neEventLogIdentityTranslation } 
    STATUS      current
    DESCRIPTION   "No MEP is attached to this FLW."
    ::=  { layer2TrapsPrefix 100005 }


alarmPriVidNotEqualExtVidL2 NOTIFICATION-TYPE 
    OBJECTS     { flowCurrentConditionSeverity,flowCurrentConditionAffect,neEventLogTimeStamp,neEventLogIdentityTranslation } 
    STATUS      current
    DESCRIPTION   "The MEP PRIMARY-VID and the EXT-VID/SVID on the FLW is not equal"
    ::=  { layer2TrapsPrefix 100006 }


alarmSwitchtoProtectionInhibitedL2 NOTIFICATION-TYPE 
    OBJECTS     { flowCurrentConditionSeverity,flowCurrentConditionAffect,neEventLogTimeStamp,neEventLogIdentityTranslation } 
    STATUS      current
    DESCRIPTION   "Protection Switch Inhibited. Switch to PROTN facility Locked Out. Reported by WKG facility. Leads to PSI state."
    ::=  { layer2TrapsPrefix 100007 }


alarmManswL2 NOTIFICATION-TYPE 
    OBJECTS     { flowCurrentConditionSeverity,flowCurrentConditionAffect,neEventLogTimeStamp,neEventLogIdentityTranslation } 
    STATUS      current
    DESCRIPTION   "This condition will only be shown on the working entity, meaning the MANSW has switched traffic from the working entity to the protection entity."
    ::=  { layer2TrapsPrefix 100008 }


alarmSfCfmLevel0L2  NOTIFICATION-TYPE 
    OBJECTS     { flowCurrentConditionSeverity,flowCurrentConditionAffect,neEventLogTimeStamp,neEventLogIdentityTranslation } 
    STATUS      current
    DESCRIPTION   "SF alarm on Level 0"
    ::=  { layer2TrapsPrefix 100009 }


alarmSfCfmLevel1L2  NOTIFICATION-TYPE 
    OBJECTS     { flowCurrentConditionSeverity,flowCurrentConditionAffect,neEventLogTimeStamp,neEventLogIdentityTranslation } 
    STATUS      current
    DESCRIPTION   "SF alarm on Level 1"
    ::=  { layer2TrapsPrefix 100010 }


alarmSfCfmLevel2L2  NOTIFICATION-TYPE 
    OBJECTS     { flowCurrentConditionSeverity,flowCurrentConditionAffect,neEventLogTimeStamp,neEventLogIdentityTranslation } 
    STATUS      current
    DESCRIPTION   "SF alarm on Level 2"
    ::=  { layer2TrapsPrefix 100011 }


alarmSfCfmLevel3L2  NOTIFICATION-TYPE 
    OBJECTS     { flowCurrentConditionSeverity,flowCurrentConditionAffect,neEventLogTimeStamp,neEventLogIdentityTranslation } 
    STATUS      current
    DESCRIPTION   "SF alarm on Level 3"
    ::=  { layer2TrapsPrefix 100012 }


alarmSfCfmLevel4L2  NOTIFICATION-TYPE 
    OBJECTS     { flowCurrentConditionSeverity,flowCurrentConditionAffect,neEventLogTimeStamp,neEventLogIdentityTranslation } 
    STATUS      current
    DESCRIPTION   "SF alarm on Level 4"
    ::=  { layer2TrapsPrefix 100013 }


alarmSfCfmLevel5L2  NOTIFICATION-TYPE 
    OBJECTS     { flowCurrentConditionSeverity,flowCurrentConditionAffect,neEventLogTimeStamp,neEventLogIdentityTranslation } 
    STATUS      current
    DESCRIPTION   "SF alarm on Level 5"
    ::=  { layer2TrapsPrefix 100014 }


alarmSfCfmLevel6L2  NOTIFICATION-TYPE 
    OBJECTS     { flowCurrentConditionSeverity,flowCurrentConditionAffect,neEventLogTimeStamp,neEventLogIdentityTranslation } 
    STATUS      current
    DESCRIPTION   "SF alarm on Level 6"
    ::=  { layer2TrapsPrefix 100015 }


alarmSfCfmLevel7L2  NOTIFICATION-TYPE 
    OBJECTS     { flowCurrentConditionSeverity,flowCurrentConditionAffect,neEventLogTimeStamp,neEventLogIdentityTranslation } 
    STATUS      current
    DESCRIPTION   "SF alarm on Level 7"
    ::=  { layer2TrapsPrefix 100016 }


alarmSwitchtoWorkingInhibitedL2 NOTIFICATION-TYPE 
    OBJECTS     { flowCurrentConditionSeverity,flowCurrentConditionAffect,neEventLogTimeStamp,neEventLogIdentityTranslation } 
    STATUS      current
    DESCRIPTION   "Protection Release Inhibited. Switch back to WKG facility Locked Out. Reported by PROTN facility. Leads to PRI state."
    ::=  { layer2TrapsPrefix 100019 }



alarmBridgeOosManagement NOTIFICATION-TYPE 
    OBJECTS     { bridgeCurrentConditionSeverity,bridgeCurrentConditionAffect,neEventLogTimeStamp,neEventLogIdentityTranslation } 
    STATUS      current
    DESCRIPTION   "Alarms are logged but not notified, service affecting changes are permitted"
    ::=  { layer2TrapsPrefix 100017 }


alarmBridgeOosAins NOTIFICATION-TYPE 
    OBJECTS     { bridgeCurrentConditionSeverity,bridgeCurrentConditionAffect,neEventLogTimeStamp,neEventLogIdentityTranslation } 
    STATUS      current
    DESCRIPTION   "Automatic In Service"
    ::=  { layer2TrapsPrefix 100018 }



flowEntityCreation NOTIFICATION-TYPE 
    OBJECTS     { flowEntityIndexEth,
                  flowEntityClass,
                  neEventLogTimeStamp,
                  neEventLogIdentityTranslation
                } 
    STATUS      current
    DESCRIPTION   "This trap is sent every time an entity is created. No containers
         or other sub-entities in the chassis are reported created by this trap,
         the NMS must read these data."
    ::=  { layer2TrapsPrefix 110001 }

ctransEntityCreation NOTIFICATION-TYPE 
    OBJECTS     { ctransEntityIndexEth,
                  ctransEntityClass,
                  neEventLogTimeStamp,
                  neEventLogIdentityTranslation
                } 
    STATUS      current
    DESCRIPTION   "This trap is sent every time an entity is created. No containers
         or other sub-entities in the chassis are reported created by this trap,
         the NMS must read these data."
    ::=  { layer2TrapsPrefix 110002 }

bridgeEntityCreation NOTIFICATION-TYPE 
    OBJECTS     { bridgeEntityClass,
                  neEventLogTimeStamp,
                  neEventLogIdentityTranslation
                } 
    STATUS      current
    DESCRIPTION   "This trap indicates BRIDGE entity creation."
    ::=  { layer2TrapsPrefix 110003 }

flowEntityDeletion NOTIFICATION-TYPE 
    OBJECTS     { flowEntityClass,
                  neEventLogTimeStamp,
                  neEventLogIdentityTranslation
                } 
    STATUS      current
    DESCRIPTION   "This trap is sent every time an entity is deleted. The
         sub-entities (containers, modules, etc.) are not reported deleted.
        "
    ::=  { layer2TrapsPrefix 110008 }

ctransEntityDeletion NOTIFICATION-TYPE 
    OBJECTS     { ctransEntityClass,
                  neEventLogTimeStamp,
                  neEventLogIdentityTranslation
                } 
    STATUS      current
    DESCRIPTION   "This trap is sent every time an entity is deleted. The
         sub-entities (containers, modules, etc.) are not reported deleted.
        "
    ::=  { layer2TrapsPrefix 110009 }

bridgeEntityDeletion NOTIFICATION-TYPE 
    OBJECTS     { bridgeEntityClass,
                  neEventLogTimeStamp,
                  neEventLogIdentityTranslation
                } 
    STATUS      current
    DESCRIPTION   "This trap indicates BRIDGE entity deletion."
    ::=  { layer2TrapsPrefix 110010 }

layer2EntityStateChange NOTIFICATION-TYPE 
    OBJECTS     { neEventLogTimeStamp,
                  neEventLogIdentityTranslation
                } 
    STATUS      current
    DESCRIPTION   "This trap is sent to indicate an entity state change."
    ::=  { layer2TrapsPrefix 110015 }

flowEntityObjectChange NOTIFICATION-TYPE 
    OBJECTS     { flowEntityIndexEth,
                  flowEntityIndexFlow,
                  flowEntityClass,
                  neEventLogTimeStamp,
                  neEventLogIdentityTranslation
                } 
    STATUS      current
    DESCRIPTION   "This trap is sent some object is changed."
    ::=  { layer2TrapsPrefix 110016 }

ctransEntityObjectChange NOTIFICATION-TYPE 
    OBJECTS     { ctransEntityIndexEth,
                  ctransEntityIndexCVlanId,
                  ctransEntityClass,
                  neEventLogTimeStamp,
                  neEventLogIdentityTranslation
                } 
    STATUS      current
    DESCRIPTION   "This trap is sent some object is changed."
    ::=  { layer2TrapsPrefix 110017 }

bridgeEntityObjectChange NOTIFICATION-TYPE 
    OBJECTS     { bridgeEntityContainedIn,
                  bridgeEntitySvid,
                  bridgeEntityClass,
                  neEventLogTimeStamp,
                  neEventLogIdentityTranslation
                } 
    STATUS      current
    DESCRIPTION   "This trap indicates properties change of BRIDGE entity."
    ::=  { layer2TrapsPrefix 110018 }

crossConnectionCreationLayer2 NOTIFICATION-TYPE 
    OBJECTS     { crossConnectionsStatusFromEth,
                  crossConnectionsStatusToEth,
                  crossConnectionsProvisioningConn,
                  neEventLogTimeStamp,
                  neEventLogIdentityTranslation
                } 
    STATUS      current
    DESCRIPTION   "This trap is sent every time an cross connection is created."
    ::=  { layer2TrapsPrefix 110030 }

crossConnectionDeletionLayer2 NOTIFICATION-TYPE 
    OBJECTS     { crossConnectionsStatusFromEth,
                  crossConnectionsStatusToEth,
                  neEventLogTimeStamp,
                  neEventLogIdentityTranslation
                } 
    STATUS      current
    DESCRIPTION   "This trap is sent every time an cross connection is deleted."
    ::=  { layer2TrapsPrefix 110031 }

crossConnectionObjectChangeLayer2 NOTIFICATION-TYPE 
    OBJECTS     { crossConnectionsStatusFromEth,
                  crossConnectionsStatusToEth,
                  neEventLogTimeStamp,
                  neEventLogIdentityTranslation
                } 
    STATUS      current
    DESCRIPTION   "This trap is sent some cross connect object is changed."
    ::=  { layer2TrapsPrefix 110032 }

ffpFlowEntityCreation NOTIFICATION-TYPE 
    OBJECTS     { flowEntityIndexEth,
                  flowProtectionAssignedEntityClass,
                  neEventLogTimeStamp,
                  neEventLogIdentityTranslation
                } 
    STATUS      current
    DESCRIPTION   "This trap is sent every time an entity is created. No containers
         or other sub-entities in the chassis are reported created by this trap,
         the NMS must read these data."
    ::=  { layer2TrapsPrefix 110033 }

ffpFlowEntityDeletion NOTIFICATION-TYPE 
    OBJECTS     { flowProtectionAssignedEntityClass,
                  neEventLogTimeStamp,
                  neEventLogIdentityTranslation
                } 
    STATUS      current
    DESCRIPTION   "This trap is sent every time an entity is deleted. The deletion of
         sub-entities (containers, modules, etc.) are not reported.
        "
    ::=  { layer2TrapsPrefix 110034 }

ffpFlowEntityObjectChange NOTIFICATION-TYPE 
    OBJECTS     { flowEntityIndexEth,
                  flowEntityIndexFlow,
                  flowProtectionAssignedEntityClass,
                  neEventLogTimeStamp,
                  neEventLogIdentityTranslation
                } 
    STATUS      current
    DESCRIPTION   "This trap is sent some object is changed."
    ::=  { layer2TrapsPrefix 110035 }

transientWorkingSwitchedtoProtectionL2 NOTIFICATION-TYPE 
    OBJECTS     { entityIndex,neEventLogTimeStamp,neEventLogIdentityTranslation } 
    STATUS      current
    DESCRIPTION   "Working Traffic (ACT) switched from WKG facility to PROTN facility automatically, sent by WKG."
    ::=  { layer2TrapsPrefix 111001 }


transientWorkingSwitchedBacktoWorkingL2 NOTIFICATION-TYPE 
    OBJECTS     { entityIndex,neEventLogTimeStamp,neEventLogIdentityTranslation } 
    STATUS      current
    DESCRIPTION   "Working Traffic (ACT) switched back to WKG facilty from PROTN facility automatically: sent by PROTN."
    ::=  { layer2TrapsPrefix 111002 }


transientManualWorkingSwitchedtoProtectionL2 NOTIFICATION-TYPE 
    OBJECTS     { entityIndex,neEventLogTimeStamp,neEventLogIdentityTranslation } 
    STATUS      current
    DESCRIPTION   "Working Traffic (ACT) switched from WKG facility to PROTN facility manually: sent by WKG."
    ::=  { layer2TrapsPrefix 111003 }


transientManualWorkingSwitchedBacktoWorkingL2 NOTIFICATION-TYPE 
    OBJECTS     { entityIndex,neEventLogTimeStamp,neEventLogIdentityTranslation } 
    STATUS      current
    DESCRIPTION   "Working Traffic (ACT) switched back to WKG facility from PROTN facility manually: sent by PROTN."
    ::=  { layer2TrapsPrefix 111004 }


flowConditionSeverityTable OBJECT-TYPE
    SYNTAX      SEQUENCE OF FlowConditionSeverityEntry
    MAX-ACCESS  not-accessible
    STATUS      current
    DESCRIPTION   "This table contains a severity value for each defined standing condition reported by an entity in the NE."
    ::=  { layer2Conditions 1 }

flowConditionSeverityEntry OBJECT-TYPE
    SYNTAX      FlowConditionSeverityEntry
    MAX-ACCESS  not-accessible
    STATUS      current
    DESCRIPTION   "Each entry in the table represents the severity assigned to a condition.'"
    INDEX       {
                  flowEntityIndexEth,
                  flowEntityIndexFlow,
                  flowConditionSeverityType
                }
    ::=  { flowConditionSeverityTable 1 }

FlowConditionSeverityEntry ::=  SEQUENCE
  { flowConditionSeverityType FspR7L2StandingConditionTypes,
    flowConditionSeverityValue TrapAlarmSeverity }

flowConditionSeverityType OBJECT-TYPE
    SYNTAX      FspR7L2StandingConditionTypes
    MAX-ACCESS  not-accessible
    STATUS      current
    DESCRIPTION   "This object identifies the type of alarm."
    ::=  { flowConditionSeverityEntry 1 }

flowConditionSeverityValue OBJECT-TYPE
    SYNTAX      TrapAlarmSeverity
    MAX-ACCESS  read-write
    STATUS      current
    DESCRIPTION   "This object identifies the severity assigned to this alarm."
    ::=  { flowConditionSeverityEntry 2 }

bridgeConditionSeverityTable OBJECT-TYPE
    SYNTAX      SEQUENCE OF BridgeConditionSeverityEntry
    MAX-ACCESS  not-accessible
    STATUS      current
    DESCRIPTION   "This table contains a severity value for each defined standing condition reported by an entity on the NE in case of BRIDGE entities."
    ::=  { layer2Conditions 2 }

bridgeConditionSeverityEntry OBJECT-TYPE
    SYNTAX      BridgeConditionSeverityEntry
    MAX-ACCESS  not-accessible
    STATUS      current
    DESCRIPTION   "Each entry in the table represents the severity assigned to a condition for BRIDGE entities."
    INDEX       {
                  bridgeEntityContainedIn,
                  bridgeEntitySvid,
                  bridgeConditionSeverityType
                }
    ::=  { bridgeConditionSeverityTable 1 }

BridgeConditionSeverityEntry ::=  SEQUENCE
  { bridgeConditionSeverityType BridgeStandingConditionTypes,
    bridgeConditionSeverityValue TrapAlarmSeverity }

bridgeConditionSeverityType OBJECT-TYPE
    SYNTAX      BridgeStandingConditionTypes
    MAX-ACCESS  not-accessible
    STATUS      current
    DESCRIPTION   "This object identifies the type of alarm."
    ::=  { bridgeConditionSeverityEntry 1 }

bridgeConditionSeverityValue OBJECT-TYPE
    SYNTAX      TrapAlarmSeverity
    MAX-ACCESS  read-write
    STATUS      current
    DESCRIPTION   "This object identifies the severity assigned to this alarm."
    ::=  { bridgeConditionSeverityEntry 2 }

flowCurrentConditionTable OBJECT-TYPE
    SYNTAX      SEQUENCE OF FlowCurrentConditionEntry
    MAX-ACCESS  not-accessible
    STATUS      current
    DESCRIPTION   ""
    ::=  { layer2Conditions 6 }

flowCurrentConditionEntry OBJECT-TYPE
    SYNTAX      FlowCurrentConditionEntry
    MAX-ACCESS  not-accessible
    STATUS      current
    DESCRIPTION   ""
    INDEX       {
                  flowEntityIndexEth,
                  flowEntityIndexFlow,
                  flowCurrentConditionType
                }
    ::=  { flowCurrentConditionTable 1 }

FlowCurrentConditionEntry ::=  SEQUENCE
  { flowCurrentConditionType FspR7L2StandingConditionTypes,
    flowCurrentConditionSeverity TrapAlarmSeverity,
    flowCurrentConditionAffect ServiceImpairment,
    flowCurrentConditionTimeStamp DateAndTime }

flowCurrentConditionType OBJECT-TYPE
    SYNTAX      FspR7L2StandingConditionTypes
    MAX-ACCESS  not-accessible
    STATUS      current
    DESCRIPTION   "List of all interface conditions"
    ::=  { flowCurrentConditionEntry 1 }

flowCurrentConditionSeverity OBJECT-TYPE
    SYNTAX      TrapAlarmSeverity
    MAX-ACCESS  read-only
    STATUS      current
    DESCRIPTION   "This object identifies the current severity of alarm."
    ::=  { flowCurrentConditionEntry 2 }

flowCurrentConditionAffect OBJECT-TYPE
    SYNTAX      ServiceImpairment
    MAX-ACCESS  read-only
    STATUS      current
    DESCRIPTION   "This object indicates the service impairment affect of the alarm."
    ::=  { flowCurrentConditionEntry 3 }

flowCurrentConditionTimeStamp OBJECT-TYPE
    SYNTAX      DateAndTime
    MAX-ACCESS  read-only
    STATUS      current
    DESCRIPTION   "Timestamp"
    ::=  { flowCurrentConditionEntry 4 }

bridgeCurrentConditionTable OBJECT-TYPE
    SYNTAX      SEQUENCE OF BridgeCurrentConditionEntry
    MAX-ACCESS  not-accessible
    STATUS      current
    DESCRIPTION   "This table contains all currently raised standing condition reported by an entity on the NE in case of BRIDGE entities."
    ::=  { layer2Conditions 7 }

bridgeCurrentConditionEntry OBJECT-TYPE
    SYNTAX      BridgeCurrentConditionEntry
    MAX-ACCESS  not-accessible
    STATUS      current
    DESCRIPTION   "Each entry in the table represents currently raised standing conditions for BRIDGE entities."
    INDEX       {
                  bridgeEntityContainedIn,
                  bridgeEntitySvid,
                  bridgeCurrentConditionType
                }
    ::=  { bridgeCurrentConditionTable 1 }

BridgeCurrentConditionEntry ::=  SEQUENCE
  { bridgeCurrentConditionType BridgeStandingConditionTypes,
    bridgeCurrentConditionSeverity TrapAlarmSeverity,
    bridgeCurrentConditionAffect ServiceImpairment,
    bridgeCurrentConditionTimeStamp DateAndTime }

bridgeCurrentConditionType OBJECT-TYPE
    SYNTAX      BridgeStandingConditionTypes
    MAX-ACCESS  not-accessible
    STATUS      current
    DESCRIPTION   "List of all interface conditions"
    ::=  { bridgeCurrentConditionEntry 1 }

bridgeCurrentConditionSeverity OBJECT-TYPE
    SYNTAX      TrapAlarmSeverity
    MAX-ACCESS  read-only
    STATUS      current
    DESCRIPTION   "This object identifies the current severity of alarm."
    ::=  { bridgeCurrentConditionEntry 2 }

bridgeCurrentConditionAffect OBJECT-TYPE
    SYNTAX      ServiceImpairment
    MAX-ACCESS  read-only
    STATUS      current
    DESCRIPTION   "This object indicates the service impairment affect of the alarm."
    ::=  { bridgeCurrentConditionEntry 3 }

bridgeCurrentConditionTimeStamp OBJECT-TYPE
    SYNTAX      DateAndTime
    MAX-ACCESS  read-only
    STATUS      current
    DESCRIPTION   "Timestamp."
    ::=  { bridgeCurrentConditionEntry 4 }

flowProtectionToAssignEntityTable OBJECT-TYPE
    SYNTAX      SEQUENCE OF FlowProtectionToAssignEntityEntry
    MAX-ACCESS  not-accessible
    STATUS      current
    DESCRIPTION   ""
    ::=  { layer2FlowProtection 11 }

flowProtectionToAssignEntityEntry OBJECT-TYPE
    SYNTAX      FlowProtectionToAssignEntityEntry
    MAX-ACCESS  not-accessible
    STATUS      current
    DESCRIPTION   ""
    INDEX       {
                  flowEntityIndexEth,
                  flowEntityIndexFlow
                }
    ::=  { flowProtectionToAssignEntityTable 1 }

FlowProtectionToAssignEntityEntry ::=  SEQUENCE
  { flowProtectionToAssignEntityIndexAid SnmpAdminString,
    flowProtectionToAssignEntityClass EntityClass,
    flowProtectionToAssignEntityClassInstanceNumber Integer32 }

flowProtectionToAssignEntityIndexAid OBJECT-TYPE
    SYNTAX      SnmpAdminString
    MAX-ACCESS  read-only
    STATUS      current
    DESCRIPTION
        "Name" 
    ::=  { flowProtectionToAssignEntityEntry 1 }

flowProtectionToAssignEntityClass OBJECT-TYPE
    SYNTAX      EntityClass
    MAX-ACCESS  read-only
    STATUS      current
    DESCRIPTION   "See EntityClass"
    ::=  { flowProtectionToAssignEntityEntry 2 }

flowProtectionToAssignEntityClassInstanceNumber OBJECT-TYPE
    SYNTAX      Integer32 (1..2000 | -2147483648)
    MAX-ACCESS  read-only
    STATUS      current
    DESCRIPTION
        "The class instance number of this entity within the module(card)" 
    ::=  { flowProtectionToAssignEntityEntry 3 }

flowProtectionAssignedEntityTable OBJECT-TYPE
    SYNTAX      SEQUENCE OF FlowProtectionAssignedEntityEntry
    MAX-ACCESS  not-accessible
    STATUS      current
    DESCRIPTION   ""
    ::=  { layer2FlowProtection 12 }

flowProtectionAssignedEntityEntry OBJECT-TYPE
    SYNTAX      FlowProtectionAssignedEntityEntry
    MAX-ACCESS  not-accessible
    STATUS      current
    DESCRIPTION   ""
    INDEX       {
                  flowEntityIndexEth,
                  flowEntityIndexFlow
                }
    ::=  { flowProtectionAssignedEntityTable 1 }

FlowProtectionAssignedEntityEntry ::=  SEQUENCE
  { flowProtectionAssignedEntityIndexAid SnmpAdminString,
    flowProtectionAssignedEntityClass EntityClass,
    flowProtectionAssignedEntityClassInstanceNumber Integer32 }

flowProtectionAssignedEntityIndexAid OBJECT-TYPE
    SYNTAX      SnmpAdminString
    MAX-ACCESS  read-only
    STATUS      current
    DESCRIPTION
        "Name" 
    ::=  { flowProtectionAssignedEntityEntry 1 }

flowProtectionAssignedEntityClass OBJECT-TYPE
    SYNTAX      EntityClass
    MAX-ACCESS  read-only
    STATUS      current
    DESCRIPTION   "See EntityClass"
    ::=  { flowProtectionAssignedEntityEntry 2 }

flowProtectionAssignedEntityClassInstanceNumber OBJECT-TYPE
    SYNTAX      Integer32 (1..2000 | -2147483648)
    MAX-ACCESS  read-only
    STATUS      current
    DESCRIPTION
        "The class instance number of this entity within the module(card)" 
    ::=  { flowProtectionAssignedEntityEntry 3 }

flowProtectionProvisionTable OBJECT-TYPE
    SYNTAX      SEQUENCE OF FlowProtectionProvisionEntry
    MAX-ACCESS  not-accessible
    STATUS      current
    DESCRIPTION   ""
    ::=  { layer2FlowProtection 13 }

flowProtectionProvisionEntry OBJECT-TYPE
    SYNTAX      FlowProtectionProvisionEntry
    MAX-ACCESS  not-accessible
    STATUS      current
    DESCRIPTION   ""
    INDEX       {
                  flowEntityIndexEth,
                  flowEntityIndexFlow
                }
    ::=  { flowProtectionProvisionTable 1 }

FlowProtectionProvisionEntry ::=  SEQUENCE
  { flowProtectionProvisionRowStatus RowStatus,
    flowProtectionProvisionWorkingEthIndex EntityIndex,
    flowProtectionProvisionWorkingFlwIndex Unsigned32,
    flowProtectionProvisionProtectionEthIndex EntityIndex,
    flowProtectionProvisionProtectionFlwIndex Unsigned32,
    flowProtectionProvisionProtectionMech ProtectionMech,
    flowProtectionProvisionRevertiveMode ApsRevertMode,
    flowProtectionProvisionBridge FspR7L2Brigde,
    flowProtectionProvisionLevelDomainMonitored FspR7L2LevelDomainMonitored,
    flowProtectionProvisionBridgeType FspR7Brigde }

flowProtectionProvisionRowStatus OBJECT-TYPE
    SYNTAX      RowStatus
    MAX-ACCESS  read-create
    STATUS      current
    DESCRIPTION   "This object is used to create, or delete a row in this table."
    ::=  { flowProtectionProvisionEntry 1 }

flowProtectionProvisionWorkingEthIndex OBJECT-TYPE
    SYNTAX      EntityIndex
    MAX-ACCESS  read-create
    STATUS      current
    DESCRIPTION   "The entityIndex (ETH part) of the working section in the APS group."
    ::=  { flowProtectionProvisionEntry 2 }

flowProtectionProvisionWorkingFlwIndex OBJECT-TYPE
    SYNTAX      Unsigned32
    MAX-ACCESS  read-create
    STATUS      current
    DESCRIPTION   "The entityIndex (FLW part) of the working section in the APS group."
    ::=  { flowProtectionProvisionEntry 3 }

flowProtectionProvisionProtectionEthIndex OBJECT-TYPE
    SYNTAX      EntityIndex
    MAX-ACCESS  read-create
    STATUS      current
    DESCRIPTION   "The entityIndex (ETH part) of the protection section in the APS group."
    ::=  { flowProtectionProvisionEntry 4 }

flowProtectionProvisionProtectionFlwIndex OBJECT-TYPE
    SYNTAX      Unsigned32
    MAX-ACCESS  read-create
    STATUS      current
    DESCRIPTION   "The entityIndex (FLW part) of the protection section in the APS group."
    ::=  { flowProtectionProvisionEntry 5 }

flowProtectionProvisionProtectionMech OBJECT-TYPE
    SYNTAX      ProtectionMech
    MAX-ACCESS  read-create
    STATUS      current
    DESCRIPTION
        "Port Based refers to HST Cards and Switches: Card Based refers to additional equipment protection" 
    ::=  { flowProtectionProvisionEntry 6 }

flowProtectionProvisionRevertiveMode OBJECT-TYPE
    SYNTAX      ApsRevertMode
    MAX-ACCESS  read-create
    STATUS      current
    DESCRIPTION
        "Revertive Protection Switching" 
    ::=  { flowProtectionProvisionEntry 7 }

flowProtectionProvisionBridge OBJECT-TYPE
    SYNTAX      FspR7L2Brigde
    MAX-ACCESS  read-create
    STATUS      obsolete
    DESCRIPTION
        "To select between diffenrent protection types" 
    ::=  { flowProtectionProvisionEntry 8 }

flowProtectionProvisionLevelDomainMonitored OBJECT-TYPE
    SYNTAX      FspR7L2LevelDomainMonitored
    MAX-ACCESS  read-create
    STATUS      current
    DESCRIPTION
        "Maintenance Domain Level monitored" 
    ::=  { flowProtectionProvisionEntry 9 }

flowProtectionProvisionBridgeType OBJECT-TYPE
    SYNTAX      FspR7Brigde
    MAX-ACCESS  read-create
    STATUS      current
    DESCRIPTION
        "To select between diffenrent protection types" 
    ::=  { flowProtectionProvisionEntry 10 }

flowProtectionProvisionCapTable OBJECT-TYPE
    SYNTAX      SEQUENCE OF FlowProtectionProvisionCapEntry
    MAX-ACCESS  not-accessible
    STATUS      current
    DESCRIPTION   ""
    ::=  { layer2FlowProtection 14  }

flowProtectionProvisionCapEntry OBJECT-TYPE
    SYNTAX      FlowProtectionProvisionCapEntry
    MAX-ACCESS  not-accessible
    STATUS      current
    DESCRIPTION   ""
    INDEX       { flowEntityIndexEth,
                  flowEntityIndexFlow }
    ::=  { flowProtectionProvisionCapTable 1 }

FlowProtectionProvisionCapEntry ::=  SEQUENCE
  { flowProtectionProvisionCapRowStatus FspR7RowStatusCaps,
    flowProtectionProvisionCapWorkingEthIndex Integer32,
    flowProtectionProvisionCapWorkingFlwIndex FspR7Unsigned32Caps,
    flowProtectionProvisionCapProtectionEthIndex Integer32,
    flowProtectionProvisionCapProtectionFlwIndex FspR7Unsigned32Caps,
    flowProtectionProvisionCapProtectionMech ProtectionMechCaps,
    flowProtectionProvisionCapRevertiveMode ApsRevertModeCaps,
    flowProtectionProvisionCapBridge FspR7L2BrigdeCaps,
    flowProtectionProvisionCapLevelDomainMonitored FspR7L2LevelDomainMonitoredCaps,
    flowProtectionProvisionCapBridgeType FspR7BrigdeCaps }

flowProtectionProvisionCapRowStatus OBJECT-TYPE
    SYNTAX      FspR7RowStatusCaps
    MAX-ACCESS  read-only
    STATUS      current
    DESCRIPTION   "This object is used to create, or delete a row in this table."
    ::=  { flowProtectionProvisionCapEntry 1 }

flowProtectionProvisionCapWorkingEthIndex OBJECT-TYPE
    SYNTAX      Integer32
    MAX-ACCESS  read-only
    STATUS      current
    DESCRIPTION   "The entityIndex (ETH part) of the working section in the APS group."
    ::=  { flowProtectionProvisionCapEntry 2 }

flowProtectionProvisionCapWorkingFlwIndex OBJECT-TYPE
    SYNTAX      FspR7Unsigned32Caps
    MAX-ACCESS  read-only
    STATUS      current
    DESCRIPTION   "The entityIndex (FLW part) of the working section in the APS group."
    ::=  { flowProtectionProvisionCapEntry 3 }

flowProtectionProvisionCapProtectionEthIndex OBJECT-TYPE
    SYNTAX      Integer32
    MAX-ACCESS  read-only
    STATUS      current
    DESCRIPTION   "The entityIndex (ETH part) of the protection section in the APS group."
    ::=  { flowProtectionProvisionCapEntry 4 }

flowProtectionProvisionCapProtectionFlwIndex OBJECT-TYPE
    SYNTAX      FspR7Unsigned32Caps
    MAX-ACCESS  read-only
    STATUS      current
    DESCRIPTION   "The entityIndex (FLW part) of the protection section in the APS group."
    ::=  { flowProtectionProvisionCapEntry 5 }

flowProtectionProvisionCapProtectionMech OBJECT-TYPE
    SYNTAX      ProtectionMechCaps
    MAX-ACCESS  read-only
    STATUS      current
    DESCRIPTION
        "Port Based refers to HST Cards and Switches: Card Based refers to additional equipment protection" 
    ::=  { flowProtectionProvisionCapEntry 6 }

flowProtectionProvisionCapRevertiveMode OBJECT-TYPE
    SYNTAX      ApsRevertModeCaps
    MAX-ACCESS  read-only
    STATUS      current
    DESCRIPTION
        "Revertive Protection Switching" 
    ::=  { flowProtectionProvisionCapEntry 7 }

flowProtectionProvisionCapBridge OBJECT-TYPE
    SYNTAX      FspR7L2BrigdeCaps
    MAX-ACCESS  read-only
    STATUS      obsolete
    DESCRIPTION
        "To select between diffenrent protection types" 
    ::=  { flowProtectionProvisionCapEntry 8 }

flowProtectionProvisionCapLevelDomainMonitored OBJECT-TYPE
    SYNTAX      FspR7L2LevelDomainMonitoredCaps
    MAX-ACCESS  read-only
    STATUS      current
    DESCRIPTION
        "Maintenance Domain Level monitored" 
    ::=  { flowProtectionProvisionCapEntry 9 }

flowProtectionProvisionCapBridgeType OBJECT-TYPE
    SYNTAX      FspR7BrigdeCaps
    MAX-ACCESS  read-only
    STATUS      current
    DESCRIPTION
        "To select between diffenrent protection types" 
    ::=  { flowProtectionProvisionCapEntry 10 }

flowProtectionProvisionDefaultsTable  OBJECT-TYPE
    SYNTAX      SEQUENCE OF FlowProtectionProvisionDefaultsEntry
    MAX-ACCESS  not-accessible
    STATUS      current
    DESCRIPTION   ""
    ::=  { layer2FlowProtection 15  }

flowProtectionProvisionDefaultsEntry OBJECT-TYPE
    SYNTAX      FlowProtectionProvisionDefaultsEntry
    MAX-ACCESS  not-accessible
    STATUS      current
    DESCRIPTION   ""
    INDEX       { flowEntityIndexEth,
                  flowEntityIndexFlow }
    ::=  { flowProtectionProvisionDefaultsTable 1 }

FlowProtectionProvisionDefaultsEntry ::=  SEQUENCE
  { flowProtectionProvisionDefaultsRowStatus RowStatus,
    flowProtectionProvisionDefaultsWorkingEthIndex EntityIndex,
    flowProtectionProvisionDefaultsWorkingFlwIndex Unsigned32,
    flowProtectionProvisionDefaultsProtectionEthIndex EntityIndex,
    flowProtectionProvisionDefaultsProtectionFlwIndex Unsigned32,
    flowProtectionProvisionDefaultsProtectionMech ProtectionMech,
    flowProtectionProvisionDefaultsRevertiveMode ApsRevertMode,
    flowProtectionProvisionDefaultsBridge FspR7L2Brigde,
    flowProtectionProvisionDefaultsLevelDomainMonitored FspR7L2LevelDomainMonitored,
    flowProtectionProvisionDefaultsBridgeType FspR7Brigde }

flowProtectionProvisionDefaultsRowStatus OBJECT-TYPE
    SYNTAX      RowStatus
    MAX-ACCESS  read-only
    STATUS      current
    DESCRIPTION   "This object is used to create, or delete a row in this table."
    ::=  { flowProtectionProvisionDefaultsEntry 1 }

flowProtectionProvisionDefaultsWorkingEthIndex OBJECT-TYPE
    SYNTAX      EntityIndex
    MAX-ACCESS  read-only
    STATUS      current
    DESCRIPTION   "The entityIndex (ETH part) of the working section in the APS group."
    ::=  { flowProtectionProvisionDefaultsEntry 2 }

flowProtectionProvisionDefaultsWorkingFlwIndex OBJECT-TYPE
    SYNTAX      Unsigned32
    MAX-ACCESS  read-only
    STATUS      current
    DESCRIPTION   "The entityIndex (FLW part) of the working section in the APS group."
    ::=  { flowProtectionProvisionDefaultsEntry 3 }

flowProtectionProvisionDefaultsProtectionEthIndex OBJECT-TYPE
    SYNTAX      EntityIndex
    MAX-ACCESS  read-only
    STATUS      current
    DESCRIPTION   "The entityIndex (ETH part) of the protection section in the APS group."
    ::=  { flowProtectionProvisionDefaultsEntry 4 }

flowProtectionProvisionDefaultsProtectionFlwIndex OBJECT-TYPE
    SYNTAX      Unsigned32
    MAX-ACCESS  read-only
    STATUS      current
    DESCRIPTION   "The entityIndex (FLW part) of the protection section in the APS group."
    ::=  { flowProtectionProvisionDefaultsEntry 5 }

flowProtectionProvisionDefaultsProtectionMech OBJECT-TYPE
    SYNTAX      ProtectionMech
    MAX-ACCESS  read-only
    STATUS      current
    DESCRIPTION
        "Port Based refers to HST Cards and Switches: Card Based refers to additional equipment protection" 
    ::=  { flowProtectionProvisionDefaultsEntry 6 }

flowProtectionProvisionDefaultsRevertiveMode OBJECT-TYPE
    SYNTAX      ApsRevertMode
    MAX-ACCESS  read-only
    STATUS      current
    DESCRIPTION
        "Revertive Protection Switching" 
    ::=  { flowProtectionProvisionDefaultsEntry 7 }

flowProtectionProvisionDefaultsBridge OBJECT-TYPE
    SYNTAX      FspR7L2Brigde
    MAX-ACCESS  read-only
    STATUS      obsolete
    DESCRIPTION
        "To select between diffenrent protection types" 
    ::=  { flowProtectionProvisionDefaultsEntry 8 }

flowProtectionProvisionDefaultsLevelDomainMonitored OBJECT-TYPE
    SYNTAX      FspR7L2LevelDomainMonitored
    MAX-ACCESS  read-only
    STATUS      current
    DESCRIPTION
        "Maintenance Domain Level monitored" 
    ::=  { flowProtectionProvisionDefaultsEntry 9 }

flowProtectionProvisionDefaultsBridgeType OBJECT-TYPE
    SYNTAX      FspR7Brigde
    MAX-ACCESS  read-only
    STATUS      current
    DESCRIPTION
        "To select between diffenrent protection types" 
    ::=  { flowProtectionProvisionDefaultsEntry 10 }

flowProtectionProvisionProtectionAidCapsTable OBJECT-TYPE
    SYNTAX      SEQUENCE OF FlowProtectionProvisionProtectionAidCapsEntry
    MAX-ACCESS  not-accessible
    STATUS      current
    DESCRIPTION   ""
    ::=  { layer2FlowProtection 16 }

flowProtectionProvisionProtectionAidCapsEntry OBJECT-TYPE
    SYNTAX      FlowProtectionProvisionProtectionAidCapsEntry
    MAX-ACCESS  not-accessible
    STATUS      current
    DESCRIPTION   ""
    INDEX       {
                  flowEntityIndexEth,
                  flowEntityIndexFlow
                }
    ::=  { flowProtectionProvisionProtectionAidCapsTable 1 }

FlowProtectionProvisionProtectionAidCapsEntry ::=  SEQUENCE
  { flowProtectionProvisionProtectionAidCapsIndex EntityIndex }

flowProtectionProvisionProtectionAidCapsIndex OBJECT-TYPE
    SYNTAX      EntityIndex
    MAX-ACCESS  read-only
    STATUS      current
    DESCRIPTION
        "Protection AID (ETH part)" 
    ::=  { flowProtectionProvisionProtectionAidCapsEntry 1 }

flowProtectionStatusTable OBJECT-TYPE
    SYNTAX      SEQUENCE OF FlowProtectionStatusEntry
    MAX-ACCESS  not-accessible
    STATUS      current
    DESCRIPTION   ""
    ::=  { layer2FlowProtection 23 }

flowProtectionStatusEntry OBJECT-TYPE
    SYNTAX      FlowProtectionStatusEntry
    MAX-ACCESS  not-accessible
    STATUS      current
    DESCRIPTION   ""
    INDEX       {
                  flowEntityIndexEth,
                  flowEntityIndexFlow
                }
    ::=  { flowProtectionStatusTable 1 }

FlowProtectionStatusEntry ::=  SEQUENCE
  { flowProtectionStatusWorkingEthIndex EntityIndex,
    flowProtectionStatusWorkingFlwIndex Unsigned32,
    flowProtectionStatusProtectionEthIndex EntityIndex,
    flowProtectionStatusProtectionFlwIndex Unsigned32,
    flowProtectionStatusApsType ApsType,
    flowProtectionStatusProtectionType FspR7ProtectionType,
    flowProtectionStatusProtectionMech ProtectionMech,
    flowProtectionStatusDirection ApsDirection,
    flowProtectionStatusRevertiveMode ApsRevertMode,
    flowProtectionStatusBridge FspR7L2Brigde,
    flowProtectionStatusLevelDomainMonitored FspR7L2LevelDomainMonitored,
    flowProtectionStatusBridgeType FspR7L2Brigde }

flowProtectionStatusWorkingEthIndex OBJECT-TYPE
    SYNTAX      EntityIndex
    MAX-ACCESS  read-only
    STATUS      current
    DESCRIPTION   "The entityIndex (ETH part) of the working section in the APS group."
    ::=  { flowProtectionStatusEntry 1 }

flowProtectionStatusWorkingFlwIndex OBJECT-TYPE
    SYNTAX      Unsigned32
    MAX-ACCESS  read-only
    STATUS      current
    DESCRIPTION   "The entityIndex (FLW part) of the working section in the APS group."
    ::=  { flowProtectionStatusEntry 2 }

flowProtectionStatusProtectionEthIndex OBJECT-TYPE
    SYNTAX      EntityIndex
    MAX-ACCESS  read-only
    STATUS      current
    DESCRIPTION   "The entityIndex (ETH part) of the protection section in the APS group."
    ::=  { flowProtectionStatusEntry 3 }

flowProtectionStatusProtectionFlwIndex OBJECT-TYPE
    SYNTAX      Unsigned32
    MAX-ACCESS  read-only
    STATUS      current
    DESCRIPTION   "The entityIndex (FLW part) of the protection section in the APS group."
    ::=  { flowProtectionStatusEntry 4 }

flowProtectionStatusApsType OBJECT-TYPE
    SYNTAX      ApsType
    MAX-ACCESS  read-only
    STATUS      current
    DESCRIPTION
        "Type of Automatic Protection Switching; triggered by standing conditions" 
    ::=  { flowProtectionStatusEntry 5 }

flowProtectionStatusProtectionType OBJECT-TYPE
    SYNTAX      FspR7ProtectionType
    MAX-ACCESS  read-only
    STATUS      current
    DESCRIPTION
        "This describes the topology and level of the protection (OCH or
         OM -Level on a ring; Line in PT-PT and Line or Dualhomed on a Feeder)." 
    ::=  { flowProtectionStatusEntry 6 }

flowProtectionStatusProtectionMech OBJECT-TYPE
    SYNTAX      ProtectionMech
    MAX-ACCESS  read-only
    STATUS      current
    DESCRIPTION
        "Port Based refers to HST Cards and Switches: Card Based refers to additional equipment protection" 
    ::=  { flowProtectionStatusEntry 7 }

flowProtectionStatusDirection OBJECT-TYPE
    SYNTAX      ApsDirection
    MAX-ACCESS  read-only
    STATUS      current
    DESCRIPTION
        "Bi-Directional | Unidirectional setup used in protection setup: Not to be used by others" 
    ::=  { flowProtectionStatusEntry 8 }

flowProtectionStatusRevertiveMode OBJECT-TYPE
    SYNTAX      ApsRevertMode
    MAX-ACCESS  read-only
    STATUS      current
    DESCRIPTION
        "Revertive Protection Switching" 
    ::=  { flowProtectionStatusEntry 9 }

flowProtectionStatusBridge OBJECT-TYPE
    SYNTAX      FspR7L2Brigde
    MAX-ACCESS  read-only
    STATUS      obsolete
    DESCRIPTION
        "To select between diffenrent protection types" 
    ::=  { flowProtectionStatusEntry 10 }

flowProtectionStatusLevelDomainMonitored OBJECT-TYPE
    SYNTAX      FspR7L2LevelDomainMonitored
    MAX-ACCESS  read-only
    STATUS      current
    DESCRIPTION
        "Maintenance Domain Level monitored" 
    ::=  { flowProtectionStatusEntry 11 }

flowProtectionStatusBridgeType OBJECT-TYPE
    SYNTAX      FspR7L2Brigde
    MAX-ACCESS  read-only
    STATUS      current
    DESCRIPTION
        "To select between diffenrent protection types" 
    ::=  { flowProtectionStatusEntry 12 }


END
