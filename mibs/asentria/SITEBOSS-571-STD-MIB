-- SiteBoss 571 MIB

-- v 1.43 December 11 2014

-- Copyright (c) 2014 by Asentria Corporation.  All rights reserved.


SITEBOSS-571-STD-MIB DEFINITIONS ::= BEGIN

IMPORTS
 DisplayString
    FROM SNMPv2-TC
 IpAddress, TimeTicks, Integer32,
 MODULE-IDENTITY, NOTIFICATION-TYPE, OBJECT-TYPE
    FROM SNMPv2-SMI
 asentria
    FROM ASENTRIA-ROOT-MIB;

--***************************************************************************************
--MODULE IDENTITY
--***************************************************************************************

  s571 MODULE-IDENTITY
    LAST-UPDATED "201412110143Z"
    ORGANIZATION "Asentria Corporation"
    CONTACT-INFO
     "Phone:  206-344-8800
      Fax:    206-344-2116
      Email:  support@asentria.com"
    DESCRIPTION
      "MIB module for managing Asentria SiteBoss 571"

    REVISION      "201412110143Z"
    DESCRIPTION
      "-v1.43
       -Changed analog-input fuel sensor objects from Integer32 to DisplayString (OMX-1177).
       -Added missing ipv6DefaultRouter object (OMX-1175).
       -Applicable since unit version 2.10.580."

    REVISION      "201410160142Z"
    DESCRIPTION
      "-v1.42
       -Added espcAIDisplayFormat object (OMX-1112).
       -Removed espcAIPolarity, espcAIConvHighSign, espcAIConvLowSign objects (OMX-1113).
       -Applicable since unit version 2.10.460."

    REVISION      "201410030141Z"
    DESCRIPTION
      "-v1.41
       -Changed analog input objects from Integer32 to DisplayString.
       -Applicable since unit version 2.10.460."

    REVISION      "201408140140Z"
    DESCRIPTION
      "-v1.40
       -Fixed description for wirelessConnIP objects (OMX-1061).
       -Applicable since unit version 2.10.390."

    REVISION      "201407030139Z"
    DESCRIPTION
      "-v1.39
       -Fixed wirelessIdleTimeout (OMX-1037).
       -Fixed CPE status objects (OMX-1036).
       -Applicable since unit version 2.10.390."

    REVISION      "201406240138Z"
    DESCRIPTION
      "-v1.38
       -Fixed CPE status objects.
       -Applicable since unit version 2.10.340."

    REVISION      "201405290137Z"
    DESCRIPTION
      "-v1.37
       -Added various missing objects (OMX-751).
       -Added CPE objects (OMX-162).
       -Applicable since unit version 2.10.320."

    REVISION      "201404110136Z"
    DESCRIPTION
      "-v1.36
       -Clarified relay and power output function and documentation (OMX-926).
       -Applicable since unit version 2.10.300."

    REVISION      "201401170135Z"
    DESCRIPTION
      "-v1.35
       -Added IPv6 objects (OMX-705).
       -Added power distribution objects (powerDistributionStatus branch) (OMX-708).
       -Fixed ipRestrictionMask wrong type (OMX-743).
       -Added ftpPushPermissions (OMX-737).
       -Added snmpProxy objects (OMX-747).
       -Applicable since unit version 2.10.150."

    REVISION      "201312040134Z"
    DESCRIPTION
      "-v1.34
       -Added fsGenEnable (OMX-661).
       -Applicable since unit version 2.10.110."

    REVISION      "201309040133Z"
    DESCRIPTION
      "-v1.33
       -Added pdSystemCurrent and pdSystemPower objects (OMX-527).
       -Added pdnDeviceCurrentValue and pdnDeviceCurrentValueStr objects (OMX-528).
       -Applicable since unit version 2.09.626."

    REVISION      "201308010132Z"
    DESCRIPTION
      "-v1.32
       -Added missing trapEventTypeNumber available values in description (OMX-437).
       -Applicable since unit version 2.09.560."

    REVISION      "201307170131Z"
    DESCRIPTION
      "-v1.31
       -Corrected snmpPBufferAllPeriod object.
       -Applicable since unit version 2.09.560."

    REVISION      "201307020130Z"
    DESCRIPTION
      "-v1.30
       -Added snmpPoll objects (OMX-394).
       -Applicable since unit version 2.09.560."

    REVISION      "201306280129Z"
    DESCRIPTION
      "-v1.29
       -Removed Ethernet Expansion card objects.
       -Applicable since unit version 2.09.540."

    REVISION      "201306130128Z"
    DESCRIPTION
      "-v1.28
       -Added sysFileTransfer and sysUpdate objects. (OMX-42)
       -Applicable since unit version 2.09.520."

    REVISION      "201306120127Z"
    DESCRIPTION
      "-v1.27
       -Renamed EX10 to Ethernet Expansion (OMX-364)
       -Applicable since unit version 2.09.510."

    REVISION      "201305280126Z"
    DESCRIPTION
      "-v1.26
       -Fixed incorrect SYNTAX for sysCharMask (OMX-328).
       -Applicable since unit version 2.09.380."

    REVISION      "201305100125Z"
    DESCRIPTION
      "-v1.25
       -Fixed incorrect SYNTAX statements for various objects (OMX-314).
       -Applicable since unit version 2.09.380."

    REVISION      "201303150124Z"
    DESCRIPTION
      "-v1.24
       -Renamed sysLocation branch to sysLoc (OMX-198).
       -Applicable since unit version 2.09.240."

    REVISION      "201302060123Z"
    DESCRIPTION
      "-v1.23
       -Added ex10 branch.
       -Renamed telnet* objects.
       -Applicable since unit version 2.09.240."

    REVISION      "201301140122Z"
    DESCRIPTION
      "-v1.22
       -Added evReset branch and associated notification (OMX-83).
       -Applicable since unit version 2.09.220."

    REVISION      "201211260121Z"
    DESCRIPTION
      "-v1.21
       -Fixed backwards pppRoutingEnable/ethRoutingEnable comments.  (BN 4620)"

    REVISION      "201208220120Z"
    DESCRIPTION
      "-v1.20
       -Added additional AC power monitor items."

    REVISION      "201207090119Z"
    DESCRIPTION
      "-v1.19
       -Removed wirelessBand object.
       -Removed secSSH objects."

    REVISION      "201206120118Z"
    DESCRIPTION
      "-v1.18
       -Removed user credentials objects.
       -Added combined power distributor status objects."

    REVISION      "201204090117Z"
    DESCRIPTION
      "-v1.17
       -Added eth2WanRoutingEnable object."

    REVISION      "201204050116Z"
    DESCRIPTION
      "-v1.16
       -Added combined eventsensor status objects."

    REVISION      "201203060115Z"
    DESCRIPTION
      "-v1.15
       -Added objects and trap definitions for fuel sensor and AC power monitor."

    REVISION      "201112050900Z"
    DESCRIPTION
      "-v1.14
       -Added s571StockScriptTrap notification definition."

    REVISION      "201110240900Z"
    DESCRIPTION
      "-v1.13
       -Added s571StockLoadSheddingTrap notification definition."

    REVISION      "201108080900Z"
    DESCRIPTION
      "-v1.12
       -Added s571StockOutputTrap notification definition."

    REVISION      "201108010900Z"
    DESCRIPTION
      "-v1.11
       -Added evMgmtReprocess object."

    REVISION      "201107200900Z"
    DESCRIPTION
      "-v1.10
       -Added aisgStatus branch."

    REVISION      "201107080900Z"
    DESCRIPTION
      "-v1.09
       -Added wirelessModemStatus branch."

    REVISION      "201101050900Z"
    DESCRIPTION
      "-v1.08
       -Added espcCCNormalThreshold object."

    REVISION      "201012010900Z"
    DESCRIPTION
      "-v1.07
       -Added support for PowerBoss external power distributors.  This is in the
       pdNextGen object branch which also supports the internal power distributor
       of the SiteBoss 571.  The old SNMP support for the internal power
       distributor is kept in the older sub-branches of the powerDistributionStatus
       branch (pdConfig, pdMain, pdOutput).  The idea behind the pdNextGen object
       branch is that there are 31 items for power monitoring and alarming, and
       these items are organized in a double-indexed SNMP table object: the first
       index is for the power distributor (and has the same numbering scheme as an
       EventSensor  -- like esIndexES, but is called pdnIndexPD), and the second
       index is the power output to which the item applies (or just '1' if the item
       is not specific to a particular power output).  E.g., to read the main
       current of the internal power distributor, you can use the old object
       (pdMainCurrentValue.0) or you can use the new object
       (pdnMainCurrentValue.200.1).  To read the fuse event state of power output
       number 8 on the power distributor (PowerBoss) at index 2, read
       pdnOutputFuseInEventState.2.8."

    REVISION      "201011030900Z"
    DESCRIPTION
      "-v1.06
       -Changed deadband, threshold, and current values for temperature
       sensors from integer to floating-point type.  This means the
       SNMP object type for the temperature settings (deadbands and
       thresholds) changed from Integer32 to DisplayString.
       -Fixed bug where SNMP integer range defined in the MIB for
       trapIncludedValue was 16-bit instead of 32-bit."

    REVISION      "201008240900Z"
    DESCRIPTION
      "-v1.05
       -Fixed bug where some stock traps had too few varbinds declared.
       -Removed useless trap definitions."

    REVISION      "201003170900Z"
    DESCRIPTION
      "-v1.04
       -Removed useless object consoleInlineHsk.
       -Added asset management object branch.
       -Added altitude location object.
       -Removed all obsolete switch references, made everything consistent
        on outputs (relay outputs or power outputs).
       -Added threshold objects for power distribution sensors.
       -Added pdOutputCurrentValue object.
       -Fixed description for pdOutputCurrentInEventState."

    REVISION      "201001190900Z"
    DESCRIPTION
      "-v1.03
       -Increased range for esPointValueInt"

    REVISION      "200910080900Z"
    DESCRIPTION
      "-v1.02
       -Incremental pre-release changes"

    REVISION      "200910050900Z"
    DESCRIPTION
      "-v1.01
       -Incremental pre-release changes"

    REVISION      "200909170900Z"
    DESCRIPTION
      "-v1.00
       -Initial version."

    ::= { asentria 14 }
    --1.3.6.1.4.1.3052.14



--***************************************************************************************
--Concise MIB View: Top Level Branches
--***************************************************************************************

--  status                                 .1
--    eventSensorStatus                    .1.1
--      esPointTable                       .1.1.1
--    dataEventStatus                      .1.2
--      deStatusTable                      .1.2.1
--    modemStatus                          .1.3
--    modemCLIDLogTable                    .1.4
--    powerDistributionStatus              .1.5
--    fuelSensorStatus                     .1.6
--      fsStatusTable                      .1.6.1
--    wirelessModemStatus                  .1.7
--    acPowerMonitorStatus                 .1.8
--      acpmStatusTable                    .1.8.1
--    aisgStatus                           .1.9
--  config                                 .2
--    eventSensorBasics                    .2.1
--      esNumberEventSensors               .2.1.1
--      esTable                            .2.1.2
--        esNewSensors                     .2.1.3
--    eventSensorPointConfig               .2.2
--      esPointConfigTempTable             .2.2.1
--      esPointConfigCCTable               .2.2.2
--      esPointConfigHumidTable            .2.2.3
--      esPointConfigAITable               .2.2.5
--      esPointConfigOutputTable           .2.2.6
--    serialPorts                          .2.3
--      numberPorts                        .2.3.1
--      portConfigTable                    .2.3.2
--    network                              .2.4
--      interface                          .2.4.1
--      defaultRouter                      .2.4.2
--      dnsTable                           .2.4.3
--      hostname                           .2.4.4
--      hostTable                          .2.4.5
--      ncpDuplex                          .2.4.6
--      ncpTimeout                         .2.4.7
--      snmp                               .2.4.8
--      ftpPush                            .2.4.9
--      ppp                                .2.4.10
--      routing                            .2.4.11
--      netSecurity                        .2.4.12
--      rts                                .2.4.13
--      trap                               .2.4.14
--      routeTest                          .2.4.15
--      gprs                               .2.4.16
--      email                              .2.4.17
--      netAdvanced                        .2.4.18
--      web                                .2.4.19
--      ipv6                               .2.4.21
--      cpe                                .2.4.22
--    modem                                .2.5
--    time                                 .2.8
--      clock                              .2.8.1
--    console                              .2.10
--    unitSecurity                         .2.11
--      secCore                            .2.11.1
--      secUserTable                       .2.11.2
--      secFactory                         .2.11.3
--      secVPN                             .2.11.5
--    event                                .2.12
--      evCore                             .2.12.1
--      evData                             .2.12.2
--      evNoData1                          .2.12.3
--      evNoData2                          .2.12.4
--      evSched1                           .2.12.5
--      evSched2                           .2.12.6
--      evShskLowTable                     .2.12.7
--      evShskHighTable                    .2.12.8
--      evNoSensor                         .2.12.9
--      fuelSensor                         .2.12.11
--        fuelSensorGeneralTable           .2.12.11.1
--        fuelSensorTankTable              .2.12.11.2
--        fuelSensorCustomTankTable        .2.12.11.3
--        fuelSensorVolumeTable            .2.12.11.4
--        fuelSensorDisconnectTable        .2.12.11.5
--      acPowerMonitor                     .2.12.12
--      evReset                            .2.12.16
--    action                               .2.14
--      actionCallNumberTable              .2.14.1
--      actionPagerTable                   .2.14.2
--      actionSched                        .2.14.3
--      actionAsentria                     .2.14.4
--      actionHostTable                    .2.14.6
--      actionEmailTable                   .2.14.7
--      actionParseError                   .2.14.8
--    sys                                  .2.16
--      sysTime                            .2.16.1
--      sysPT                              .2.16.2
--      sysMTU                             .2.16.3
--      sysAnswerString                    .2.16.4
--      sysEventFileID                     .2.16.6
--      sysEscapeCharacter                 .2.16.7
--      sysTimeStamp                       .2.16.8
--      sysLog                             .2.16.9
--      sysCRDB                            .2.16.10
--      sysCharMask                        .2.16.11
--      sysPrompt                          .2.16.12
--      sysBootStatus                      .2.16.13
--      sysLoc                             .2.16.14
--      sysAssetMgmt                       .2.16.15
--      sysFileTransfer                    .2.16.17
--      sysUpdate                          .2.16.18
--    auditLog                             .2.17
--    scripting                            .2.18
--      scrGlobalEnable                    .2.18.1
--      scrDTRCtrlPortEnableTable          .2.18.2
--      scrTable                           .2.18.3
--      scrVolatileStringTable             .2.18.4
--      scrVolatileIntTable                .2.18.5
--      scrNonVolatileStringTable          .2.18.6
--      scrNonVolatileIntTable             .2.18.7
--  productIds                             .3
--    siteName                              3.1
--    thisProduct                          .3.2
--    stockTrapString                      .3.3
--    trapEventTypeNumber                  .3.4
--    trapEventTypeName                    .3.5
--    trapIncludedValue                    .3.6
--    trapIncludedString                   .3.7
--    trapTypeString                       .3.8
--    trapEventClassNumber                 .3.9
--    trapEventClassName                   .3.10
--  keyInterface                           .4.0

--***************************************************************************************
--Complete MIB View: All Objects
--***************************************************************************************

--  status                                           .1
--    eventSensorStatus                              .1.1
--      esPointTable                                 .1.1.1
--        esPointEntry                               .1.1.1.1
--          esIndexES                                .1.1.1.1.1
--          esIndexPC                                .1.1.1.1.2
--          esIndexPoint                             .1.1.1.1.3
--          esPointName                              .1.1.1.1.4
--          esPointInEventState                      .1.1.1.1.5
--          esPointValueInt                          .1.1.1.1.6
--          esPointValueStr                          .1.1.1.1.7
--          esPointTimeLastChange                    .1.1.1.1.8
--          esPointTimetickLastChange                .1.1.1.1.9
--    dataEventStatus                                .1.2
--      deStatusTable                                .1.2.1
--        deStatusEntry                              .1.2.1.1
--          deStatusIndex                            .1.2.1.1.1
--          deStatusName                             .1.2.1.1.2
--          deStatusCounter                          .1.2.1.1.3
--          deStatusThreshold                        .1.2.1.1.4
--    modemStatus                                    .1.3
--    modemCLIDLogTable                              .1.4
--      modemCLIDLogEntry                            .1.4.1
--        modemCLIDLogIndex                          .1.4.1.1
--        modemCLIDLogNumber                         .1.4.1.2
--    powerDistributionStatus                        .1.5
--      pdConfig                                     .1.5.1
--      pdMain                                       .1.5.2
--        pdMainCurrent                              .1.5.2.1
--          pdMainCurrentInEventState                .1.5.2.1.2
--          pdMainCurrentValue                       .1.5.2.1.3
--          pdMainCurrentValueStr                    .1.5.2.1.4
--          pdMainCurrentDeadband                    .1.5.2.1.10
--          pdMainCurrentVHighCurrent                .1.5.2.1.11
--          pdMainCurrentHighCurrent                 .1.5.2.1.12
--          pdMainCurrentLowCurrent                  .1.5.2.1.13
--          pdMainCurrentVLowCurrent                 .1.5.2.1.14
--        pdMainVoltage                              .1.5.2.2
--          pdMainVoltageInEventState                .1.5.2.2.2
--          pdMainVoltageValue                       .1.5.2.2.3
--          pdMainVoltageValueStr                    .1.5.2.2.4
--          pdMainVoltageDeadband                    .1.5.2.2.10
--          pdMainVoltageVHighVoltage                .1.5.2.2.11
--          pdMainVoltageHighVoltage                 .1.5.2.2.12
--          pdMainVoltageLowVoltage                  .1.5.2.2.13
--          pdMainVoltageVLowVoltage                 .1.5.2.2.14
--        pdMainPower                                .1.5.2.3
--          pdMainPowerValue                         .1.5.2.3.3
--          pdMainPowerValueStr                      .1.5.2.3.4
--      pdOutput                                     .1.5.3
--        pdOutputCurrentTable                       .1.5.3.1
--          pdOutputCurrentEntry                     .1.5.3.1.1
--            pdOutputCurrentIndex                   .1.5.3.1.1.1
--            pdOutputCurrentInEventState            .1.5.3.1.1.2
--            pdOutputCurrentValue                   .1.5.3.1.1.3
--            pdOutputCurrentValueStr                .1.5.3.1.1.4
--            pdOutputCurrentDeadband                .1.5.3.1.1.10
--            pdOutputCurrentVHighCurrent            .1.5.3.1.1.11
--            pdOutputCurrentHighCurrent             .1.5.3.1.1.12
--            pdOutputCurrentLowCurrent              .1.5.3.1.1.13
--            pdOutputCurrentVLowCurrent             .1.5.3.1.1.14
--        pdOutputFuseTable                          .1.5.3.4
--          pdOutputFuseEntry                        .1.5.3.4.1
--            pdOutputFuseIndex                      .1.5.3.4.1.1
--            pdOutputFuseInEventState               .1.5.3.4.1.2
--            pdOutputFuseValueStr                   .1.5.3.4.1.4
--      pdNextGen                                    .1.5.4
--        pdnTable                                   .1.5.4.1
--          pdnEntry                                 .1.5.4.1.1
--            pdnIndexPD                             .1.5.4.1.1.1
--            pdnIndexOutput                         .1.5.4.1.1.2
--            pdnConfig                              .1.5.4.1.1.3
--            pdnMainCurrentInEventState             .1.5.4.1.1.4
--            pdnMainCurrentValue                    .1.5.4.1.1.5
--            pdnMainCurrentValueStr                 .1.5.4.1.1.6
--            pdnMainCurrentDeadband                 .1.5.4.1.1.7
--            pdnMainCurrentVHighCurrent             .1.5.4.1.1.8
--            pdnMainCurrentHighCurrent              .1.5.4.1.1.9
--            pdnMainCurrentLowCurrent               .1.5.4.1.1.10
--            pdnMainCurrentVLowCurrent              .1.5.4.1.1.11
--            pdnMainVoltageInEventState             .1.5.4.1.1.12
--            pdnMainVoltageValue                    .1.5.4.1.1.13
--            pdnMainVoltageValueStr                 .1.5.4.1.1.14
--            pdnMainVoltageDeadband                 .1.5.4.1.1.15
--            pdnMainVoltageVHighVoltage             .1.5.4.1.1.16
--            pdnMainVoltageHighVoltage              .1.5.4.1.1.17
--            pdnMainVoltageLowVoltage               .1.5.4.1.1.18
--            pdnMainVoltageVLowVoltage              .1.5.4.1.1.19
--            pdnMainPowerValue                      .1.5.4.1.1.20
--            pdnMainPowerValueStr                   .1.5.4.1.1.21
--            pdnOutputCurrentInEventState           .1.5.4.1.1.22
--            pdnOutputCurrentValue                  .1.5.4.1.1.23
--            pdnOutputCurrentValueStr               .1.5.4.1.1.24
--            pdnOutputCurrentDeadband               .1.5.4.1.1.25
--            pdnOutputCurrentVHighCurrent           .1.5.4.1.1.26
--            pdnOutputCurrentHighCurrent            .1.5.4.1.1.27
--            pdnOutputCurrentLowCurrent             .1.5.4.1.1.28
--            pdnOutputCurrentVLowCurrent            .1.5.4.1.1.29
--            pdnOutputFuseInEventState              .1.5.4.1.1.30
--            pdnOutputFuseValueStr                  .1.5.4.1.1.31
--            pdnMainCombinedStatus                  .1.5.4.1.1.32
--            pdnOutputCombinedStatusBlock1          .1.5.4.1.1.33
--            pdnOutputCombinedStatusBlock2          .1.5.4.1.1.34
--            pdnDeviceCurrentValue                  .1.5.4.1.1.35
--            pdnDeviceCurrentValueStr               .1.5.4.1.1.36
--      pdSystem                                     .1.5.5
--        pdSystemCurrent                            .1.5.5.1
--        pdSystemPower                              .1.5.5.2
--    fuelSensorStatus                               .1.6
--      fsStatusTable                                .1.6.1
--        fsStatusEntry                              .1.6.1.1
--          fsStatusIndex                            .1.6.1.1.1
--          fsStatusName                             .1.6.1.1.2
--          fsStatusDeviceState                      .1.6.1.1.3
--          fsStatusVolumeValueString                .1.6.1.1.4
--          fsStatusVolumePercentLevel               .1.6.1.1.7
--          fsStatusVolumeInEventState               .1.6.1.1.8
--          fsStatusCombined                         .1.6.1.1.9
--    wirelessModemStatus                            .1.7
--      wmsStatus                                    .1.7.1
--      wmsSignal                                    .1.7.2
--      wmsRSSI                                      .1.7.3
--      wmsBER                                       .1.7.4
--      wmsUpdated                                   .1.7.5
--      wmsRegistration                              .1.7.6
--      wmsLAC                                       .1.7.7
--      wmsCellID                                    .1.7.8
--      wmsIMSI                                      .1.7.9
--      wmsPhnum                                     .1.7.10
--      wmsLocalIP                                   .1.7.11
--      wmsMgfID                                     .1.7.12
--      wmsModelID                                   .1.7.13
--      wmsIMEI                                      .1.7.14
--      wmsRevID                                     .1.7.15
--      wmsNetName                                   .1.7.16
--      wmsGPRSStatus                                .1.7.17
--      wmsBand                                      .1.7.18
--      wmsChannel                                   .1.7.19
--      wmsCountryCode                               .1.7.20
--      wmsNetCode                                   .1.7.21
--      wmsPLMNColor                                 .1.7.22
--      wmsBScolor                                   .1.7.23
--      wmsMpRACH                                    .1.7.24
--      wmsMinRxLevel                                .1.7.25
--      wmsBaseCoeff                                 .1.7.26
--      wmsSIMStatus                                 .1.7.27
--      wmsICCID                                     .1.7.28
--      wmsModemType                                 .1.7.29
--    acPowerMonitorStatus                           .1.8
--      acpmStatusTable                              .1.8.1
--        acpmStatusEntry                            .1.8.1.1
--          acpmsIndex                               .1.8.1.1.1
--          acpmsName                                .1.8.1.1.2
--          acpmsAvgVoltageValueStr                  .1.8.1.1.3
--          acpmsAvgVoltageMinStr                    .1.8.1.1.4
--          acpmsAvgVoltageMaxStr                    .1.8.1.1.5
--          acpmsAvgVoltageAvgStr                    .1.8.1.1.6
--          acpmsAvgVoltageInEventState              .1.8.1.1.7
--          acpmsVoltagePhaseAValueStr               .1.8.1.1.8
--          acpmsVoltagePhaseBValueStr               .1.8.1.1.9
--          acpmsVoltagePhaseCValueStr               .1.8.1.1.10
--          acpmsAvgCurrentValueStr                  .1.8.1.1.11
--          acpmsAvgCurrentMinStr                    .1.8.1.1.12
--          acpmsAvgCurrentMaxStr                    .1.8.1.1.13
--          acpmsAvgCurrentAvgStr                    .1.8.1.1.14
--          acpmsAvgCurrentInEventState              .1.8.1.1.15
--          acpmsCurrentPhaseAValueStr               .1.8.1.1.16
--          acpmsCurrentPhaseBValueStr               .1.8.1.1.17
--          acpmsCurrentPhaseCValueStr               .1.8.1.1.18
--          acpmsFreqValueStr                        .1.8.1.1.19
--          acpmsFreqMinStr                          .1.8.1.1.20
--          acpmsFreqMaxStr                          .1.8.1.1.21
--          acpmsFreqAvgStr                          .1.8.1.1.22
--          acpmsFreqInEventState                    .1.8.1.1.23
--          acpmsTRPValueStr                         .1.8.1.1.24
--          acpmsTRPMinStr                           .1.8.1.1.25
--          acpmsTRPMaxStr                           .1.8.1.1.26
--          acpmsTRPAvgStr                           .1.8.1.1.27
--          acpmsTRPInEventState                     .1.8.1.1.28
--          acpmsRPPhaseAValueStr                    .1.8.1.1.29
--          acpmsRPPhaseBValueStr                    .1.8.1.1.30
--          acpmsRPPhaseCValueStr                    .1.8.1.1.31
--          acpmsCombined                            .1.8.1.1.32
--          acpmsTPFValueStr                         .1.8.1.1.33
--          acpmsTPFMinStr                           .1.8.1.1.34
--          acpmsTPFMaxStr                           .1.8.1.1.35
--          acpmsTPFAvgStr                           .1.8.1.1.36
--          acpmsTPFInEventState                     .1.8.1.1.37
--          acpmsPFPhaseAValueStr                    .1.8.1.1.38
--          acpmsPFPhaseBValueStr                    .1.8.1.1.39
--          acpmsPFPhaseCValueStr                    .1.8.1.1.40
--          acpmsTRcPValueStr                        .1.8.1.1.41
--          acpmsTRcPMinStr                          .1.8.1.1.42
--          acpmsTRcPMaxStr                          .1.8.1.1.43
--          acpmsTRcPAvgStr                          .1.8.1.1.44
--          acpmsRcPPhaseAValueStr                   .1.8.1.1.45
--          acpmsRcPPhaseBValueStr                   .1.8.1.1.46
--          acpmsRcPPhaseCValueStr                   .1.8.1.1.47
--          acpmsTAPValueStr                         .1.8.1.1.48
--          acpmsTAPMinStr                           .1.8.1.1.49
--          acpmsTAPMaxStr                           .1.8.1.1.50
--          acpmsTAPAvgStr                           .1.8.1.1.51
--          acpmsAPPhaseAValueStr                    .1.8.1.1.52
--          acpmsAPPhaseBValueStr                    .1.8.1.1.53
--          acpmsAPPhaseCValueStr                    .1.8.1.1.54
--          acpmsTotalEnergyWh                       .1.8.1.1.55
--          acpmsTotalEnergyVAR                      .1.8.1.1.56
--          acpmsTotalEnergyVA                       .1.8.1.1.57
--    aisgStatus                                     .1.9
--      aisgsPower                                   .1.9.1
--      aisgsBaseStationID                           .1.9.2
--      aisgsALDTable                                .1.9.3
--        aisgsALDEntry                              .1.9.3.1
--          aisgsALDIndex                            .1.9.3.1.1
--          aisgsALDSectorID                         .1.9.3.1.2
--          aisgsALDType                             .1.9.3.1.3
--          aisgsALDDescription                      .1.9.3.1.4
--          aisgsALDStatus                           .1.9.3.1.5
--          aisgsALDID                               .1.9.3.1.6
--          aisgsALDTilt                             .1.9.3.1.7
--          aisgsALDHwVersion                        .1.9.3.1.8
--          aisgsALDSwVersion                        .1.9.3.1.9
--          aisgsALDModel                            .1.9.3.1.10
--          aisgsALDAntennaModel                     .1.9.3.1.11
--          aisgsALDMinTilt                          .1.9.3.1.12
--          aisgsALDMaxTilt                          .1.9.3.1.13
--          aisgsALDAISGVersion                      .1.9.3.1.14
--      aisgsFileTable                               .1.9.4
--        aisgsFileEntry                             .1.9.4.1
--          aisgsFileIndex                           .1.9.4.1.1
--          aisgsFileName                            .1.9.4.1.2
--          aisgsFileType                            .1.9.4.1.3
--          aisgsFileVersion                         .1.9.4.1.4
--      aisgsAutoTable                               .1.9.5
--        aisgsAutoEntry                             .1.9.5.1
--          aisgsAutoIndex                           .1.9.5.1.1
--          aisgsAutoVendor                          .1.9.5.1.2
--          aisgsAutoALDModel                        .1.9.5.1.3
--          aisgsAutoSoftware                        .1.9.5.1.4
--          aisgsAutoConfig                          .1.9.5.1.5
--          aisgsAutoTilt                            .1.9.5.1.6
--      aisgsAAATable                                .1.9.6
--        aisgsAAAEntry                              .1.9.6.1
--          aisgsAAAIndex                            .1.9.6.1.1
--          aisgsAAAALDID                            .1.9.6.1.2
--          aisgsAAAAntennaSN                        .1.9.6.1.3
--          aisgsAAASectorID                         .1.9.6.1.4

--  config                                           .2
--    eventSensorBasics                              .2.1
--      esNumberEventSensors                         .2.1.1
--      esTable                                      .2.1.2
--        esEntry                                    .2.1.2.1
--          esIndex                                  .2.1.2.1.1
--          esName                                   .2.1.2.1.2
--          esID                                     .2.1.2.1.3
--          esNumberTempSensors                      .2.1.2.1.4
--          esTempReportingMode                      .2.1.2.1.5
--          esNumberCCs                              .2.1.2.1.6
--          esCCReportingMode                        .2.1.2.1.7
--          esNumberHumidSensors                     .2.1.2.1.8
--          esHumidReportingMode                     .2.1.2.1.9
--          esNumberNoiseSensors                     .2.1.2.1.10
--          esNoiseReportingMode                     .2.1.2.1.11
--          esNumberAirflowSensors                   .2.1.2.1.12
--          esAirflowReportingMode                   .2.1.2.1.13
--          esNumberAnalog                           .2.1.2.1.14
--          esAnalogReportingMode                    .2.1.2.1.15
--          esNumberOutputs                          .2.1.2.1.16
--          esOutputReportingMode                    .2.1.2.1.17
--          esTempCombinedStatus                     .2.1.2.1.18
--          esCCCombinedStatusBlock1                 .2.1.2.1.19
--          esCCCombinedStatusBlock2                 .2.1.2.1.20
--          esCCCombinedStatusBlock3                 .2.1.2.1.21
--          esCCCombinedStatusBlock4                 .2.1.2.1.22
--          esCCCombinedStatusBlock5                 .2.1.2.1.23
--          esCCCombinedStatusBlock6                 .2.1.2.1.24
--          esCCCombinedStatusBlock7                 .2.1.2.1.25
--          esCCCombinedStatusBlock8                 .2.1.2.1.26
--          esHumidCombinedStatus                    .2.1.2.1.27
--          esAnalogCombinedStatusBlock1             .2.1.2.1.28
--          esAnalogCombinedStatusBlock2             .2.1.2.1.29
--          esAnalogCombinedStatusBlock3             .2.1.2.1.30
--          esAnalogCombinedStatusBlock4             .2.1.2.1.31
--          esAnalogCombinedStatusBlock5             .2.1.2.1.32
--          esAnalogCombinedStatusBlock6             .2.1.2.1.33
--          esOutputCombinedStatusBlock1             .2.1.2.1.34
--          esOutputCombinedStatusBlock2             .2.1.2.1.35
--        esNewSensors                               .2.1.3
--    eventSensorPointConfig                         .2.2
--      esPointConfigTempTable                       .2.2.1
--        esPointConfigTempEntry                     .2.2.1.1
--          espcTempIndexES                          .2.2.1.1.1
--          espcTempIndexPoint                       .2.2.1.1.2
--          espcTempEnable                           .2.2.1.1.3
--          espcTempScale                            .2.2.1.1.4
--          espcTempDeadband                         .2.2.1.1.5
--          espcTempVHighTemp                        .2.2.1.1.6
--          espcTempVHighActions                     .2.2.1.1.7
--          espcTempVHighTrapnum                     .2.2.1.1.8
--          espcTempVHighClass                       .2.2.1.1.9
--          espcTempHighTemp                         .2.2.1.1.10
--          espcTempHighActions                      .2.2.1.1.11
--          espcTempHighTrapnum                      .2.2.1.1.12
--          espcTempHighClass                        .2.2.1.1.13
--          espcTempNormalActions                    .2.2.1.1.14
--          espcTempNormalTrapnum                    .2.2.1.1.15
--          espcTempNormalClass                      .2.2.1.1.16
--          espcTempLowTemp                          .2.2.1.1.17
--          espcTempLowActions                       .2.2.1.1.18
--          espcTempLowTrapnum                       .2.2.1.1.19
--          espcTempLowClass                         .2.2.1.1.20
--          espcTempVLowTemp                         .2.2.1.1.21
--          espcTempVLowActions                      .2.2.1.1.22
--          espcTempVLowTrapnum                      .2.2.1.1.23
--          espcTempVLowClass                        .2.2.1.1.24
--      esPointConfigCCTable                         .2.2.2
--        esPointConfigCCEntry                       .2.2.2.1
--          espcCCIndexES                            .2.2.2.1.1
--          espcCCIndexPoint                         .2.2.2.1.2
--          espcCCEnable                             .2.2.2.1.3
--          espcCCName                               .2.2.2.1.4
--          espcCCEventState                         .2.2.2.1.5
--          espcCCThreshold                          .2.2.2.1.6
--          espcCCEventActions                       .2.2.2.1.7
--          espcCCEventTrapnum                       .2.2.2.1.8
--          espcCCEventClass                         .2.2.2.1.9
--          espcCCNormalActions                      .2.2.2.1.10
--          espcCCNormalTrapnum                      .2.2.2.1.11
--          espcCCNormalClass                        .2.2.2.1.12
--          espcCCAlarmAlias                         .2.2.2.1.13
--          espcCCNormalAlias                        .2.2.2.1.14
--          espcCCNormalThreshold                    .2.2.2.1.15
--          espcCCOverrideGlobalReminder             .2.2.2.1.16
--          espcCCReminderInterval                   .2.2.2.1.17
--      esPointConfigHumidTable                      .2.2.3
--        esPointConfigHumidEntry                    .2.2.3.1
--          espcHumidIndexES                         .2.2.3.1.1
--          espcHumidIndexPoint                      .2.2.3.1.2
--          espcHumidEnable                          .2.2.3.1.3
--          espcHumidDeadband                        .2.2.3.1.4
--          espcHumidVHighHumid                      .2.2.3.1.5
--          espcHumidVHighActions                    .2.2.3.1.6
--          espcHumidVHighTrapnum                    .2.2.3.1.7
--          espcHumidVHighClass                      .2.2.3.1.8
--          espcHumidHighHumid                       .2.2.3.1.9
--          espcHumidHighActions                     .2.2.3.1.10
--          espcHumidHighTrapnum                     .2.2.3.1.11
--          espcHumidHighClass                       .2.2.3.1.12
--          espcHumidNormalActions                   .2.2.3.1.13
--          espcHumidNormalTrapnum                   .2.2.3.1.14
--          espcHumidNormalClass                     .2.2.3.1.15
--          espcHumidLowHumid                        .2.2.3.1.16
--          espcHumidLowActions                      .2.2.3.1.17
--          espcHumidLowTrapnum                      .2.2.3.1.18
--          espcHumidLowClass                        .2.2.3.1.19
--          espcHumidVLowHumid                       .2.2.3.1.20
--          espcHumidVLowActions                     .2.2.3.1.21
--          espcHumidVLowTrapnum                     .2.2.3.1.22
--          espcHumidVLowClass                       .2.2.3.1.23
--      esPointConfigAITable                         .2.2.5
--        esPointConfigAIEntry                       .2.2.5.1
--          espcAIIndexES                            .2.2.5.1.1
--          espcAIIndexPoint                         .2.2.5.1.2
--          espcAIEnable                             .2.2.5.1.3
--          espcAIDeadband                           .2.2.5.1.5
--          espcAIVhighValue                         .2.2.5.1.6
--          espcAIVhighActions                       .2.2.5.1.7
--          espcAIVhighTrapnum                       .2.2.5.1.8
--          espcAIVhighClass                         .2.2.5.1.9
--          espcAIHighValue                          .2.2.5.1.10
--          espcAIHighActions                        .2.2.5.1.11
--          espcAIHighTrapnum                        .2.2.5.1.12
--          espcAIHighClass                          .2.2.5.1.13
--          espcAINormalActions                      .2.2.5.1.14
--          espcAINormalTrapnum                      .2.2.5.1.15
--          espcAINormalClass                        .2.2.5.1.16
--          espcAILowValue                           .2.2.5.1.17
--          espcAILowActions                         .2.2.5.1.18
--          espcAILowTrapnum                         .2.2.5.1.19
--          espcAILowClass                           .2.2.5.1.20
--          espcAIVlowValue                          .2.2.5.1.21
--          espcAIVlowActions                        .2.2.5.1.22
--          espcAIVlowTrapnum                        .2.2.5.1.23
--          espcAIVlowClass                          .2.2.5.1.24
--          espcAIConvUnitName                       .2.2.5.1.25
--          espcAIConvHighValue                      .2.2.5.1.26
--          espcAIConvHighUnit                       .2.2.5.1.27
--          espcAIConvLowValue                       .2.2.5.1.29
--          espcAIConvLowUnit                        .2.2.5.1.30
--          espcAIDisplayFormat                      .2.2.5.1.32
--      esPointConfigOutputTable                     .2.2.6
--        esPointConfigOutputEntry                   .2.2.6.1
--          espcOutputIndexES                        .2.2.6.1.1
--          espcOutputIndexPoint                     .2.2.6.1.2
--          espcOutputEnable                         .2.2.6.1.3
--          espcOutputActiveState                    .2.2.6.1.4
--          espcOutputType                           .2.2.6.1.5
--          espcOutputAliasValue                     .2.2.6.1.6
--          espcOutputAliasColor                     .2.2.6.1.7
--          espcOutputActiveAlias                    .2.2.6.1.10
--          espcOutputActiveColor                    .2.2.6.1.11
--          espcOutputActiveActions                  .2.2.6.1.12
--          espcOutputActiveTrapnum                  .2.2.6.1.13
--          espcOutputActiveClass                    .2.2.6.1.14
--          espcOutputInactiveAlias                  .2.2.6.1.20
--          espcOutputInactiveColor                  .2.2.6.1.21
--          espcOutputInactiveActions                .2.2.6.1.22
--          espcOutputInactiveTrapnum                .2.2.6.1.23
--          espcOutputInactiveClass                  .2.2.6.1.24
--    serialPorts                                    .2.3
--      numberPorts                                  .2.3.1
--      portConfigTable                              .2.3.2
--        portConfigEntry                            .2.3.2.1
--          portConfigIndex                          .2.3.2.1.1
--          portConfigBaud                           .2.3.2.1.2
--          portConfigDataFormat                     .2.3.2.1.3
--          portConfigStripPtOutputLfs               .2.3.2.1.4
--          portConfigStripPtInputLfs                .2.3.2.1.5
--          portConfigMaskEnable                     .2.3.2.1.7
--          portConfigDAEnable                       .2.3.2.1.8
--          portConfigStoreAlarmsDPT                 .2.3.2.1.9
--          portConfigRecordTimeout                  .2.3.2.1.10
--          portConfigDataType                       .2.3.2.1.11
--          portConfigEtxToCRLF                      .2.3.2.1.12
--          portConfigMLREnable                      .2.3.2.1.13
--          portConfigMLRStartField1Pos              .2.3.2.1.14
--          portConfigMLRStartField1Text             .2.3.2.1.15
--          portConfigMLRStartField2Pos              .2.3.2.1.16
--          portConfigMLRStartField2Text             .2.3.2.1.17
--          portConfigMLRNumLinesBefore              .2.3.2.1.18
--          portConfigMLREndDetection                .2.3.2.1.19
--          portConfigMLRLineCount                   .2.3.2.1.20
--          portConfigMLREndField1Pos                .2.3.2.1.21
--          portConfigMLREndField1Text               .2.3.2.1.22
--          portConfigMLREndField2Pos                .2.3.2.1.23
--          portConfigMLREndField2Text               .2.3.2.1.24
--          portConfigMLRUseComplexRules             .2.3.2.1.25
--          portConfigBufferPT                       .2.3.2.1.26
--          portConfigId                             .2.3.2.1.27
--          portConfigMode                           .2.3.2.1.28
--          portConfigHsk                            .2.3.2.1.29
--    network                                        .2.4
--      interface                                    .2.4.1
--        ethernet                                   .2.4.1.1
--          ethernet1                                .2.4.1.1.1
--            eth1Mode                               .2.4.1.1.1.1
--            eth1Address                            .2.4.1.1.1.2
--            eth1SubnetMask                         .2.4.1.1.1.3
--            eth1Router                             .2.4.1.1.1.4
--            eth1VLAN                               .2.4.1.1.1.5
--              eth1VLAN1                            .2.4.1.1.1.5.1
--                eth1VLAN1ID                        .2.4.1.1.1.5.1.1
--                eth1VLAN1Priority                  .2.4.1.1.1.5.1.2
--                eth1VLAN1Address                   .2.4.1.1.1.5.1.3
--                eth1VLAN1SubnetMask                .2.4.1.1.1.5.1.4
--                eth1VLAN1Router                    .2.4.1.1.1.5.1.5
--              eth1VLAN2                            .2.4.1.1.1.5.2
--                eth1VLAN2ID                        .2.4.1.1.1.5.2.1
--                eth1VLAN2Priority                  .2.4.1.1.1.5.2.2
--                eth1VLAN2Address                   .2.4.1.1.1.5.2.3
--                eth1VLAN2SubnetMask                .2.4.1.1.1.5.2.4
--                eth1VLAN2Router                    .2.4.1.1.1.5.2.5
--              eth1VLAN3                            .2.4.1.1.1.5.3
--                eth1VLAN3ID                        .2.4.1.1.1.5.3.1
--                eth1VLAN3Priority                  .2.4.1.1.1.5.3.2
--                eth1VLAN3Address                   .2.4.1.1.1.5.3.3
--                eth1VLAN3SubnetMask                .2.4.1.1.1.5.3.4
--                eth1VLAN3Router                    .2.4.1.1.1.5.3.5
--              eth1VLAN4                            .2.4.1.1.1.5.4
--                eth1VLAN4ID                        .2.4.1.1.1.5.4.1
--                eth1VLAN4Priority                  .2.4.1.1.1.5.4.2
--                eth1VLAN4Address                   .2.4.1.1.1.5.4.3
--                eth1VLAN4SubnetMask                .2.4.1.1.1.5.4.4
--                eth1VLAN4Router                    .2.4.1.1.1.5.4.5
--              eth1VLAN5                            .2.4.1.1.1.5.5
--                eth1VLAN5ID                        .2.4.1.1.1.5.5.1
--                eth1VLAN5Priority                  .2.4.1.1.1.5.5.2
--                eth1VLAN5Address                   .2.4.1.1.1.5.5.3
--                eth1VLAN5SubnetMask                .2.4.1.1.1.5.5.4
--                eth1VLAN5Router                    .2.4.1.1.1.5.5.5
--              eth1VLAN6                            .2.4.1.1.1.5.6
--                eth1VLAN6ID                        .2.4.1.1.1.5.6.1
--                eth1VLAN6Priority                  .2.4.1.1.1.5.6.2
--                eth1VLAN6Address                   .2.4.1.1.1.5.6.3
--                eth1VLAN6SubnetMask                .2.4.1.1.1.5.6.4
--                eth1VLAN6Router                    .2.4.1.1.1.5.6.5
--              eth1MAC                              .2.4.1.1.1.6
--            eth1IPv6                               .2.4.1.1.1.7
--              eth1IPv6Mode                         .2.4.1.1.1.7.1
--              eth1IPv6Static                       .2.4.1.1.1.7.2
--                eth1IPv6StaticAddress              .2.4.1.1.1.7.2.1
--                eth1IPv6StaticRouter               .2.4.1.1.1.7.2.2
--              eth1IPv6Auto                         .2.4.1.1.1.7.3
--                eth1IPv6AutoAddress1               .2.4.1.1.1.7.3.1
--                eth1IPv6AutoAddress2               .2.4.1.1.1.7.3.2
--                eth1IPv6AutoAddress3               .2.4.1.1.1.7.3.3
--                eth1IPv6AutoAddress4               .2.4.1.1.1.7.3.4
--              eth1IPv6LinkLocalAddress             .2.4.1.1.1.7.4
--          ethernet2                                .2.4.1.1.2
--            eth2Mode                               .2.4.1.1.2.1
--            eth2Address                            .2.4.1.1.2.2
--            eth2SubnetMask                         .2.4.1.1.2.3
--            eth2Router                             .2.4.1.1.2.4
--            eth2VLAN                               .2.4.1.1.2.5
--              eth2VLAN1                            .2.4.1.1.2.5.1
--                eth2VLAN1ID                        .2.4.1.1.2.5.1.1
--                eth2VLAN1Priority                  .2.4.1.1.2.5.1.2
--                eth2VLAN1Address                   .2.4.1.1.2.5.1.3
--                eth2VLAN1SubnetMask                .2.4.1.1.2.5.1.4
--                eth2VLAN1Router                    .2.4.1.1.2.5.1.5
--              eth2VLAN2                            .2.4.1.1.2.5.2
--                eth2VLAN2ID                        .2.4.1.1.2.5.2.1
--                eth2VLAN2Priority                  .2.4.1.1.2.5.2.2
--                eth2VLAN2Address                   .2.4.1.1.2.5.2.3
--                eth2VLAN2SubnetMask                .2.4.1.1.2.5.2.4
--                eth2VLAN2Router                    .2.4.1.1.2.5.2.5
--              eth2VLAN3                            .2.4.1.1.2.5.3
--                eth2VLAN3ID                        .2.4.1.1.2.5.3.1
--                eth2VLAN3Priority                  .2.4.1.1.2.5.3.2
--                eth2VLAN3Address                   .2.4.1.1.2.5.3.3
--                eth2VLAN3SubnetMask                .2.4.1.1.2.5.3.4
--                eth2VLAN3Router                    .2.4.1.1.2.5.3.5
--              eth2VLAN4                            .2.4.1.1.2.5.4
--                eth2VLAN4ID                        .2.4.1.1.2.5.4.1
--                eth2VLAN4Priority                  .2.4.1.1.2.5.4.2
--                eth2VLAN4Address                   .2.4.1.1.2.5.4.3
--                eth2VLAN4SubnetMask                .2.4.1.1.2.5.4.4
--                eth2VLAN4Router                    .2.4.1.1.2.5.4.5
--              eth2VLAN5                            .2.4.1.1.2.5.5
--                eth2VLAN5ID                        .2.4.1.1.2.5.5.1
--                eth2VLAN5Priority                  .2.4.1.1.2.5.5.2
--                eth2VLAN5Address                   .2.4.1.1.2.5.5.3
--                eth2VLAN5SubnetMask                .2.4.1.1.2.5.5.4
--                eth2VLAN5Router                    .2.4.1.1.2.5.5.5
--              eth2VLAN6                            .2.4.1.1.2.5.6
--                eth2VLAN6ID                        .2.4.1.1.2.5.6.1
--                eth2VLAN6Priority                  .2.4.1.1.2.5.6.2
--                eth2VLAN6Address                   .2.4.1.1.2.5.6.3
--                eth2VLAN6SubnetMask                .2.4.1.1.2.5.6.4
--                eth2VLAN6Router                    .2.4.1.1.2.5.6.5
--              eth2MAC                              .2.4.1.1.2.6
--            eth2IPv6                               .2.4.1.1.2.7
--              eth2IPv6Mode                         .2.4.1.1.2.7.1
--              eth2IPv6Static                       .2.4.1.1.2.7.2
--                eth2IPv6StaticAddress              .2.4.1.1.2.7.2.1
--                eth2IPv6StaticRouter               .2.4.1.1.2.7.2.2
--              eth2IPv6Auto                         .2.4.1.1.2.7.3
--                eth2IPv6AutoAddress1               .2.4.1.1.2.7.3.1
--                eth2IPv6AutoAddress2               .2.4.1.1.2.7.3.2
--                eth2IPv6AutoAddress3               .2.4.1.1.2.7.3.3
--                eth2IPv6AutoAddress4               .2.4.1.1.2.7.3.4
--              eth2IPv6LinkLocalAddress             .2.4.1.1.2.7.4
--      defaultRouter                                .2.4.2
--      dnsTable                                     .2.4.3
--        dnsEntry                                   .2.4.3.1
--          dnsIndex                                 .2.4.3.1.1
--          dnsAddress                               .2.4.3.1.2
--      hostname                                     .2.4.4
--      hostTable                                    .2.4.5
--        hostEntry                                  .2.4.5.1
--          hostIndex                                .2.4.5.1.1
--          hostDeclaration                          .2.4.5.1.2
--      ncpDuplex                                    .2.4.6
--      ncpTimeout                                   .2.4.7
--      snmp                                         .2.4.8
--        snmpAgentEnable                            .2.4.8.1
--        snmpNotificationCaptureEnable              .2.4.8.5
--        snmpNotificationCaptureFile                .2.4.8.6
--        snmpNotificationTx                         .2.4.8.7
--          snmpNtfnAttempts                         .2.4.8.7.1
--          snmpNtfnTimeout                          .2.4.8.7.2
--          snmpNtfnCycles                           .2.4.8.7.3
--          snmpNtfnSnooze                           .2.4.8.7.4
--        snmpPoll                                   .2.4.8.9
--          snmpPMode                                .2.4.8.9.1
--          snmpPBufferFile                          .2.4.8.9.2
--          snmpPBufferAllPeriod                     .2.4.8.9.3
--          snmpPRequestTable                        .2.4.8.9.4
--            snmpPRequestEntry                      .2.4.8.9.4.1
--              snmpPRequestIndex                    .2.4.8.9.4.1.1
--              snmpPRequestDescription              .2.4.8.9.4.1.2
--              snmpPRequestAgent                    .2.4.8.9.4.1.3
--              snmpPRequestReadcom                  .2.4.8.9.4.1.4
--              snmpPRequestOID                      .2.4.8.9.4.1.5
--              snmpPRequestPeriod                   .2.4.8.9.4.1.6
--              snmpPRequestID                       .2.4.8.9.4.1.7
--              snmpPRequestThreshold                .2.4.8.9.4.1.8
--              snmpPRequestResultStatus             .2.4.8.9.4.1.10
--              snmpPRequestResultValue              .2.4.8.9.4.1.11
--              snmpPRequestResultTime               .2.4.8.9.4.1.12
--              snmpPRequestResultType               .2.4.8.9.4.1.13
--      ftpPush                                      .2.4.9
--        ftpPushEnable                              .2.4.9.1
--        ftpPushServer                              .2.4.9.2
--        ftpPushAccount                             .2.4.9.5
--        ftpPushDirectory                           .2.4.9.6
--        ftpPushperiod                              .2.4.9.7
--        ftpPushPushFileTable                       .2.4.9.8
--          ftpPushPushFileEntry                     .2.4.9.8.1
--            ftpPushPushFileIndex                   .2.4.9.8.1.1
--            ftpPushPushFile                        .2.4.9.8.1.2
--        ftpPushPushAudit                           .2.4.9.9
--        ftpPushPushAlarms                          .2.4.9.10
--        ftpPushRemoteFileTable                     .2.4.9.11
--          ftpPushRemoteFileEntry                   .2.4.9.11.1
--            ftpPushRemoteFileIndex                 .2.4.9.11.1.1
--            ftpPushRemoteFileName                  .2.4.9.11.1.2
--        ftpPushRemoteAlarmName                     .2.4.9.12
--        ftpPushPassive                             .2.4.9.13
--        ftpPushIncludeDate                         .2.4.9.14
--        ftpPushIncludeTime                         .2.4.9.15
--        ftpPushIncludeSeq                          .2.4.9.16
--        ftpPushPermissions                         .2.4.9.17
--      ppp                                          .2.4.10
--        pppDial                                    .2.4.10.1
--          pppDialEnable                            .2.4.10.1.1
--          pppDialNumber                            .2.4.10.1.2
--          pppDialIdleTimeout                       .2.4.10.1.5
--          pppDialRetries                           .2.4.10.1.6
--          pppDialCDTimeout                         .2.4.10.1.7
--          pppDialLoginTimeout                      .2.4.10.1.8
--          pppDialMdmInit                           .2.4.10.1.9
--          pppDialSuggestIP                         .2.4.10.1.10
--          pppDialPlainLogin                        .2.4.10.1.11
--        pppHost                                    .2.4.10.2
--          pppHostEnable                            .2.4.10.2.1
--          pppHostIdleTimeout                       .2.4.10.2.2
--          pppHostLocalIP                           .2.4.10.2.3
--          pppHostRemoteIP                          .2.4.10.2.4
--      routing                                      .2.4.11
--        pppRoutingEnable                           .2.4.11.1
--        ethRoutingEnable                           .2.4.11.2
--        ethRoutingNATEnable                        .2.4.11.3
--        routingInterface                           .2.4.11.4
--        eth2WanRoutingEnable                       .2.4.11.5
--      netSecurity                                  .2.4.12
--        ipRestriction                              .2.4.12.1
--          ipRestrictionTable                       .2.4.12.1.1
--            ipRestrictionEntry                     .2.4.12.1.1.1
--              ipRestrictionIndex                   .2.4.12.1.1.1.1
--              ipRestrictionEnable                  .2.4.12.1.1.1.2
--              ipRestrictionMask                    .2.4.12.1.1.1.3
--      rts                                          .2.4.13
--        rtsFileTable                               .2.4.13.1
--          rtsFileEntry                             .2.4.13.1.1
--            rtsFileIndex                           .2.4.13.1.1.1
--            rtsFileMode                            .2.4.13.1.1.2
--            rtsFileShowAnswer                      .2.4.13.1.1.3
--            rtsFileReqXON                          .2.4.13.1.1.4
--            rtsFileTimeout                         .2.4.13.1.1.5
--            rtsFileEmptyClose                      .2.4.13.1.1.6
--            rtsFilePushHost                        .2.4.13.1.1.7
--            rtsFilePushPort                        .2.4.13.1.1.8
--            rtsFilePushRetryTimer                  .2.4.13.1.1.9
--        rtsAlarms                                  .2.4.13.2
--          rtsAlarmsMode                            .2.4.13.2.1
--          rtsAlarmsShowAnswer                      .2.4.13.2.2
--          rtsAlarmsReqXON                          .2.4.13.2.3
--          rtsAlarmsTimeout                         .2.4.13.2.4
--          rtsAlarmsEmptyClose                      .2.4.13.2.5
--          rtsAlarmsPushHost                        .2.4.13.2.6
--          rtsAlarmsPushPort                        .2.4.13.2.7
--          rtsAlarmsPushRetryTimer                  .2.4.13.2.8
--      trap                                         .2.4.14
--        trapInclude                                .2.4.14.1
--          trapIncludeDateTime                      .2.4.14.1.1
--          trapIncludeSiteName                      .2.4.14.1.2
--          trapIncludeSensorID                      .2.4.14.1.3
--          trapIncludeUDName                        .2.4.14.1.4
--          trapIncludeUDState                       .2.4.14.1.5
--          trapIncludeSourceAddress                 .2.4.14.1.6
--        trapAuthFailEnable                         .2.4.14.2
--      routeTest                                    .2.4.15
--        routeTestEnable                            .2.4.15.1
--        routeTestPeriod                            .2.4.15.2
--        routeTestAddressTable                      .2.4.15.3
--          routeTestAddressEntry                    .2.4.15.3.1
--            routeTestAddressIndex                  .2.4.15.3.1.1
--            routeTestAddress                       .2.4.15.3.1.2
--      wireless                                     .2.4.16
--        wirelessMode                               .2.4.16.1
--        wirelessAPN                                .2.4.16.2
--        wirelessIdleTimeout                        .2.4.16.3
--        wirelessPIN                                .2.4.16.5
--        wirelessDRE                                .2.4.16.9
--        wirelessPPPUsername                        .2.4.16.10
--        wirelessFirewall                           .2.4.16.11
--        wirelessKeepaliveThreshold                 .2.4.16.12
--        wirelessPPPDebug                           .2.4.16.13
--        wirelessConnectivity                       .2.4.16.20
--          wirelessConnEnable                       .2.4.16.20.1
--          wirelessConnCheckInterval                .2.4.16.20.2
--          wirelessConnFailThreshold                .2.4.16.20.3
--          wirelessConnIP1                          .2.4.16.20.10
--          wirelessConnIP2                          .2.4.16.20.11
--      email                                        .2.4.17
--        emailServer                                .2.4.17.1
--        emailDomain                                .2.4.17.2
--        emailAuthEnable                            .2.4.17.3
--      netAdvanced                                  .2.4.18
--        arpFilter                                  .2.4.18.1
--      web                                          .2.4.19
--        webEnable                                  .2.4.19.1
--        webPort                                    .2.4.19.1
--        webTimeout                                 .2.4.19.1
--      ipv6                                         .2.4.21
--        ipv6DefaultRouter                          .2.4.21.1
--      cpe                                          .2.4.22
--        cpeTable                                   .2.4.22.1
--          cpeEntry                                 .2.4.22.1.1
--            cpeIndex                               .2.4.22.1.1.1
--            cpeHost                                .2.4.22.1.1.2
--            cpeName                                .2.4.22.1.1.3
--            cpeDescription                         .2.4.22.1.1.4
--            cpeKeepalive                           .2.4.22.1.1.5
--            cpeThreshold                           .2.4.22.1.1.6
--            cpeEventReminderInterval               .2.4.22.1.1.7
--            cpeKeepaliveTicks                      .2.4.22.1.1.20
--            cpePingSize                            .2.4.22.1.1.21
--            cpeInfoReset                           .2.4.22.1.1.30
--            cpeInfoNumReq                          .2.4.22.1.1.31
--            cpeInfoNumGoodResp                     .2.4.22.1.1.32
--            cpeInfoNumBadResp                      .2.4.22.1.1.33
--            cpeInfoNumLostResp                     .2.4.22.1.1.34
--            cpeInfoPercentLoss                     .2.4.22.1.1.35
--            cpeInfoPercentBad                      .2.4.22.1.1.36
--    modem                                          .2.5
--      modemFormat                                  .2.5.1
--      modemInitString                              .2.5.2
--      modemCallAttempts                            .2.5.4
--      modemCallDelay                               .2.5.5
--      modemCmdTimout                               .2.5.6
--      modemGoto                                    .2.5.7
--      modemClid                                    .2.5.8
--        modemCLIDEnable                            .2.5.8.1
--        modemCLIDNumberTable                       .2.5.8.2
--          modemCLIDNumberEntry                     .2.5.8.2.1
--            modemCLIDNumberIndex                   .2.5.8.2.1.1
--            modemCLIDNumber                        .2.5.8.2.1.2
--      modemTAPInitString                           .2.5.9
--      modemTAP8N1                                  .2.5.10
--    time                                           .2.8
--      clock                                        .2.8.1
--    console                                        .2.10
--      consoleDuplex                                .2.10.1
--      consoleTimeout                               .2.10.2
--      consoleBaud                                  .2.10.4
--      consoleFormat                                .2.10.5
--      consoleHsk                                   .2.10.6
--      consoleConfirm                               .2.10.7
--    unitSecurity                                   .2.11
--      secCore                                      .2.11.1
--        scShowPasswordPrompt                       .2.11.1.1
--        scConsoleLoginRequired                     .2.11.1.2
--        scModemLoginRequired                       .2.11.1.3
--        scTelnetLoginRequired                      .2.11.1.4
--        scTelnetPTLoginRequired                    .2.11.1.5
--        scRTSLoginRequired                         .2.11.1.6
--        scAuthMode                                 .2.11.1.7
--        scRightsGroup                              .2.11.1.8
--        scSecret                                   .2.11.1.9
--      secUserTable                                 .2.11.2
--        secUserEntry                               .2.11.2.1
--          secUserIndex                             .2.11.2.1.1
--          secUserEnable                            .2.11.2.1.2
--          secUserConnectVia                        .2.11.2.1.5
--          secUserLoginTo                           .2.11.2.1.6
--          secUserAccessFile                        .2.11.2.1.7
--          secUserPTEscapeTo                        .2.11.2.1.9
--          secUserPPPType                           .2.11.2.1.10
--          secUserRights                            .2.11.2.1.11
--          secUserEventsReadAccess                  .2.11.2.1.13
--          secUserAuditReadAccess                   .2.11.2.1.14
--          secUserEventsWriteAccess                 .2.11.2.1.16
--          secUserAuditWriteAccess                  .2.11.2.1.17
--          secUserExpiration                        .2.11.2.1.18
--          secUserCallbackNumber1                   .2.11.2.1.19
--          secUserCallbackNumber2                   .2.11.2.1.20
--          secUserCallbackNumber3                   .2.11.2.1.21
--          secUserChallengeTelnetMode               .2.11.2.1.22
--          secUserChallengeModemMode                .2.11.2.1.23
--          secUserChallengeConsoleMode              .2.11.2.1.24
--          secUserChallengeTelnetSendTo             .2.11.2.1.25
--          secUserChallengeModemSendTo              .2.11.2.1.26
--          secUserChallengeExpiration               .2.11.2.1.27
--      secFactory                                   .2.11.3
--        sfEnable                                   .2.11.3.1
--        sfSecret                                   .2.11.3.2
--      secSSH                                       .2.11.4
--      secVPN                                       .2.11.5
--    event                                          .2.12
--      evCore                                       .2.12.1
--        evClassNameTable                           .2.12.1.1
--          evClassNameEntry                         .2.12.1.1.1
--            evClassNameIndex                       .2.12.1.1.1.1
--            evClassName                            .2.12.1.1.1.2
--        evReminderInterval                         .2.12.1.2
--        evLog                                      .2.12.1.3
--          evLogEnable                              .2.12.1.3.1
--          evLogStoreAlarm                          .2.12.1.3.2
--          evLogMaxSize                             .2.12.1.3.3
--          evLogStoreSensor                         .2.12.1.3.4
--          evLogTimeStampAlarms                     .2.12.1.3.5
--          evLogPrependName                         .2.12.1.3.6
--        evMgmt                                     .2.12.1.4
--          evMgmtReprocess                          .2.12.1.4.3
--      evData                                       .2.12.2
--        evdCore                                    .2.12.2.1
--          evdExitOnTrue                            .2.12.2.1.1
--          evdFilterAction                          .2.12.2.1.2
--          evdWildCardChar                          .2.12.2.1.3
--        evdTable                                   .2.12.2.2
--          evdEntry                                 .2.12.2.2.1
--            evdIndex                               .2.12.2.2.1.1
--            evdEnable                              .2.12.2.2.1.2
--            evdName                                .2.12.2.2.1.3
--            evdEquation                            .2.12.2.2.1.4
--            evdThreshold                           .2.12.2.2.1.5
--            evdAutoclear                           .2.12.2.2.1.6
--            evdClearInterval                       .2.12.2.2.1.7
--            evdClearTime                           .2.12.2.2.1.8
--            evdActions                             .2.12.2.2.1.9
--            evdClass                               .2.12.2.2.1.10
--            evdTrapNum                             .2.12.2.2.1.11
--            evdMode                                .2.12.2.2.1.12
--        evdFieldTable                              .2.12.2.3
--          evdFieldEntry                            .2.12.2.3.1
--            evdFieldIndex                          .2.12.2.3.1.1
--            evdFieldStart                          .2.12.2.3.1.2
--            evdFieldLength                         .2.12.2.3.1.3
--            evdFieldName                           .2.12.2.3.1.4
--            evdFieldLine                           .2.12.2.3.1.5
--            evdFieldType                           .2.12.2.3.1.6
--        evdMacroTable                              .2.12.2.4
--          evdMacroEntry                            .2.12.2.4.1
--            evdMacroIndex                          .2.12.2.4.1.1
--            evdMacroName                           .2.12.2.4.1.2
--            evdMacroEquation                       .2.12.2.4.1.3
--      evNoData1                                    .2.12.3
--        evNoData1Enable                            .2.12.3.1
--        evNoData1Actions                           .2.12.3.2
--        evNoData1Message                           .2.12.3.3
--        evNoData1TrapNum                           .2.12.3.4
--        evNoData1Class                             .2.12.3.5
--        evNoData1Sched1Begin                       .2.12.3.6
--        evNoData1Sched1End                         .2.12.3.7
--        evNoData1Sched1Duration                    .2.12.3.8
--        evNoData1Sched2Begin                       .2.12.3.9
--        evNoData1Sched2End                         .2.12.3.10
--        evNoData1Sched2Duration                    .2.12.3.11
--        evNoData1PortEnableTable                   .2.12.3.12
--          evNoData1PortEnableEntry                 .2.12.3.12.1
--            evNoData1PortEnableIndex               .2.12.3.12.1.1
--            evNoData1PortEnable                    .2.12.3.12.1.2
--        evNoData1Exclusions                        .2.12.3.13
--        evNoData1Days                              .2.12.3.14
--      evNoData2                                    .2.12.4
--        evNoData2Enable                            .2.12.4.1
--        evNoData2Actions                           .2.12.4.2
--        evNoData2Message                           .2.12.4.3
--        evNoData2TrapNum                           .2.12.4.4
--        evNoData2Class                             .2.12.4.5
--        evNoData2Sched1Begin                       .2.12.4.6
--        evNoData2Sched1End                         .2.12.4.7
--        evNoData2Sched1Duration                    .2.12.4.8
--        evNoData2Sched2Begin                       .2.12.4.9
--        evNoData2Sched2End                         .2.12.4.10
--        evNoData2Sched2Duration                    .2.12.4.11
--        evNoData2PortEnableTable                   .2.12.4.12
--          evNoData2PortEnableEntry                 .2.12.4.12.1
--            evNoData2PortEnableIndex               .2.12.4.12.1.1
--            evNoData2PortEnable                    .2.12.4.12.1.2
--        evNoData2Exclusions                        .2.12.4.13
--        evNoData2Days                              .2.12.4.14
--      evSched1                                     .2.12.5
--        evSched1Enable                             .2.12.5.1
--        evSched1Actions                            .2.12.5.2
--        evSched1Message                            .2.12.5.3
--        evSched1TrapNum                            .2.12.5.4
--        evSched1Class                              .2.12.5.5
--        evSched1Sunday                             .2.12.5.6
--        evSched1Monday                             .2.12.5.7
--        evSched1Tuesday                            .2.12.5.8
--        evSched1Wednesday                          .2.12.5.9
--        evSched1Thursday                           .2.12.5.10
--        evSched1Friday                             .2.12.5.11
--        evSched1Saturday                           .2.12.5.12
--        evSched1Exclusions                         .2.12.5.13
--      evSched2                                     .2.12.6
--        evSched2Enable                             .2.12.6.1
--        evSched2Actions                            .2.12.6.2
--        evSched2Message                            .2.12.6.3
--        evSched2TrapNum                            .2.12.6.4
--        evSched2Class                              .2.12.6.5
--        evSched2Sunday                             .2.12.6.6
--        evSched2Monday                             .2.12.6.7
--        evSched2Tuesday                            .2.12.6.8
--        evSched2Wednesday                          .2.12.6.9
--        evSched2Thursday                           .2.12.6.10
--        evSched2Friday                             .2.12.6.11
--        evSched2Saturday                           .2.12.6.12
--        evSched2Exclusions                         .2.12.6.13
--      evShskLowTable                               .2.12.7
--        evShskLowEntry                             .2.12.7.1
--          evShskLowIndex                           .2.12.7.1.1
--          evShskLowEnable                          .2.12.7.1.2
--          evShskLowActions                         .2.12.7.1.3
--          evShskLowMessage                         .2.12.7.1.4
--          evShskLowClass                           .2.12.7.1.5
--          evShskLowTrapNum                         .2.12.7.1.6
--      evShskHighTable                              .2.12.8
--        evShskHighEntry                            .2.12.8.1
--          evShskHighIndex                          .2.12.8.1.1
--          evShskHighEnable                         .2.12.8.1.2
--          evShskHighActions                        .2.12.8.1.3
--          evShskHighMessage                        .2.12.8.1.4
--          evShskHighClass                          .2.12.8.1.5
--          evShskHighTrapNum                        .2.12.8.1.6
--      evNoSensor                                   .2.12.9
--        evNoSensorTimeout                          .2.12.9.1
--        evNoSensorActions                          .2.12.9.2
--        evNoSensorTrapNum                          .2.12.9.3
--        evNoSensorClass                            .2.12.9.4
--      fuelSensor                                   .2.12.11
--        fuelSensorGeneralTable                     .2.12.11.1
--          fsGenEntry                               .2.12.11.1.1
--            fsGenIndex                             .2.12.11.1.1.1
--            fsGenName                              .2.12.11.1.1.2
--            fsGenSensorType                        .2.12.11.1.1.3
--            fsGenDistanceUnit                      .2.12.11.1.1.4
--            fsGenRawValueTop                       .2.12.11.1.1.5
--            fsGenTopOffset                         .2.12.11.1.1.6
--            fsGenRawValueBottom                    .2.12.11.1.1.7
--            fsGenBottomOffset                      .2.12.11.1.1.8
--            fsGenInputES                           .2.12.11.1.1.9
--            fsGenInputPoint                        .2.12.11.1.1.10
--            fsGenFilterAveraging                   .2.12.11.1.1.11
--            fsGenSysrepEnable                      .2.12.11.1.1.12
--            fsGenSysrepThreshold                   .2.12.11.1.1.13
--            fsGenSysrepLimit                       .2.12.11.1.1.14
--            fsGenSysrepPackage                     .2.12.11.1.1.15
--            fsGenSysrepType                        .2.12.11.1.1.16
--            fsGenEnable                            .2.12.11.1.1.17
--        fuelSensorTankTable                        .2.12.11.2
--          fsTankEntry                              .2.12.11.2.1
--            fsTankIndex                            .2.12.11.2.1.1
--            fsTankHeight                           .2.12.11.2.1.2
--            fsTankDimA                             .2.12.11.2.1.3
--            fsTankDimB                             .2.12.11.2.1.4
--            fsTankVolume                           .2.12.11.2.1.5
--            fsTankVolumeUnit                       .2.12.11.2.1.6
--            fsTankShape                            .2.12.11.2.1.7
--        fuelSensorCustomTankTable                  .2.12.11.3
--          fsCustomTankEntry                        .2.12.11.3.1
--            fsCustomTankIndexFS                    .2.12.11.3.1.1
--            fsCustomTankIndexDatum                 .2.12.11.3.1.2
--            fsCustomTankHeight                     .2.12.11.3.1.3
--            fsCustomTankVolume                     .2.12.11.3.1.4
--        fuelSensorVolumeTable                      .2.12.11.4
--          fsVolumeEntry                            .2.12.11.4.1
--            fsVolumeIndex                          .2.12.11.4.1.1
--            fsVolumeEnable                         .2.12.11.4.1.2
--            fsVolumeDeadband                       .2.12.11.4.1.3
--            fsVolumeVHighValue                     .2.12.11.4.1.4
--            fsVolumeVHighActions                   .2.12.11.4.1.5
--            fsVolumeVHighTrapNum                   .2.12.11.4.1.6
--            fsVolumeVHighClass                     .2.12.11.4.1.7
--            fsVolumeHighValue                      .2.12.11.4.1.8
--            fsVolumeHighActions                    .2.12.11.4.1.9
--            fsVolumeHighTrapNum                    .2.12.11.4.1.10
--            fsVolumeHighClass                      .2.12.11.4.1.11
--            fsVolumeNormalActions                  .2.12.11.4.1.12
--            fsVolumeNormalTrapNum                  .2.12.11.4.1.13
--            fsVolumeNormalClass                    .2.12.11.4.1.14
--            fsVolumeLowValue                       .2.12.11.4.1.15
--            fsVolumeLowActions                     .2.12.11.4.1.16
--            fsVolumeLowTrapNum                     .2.12.11.4.1.17
--            fsVolumeLowClass                       .2.12.11.4.1.18
--            fsVolumeVLowValue                      .2.12.11.4.1.19
--            fsVolumeVLowActions                    .2.12.11.4.1.20
--            fsVolumeVLowTrapNum                    .2.12.11.4.1.21
--            fsVolumeVLowClass                      .2.12.11.4.1.22
--        fuelSensorDisconnectTable                  .2.12.11.5
--          fsDiscEntry                              .2.12.11.5.1
--            fsDiscIndex                            .2.12.11.5.1.1
--            fsDiscEnable                           .2.12.11.5.1.2
--            fsDiscHighValue                        .2.12.11.5.1.3
--            fsDiscLowValue                         .2.12.11.5.1.4
--            fsDiscActions                          .2.12.11.5.1.5
--            fsDiscTrapNum                          .2.12.11.5.1.6
--            fsDiscClass                            .2.12.11.5.1.7
--            fsDiscNormalActions                    .2.12.11.5.1.8
--            fsDiscNormalTrapNum                    .2.12.11.5.1.9
--            fsDiscNormalClass                      .2.12.11.5.1.10
--      acPowerMonitor                               .2.12.12
--        acpmGeneralTable                           .2.12.12.1
--          acpmGenEntry                             .2.12.12.1.1
--            acpmGenIndex                           .2.12.12.1.1.1
--            acpmGenDevice                          .2.12.12.1.1.2
--            acpmGenName                            .2.12.12.1.1.3
--            acpmGenAddress                         .2.12.12.1.1.4
--            acpmGenPtRatio                         .2.12.12.1.1.5
--            acpmGenCtRatio                         .2.12.12.1.1.6
--            acpmGenPowerType                       .2.12.12.1.1.7
--            acpmGenSysrepPackage                   .2.12.12.1.1.8
--            acpmGenSysrepType                      .2.12.12.1.1.9
--            acpmGenEnable                          .2.12.12.1.1.10
--        acpmAvgVoltageTable                        .2.12.12.2
--          acpmAvgVoltageEntry                      .2.12.12.2.1
--            acpmAvgVoltageIndex                    .2.12.12.2.1.1
--            acpmAvgVoltageEnable                   .2.12.12.2.1.2
--            acpmAvgVoltageDeadband                 .2.12.12.2.1.3
--            acpmAvgVoltageVHighValue               .2.12.12.2.1.4
--            acpmAvgVoltageVHighActions             .2.12.12.2.1.5
--            acpmAvgVoltageVHighTrapNum             .2.12.12.2.1.6
--            acpmAvgVoltageVHighClass               .2.12.12.2.1.7
--            acpmAvgVoltageHighValue                .2.12.12.2.1.8
--            acpmAvgVoltageHighActions              .2.12.12.2.1.9
--            acpmAvgVoltageHighTrapNum              .2.12.12.2.1.10
--            acpmAvgVoltageHighClass                .2.12.12.2.1.11
--            acpmAvgVoltageNormalActions            .2.12.12.2.1.12
--            acpmAvgVoltageNormalTrapNum            .2.12.12.2.1.13
--            acpmAvgVoltageNormalClass              .2.12.12.2.1.14
--            acpmAvgVoltageLowValue                 .2.12.12.2.1.15
--            acpmAvgVoltageLowActions               .2.12.12.2.1.16
--            acpmAvgVoltageLowTrapNum               .2.12.12.2.1.17
--            acpmAvgVoltageLowClass                 .2.12.12.2.1.18
--            acpmAvgVoltageVLowValue                .2.12.12.2.1.19
--            acpmAvgVoltageVLowActions              .2.12.12.2.1.20
--            acpmAvgVoltageVLowTrapNum              .2.12.12.2.1.21
--            acpmAvgVoltageVLowClass                .2.12.12.2.1.22
--            acpmAvgVoltageSysrepEnable             .2.12.12.2.1.23
--            acpmAvgVoltageSysrepThreshold          .2.12.12.2.1.24
--            acpmAvgVoltageSysrepLimit              .2.12.12.2.1.25
--        acpmAvgCurrentTable                        .2.12.12.3
--          acpmAvgCurrentEntry                      .2.12.12.3.1
--            acpmAvgCurrentIndex                    .2.12.12.3.1.1
--            acpmAvgCurrentEnable                   .2.12.12.3.1.2
--            acpmAvgCurrentDeadband                 .2.12.12.3.1.3
--            acpmAvgCurrentVHighValue               .2.12.12.3.1.4
--            acpmAvgCurrentVHighActions             .2.12.12.3.1.5
--            acpmAvgCurrentVHighTrapNum             .2.12.12.3.1.6
--            acpmAvgCurrentVHighClass               .2.12.12.3.1.7
--            acpmAvgCurrentHighValue                .2.12.12.3.1.8
--            acpmAvgCurrentHighActions              .2.12.12.3.1.9
--            acpmAvgCurrentHighTrapNum              .2.12.12.3.1.10
--            acpmAvgCurrentHighClass                .2.12.12.3.1.11
--            acpmAvgCurrentNormalActions            .2.12.12.3.1.12
--            acpmAvgCurrentNormalTrapNum            .2.12.12.3.1.13
--            acpmAvgCurrentNormalClass              .2.12.12.3.1.14
--            acpmAvgCurrentLowValue                 .2.12.12.3.1.15
--            acpmAvgCurrentLowActions               .2.12.12.3.1.16
--            acpmAvgCurrentLowTrapNum               .2.12.12.3.1.17
--            acpmAvgCurrentLowClass                 .2.12.12.3.1.18
--            acpmAvgCurrentVLowValue                .2.12.12.3.1.19
--            acpmAvgCurrentVLowActions              .2.12.12.3.1.20
--            acpmAvgCurrentVLowTrapNum              .2.12.12.3.1.21
--            acpmAvgCurrentVLowClass                .2.12.12.3.1.22
--            acpmAvgCurrentSysrepEnable             .2.12.12.3.1.23
--            acpmAvgCurrentSysrepThreshold          .2.12.12.3.1.24
--            acpmAvgCurrentSysrepLimit              .2.12.12.3.1.25
--        acpmFreqTable                              .2.12.12.4
--          acpmFreqEntry                            .2.12.12.4.1
--            acpmFreqIndex                          .2.12.12.4.1.1
--            acpmFreqEnable                         .2.12.12.4.1.2
--            acpmFreqDeadband                       .2.12.12.4.1.3
--            acpmFreqVHighValue                     .2.12.12.4.1.4
--            acpmFreqVHighActions                   .2.12.12.4.1.5
--            acpmFreqVHighTrapNum                   .2.12.12.4.1.6
--            acpmFreqVHighClass                     .2.12.12.4.1.7
--            acpmFreqHighValue                      .2.12.12.4.1.8
--            acpmFreqHighActions                    .2.12.12.4.1.9
--            acpmFreqHighTrapNum                    .2.12.12.4.1.10
--            acpmFreqHighClass                      .2.12.12.4.1.11
--            acpmFreqNormalActions                  .2.12.12.4.1.12
--            acpmFreqNormalTrapNum                  .2.12.12.4.1.13
--            acpmFreqNormalClass                    .2.12.12.4.1.14
--            acpmFreqLowValue                       .2.12.12.4.1.15
--            acpmFreqLowActions                     .2.12.12.4.1.16
--            acpmFreqLowTrapNum                     .2.12.12.4.1.17
--            acpmFreqLowClass                       .2.12.12.4.1.18
--            acpmFreqVLowValue                      .2.12.12.4.1.19
--            acpmFreqVLowActions                    .2.12.12.4.1.20
--            acpmFreqVLowTrapNum                    .2.12.12.4.1.21
--            acpmFreqVLowClass                      .2.12.12.4.1.22
--            acpmFreqSysrepEnable                   .2.12.12.4.1.23
--            acpmFreqSysrepThreshold                .2.12.12.4.1.24
--            acpmFreqSysrepLimit                    .2.12.12.4.1.25
--        acpmTotalRealPowerTable                    .2.12.12.5
--          acpmTRPEntry                             .2.12.12.5.1
--            acpmTRPIndex                           .2.12.12.5.1.1
--            acpmTRPEnable                          .2.12.12.5.1.2
--            acpmTRPDeadband                        .2.12.12.5.1.3
--            acpmTRPVHighValue                      .2.12.12.5.1.4
--            acpmTRPVHighActions                    .2.12.12.5.1.5
--            acpmTRPVHighTrapNum                    .2.12.12.5.1.6
--            acpmTRPVHighClass                      .2.12.12.5.1.7
--            acpmTRPHighValue                       .2.12.12.5.1.8
--            acpmTRPHighActions                     .2.12.12.5.1.9
--            acpmTRPHighTrapNum                     .2.12.12.5.1.10
--            acpmTRPHighClass                       .2.12.12.5.1.11
--            acpmTRPNormalActions                   .2.12.12.5.1.12
--            acpmTRPNormalTrapNum                   .2.12.12.5.1.13
--            acpmTRPNormalClass                     .2.12.12.5.1.14
--            acpmTRPLowValue                        .2.12.12.5.1.15
--            acpmTRPLowActions                      .2.12.12.5.1.16
--            acpmTRPLowTrapNum                      .2.12.12.5.1.17
--            acpmTRPLowClass                        .2.12.12.5.1.18
--            acpmTRPVLowValue                       .2.12.12.5.1.19
--            acpmTRPVLowActions                     .2.12.12.5.1.20
--            acpmTRPVLowTrapNum                     .2.12.12.5.1.21
--            acpmTRPVLowClass                       .2.12.12.5.1.22
--            acpmTRPSysrepEnable                    .2.12.12.5.1.23
--            acpmTRPSysrepThreshold                 .2.12.12.5.1.24
--            acpmTRPSysrepLimit                     .2.12.12.5.1.25
--        acpmDisconnectTable                        .2.12.12.6
--          acpmDisconnectEntry                      .2.12.12.6.1
--            acpmDisconnectIndex                    .2.12.12.6.1.1
--            acpmDisconnectEnable                   .2.12.12.6.1.2
--            acpmDisconnectActions                  .2.12.12.6.1.3
--            acpmDisconnectTrapNum                  .2.12.12.6.1.4
--            acpmDisconnectClass                    .2.12.12.6.1.5
--            acpmDisconnectNormalActions            .2.12.12.6.1.6
--            acpmDisconnectNormalTrapNum            .2.12.12.6.1.7
--            acpmDisconnectNormalClass              .2.12.12.6.1.8
--        acpmTotalPowerFactorTable                  .2.12.12.7
--          acpmTPFEntry                             .2.12.12.7.1
--            acpmTPFIndex                           .2.12.12.7.1.1
--            acpmTPFEnable                          .2.12.12.7.1.2
--            acpmTPFDeadband                        .2.12.12.7.1.3
--            acpmTPFNormalActions                   .2.12.12.7.1.4
--            acpmTPFNormalTrapNum                   .2.12.12.7.1.5
--            acpmTPFNormalClass                     .2.12.12.7.1.6
--            acpmTPFLowValue                        .2.12.12.7.1.7
--            acpmTPFLowActions                      .2.12.12.7.1.8
--            acpmTPFLowTrapNum                      .2.12.12.7.1.9
--            acpmTPFLowClass                        .2.12.12.7.1.10
--            acpmTPFVLowValue                       .2.12.12.7.1.11
--            acpmTPFVLowActions                     .2.12.12.7.1.12
--            acpmTPFVLowTrapNum                     .2.12.12.7.1.13
--            acpmTPFVLowClass                       .2.12.12.7.1.14
--            acpmTPFSysrepEnable                    .2.12.12.7.1.15
--            acpmTPFSysrepThreshold                 .2.12.12.7.1.16
--            acpmTPFSysrepLimit                     .2.12.12.7.1.17
--      evReset                                      .2.12.16
--        evResetEnable                              .2.12.16.1
--        evResetDelay                               .2.12.16.2
--        evResetActions                             .2.12.16.3
--        evResetMessage                             .2.12.16.4
--        evResetTrapnum                             .2.12.16.5
--        evResetClass                               .2.12.16.6
--    action                                         .2.14
--      actionCallNumberTable                        .2.14.1
--        actionCallNumberEntry                      .2.14.1.1
--          actionCallNumberIndex                    .2.14.1.1.1
--          actionCallNumber                         .2.14.1.1.2
--      actionPagerTable                             .2.14.2
--        actionPagerEntry                           .2.14.2.1
--          actionPagerIndex                         .2.14.2.1.1
--          actionPagerType                          .2.14.2.1.2
--          actionPagerNumber                        .2.14.2.1.3
--          actionPagerID                            .2.14.2.1.4
--          actionPagerMessage                       .2.14.2.1.5
--          actionPagerPostCalloutDelay              .2.14.2.1.6
--          actionPagerPostIDDelay                   .2.14.2.1.7
--      actionSched                                  .2.14.3
--        actionSchedEnable                          .2.14.3.1
--        actionSchedBegin                           .2.14.3.2
--        actionSchedEnd                             .2.14.3.3
--        actionSchedWeekdaysOnly                    .2.14.3.4
--      actionAsentria                               .2.14.4
--        actionAsentriaRequireAck                   .2.14.4.1
--        actionAsentriaVersion                      .2.14.4.2
--        actionAsentriaTCPPort                      .2.14.4.3
--      actionHostTable                              .2.14.6
--        actionHostEntry                            .2.14.6.1
--          actionHostIndex                          .2.14.6.1.1
--          actionHost                               .2.14.6.1.2
--      actionEmailTable                             .2.14.7
--        actionEmailEntry                           .2.14.7.1
--          actionEmailIndex                         .2.14.7.1.1
--          actionEmail                              .2.14.7.1.2
--      actionParseError                             .2.14.8
--    sys                                            .2.16
--      sysTime                                      .2.16.1
--        sysTimeAutoDST                             .2.16.1.1
--        sysTimeGMTOffset                           .2.16.1.2
--        sysTimeGMTDirection                        .2.16.1.3
--        sysTimeNet                                 .2.16.1.4
--          sysTimeNetEnable                         .2.16.1.4.1
--          sysTimeNetHostTable                      .2.16.1.4.2
--            sysTimeNetHostEntry                    .2.16.1.4.2.1
--              sysTimeNetHostIndex                  .2.16.1.4.2.1.1
--              sysTimeNetHost                       .2.16.1.4.2.1.2
--      sysPT                                        .2.16.2
--        sysPTTimeout                               .2.16.2.1
--        sysPTEndPause                              .2.16.2.2
--        sysPTJoinable                              .2.16.2.3
--      sysMTU                                       .2.16.3
--      sysAnswerString                              .2.16.4
--      sysEventFileID                               .2.16.6
--      sysEscapeCharacter                           .2.16.7
--      sysTimeStamp                                 .2.16.8
--        sysTimeStampTimeFormat                     .2.16.8.1
--        sysTimeStampDateFormat                     .2.16.8.2
--        sysTimeStampSpaceAfter                     .2.16.8.3
--      sysLog                                       .2.16.9
--        sysLogMode                                 .2.16.9.1
--        sysLoghost                                 .2.16.9.2
--        sysLogFilter                               .2.16.9.3
--        sysLogFileSize                             .2.16.9.4
--        sysLogFileCount                            .2.16.9.5
--        sysLogListenPort                           .2.16.9.6
--      sysCRDB                                      .2.16.10
--        sysCRDBCapacity                            .2.16.10.1
--        sysCRDBPercentFull                         .2.16.10.2
--        sysCRDBFileIDTable                         .2.16.10.3
--          sysCRDBFileIDEntry                       .2.16.10.3.1
--            sysCRDBFileIDIndex                     .2.16.10.3.1.1
--            sysCRDBFileID                          .2.16.10.3.1.2
--        sysCRDBFileEnforceMinTable                 .2.16.10.4
--          sysCRDBFileEnforceMinEntry               .2.16.10.4.1
--            sysCRDBFileEnforceMinIndex             .2.16.10.4.1.1
--            sysCRDBFileEnforceMin                  .2.16.10.4.1.2
--      sysCharMask                                  .2.16.11
--      sysPrompt                                    .2.16.12
--      sysBootStatus                                .2.16.13
--      sysLoc                                       .2.16.14
--        sysLocLatitude                             .2.16.14.1
--        sysLocLongitude                            .2.16.14.2
--        sysLocXOffset                              .2.16.14.3
--        sysLocYOffset                              .2.16.14.4
--        sysLocAngle                                .2.16.14.5
--        sysLocAltitude                             .2.16.14.6
--      sysAssetMgmt                                 .2.16.15
--        sysAMManufacturer                          .2.16.15.1
--        sysAMProduct                               .2.16.15.2
--        sysAMSerialNumber                          .2.16.15.3
--        sysAMHardwareOptions                       .2.16.15.4
--        sysAMSoftwareVersion                       .2.16.15.5
--        sysAMSiteName                              .2.16.15.6
--      sysFileTransfer                              .2.16.17
--        sysFileTransferStatus                      .2.16.17.1
--        sysFileTransferURL                         .2.16.17.2
--        sysFileTransferUsername                    .2.16.17.3
--        sysFileTransferPassword                    .2.16.17.4
--      sysUpdate                                    .2.16.18
--        sysUpdateStatus                            .2.16.18.1
--    auditLog                                       .2.17
--      auditLogEnable                               .2.17.1
--      auditLogStoreResets                          .2.17.2
--      auditLogStoreCommands                        .2.17.3
--      auditLogStoreOutputs                         .2.17.4
--      auditLogStoreAlarmActions                    .2.17.5
--      auditLogStorePwdFailures                     .2.17.6
--      auditLogStoreLogins                          .2.17.7
--      auditLogStoreSHSK                            .2.17.8
--      auditLogStorePassthrough                     .2.17.9
--      auditLogStoreInactivity                      .2.17.10
--      auditLogStorePolling                         .2.17.11
--      auditLogMaxSize                              .2.17.12
--    scripting                                      .2.18
--      scrGlobalEnable                              .2.18.1
--      scrDTRCtrlPortEnableTable                    .2.18.2
--        scrDTRCtrlPortEnableEnabletry              .2.18.2.1
--          scrDTRCtrlPortEnableIndex                .2.18.2.1.1
--          scrDTRCtrlPortEnable                     .2.18.2.1.2
--      scrTable                                     .2.18.3
--        scrEntry                                   .2.18.3.1
--          scrIndex                                 .2.18.3.1.1
--          scrEnable                                .2.18.3.1.2
--          scrName                                  .2.18.3.1.3
--          scrFilename                              .2.18.3.1.4
--          scrRunAlways                             .2.18.3.1.5
--          scrRunAtStartup                          .2.18.3.1.6
--          scrRunScheduled                          .2.18.3.1.7
--          scrScheduleTime                          .2.18.3.1.8
--          scrArguments                             .2.18.3.1.9
--          scrRepeatInterval                        .2.18.3.1.10
--      scrVolatileStringTable                       .2.18.4
--        scrVolatileStringEntry                     .2.18.4.1
--          scrVolatileStringIndex                   .2.18.4.1.1
--          scrVolatileString                        .2.18.4.1.2
--      scrVolatileIntTable                          .2.18.5
--        scrVolatileIntEntry                        .2.18.5.1
--          scrVolatileIntIndex                      .2.18.5.1.1
--          scrVolatileInt                           .2.18.5.1.2
--      scrNonVolatileStringTable                    .2.18.6
--        scrNonVolatileStringEntry                  .2.18.6.1
--          scrNonVolatileStringIndex                .2.18.6.1.1
--          scrNonVolatileString                     .2.18.6.1.2
--      scrNonVolatileIntTable                       .2.18.7
--        scrNonVolatileIntEntry                     .2.18.7.1
--          scrNonVolatileIntIndex                   .2.18.7.1.1
--          scrNonVolatileInt                        .2.18.7.1.2

--  productIds                                       .3
--    siteName                                        3.1
--    thisProduct                                    .3.2
--    stockTrapString                                .3.3
--    trapEventTypeNumber                            .3.4
--    trapEventTypeName                              .3.5
--    trapIncludedValue                              .3.6
--    trapIncludedString                             .3.7
--    trapTypeString                                 .3.8
--    trapEventClassNumber                           .3.9
--    trapEventClassName                             .3.10

--  keyInterface                                     .4.0


--***************************************************************************************
--TOP-LEVEL OBJECT IDENTIFIERS
--***************************************************************************************



    status OBJECT IDENTIFIER ::= { s571 1 }
    --1.3.6.1.4.1.3052.14.1

        eventSensorStatus OBJECT IDENTIFIER ::= { status 1 }
        --1.3.6.1.4.1.3052.14.1.1

        dataEventStatus OBJECT IDENTIFIER ::= { status 2 }
        --1.3.6.1.4.1.3052.14.1.2

        powerDistributionStatus OBJECT IDENTIFIER ::= { status 5 }
        --1.3.6.1.4.1.3052.14.1.5

            pdMain OBJECT IDENTIFIER ::= { powerDistributionStatus 2 }
            --1.3.6.1.4.1.3052.14.1.5.2

                pdMainCurrent OBJECT IDENTIFIER ::= { pdMain 1 }
                --1.3.6.1.4.1.3052.14.1.5.2.1

                pdMainVoltage OBJECT IDENTIFIER ::= { pdMain 2 }
                --1.3.6.1.4.1.3052.14.1.5.2.2

                pdMainPower OBJECT IDENTIFIER ::= { pdMain 3 }
                --1.3.6.1.4.1.3052.14.1.5.2.3

            pdOutput OBJECT IDENTIFIER ::= { powerDistributionStatus 3 }
            --1.3.6.1.4.1.3052.14.1.5.3

              pdOutputCurrent OBJECT IDENTIFIER ::= { pdOutput 1 }
              --1.3.6.1.4.1.3052.14.1.5.3.1

              pdOutputFuse OBJECT IDENTIFIER ::= { pdOutput 4 }
              --1.3.6.1.4.1.3052.14.1.5.3.4

            pdNextGen OBJECT IDENTIFIER ::= { powerDistributionStatus 4 }
            --1.3.6.1.4.1.3052.14.1.5.4

            pdSystem OBJECT IDENTIFIER ::= { powerDistributionStatus 5 }
            --1.3.6.1.4.1.3052.14.1.5.5

        fuelSensorStatus OBJECT IDENTIFIER ::= { status 6 }
        --1.3.6.1.4.1.3052.14.1.6

        wirelessModemStatus OBJECT IDENTIFIER ::= { status 7 }
        --1.3.6.1.4.1.3052.14.1.7

        acPowerMonitorStatus OBJECT IDENTIFIER ::= { status 8 }
        --1.3.6.1.4.1.3052.14.1.8

        aisgStatus OBJECT IDENTIFIER ::= { status 9 }
        --1.3.6.1.4.1.3052.14.1.9


    config OBJECT IDENTIFIER ::= { s571 2 }
    --1.3.6.1.4.1.3052.14.2

        eventSensorBasics OBJECT IDENTIFIER ::= { config 1 }
        --1.3.6.1.4.1.3052.14.2.1

        eventSensorPointConfig OBJECT IDENTIFIER ::= { config 2 }
        --1.3.6.1.4.1.3052.14.2.2

        serialPorts OBJECT IDENTIFIER ::= { config 3 }
        --1.3.6.1.4.1.3052.14.2.3

        network OBJECT IDENTIFIER ::= { config 4 }
        --1.3.6.1.4.1.3052.14.2.4

            interface OBJECT IDENTIFIER ::= { network 1 }
            --1.3.6.1.4.1.3052.14.2.4

                ethernet OBJECT IDENTIFIER ::= { interface 1 }
                --1.3.6.1.4.1.3052.14.2.4.1

                    ethernet1 OBJECT IDENTIFIER ::= { ethernet 1 }
                    --1.3.6.1.4.1.3052.14.2.4.1.1

                        eth1VLAN OBJECT IDENTIFIER ::= { ethernet1 5 }
                        --1.3.6.1.4.1.3052.14.2.4.1.1.5

                            eth1VLAN1 OBJECT IDENTIFIER ::= { eth1VLAN 1 }
                            --1.3.6.1.4.1.3052.14.2.4.1.1.5.1

                            eth1VLAN2 OBJECT IDENTIFIER ::= { eth1VLAN 2 }
                            --1.3.6.1.4.1.3052.14.2.4.1.1.5.2

                            eth1VLAN3 OBJECT IDENTIFIER ::= { eth1VLAN 3 }
                            --1.3.6.1.4.1.3052.14.2.4.1.1.5.3

                            eth1VLAN4 OBJECT IDENTIFIER ::= { eth1VLAN 4 }
                            --1.3.6.1.4.1.3052.14.2.4.1.1.5.4

                            eth1VLAN5 OBJECT IDENTIFIER ::= { eth1VLAN 5 }
                            --1.3.6.1.4.1.3052.14.2.4.1.1.5.5

                            eth1VLAN6 OBJECT IDENTIFIER ::= { eth1VLAN 6 }
                            --1.3.6.1.4.1.3052.14.2.4.1.1.5.6

                        eth1IPv6 OBJECT IDENTIFIER ::= { ethernet1 7 }
                        --1.3.6.1.4.1.3052.14.2.4.1.1.7

                            eth1IPv6Static OBJECT IDENTIFIER ::= { eth1IPv6 2 }
                            --1.3.6.1.4.1.3052.14.2.4.1.1.7.2

                            eth1IPv6Auto OBJECT IDENTIFIER ::= { eth1IPv6 3 }
                            --1.3.6.1.4.1.3052.14.2.4.1.1.7.3

                    ethernet2 OBJECT IDENTIFIER ::= { ethernet 2 }
                    --1.3.6.1.4.1.3052.14.2.4.1.2

                        eth2VLAN OBJECT IDENTIFIER ::= { ethernet2 5 }
                        --1.3.6.1.4.1.3052.14.2.4.1.2.5

                            eth2VLAN1 OBJECT IDENTIFIER ::= { eth2VLAN 1 }
                            --1.3.6.1.4.1.3052.14.2.4.1.2.5.1

                            eth2VLAN2 OBJECT IDENTIFIER ::= { eth2VLAN 2 }
                            --1.3.6.1.4.1.3052.14.2.4.1.2.5.2

                            eth2VLAN3 OBJECT IDENTIFIER ::= { eth2VLAN 3 }
                            --1.3.6.1.4.1.3052.14.2.4.1.2.5.3

                            eth2VLAN4 OBJECT IDENTIFIER ::= { eth2VLAN 4 }
                            --1.3.6.1.4.1.3052.14.2.4.1.2.5.4

                            eth2VLAN5 OBJECT IDENTIFIER ::= { eth2VLAN 5 }
                            --1.3.6.1.4.1.3052.14.2.4.1.2.5.5

                            eth2VLAN6 OBJECT IDENTIFIER ::= { eth2VLAN 6 }
                            --1.3.6.1.4.1.3052.14.2.4.1.2.5.6

                        eth2IPv6 OBJECT IDENTIFIER ::= { ethernet2 7 }
                        --1.3.6.1.4.1.3052.14.2.4.1.2.7

                            eth2IPv6Static OBJECT IDENTIFIER ::= { eth2IPv6 2 }
                            --1.3.6.1.4.1.3052.14.2.4.1.2.7.2

                            eth2IPv6Auto OBJECT IDENTIFIER ::= { eth2IPv6 3 }
                            --1.3.6.1.4.1.3052.14.2.4.1.2.7.3

            snmp OBJECT IDENTIFIER ::= { network 8 }
            --1.3.6.1.4.1.3052.14.2.4.8

                snmpNotificationTx OBJECT IDENTIFIER ::= { snmp 7 }
                --1.3.6.1.4.1.3052.14.2.4.8.7

                snmpPoll OBJECT IDENTIFIER ::= { snmp 9 }
                --1.3.6.1.4.1.3052.14.2.4.8.9

            ftpPush OBJECT IDENTIFIER ::= { network 9 }
            --1.3.6.1.4.1.3052.14.2.4.9

            ppp OBJECT IDENTIFIER ::= { network 10 }
            --1.3.6.1.4.1.3052.14.2.4.10

                pppDial OBJECT IDENTIFIER ::= { ppp 1 }
                --1.3.6.1.4.1.3052.14.2.4.10.1

                pppHost OBJECT IDENTIFIER ::= { ppp 2 }
                --1.3.6.1.4.1.3052.14.2.4.10.2

            routing OBJECT IDENTIFIER ::= { network 11 }
            --1.3.6.1.4.1.3052.14.2.4.11

            netSecurity OBJECT IDENTIFIER ::= { network 12 }
            --1.3.6.1.4.1.3052.14.2.4.12

                ipRestriction OBJECT IDENTIFIER ::= { netSecurity 1 }
                --1.3.6.1.4.1.3052.14.2.4.12.1

            rts OBJECT IDENTIFIER ::= { network 13 }
            --1.3.6.1.4.1.3052.14.2.4.13

                rtsAlarms OBJECT IDENTIFIER ::= { rts 2 }
                --1.3.6.1.4.1.3052.14.2.4.13.2

            trap OBJECT IDENTIFIER ::= { network 14 }
            --1.3.6.1.4.1.3052.14.2.4.14

                trapInclude OBJECT IDENTIFIER ::= { trap 1}
                --1.3.6.1.4.1.3052.14.2.4.14.1

            routeTest OBJECT IDENTIFIER ::= { network 15 }
            --1.3.6.1.4.1.3052.14.2.4.15

            wireless OBJECT IDENTIFIER ::= { network 16 }
            --1.3.6.1.4.1.3052.14.2.4.16

                wirelessConnectivity OBJECT IDENTIFIER ::= { wireless 20 }
                --1.3.6.1.4.1.3052.14.2.4.16.20

            email OBJECT IDENTIFIER ::= { network 17 }
            --1.3.6.1.4.1.3052.14.2.4.17

            netAdvanced OBJECT IDENTIFIER ::= { network 18 }
            --1.3.6.1.4.1.3052.14.2.4.18

            web OBJECT IDENTIFIER ::= { network 19 }
            --1.3.6.1.4.1.3052.14.2.4.19

            ipv6 OBJECT IDENTIFIER ::= { network 21 }
            --1.3.6.1.4.1.3052.14.2.4.21

            cpe OBJECT IDENTIFIER ::= { network 22 }
            --1.3.6.1.4.1.3052.14.2.4.22

        modem OBJECT IDENTIFIER ::= { config 5 }
        --1.3.6.1.4.1.3052.14.2.5

            modemClid OBJECT IDENTIFIER ::= { modem 8 }
            --1.3.6.1.4.1.3052.14.2.5.7

        time OBJECT IDENTIFIER ::= { config 8 }
        --1.3.6.1.4.1.3052.14.2.8

        console OBJECT IDENTIFIER ::= { config 10 }
        --1.3.6.1.4.1.3052.14.2.10

        unitSecurity OBJECT IDENTIFIER ::= { config 11 }
        --1.3.6.1.4.1.3052.14.2.11

            secCore OBJECT IDENTIFIER ::= { unitSecurity 1 }
            --1.3.6.1.4.1.3052.14.2.11.1

            secFactory OBJECT IDENTIFIER ::= { unitSecurity 3 }
            --1.3.6.1.4.1.3052.14.2.11.3

            secSSH OBJECT IDENTIFIER ::= { unitSecurity 4 }
            --1.3.6.1.4.1.3052.14.2.11.4

            secVPN OBJECT IDENTIFIER ::= { unitSecurity 5 }
            --1.3.6.1.4.1.3052.14.2.11.5

        event OBJECT IDENTIFIER ::= { config 12 }
        --1.3.6.1.4.1.3052.14.2.12

            evCore OBJECT IDENTIFIER ::= { event 1 }
            --1.3.6.1.4.1.3052.14.2.12.1

                evLog OBJECT IDENTIFIER ::= { evCore 3 }
                --1.3.6.1.4.1.3052.14.2.12.1.3

                evMgmt OBJECT IDENTIFIER ::= { evCore 4 }
                --1.3.6.1.4.1.3052.14.2.12.1.4

            evData OBJECT IDENTIFIER ::= { event 2 }
            --1.3.6.1.4.1.3052.14.2.12.1

                evdCore OBJECT IDENTIFIER ::= { evData 1 }
                --1.3.6.1.4.1.3052.14.2.12.2.1

            evNoData1 OBJECT IDENTIFIER ::= { event 3 }
            --1.3.6.1.4.1.3052.14.2.12.1

            evNoData2 OBJECT IDENTIFIER ::= { event 4 }
            --1.3.6.1.4.1.3052.14.2.12.1

            evSched1 OBJECT IDENTIFIER ::= { event 5 }
            --1.3.6.1.4.1.3052.14.2.12.1

            evSched2 OBJECT IDENTIFIER ::= { event 6 }
            --1.3.6.1.4.1.3052.14.2.12.1

            evNoSensor OBJECT IDENTIFIER ::= { event 9 }
            --1.3.6.1.4.1.3052.14.2.12.1

            fuelSensor OBJECT IDENTIFIER ::= { event 11 }
            --1.3.6.1.4.1.3052.14.2.12.11

            acPowerMonitor OBJECT IDENTIFIER ::= { event 12 }
            --1.3.6.1.4.1.3052.14.2.12.12

            evReset OBJECT IDENTIFIER ::= { event 16 }
            --1.3.6.1.4.1.3052.14.2.12.16

        action OBJECT IDENTIFIER ::= { config 14 }
        --1.3.6.1.4.1.3052.14.2.14

            actionSched OBJECT IDENTIFIER ::= { action 3 }
            --1.3.6.1.4.1.3052.14.2.14.3

            actionAsentria OBJECT IDENTIFIER ::= { action 4 }
            --1.3.6.1.4.1.3052.14.2.14.4

        sys OBJECT IDENTIFIER ::= { config 16 }
        --1.3.6.1.4.1.3052.14.2.16

            sysTime OBJECT IDENTIFIER ::= { sys 1 }
            --1.3.6.1.4.1.3052.14.2.16.1

                sysTimeNet OBJECT IDENTIFIER ::= { sysTime 4 }
                --1.3.6.1.4.1.3052.14.2.16.1.4

            sysPT OBJECT IDENTIFIER ::= { sys 2 }
            --1.3.6.1.4.1.3052.14.2.16.2

            sysTimeStamp OBJECT IDENTIFIER ::= { sys 8 }
            --1.3.6.1.4.1.3052.14.2.16.8

            sysLog OBJECT IDENTIFIER ::= { sys 9 }
            --1.3.6.1.4.1.3052.14.2.16.9

            sysCRDB OBJECT IDENTIFIER ::= { sys 10 }
            --1.3.6.1.4.1.3052.14.2.16.10

            sysLoc OBJECT IDENTIFIER ::= { sys 14 }
            --1.3.6.1.4.1.3052.14.2.16.14

            sysAssetMgmt OBJECT IDENTIFIER ::= { sys 15 }
            --1.3.6.1.4.1.3052.14.2.16.15

            sysFileTransfer OBJECT IDENTIFIER ::= { sys 17 }
            --1.3.6.1.4.1.3052.14.2.16.17

            sysUpdate OBJECT IDENTIFIER ::= { sys 18 }
            --1.3.6.1.4.1.3052.14.2.16.18

        auditLog OBJECT IDENTIFIER ::= { config 17 }
        --1.3.6.1.4.1.3052.14.2.17

        scripting OBJECT IDENTIFIER ::= { config 18 }
        --1.3.6.1.4.1.3052.14.2.18

    productIds OBJECT IDENTIFIER ::= { s571 3 }
    --1.3.6.1.4.1.3052.14.3

--***************************************************************************************
--OBJECT DEFINITIONS
--***************************************************************************************

--***************************************************************************************
--EventSensor Status Section    1.1
--***************************************************************************************

esPointTable OBJECT-TYPE
    SYNTAX SEQUENCE OF ESPoint
    MAX-ACCESS not-accessible
    STATUS current
    DESCRIPTION
        "
        This table organizes 4 basic attributes of points.  A point
        is a particular sensor on an EventSensor (e.g., temperature,
        humidity, contact closure 2, output 5, etc.).  The 4 point
        attributes are its name, whether it's in its event state,
        the point's value as a number and its value as a string.

        Points are referenced by a point index.  The point index
        is a string of 3 numbers separated by periods.
        It contains all the information necessary for getting a piece
        of data off an event sensor; namely, which EventSensor,
        point class, and which-sensor-of-that-class (a.k.a. point).
        "
    ::= { eventSensorStatus 1 }
    --1.3.6.1.4.1.3052.14.1.1.1

esPointEntry OBJECT-TYPE
    SYNTAX ESPoint
    MAX-ACCESS not-accessible
    STATUS current
    DESCRIPTION
        "Entry for EventSensor point table"
    INDEX { esIndexES, esIndexPC, esIndexPoint }
    ::= { esPointTable 1 }
    --1.3.6.1.4.1.3052.14.1.1.1.1

esIndexES OBJECT-TYPE
    SYNTAX Integer32 (1..200)
    MAX-ACCESS read-only
    STATUS current
    DESCRIPTION
        "The part of the point index that refers to an
        EventSensor.

        The point index is a string of 3 numbers separated
        by periods.  It contains all the information
        necessary for getting a piece of data off an event
        sensor; namely, which EventSensor, point class,
        and which-sensor-of-that-class (a.k.a. point).

        This object's allowable values are 1 through 16,
        and 200.  200 always refers to the EventSensor
        inside the unit.  1 through 16 refer to additional
        attached EventSensors.

        The number corresponding to an EventSensor is
        determined by the user at the initial configuration
        time.  If there is an internal sensor in the unit,
        it will always be the first item in the Sensor
        Events setup menu.

        For example, if a new EventSensor is configured as
        the 2nd entry AFTER the internal EventSensor (if
        one exists) in the Sensor Events Setup Menu, then
        that EventSensor will be known from then on as
        EventSensor 2.  All point indeces with esIndexES=2
        will now refer to that particular EventSensor.
        "
    ::= { esPointEntry 1 }
    --1.3.6.1.4.1.3052.14.1.1.1.1.1

esIndexPC OBJECT-TYPE
    SYNTAX Integer32 (1..6)
    MAX-ACCESS read-only
    STATUS current
    DESCRIPTION
        "The part of the point index that refers to point class.

        The point index is a string of 3 numbers separated by periods.
        It contains all the information necessary for getting a piece
        of data off an event sensor; namely, which EventSensor,
        point class, and which-sensor-of-that-class (a.k.a. point).

        The values for this object are:
        1=temperature sensor
        2=contact closure
        3=humidity sensor
        4=noise sensor
        5=analog input
        6=output (relay output or power output)
        "
    ::= { esPointEntry 2 }
    --1.3.6.1.4.1.3052.14.1.1.1.1.2

esIndexPoint OBJECT-TYPE
    SYNTAX Integer32 (1..64)
    MAX-ACCESS read-only
    STATUS current
    DESCRIPTION
        "The part of the point index that delineates which
        sensor on the EventSensor.

        So this combined with esIndexPC (Point Class or type)
        and esIndexES (which EventSensor) uniquely defines each
        point (sensor or output) attached to a unit.  For
        example, if esIndexES is 3, esIndexPC is 1 and
        esIndexPoint is 4 then this is the Fourth Temperature
        Sensor on EventSensor number 3."
    ::= { esPointEntry 3 }
    --1.3.6.1.4.1.3052.14.1.1.1.1.3

esPointName OBJECT-TYPE
    SYNTAX DisplayString
    MAX-ACCESS read-write
    STATUS current
    DESCRIPTION
        "The name of the point on an EventSensor. For example,
        'AC temp' (in the case of the temperature sensor on an
        EventSensor).

        There can be multiple points of the same point class on an
        EventSensor (e.g., 8 contact closures) and multiple sensor
        classes on an EventSensor (e.g., temperature, contact closure,
        humidity).

        If the point referenced by a given point index is solitary
        (e.g., temperature sensor, because there can be only one on
        an EventSensor), then this object reads as '<EventSensor
        name>'.  Setting this object for solitary point indices sets
        the EventSensor name only.

        On the other hand, if a given point is among other points of
        the same point class on an EventSensor, then this object reads
        as '<Sensor name>'.  Setting this object for these NON-
        solitary point indices sets the sensor name only - not the
        EventSensor name."
    ::= { esPointEntry 4 }
    --1.3.6.1.4.1.3052.14.1.1.1.1.4

esPointInEventState OBJECT-TYPE
    SYNTAX Integer32
    MAX-ACCESS read-write
    STATUS current
    DESCRIPTION
        "A number referring to the event state of a point
        on an EventSensor.  This number can have different
        meanings depending on the point class.

        If the point class is temperature, humidity, or
        analog input, then the values of this object are:
        1=very low
        2=low
        3=normal
        4=high
        5=very high

        For contact closures the values of this object are:
        1=point in event state
        2=point in normal state

        For outputs the values of this object is the numeric
        code for the logical state of the output: 1 or 2.  The
        logical state of the output is either active/inactive for
        relay outputs or on/off for power outputs.  The logical
        state of the output has different nomenclature depending
        on the type of the output (relay output or power output):

        1=active (for relay output) or on (for power output)
        2=inactive (for relay output) or off (for power output)

        This is not necessarily representative of physical state
        of the output.  Physical state is energized/de-energized,
        for both relay and power outputs.  For relay outputs,
        the active logical state corresponds to either the energized
        physical state or the de-energized physical state depending
        on how the relay output is configured.  For power outputs,
        the on logical state always corresponds to the energized
        physical state.

        For any point class and any point, if the event
        state is undefined, then the value of this object
        is 0.

        For any point class except output, this object is read-only.
        For outputs, setting this object to 1 puts the output into
        its active logical state.

        Setting this object to 2 puts the output into its inactive
        logical state.

        Setting this object to any value greater than 2 puts the
        output into its active logical state for that many seconds
        (up to 3600), after which time it puts the output into its
        inactive logical state.
        "
    ::= { esPointEntry 5 }
    --1.3.6.1.4.1.3052.14.1.1.1.1.5

esPointValueInt OBJECT-TYPE
    SYNTAX Integer32 (-2147483648..2147483647)
    MAX-ACCESS read-write
    STATUS current
    DESCRIPTION
        "A read-only number referring to the value of a
        point on an EventSensor.

        If the point class is temperature, then this object
        is the temperature in its configured scale (default
        is Fahrenheit).

        If the point class is contact closure, then
        this object is either 0 (open) or 1 (closed).

        If the point class is humidity, then this object
        is the percent relative humidity.

        If the point class is analog input, then this
        object is the signed input value in tenths of the
        configured units.

        If the point class is an output, then this object is
        the numeric code for the physical state of the output.
        0=de-energized
        1=energized

        This object cannot be used to control the output, i.e,
        change its logical or physical state (instead use
        the esPointInEventState object).
        "
    ::= { esPointEntry 6 }
    --1.3.6.1.4.1.3052.14.1.1.1.1.6

esPointValueStr OBJECT-TYPE
    SYNTAX DisplayString
    MAX-ACCESS read-only
    STATUS current
    DESCRIPTION
        "A string referring to the value of a point on an
        EventSensor.

        For contact closures this object is either 'Open'
        or 'Closed'.

        For outputs this object is a concatenation of the
        logical state and physical state, separated by '/'.

        For a relay output this object can be one of the
        following 4 possible values:

        Active/Energized
        Inactive/Energized
        Active/De-energized
        Inactve/De-energized

        For a power output this object can be one of the
        following 2 possible values:

        On/Energized
        Off/De-energized

        For temperature and humidity point classes, this
        object is the string representation of the
        esPointValueInt object.  For temperature, 'C' or
        'F' is including in the string to indicate scale.

        For analog inputs, this object is the string
        representation of the plus/minus input in the
        configured units appended with the unit name.
        "
    ::= { esPointEntry 7 }
    --1.3.6.1.4.1.3052.14.1.1.1.1.7

esPointTimeLastChange OBJECT-TYPE
    SYNTAX DisplayString
    MAX-ACCESS read-only
    STATUS current
    DESCRIPTION
        "The time of the last time an event was
        triggerred for a point on an EventSensor in
        MM/DD/YY HH:MM:SS format.

        For contact closures, the possible events are
        Active and Inactive.  For temperature, humidity,
        and analog inputs, the possible events are Normal,
        High, Very High, Low, and Very Low.

        For outputs, this object is a null string."
    ::= { esPointEntry 8 }
    --1.3.6.1.4.1.3052.14.1.1.1.1.8

esPointTimetickLastChange OBJECT-TYPE
    SYNTAX TimeTicks
    MAX-ACCESS read-only
    STATUS current
    DESCRIPTION
        "The time of the last time an event was
        triggerred for a point on an EventSensor in
        100ths of seconds since reset.

        For contact closures, the possible events are
        Active and Inactive.  For temperature, humidity,
        and analog inputs, the possible events are Normal,
        High, Very High, Low, and Very Low.

        For outputs, this object is 0."
    ::= { esPointEntry 9 }
    --1.3.6.1.4.1.3052.14.1.1.1.1.9

--***************************************************************************************
--Data Event Status Section 1.2
--***************************************************************************************

deStatusTable OBJECT-TYPE
    SYNTAX SEQUENCE OF DEStatus
    MAX-ACCESS not-accessible
    STATUS current
    DESCRIPTION
        "Data Event Status Table"
    ::= { dataEventStatus 1 }
    --1.3.6.1.4.1.3052.14.1.2.1

deStatusEntry OBJECT-TYPE
    SYNTAX DEStatus
    MAX-ACCESS not-accessible
    STATUS current
    DESCRIPTION
        "EventSensor status entry"
    INDEX { deStatusIndex }
    ::= { deStatusTable 1 }
    --1.3.6.1.4.1.3052.14.1.2.1.1

deStatusIndex OBJECT-TYPE
    SYNTAX Integer32 (1..100)
    MAX-ACCESS read-only
    STATUS current
    DESCRIPTION
        "Index for Data Events"
    ::= { deStatusEntry 1 }
    --1.3.6.1.4.1.3052.14.1.2.1.1.1

deStatusName OBJECT-TYPE
    SYNTAX DisplayString
    MAX-ACCESS read-only
    STATUS current
    DESCRIPTION
        "Data Event name"
    ::= { deStatusEntry 2 }
    --1.3.6.1.4.1.3052.14.1.2.1.1.2

deStatusCounter OBJECT-TYPE
    SYNTAX Integer32
    MAX-ACCESS read-only
    STATUS current
    DESCRIPTION
        "Number of times a data record has matched this
        event's equation.
        Range: 1-999999999"
    ::= { deStatusEntry 3 }
    --1.3.6.1.4.1.3052.14.1.2.1.1.3

deStatusThreshold OBJECT-TYPE
    SYNTAX Integer32
    MAX-ACCESS read-only
    STATUS current
    DESCRIPTION
        "Number of times the equation is matched before
        an event is triggered.
        Range: 1-999999999"
    ::= { deStatusEntry 4 }
    --1.3.6.1.4.1.3052.14.1.2.1.1.4

modemStatus OBJECT-TYPE
    SYNTAX DisplayString
    MAX-ACCESS read-only
    STATUS current
    DESCRIPTION
        "status of modem (idle, dialing, connected, etc.)"
    ::= { status 3 }
    --1.3.6.1.4.1.3052.14.1.3

modemCLIDLogTable OBJECT-TYPE
    SYNTAX SEQUENCE OF ModemCLIDLogConfig
    MAX-ACCESS not-accessible
    STATUS current
    DESCRIPTION
        "Table of numbers of recent dialing parties"
    ::= { status 4 }
    --1.3.6.1.4.1.3052.14.1.4

modemCLIDLogEntry OBJECT-TYPE
    SYNTAX ModemCLIDLogConfig
    MAX-ACCESS not-accessible
    STATUS current
    DESCRIPTION
        "Entry for table of CLID log entries"
    INDEX { modemCLIDLogIndex }
    ::= { modemCLIDLogTable 1 }
    --1.3.6.1.4.1.3052.14.1.4.1

modemCLIDLogIndex OBJECT-TYPE
    SYNTAX Integer32 (1..8)
    MAX-ACCESS read-only
    STATUS current
    DESCRIPTION
        "Index for table of CLID log entries"
    ::= { modemCLIDLogEntry 1 }
    --1.3.6.1.4.1.3052.14.1.4.1.1

modemCLIDLogNumber OBJECT-TYPE
    SYNTAX DisplayString
    MAX-ACCESS read-write
    STATUS current
    DESCRIPTION
        "recently logged number of dialing party"
    ::= { modemCLIDLogEntry 2 }
    --1.3.6.1.4.1.3052.14.1.4.1.2

--***************************************************************************************
--Power Distribution Status Section 1.5
--***************************************************************************************

pdConfig OBJECT-TYPE
    SYNTAX DisplayString
    MAX-ACCESS read-only
    STATUS current
    DESCRIPTION
        "Power Distribution output configuration"
    ::= { powerDistributionStatus 1 }
    --1.3.6.1.4.1.3052.14.1.5.1

pdMainCurrentInEventState OBJECT-TYPE
    SYNTAX DisplayString
    MAX-ACCESS read-only
    STATUS current
    DESCRIPTION
        "Power Distribution main current event state"
    ::= { pdMainCurrent 2 }
    --1.3.6.1.4.1.3052.14.1.5.2.1.2

pdMainCurrentValue OBJECT-TYPE
    SYNTAX Integer32
    MAX-ACCESS read-only
    STATUS current
    DESCRIPTION
        "Power Distribution main current value in mA"
    ::= { pdMainCurrent 3 }
    --1.3.6.1.4.1.3052.14.1.5.2.1.3

pdMainCurrentValueStr OBJECT-TYPE
    SYNTAX DisplayString
    MAX-ACCESS read-only
    STATUS current
    DESCRIPTION
        "Power Distribution main current value formatted as a string"
    ::= { pdMainCurrent 4 }
    --1.3.6.1.4.1.3052.14.1.5.2.1.4

pdMainCurrentDeadband OBJECT-TYPE
    SYNTAX Integer32
    MAX-ACCESS read-write
    STATUS current
    DESCRIPTION
        "Power Distribution main current sensor deadband in mA"
    ::= { pdMainCurrent 10 }
    --1.3.6.1.4.1.3052.14.1.5.2.1.10

pdMainCurrentVHighCurrent OBJECT-TYPE
    SYNTAX Integer32
    MAX-ACCESS read-write
    STATUS current
    DESCRIPTION
        "Power Distribution main current sensor very high threshold in mA"
    ::= { pdMainCurrent 11 }
    --1.3.6.1.4.1.3052.14.1.5.2.1.11

pdMainCurrentHighCurrent OBJECT-TYPE
    SYNTAX Integer32
    MAX-ACCESS read-write
    STATUS current
    DESCRIPTION
        "Power Distribution main current sensor high threshold in mA"
    ::= { pdMainCurrent 12 }
    --1.3.6.1.4.1.3052.14.1.5.2.1.12

pdMainCurrentLowCurrent OBJECT-TYPE
    SYNTAX Integer32
    MAX-ACCESS read-write
    STATUS current
    DESCRIPTION
        "Power Distribution main current sensor low threshold in mA"
    ::= { pdMainCurrent 13 }
    --1.3.6.1.4.1.3052.14.1.5.2.1.13

pdMainCurrentVLowCurrent OBJECT-TYPE
    SYNTAX Integer32
    MAX-ACCESS read-write
    STATUS current
    DESCRIPTION
        "Power Distribution main current sensor very low threshold in mA"
    ::= { pdMainCurrent 14 }
    --1.3.6.1.4.1.3052.14.1.5.2.1.14

pdMainVoltageInEventState OBJECT-TYPE
    SYNTAX DisplayString
    MAX-ACCESS read-only
    STATUS current
    DESCRIPTION
        "Power Distribution main voltage event state"
    ::= { pdMainVoltage 2 }
    --1.3.6.1.4.1.3052.14.1.5.2.2.2

pdMainVoltageValue OBJECT-TYPE
    SYNTAX Integer32
    MAX-ACCESS read-only
    STATUS current
    DESCRIPTION
        "Power Distribution main voltage value in mV"
    ::= { pdMainVoltage 3 }
    --1.3.6.1.4.1.3052.14.1.5.2.2.3

pdMainVoltageValueStr OBJECT-TYPE
    SYNTAX DisplayString
    MAX-ACCESS read-only
    STATUS current
    DESCRIPTION
        "Power Distribution main voltage value formatted as a string"
    ::= { pdMainVoltage 4 }
    --1.3.6.1.4.1.3052.14.1.5.2.2.4

pdMainVoltageDeadband OBJECT-TYPE
    SYNTAX Integer32
    MAX-ACCESS read-write
    STATUS current
    DESCRIPTION
        "Power Distribution main voltage sensor deadband in mV"
    ::= { pdMainVoltage 10 }
    --1.3.6.1.4.1.3052.14.1.5.2.2.10

pdMainVoltageVHighVoltage OBJECT-TYPE
    SYNTAX Integer32
    MAX-ACCESS read-write
    STATUS current
    DESCRIPTION
        "Power Distribution main voltage sensor very high threshold in mV"
    ::= { pdMainVoltage 11 }
    --1.3.6.1.4.1.3052.14.1.5.2.2.11

pdMainVoltageHighVoltage OBJECT-TYPE
    SYNTAX Integer32
    MAX-ACCESS read-write
    STATUS current
    DESCRIPTION
        "Power Distribution main voltage sensor high threshold in mV"
    ::= { pdMainVoltage 12 }
    --1.3.6.1.4.1.3052.14.1.5.2.2.12

pdMainVoltageLowVoltage OBJECT-TYPE
    SYNTAX Integer32
    MAX-ACCESS read-write
    STATUS current
    DESCRIPTION
        "Power Distribution main voltage sensor low threshold in mV"
    ::= { pdMainVoltage 13 }
    --1.3.6.1.4.1.3052.14.1.5.2.2.13

pdMainVoltageVLowVoltage OBJECT-TYPE
    SYNTAX Integer32
    MAX-ACCESS read-write
    STATUS current
    DESCRIPTION
        "Power Distribution main voltage sensor very low threshold in mV"
    ::= { pdMainVoltage 14 }
    --1.3.6.1.4.1.3052.14.1.5.2.2.14

pdMainPowerValue OBJECT-TYPE
    SYNTAX Integer32
    MAX-ACCESS read-only
    STATUS current
    DESCRIPTION
        "Power Distribution main power value in Watts"
    ::= { pdMainPower 3 }
    --1.3.6.1.4.1.3052.14.1.5.2.3.3

pdMainPowerValueStr OBJECT-TYPE
    SYNTAX DisplayString
    MAX-ACCESS read-only
    STATUS current
    DESCRIPTION
        "Power Distribution main power value formatted as a string"
    ::= { pdMainPower 4 }
    --1.3.6.1.4.1.3052.14.1.5.2.3.4

pdOutputCurrentTable OBJECT-TYPE
    SYNTAX SEQUENCE OF PowerDistribOutputCurrent
    MAX-ACCESS not-accessible
    STATUS current
    DESCRIPTION
        "Table of power output current values"
    ::= { pdOutput 1 }
    --1.3.6.1.4.1.3052.14.1.5.3.1

pdOutputCurrentEntry OBJECT-TYPE
    SYNTAX PowerDistribOutputCurrent
    MAX-ACCESS not-accessible
    STATUS current
    DESCRIPTION
        "Entry for table of output current values"
    INDEX { pdOutputCurrentIndex }
    ::= { pdOutputCurrentTable 1 }
    --1.3.6.1.4.1.3052.14.1.5.3.1.1

pdOutputCurrentIndex OBJECT-TYPE
    SYNTAX Integer32 (1..13)
    MAX-ACCESS read-only
    STATUS current
    DESCRIPTION
        "Index for table of power output current values"
    ::= { pdOutputCurrentEntry 1 }
    --1.3.6.1.4.1.3052.14.1.5.3.1.1.1

pdOutputCurrentInEventState OBJECT-TYPE
    SYNTAX DisplayString
    MAX-ACCESS read-only
    STATUS current
    DESCRIPTION
        "The event state of this power distribution output
        current (Very Low, Low, Normal, High, Very High)"
    ::= { pdOutputCurrentEntry 2 }
    --1.3.6.1.4.1.3052.14.1.5.3.1.1.2

pdOutputCurrentValue OBJECT-TYPE
    SYNTAX Integer32
    MAX-ACCESS read-only
    STATUS current
    DESCRIPTION
        "Output current value in mA"
    ::= { pdOutputCurrentEntry 3 }
    --1.3.6.1.4.1.3052.14.1.5.3.1.1.3

pdOutputCurrentValueStr OBJECT-TYPE
    SYNTAX DisplayString
    MAX-ACCESS read-only
    STATUS current
    DESCRIPTION
        "Output current value formatted as a fixed-point string
        in Amps."
    ::= { pdOutputCurrentEntry 4 }
    --1.3.6.1.4.1.3052.14.1.5.3.1.1.4

pdOutputCurrentDeadband OBJECT-TYPE
    SYNTAX Integer32
    MAX-ACCESS read-write
    STATUS current
    DESCRIPTION
        "Deadband for this power output current sensor"
    ::= { pdOutputCurrentEntry 10 }
    --1.3.6.1.4.1.3052.14.1.5.3.1.1.10

pdOutputCurrentVHighCurrent OBJECT-TYPE
    SYNTAX Integer32
    MAX-ACCESS read-write
    STATUS current
    DESCRIPTION
        "Very high threshold for this power output current sensor"
    ::= { pdOutputCurrentEntry 11 }
    --1.3.6.1.4.1.3052.14.1.5.3.1.1.11

pdOutputCurrentHighCurrent OBJECT-TYPE
    SYNTAX Integer32
    MAX-ACCESS read-write
    STATUS current
    DESCRIPTION
        "High threshold for this power output current sensor"
    ::= { pdOutputCurrentEntry 12 }
    --1.3.6.1.4.1.3052.14.1.5.3.1.1.12

pdOutputCurrentVLowCurrent OBJECT-TYPE
    SYNTAX Integer32
    MAX-ACCESS read-write
    STATUS current
    DESCRIPTION
        "Very low threshold for this power output current sensor"
    ::= { pdOutputCurrentEntry 13 }
    --1.3.6.1.4.1.3052.14.1.5.3.1.1.13

pdOutputCurrentLowCurrent OBJECT-TYPE
    SYNTAX Integer32
    MAX-ACCESS read-write
    STATUS current
    DESCRIPTION
        "Low threshold for this power output current sensor"
    ::= { pdOutputCurrentEntry 14 }
    --1.3.6.1.4.1.3052.14.1.5.3.1.1.14

pdOutputFuseTable OBJECT-TYPE
    SYNTAX SEQUENCE OF PowerDistribOutputFuse
    MAX-ACCESS not-accessible
    STATUS current
    DESCRIPTION
        "Table of output fuse values"
    ::= { pdOutput 4 }
    --1.3.6.1.4.1.3052.14.1.5.3.4

pdOutputFuseEntry OBJECT-TYPE
    SYNTAX PowerDistribOutputFuse
    MAX-ACCESS not-accessible
    STATUS current
    DESCRIPTION
        "Entry for table of output fuse values"
    INDEX { pdOutputFuseIndex }
    ::= { pdOutputFuseTable 1 }
    --1.3.6.1.4.1.3052.14.1.5.3.4.1

pdOutputFuseIndex OBJECT-TYPE
    SYNTAX Integer32 (1..13)
    MAX-ACCESS read-only
    STATUS current
    DESCRIPTION
        "Index for table of output fuse values"
    ::= { pdOutputFuseEntry 1 }
    --1.3.6.1.4.1.3052.14.1.5.3.4.1.1

pdOutputFuseInEventState OBJECT-TYPE
    SYNTAX DisplayString
    MAX-ACCESS read-only
    STATUS current
    DESCRIPTION
        "A number referring to the event state of a power
        distribution output fuse.

        14=fuse blown
        15=fuse ok"
    ::= { pdOutputFuseEntry 2 }
    --1.3.6.1.4.1.3052.14.1.5.3.4.1.2

pdOutputFuseValueStr OBJECT-TYPE
    SYNTAX DisplayString
    MAX-ACCESS read-only
    STATUS current
    DESCRIPTION
        "Output fuse value formatted as a string.  E.g.,
        'BLOWN' or 'OK'"
    ::= { pdOutputFuseEntry 4 }
    --1.3.6.1.4.1.3052.14.1.5.3.4.1.4

pdnTable OBJECT-TYPE
    SYNTAX SEQUENCE OF PowerDistribNextGen
    MAX-ACCESS not-accessible
    STATUS current
    DESCRIPTION
        "Table of power distribution objects arranged according
        to next-generation methodology (i.e., using multiple PowerBoss
        power distributors in addition to the on-board power
        distributor)."
    ::= { pdNextGen 1 }
    --1.3.6.1.4.1.3052.14.1.5.4.1

pdnEntry OBJECT-TYPE
    SYNTAX PowerDistribNextGen
    MAX-ACCESS not-accessible
    STATUS current
    DESCRIPTION
        "Entry for table of power distribution objects arranged according
        to next-generation methodology (i.e., using multiple PowerBoss
        power distributors in addition to the on-board power
        distributor)."
    INDEX { pdnIndexPD, pdnIndexOutput }
    ::= { pdnTable 1 }
    --1.3.6.1.4.1.3052.14.1.5.4.1.1

pdnIndexPD OBJECT-TYPE
    SYNTAX Integer32 (1..200)
    MAX-ACCESS read-only
    STATUS current
    DESCRIPTION
        "Index for table of power distribution objects, specifically the
        index that refers to which power distributor.  A value of 200 means
        the internal power distributor.  A value from 1 to 16 refers to a
        PowerBoss external power distributor, and is the same value as esIndexES,
        which refers to the PowerBoss as an EventSensor in the eventSensorStatus
        object table.  In other words, pdnIndexPD is the same as esIndexES:
        esIndexES is used to refer to the PowerBoss as an eventsensor (i.e., control
        outputs), while pdnIndexPD is used to refer to the PowerBoss when used for
        power distribution monitoring (i.e., to alarm on output
        current/voltage/fuse status)."
    ::= { pdnEntry 1 }
    --1.3.6.1.4.1.3052.14.1.5.4.1.1.1

pdnIndexOutput OBJECT-TYPE
    SYNTAX Integer32 (1..12)
    MAX-ACCESS read-only
    STATUS current
    DESCRIPTION
        "Index for table of power distribution objects, specifically the
        index that refers to which output on the power distributor specified
        by pdnIndexPD.  For objects where the output is irrelevant, this index
        should be 1."
    ::= { pdnEntry 2 }
    --1.3.6.1.4.1.3052.14.1.5.4.1.1.2

pdnConfig OBJECT-TYPE
    SYNTAX DisplayString
    MAX-ACCESS read-only
    STATUS current
    DESCRIPTION
        "The number of outputs on the power distributor specified by pdnIndexPD.
        pdnIndexOutput should be 1 for this object."
    ::= { pdnEntry 3 }
    --1.3.6.1.4.1.3052.14.1.5.4.1.1.3

pdnMainCurrentInEventState OBJECT-TYPE
    SYNTAX DisplayString
    MAX-ACCESS read-only
    STATUS current
    DESCRIPTION
        "The event state of the current (i.e. Amps) event of the power distributor
        specified by pdnIndexPD.  pdnIndexOutput should be 1 for this object.
        Possible values for this object are: 'Very Low', 'Low', 'Normal', 'High',
        'Very High'."
    ::= { pdnEntry 4 }
    --1.3.6.1.4.1.3052.14.1.5.4.1.1.4

pdnMainCurrentValue OBJECT-TYPE
    SYNTAX Integer32
    MAX-ACCESS read-only
    STATUS current
    DESCRIPTION
        "The current drawn, in mA, for the power distributor specified by pdnIndexPD.
        If pdnIndexPD is 200 then this is the internal power distributor and refers to
        the current drawn by the S571 (which is comprised of the internal power
        distributor and ancillary internal equipment) and all equipment powered by the
        S571's internal power outputs.  If pdnIndexPD is 1-16 then this is an external
        power distributor (PowerBoss) and refers to the current drawn by that PowerBoss and all
        equipment powered by that PowerBoss.  pdnIndexOutput should be 1 for this object."
    ::= { pdnEntry 5 }
    --1.3.6.1.4.1.3052.14.1.5.4.1.1.5

pdnMainCurrentValueStr OBJECT-TYPE
    SYNTAX DisplayString
    MAX-ACCESS read-only
    STATUS current
    DESCRIPTION
        "Essentially pdnMainCurrentValue formatted as a string in units of Amps, with
        3 decimal places.  pdnIndexOutput should be 1 for this object."
    ::= { pdnEntry 6 }
    --1.3.6.1.4.1.3052.14.1.5.4.1.1.6

pdnMainCurrentDeadband OBJECT-TYPE
    SYNTAX Integer32
    MAX-ACCESS read-only
    STATUS current
    DESCRIPTION
        "The deadband, in mA, for the main current sensor for the power distributor
        specified by pdIndexPD.  pdnIndexOutput should be 1 for this object."
    ::= { pdnEntry 7 }
    --1.3.6.1.4.1.3052.14.1.5.4.1.1.7

pdnMainCurrentVHighCurrent OBJECT-TYPE
    SYNTAX Integer32
    MAX-ACCESS read-only
    STATUS current
    DESCRIPTION
        "The current, in mA, for the main current sensor's Very High event threshold,
        for the power distributor specified by pdIndexPD.  pdnIndexOutput should be 1
        for this object."
    ::= { pdnEntry 8 }
    --1.3.6.1.4.1.3052.14.1.5.4.1.1.8

pdnMainCurrentHighCurrent OBJECT-TYPE
    SYNTAX Integer32
    MAX-ACCESS read-only
    STATUS current
    DESCRIPTION
        "The current, in mA, for the main current sensor's High event threshold,
        for the power distributor specified by pdIndexPD.  pdnIndexOutput should be 1
        for this object."
    ::= { pdnEntry 9 }
    --1.3.6.1.4.1.3052.14.1.5.4.1.1.9

pdnMainCurrentLowCurrent OBJECT-TYPE
    SYNTAX Integer32
    MAX-ACCESS read-only
    STATUS current
    DESCRIPTION
        "The current, in mA, for the main current sensor's Low event threshold,
        for the power distributor specified by pdIndexPD.  pdnIndexOutput should be 1
        for this object."
    ::= { pdnEntry 10 }
    --1.3.6.1.4.1.3052.14.1.5.4.1.1.10

pdnMainCurrentVLowCurrent OBJECT-TYPE
    SYNTAX Integer32
    MAX-ACCESS read-only
    STATUS current
    DESCRIPTION
        "The current, in mA, for the main current sensor's Very Low event threshold,
        for the power distributor specified by pdIndexPD.  pdnIndexOutput should be 1
        for this object."
    ::= { pdnEntry 11 }
    --1.3.6.1.4.1.3052.14.1.5.4.1.1.11

pdnMainVoltageInEventState OBJECT-TYPE
    SYNTAX DisplayString
    MAX-ACCESS read-only
    STATUS current
    DESCRIPTION
        "The event state of the voltage event of the power distributor
        specified by pdnIndexPD.  pdnIndexOutput should be 1 for this object.
        Possible values for this object are: 'Very Low', 'Low', 'Normal', 'High',
        'Very High'."
    ::= { pdnEntry 12 }
    --1.3.6.1.4.1.3052.14.1.5.4.1.1.12

pdnMainVoltageValue OBJECT-TYPE
    SYNTAX Integer32
    MAX-ACCESS read-only
    STATUS current
    DESCRIPTION
        "The voltage, in mV, at the power distributor specified by pdnIndexPD.
        If pdnIndexPD is 200 then this is the internal power distributor and refers to
        the voltage at the S571 (which is comprised of the internal power
        distributor and ancillary internal equipment) and all equipment powered by the
        S571's internal power outputs.  If pdnIndexPD is 1-16 then this is an external
        power distributor (PowerBoss) and refers to the voltage at that PowerBoss and all
        equipment powered by that PowerBoss.  pdnIndexOutput should be 1 for this object."
    ::= { pdnEntry 13 }
    --1.3.6.1.4.1.3052.14.1.5.4.1.1.13

pdnMainVoltageValueStr OBJECT-TYPE
    SYNTAX DisplayString
    MAX-ACCESS read-only
    STATUS current
    DESCRIPTION
        "Essentially pdnMainVoltageValue formatted as a string in units of Volts, with
        3 decimal places.  pdnIndexOutput should be 1 for this object."
    ::= { pdnEntry 14 }
    --1.3.6.1.4.1.3052.14.1.5.4.1.1.14

pdnMainVoltageDeadband OBJECT-TYPE
    SYNTAX Integer32
    MAX-ACCESS read-only
    STATUS current
    DESCRIPTION
        "The deadband, in mV, for the main voltage sensor for the power distributor
        specified by pdIndexPD.  pdnIndexOutput should be 1 for this object."
    ::= { pdnEntry 15 }
    --1.3.6.1.4.1.3052.14.1.5.4.1.1.15

pdnMainVoltageVHighVoltage OBJECT-TYPE
    SYNTAX Integer32
    MAX-ACCESS read-only
    STATUS current
    DESCRIPTION
        "The voltage, in mA, for the main voltage sensor's Very High event threshold,
        for the power distributor specified by pdIndexPD.  pdnIndexOutput should be 1
        for this object."
    ::= { pdnEntry 16 }
    --1.3.6.1.4.1.3052.14.1.5.4.1.1.16

pdnMainVoltageHighVoltage OBJECT-TYPE
    SYNTAX Integer32
    MAX-ACCESS read-only
    STATUS current
    DESCRIPTION
        "The voltage, in mV, for the main voltage sensor's High event threshold,
        for the power distributor specified by pdIndexPD.  pdnIndexOutput should be 1
        for this object."
    ::= { pdnEntry 17 }
    --1.3.6.1.4.1.3052.14.1.5.4.1.1.17

pdnMainVoltageLowVoltage OBJECT-TYPE
    SYNTAX Integer32
    MAX-ACCESS read-only
    STATUS current
    DESCRIPTION
        "The voltage, in mV, for the main voltage sensor's Low event threshold,
        for the power distributor specified by pdIndexPD.  pdnIndexOutput should be 1
        for this object."
    ::= { pdnEntry 18 }
    --1.3.6.1.4.1.3052.14.1.5.4.1.1.18

pdnMainVoltageVLowVoltage OBJECT-TYPE
    SYNTAX Integer32
    MAX-ACCESS read-only
    STATUS current
    DESCRIPTION
        "The voltage, in mV, for the main voltage sensor's Very Low event threshold,
        for the power distributor specified by pdIndexPD.  pdnIndexOutput should be 1
        for this object."
    ::= { pdnEntry 19 }
    --1.3.6.1.4.1.3052.14.1.5.4.1.1.19

pdnMainPowerValue OBJECT-TYPE
    SYNTAX Integer32
    MAX-ACCESS read-only
    STATUS current
    DESCRIPTION
        "The power, in Watts, for the power distributor specified by pdIndexPD.
        pdnIndexOutput should be 1 for this object."
    ::= { pdnEntry 20 }
    --1.3.6.1.4.1.3052.14.1.5.4.1.1.20

pdnMainPowerValueStr OBJECT-TYPE
    SYNTAX DisplayString
    MAX-ACCESS read-only
    STATUS current
    DESCRIPTION
        "The power, in Watts, for the power distributor specified by pdIndexPD,
        formatted as a string with the unit name 'Watts'.  pdnIndexOutput should be 1
        for this object."
    ::= { pdnEntry 21 }
    --1.3.6.1.4.1.3052.14.1.5.4.1.1.21

pdnOutputCurrentInEventState OBJECT-TYPE
    SYNTAX DisplayString
    MAX-ACCESS read-only
    STATUS current
    DESCRIPTION
        "The event state of the current (i.e. Amps) event of the power distributor
        output specified by pdnIndexPD and pdnIndexOutput.  E.g., for pdnIndexPD=200
        and pdnIndexOutput=2, this refers to power output #2 of the internal power
        distributor. Possible values for this object are: 'Very Low', 'Low', 'Normal',
        'High', 'Very High'."
    ::= { pdnEntry 22 }
    --1.3.6.1.4.1.3052.14.1.5.4.1.1.22

pdnOutputCurrentValue OBJECT-TYPE
    SYNTAX Integer32
    MAX-ACCESS read-only
    STATUS current
    DESCRIPTION
        "The current drawn, in mA, for the power distributor output specified by
        pdnIndexPD and pdIndexOutput.  If pdnIndexPD is 200 then this is the internal
        power distributor and refers to the current drawn by a specific power output
        on the S571.  If pdIndexPD is 3 then this is an external power distributor (PowerBoss)
        identified as 'power distributor 3' and refers to the current drawn by a
        specific power output on that PowerBoss.  The specific power output is specified by
        pdIndexOutput."
    ::= { pdnEntry 23 }
    --1.3.6.1.4.1.3052.14.1.5.4.1.1.23

pdnOutputCurrentValueStr OBJECT-TYPE
    SYNTAX DisplayString
    MAX-ACCESS read-only
    STATUS current
    DESCRIPTION
        "Essentially pdnOutputCurrentValue formatted as a string in units of Amps, with
        3 decimal places."
    ::= { pdnEntry 24 }
    --1.3.6.1.4.1.3052.14.1.5.4.1.1.24

pdnOutputCurrentDeadband OBJECT-TYPE
    SYNTAX Integer32
    MAX-ACCESS read-only
    STATUS current
    DESCRIPTION
        "The deadband, in mA, for the main current sensor for the power distributor
        specified by pdIndexPD.  The power output is specified by pdnIndexOutput."
    ::= { pdnEntry 25 }
    --1.3.6.1.4.1.3052.14.1.5.4.1.1.25

pdnOutputCurrentVHighCurrent OBJECT-TYPE
    SYNTAX Integer32
    MAX-ACCESS read-only
    STATUS current
    DESCRIPTION
        "The current, in mA, for a specific power output's current sensor Very High
        event threshold, for the power distributor specified by pdIndexPD.  The power
        output is specified by pdnIndexOutput."
    ::= { pdnEntry 26 }
    --1.3.6.1.4.1.3052.14.1.5.4.1.1.26

pdnOutputCurrentHighCurrent OBJECT-TYPE
    SYNTAX Integer32
    MAX-ACCESS read-only
    STATUS current
    DESCRIPTION
        "The current, in mA, for a specific power output's current sensor High event
        threshold, for the power distributor specified by pdIndexPD.  The power output
        is specified by pdnIndexOutput for this object."
    ::= { pdnEntry 27 }
    --1.3.6.1.4.1.3052.14.1.5.4.1.1.27

pdnOutputCurrentLowCurrent OBJECT-TYPE
    SYNTAX Integer32
    MAX-ACCESS read-only
    STATUS current
    DESCRIPTION
        "The current, in mA, for a specific power output's current sensor Low event
        threshold, for the power distributor specified by pdIndexPD.  The power output
        is specified by pdnIndexOutput for this object."
    ::= { pdnEntry 28 }
    --1.3.6.1.4.1.3052.14.1.5.4.1.1.28

pdnOutputCurrentVLowCurrent OBJECT-TYPE
    SYNTAX Integer32
    MAX-ACCESS read-only
    STATUS current
    DESCRIPTION
        "The current, in mA, for a specific power output's current sensor Very Low
        event threshold, for the power distributor specified by pdIndexPD.  The power
        output is specified by pdnIndexOutput for this object."
    ::= { pdnEntry 29 }
    --1.3.6.1.4.1.3052.14.1.5.4.1.1.29

pdnOutputFuseInEventState OBJECT-TYPE
    SYNTAX DisplayString
    MAX-ACCESS read-only
    STATUS current
    DESCRIPTION
        "The event state of the fuse event of the power distributor output specified
        by pdnIndexPD and pdnIndexOutput.  E.g., for pdnIndexPD=14 and pdnIndexOutput=2,
        this refers to power output #2 of the PowerBoss external power distributor,
        identified as 'power distributor 14'. Possible values for this object are:
        'Very Low', 'Low', 'Normal', 'High', 'Very High'.  This object exists only for
        power distributors with fuse monitoring support."
    ::= { pdnEntry 30 }
    --1.3.6.1.4.1.3052.14.1.5.4.1.1.30

pdnOutputFuseValueStr OBJECT-TYPE
    SYNTAX DisplayString
    MAX-ACCESS read-only
    STATUS current
    DESCRIPTION
        "The state of the fuse of the power distributor output specified
        by pdnIndexPD and pdnIndexOutput.  Possible values for this object are:
        'BLOWN' and 'OK'.  This object exists only for power distributors with
        fuse monitoring support."
    ::= { pdnEntry 31 }
    --1.3.6.1.4.1.3052.14.1.5.4.1.1.31

pdnMainCombinedStatus OBJECT-TYPE
    SYNTAX DisplayString
    MAX-ACCESS read-only
    STATUS current
    DESCRIPTION
        "Combined status string intended to be parsed by NMS:
        format: voltageColorCode`voltageEventState`voltageValue`mainCurrentColorCode`mainCurrentEventState`mainCurrentValue`deviceCurrentValue`mainPowerValue"
    ::= { pdnEntry 32 }
    --1.3.6.1.4.1.3052.14.1.5.4.1.1.32

pdnOutputCombinedStatusBlock1 OBJECT-TYPE
    SYNTAX DisplayString
    MAX-ACCESS read-only
    STATUS current
    DESCRIPTION
        "Combined status string intended to be parsed by NMS:
        format: numInBlock~outputCurrentColorCode1`outputCurrentEventState1`outputCurrentValue1`fuseColorCode1`fuseValue1~..."
    ::= { pdnEntry 33 }
    --1.3.6.1.4.1.3052.14.1.5.4.1.1.33

pdnOutputCombinedStatusBlock2 OBJECT-TYPE
    SYNTAX DisplayString
    MAX-ACCESS read-only
    STATUS current
    DESCRIPTION
        "Combined status string intended to be parsed by NMS:
        format: numInBlock~outputCurrentColorCode1`outputCurrentEventState1`outputCurrentValue1`fuseColorCode1`fuseValue1~..."
    ::= { pdnEntry 34 }
    --1.3.6.1.4.1.3052.14.1.5.4.1.1.34

pdnDeviceCurrentValue OBJECT-TYPE
    SYNTAX Integer32
    MAX-ACCESS read-only
    STATUS current
    DESCRIPTION
        "Current drawn by device in mA.  For the internal power distributor device,
        this is the current drawn by the SiteBoss 571.  For an external power
        distributor device (PowerBoss), this is the current drawn by the
        PowerBoss.  This object exists only for power distributors with device
        current monitoring support."
    ::= { pdnEntry 35 }
    --1.3.6.1.4.1.3052.14.1.5.4.1.1.35

pdnDeviceCurrentValueStr OBJECT-TYPE
    SYNTAX DisplayString
    MAX-ACCESS read-only
    STATUS current
    DESCRIPTION
        "Current drawn by device as a string with units (Amps).  For the internal
        power distributor device, this is the current drawn by the SiteBoss 571.
        For an external power distributor device (PowerBoss), this is the
        current drawn by the PowerBoss.  This object exists only for power
        distributors with device current monitoring support."
    ::= { pdnEntry 36 }
    --1.3.6.1.4.1.3052.14.1.5.4.1.1.36

pdSystemCurrent OBJECT-TYPE
    SYNTAX DisplayString
    MAX-ACCESS read-only
    STATUS current
    DESCRIPTION
        "Total current drawn by all power distributors in system; that is, the
        sum of all pdnMainCurrentValue objects for all connected power
        distributors: internal and external."
    ::= { pdSystem 1 }
    --1.3.6.1.4.1.3052.14.1.5.5.1

pdSystemPower OBJECT-TYPE
    SYNTAX DisplayString
    MAX-ACCESS read-only
    STATUS current
    DESCRIPTION
        "Total power used by all power distributors in system; that is, the
        sum of all pdnMainPowerValue objects for all connected power
        distributors: internal and external."
    ::= { pdSystem 2 }
    --1.3.6.1.4.1.3052.14.1.5.5.2


--***************************************************************************************
--Fuel Sensor 1.5
--***************************************************************************************

fsStatusTable OBJECT-TYPE
    SYNTAX SEQUENCE OF FSStatus
    MAX-ACCESS not-accessible
    STATUS current
    DESCRIPTION
        "Fuel sensor status table"
    ::= { fuelSensorStatus 1 }
    --1.3.6.1.4.1.3052.14.1.6.1

fsStatusEntry OBJECT-TYPE
    SYNTAX FSStatus
    MAX-ACCESS not-accessible
    STATUS current
    DESCRIPTION
        "Fuel sensor status table entry"
    INDEX { fsStatusIndex }
    ::= { fsStatusTable 1 }
    --1.3.6.1.4.1.3052.14.1.6.1.1

fsStatusIndex OBJECT-TYPE
    SYNTAX Integer32 (1..3)
    MAX-ACCESS read-only
    STATUS current
    DESCRIPTION
        "Index for fuel sensors"
    ::= { fsStatusEntry 1 }
    --1.3.6.1.4.1.3052.14.1.6.1.1.1

fsStatusName OBJECT-TYPE
    SYNTAX DisplayString
    MAX-ACCESS read-only
    STATUS current
    DESCRIPTION
        "Fuel sensor name"
    ::= { fsStatusEntry 2 }
    --1.3.6.1.4.1.3052.14.1.6.1.1.2

fsStatusDeviceState OBJECT-TYPE
    SYNTAX DisplayString
    MAX-ACCESS read-only
    STATUS current
    DESCRIPTION
        "Fuel sensor device state"
    ::= { fsStatusEntry 3 }
    --1.3.6.1.4.1.3052.14.1.6.1.1.3

fsStatusVolumeValueString OBJECT-TYPE
    SYNTAX DisplayString
    MAX-ACCESS read-only
    STATUS current
    DESCRIPTION
        "Fuel volume. Range is -2,147,483,648 to 2,147,483,647. This value reads
         -999 when the fuel sensor is disconnected"
    ::= { fsStatusEntry 4 }
    --1.3.6.1.4.1.3052.14.1.6.1.1.4

fsStatusVolumePercentLevel OBJECT-TYPE
    SYNTAX DisplayString
    MAX-ACCESS read-only
    STATUS current
    DESCRIPTION
        "Height of the fluid in the tank expressed as a percentage of the tank
         height, in hundredths of a percent."
    ::= { fsStatusEntry 7 }
    --1.3.6.1.4.1.3052.14.1.6.1.1.7

fsStatusVolumeInEventState OBJECT-TYPE
    SYNTAX DisplayString
    MAX-ACCESS read-only
    STATUS current
    DESCRIPTION
        "Current event status of the fuel sensor."
    ::= { fsStatusEntry 8 }
    --1.3.6.1.4.1.3052.14.1.6.1.1.8

fsStatusCombined OBJECT-TYPE
    SYNTAX DisplayString
    MAX-ACCESS read-only
    STATUS current
    DESCRIPTION
        "Combined status string intended to be parsed by NMS:
        deviceState`deviceStateColorCode`percentRounded`valueAsFloat`volumeEventState`volumeEventStateColorCode`capacity`units`name"
    ::= { fsStatusEntry 9 }
    --1.3.6.1.4.1.3052.14.1.6.1.1.9


--***************************************************************************************
--Wireless Modem Status Section  1.7
--***************************************************************************************

wmsStatus OBJECT-TYPE
    SYNTAX DisplayString
    MAX-ACCESS read-only
    STATUS current
    DESCRIPTION
        "Wireless modem status"
    ::= { wirelessModemStatus 1 }
    --1.3.6.1.4.1.3052.14.1.7.1

wmsSignal OBJECT-TYPE
    SYNTAX DisplayString
    MAX-ACCESS read-only
    STATUS current
    DESCRIPTION
        "Wireless modem Signal strength"
    ::= { wirelessModemStatus 2 }
    --1.3.6.1.4.1.3052.14.1.7.2

wmsRSSI OBJECT-TYPE
    SYNTAX DisplayString
    MAX-ACCESS read-only
    STATUS current
    DESCRIPTION
        "Wireless modem Signal strength (RSSI)"
    ::= { wirelessModemStatus 3 }
    --1.3.6.1.4.1.3052.14.1.7.3

wmsBER OBJECT-TYPE
    SYNTAX DisplayString
    MAX-ACCESS read-only
    STATUS current
    DESCRIPTION
        "Wireless modem Bit Error Rate"
    ::= { wirelessModemStatus 4 }
    --1.3.6.1.4.1.3052.14.1.7.4

wmsUpdated OBJECT-TYPE
    SYNTAX DisplayString
    MAX-ACCESS read-only
    STATUS current
    DESCRIPTION
        "Wireless modem info last update time"
    ::= { wirelessModemStatus 5 }
    --1.3.6.1.4.1.3052.14.1.7.5

wmsRegistration OBJECT-TYPE
    SYNTAX DisplayString
    MAX-ACCESS read-only
    STATUS current
    DESCRIPTION
        "Wireless modem registration status"
    ::= { wirelessModemStatus 6 }
    --1.3.6.1.4.1.3052.14.1.7.6

wmsLAC OBJECT-TYPE
    SYNTAX DisplayString
    MAX-ACCESS read-only
    STATUS current
    DESCRIPTION
        "Wireless modem Location Area Code"
    ::= { wirelessModemStatus 7 }
    --1.3.6.1.4.1.3052.14.1.7.7

wmsCellID OBJECT-TYPE
    SYNTAX DisplayString
    MAX-ACCESS read-only
    STATUS current
    DESCRIPTION
        "Wireless modem Cell ID"
    ::= { wirelessModemStatus 8 }
    --1.3.6.1.4.1.3052.14.1.7.8

wmsIMSI OBJECT-TYPE
    SYNTAX DisplayString
    MAX-ACCESS read-only
    STATUS current
    DESCRIPTION
        "Wireless modem Internation Mobile Subscriber Identity number"
    ::= { wirelessModemStatus 9 }
    --1.3.6.1.4.1.3052.14.1.7.9

wmsPhnum OBJECT-TYPE
    SYNTAX DisplayString
    MAX-ACCESS read-only
    STATUS current
    DESCRIPTION
        "Wireless modem phone number"
    ::= { wirelessModemStatus 10 }
    --1.3.6.1.4.1.3052.14.1.7.10

wmsLocalIP OBJECT-TYPE
    SYNTAX DisplayString
    MAX-ACCESS read-only
    STATUS current
    DESCRIPTION
        "Local IP address of modem on wireless network"
    ::= { wirelessModemStatus 11 }
    --1.3.6.1.4.1.3052.14.1.7.11

wmsMgfID OBJECT-TYPE
    SYNTAX DisplayString
    MAX-ACCESS read-only
    STATUS current
    DESCRIPTION
        "Wireless modem manufacturer ID"
    ::= { wirelessModemStatus 12 }
    --1.3.6.1.4.1.3052.14.1.7.12

wmsModelID OBJECT-TYPE
    SYNTAX DisplayString
    MAX-ACCESS read-only
    STATUS current
    DESCRIPTION
        "Wireless modem model ID"
    ::= { wirelessModemStatus 13 }
    --1.3.6.1.4.1.3052.14.1.7.13

wmsIMEI OBJECT-TYPE
    SYNTAX DisplayString
    MAX-ACCESS read-only
    STATUS current
    DESCRIPTION
        "Wireless modem International Mobile Equipment Identity number"
    ::= { wirelessModemStatus 14 }
    --1.3.6.1.4.1.3052.14.1.7.14

wmsRevID OBJECT-TYPE
    SYNTAX DisplayString
    MAX-ACCESS read-only
    STATUS current
    DESCRIPTION
        "Wireless modem revision ID"
    ::= { wirelessModemStatus 15 }
    --1.3.6.1.4.1.3052.14.1.7.15

wmsNetName OBJECT-TYPE
    SYNTAX DisplayString
    MAX-ACCESS read-only
    STATUS current
    DESCRIPTION
        "Wireless modem network name"
    ::= { wirelessModemStatus 16 }
    --1.3.6.1.4.1.3052.14.1.7.16

wmsGPRSStatus OBJECT-TYPE
    SYNTAX DisplayString
    MAX-ACCESS read-only
    STATUS current
    DESCRIPTION
        "Wireless modem (E)GPRS status"
    ::= { wirelessModemStatus 17 }
    --1.3.6.1.4.1.3052.14.1.7.17

wmsBand OBJECT-TYPE
    SYNTAX DisplayString
    MAX-ACCESS read-only
    STATUS current
    DESCRIPTION
        "Wireless modem band"
    ::= { wirelessModemStatus 18 }
    --1.3.6.1.4.1.3052.14.1.7.18

wmsChannel OBJECT-TYPE
    SYNTAX DisplayString
    MAX-ACCESS read-only
    STATUS current
    DESCRIPTION
        "Wireless modem channel"
    ::= { wirelessModemStatus 19 }
    --1.3.6.1.4.1.3052.14.1.7.19

wmsCountryCode OBJECT-TYPE
    SYNTAX DisplayString
    MAX-ACCESS read-only
    STATUS current
    DESCRIPTION
        "Wireless modem country code"
    ::= { wirelessModemStatus 20 }
    --1.3.6.1.4.1.3052.14.1.7.20

wmsNetCode OBJECT-TYPE
    SYNTAX DisplayString
    MAX-ACCESS read-only
    STATUS current
    DESCRIPTION
        "Wireless modem network code"
    ::= { wirelessModemStatus 21 }
    --1.3.6.1.4.1.3052.14.1.7.21

wmsPLMNColor OBJECT-TYPE
    SYNTAX DisplayString
    MAX-ACCESS read-only
    STATUS current
    DESCRIPTION
        "Wireless modem PLMN color"
    ::= { wirelessModemStatus 22 }
    --1.3.6.1.4.1.3052.14.1.7.22

wmsBScolor OBJECT-TYPE
    SYNTAX DisplayString
    MAX-ACCESS read-only
    STATUS current
    DESCRIPTION
        "Wireless modem BS color"
    ::= { wirelessModemStatus 23 }
    --1.3.6.1.4.1.3052.14.1.7.23

wmsMpRACH OBJECT-TYPE
    SYNTAX DisplayString
    MAX-ACCESS read-only
    STATUS current
    DESCRIPTION
        "Wireless modem max power RACH"
    ::= { wirelessModemStatus 24 }
    --1.3.6.1.4.1.3052.14.1.7.24

wmsMinRxLevel OBJECT-TYPE
    SYNTAX DisplayString
    MAX-ACCESS read-only
    STATUS current
    DESCRIPTION
        "Wireless modem minimum receive level"
    ::= { wirelessModemStatus 25 }
    --1.3.6.1.4.1.3052.14.1.7.25

wmsBaseCoeff OBJECT-TYPE
    SYNTAX DisplayString
    MAX-ACCESS read-only
    STATUS current
    DESCRIPTION
        "Wireless modem base coefficient"
    ::= { wirelessModemStatus 26 }
    --1.3.6.1.4.1.3052.14.1.7.26

wmsSIMStatus OBJECT-TYPE
    SYNTAX DisplayString
    MAX-ACCESS read-only
    STATUS current
    DESCRIPTION
        "WWireless modem SIM status"
    ::= { wirelessModemStatus 27 }
    --1.3.6.1.4.1.3052.14.1.7.27

wmsICCID OBJECT-TYPE
    SYNTAX DisplayString
    MAX-ACCESS read-only
    STATUS current
    DESCRIPTION
        "Wireless modem SIM ICCID"
    ::= { wirelessModemStatus 28 }
    --1.3.6.1.4.1.3052.14.1.7.28

wmsModemType OBJECT-TYPE
    SYNTAX DisplayString
    MAX-ACCESS read-only
    STATUS current
    DESCRIPTION
        "Wireless modem type"
    ::= { wirelessModemStatus 29 }
    --1.3.6.1.4.1.3052.14.1.7.29


--***************************************************************************************
--AC Power Monitor Section 1.8
--***************************************************************************************

acpmStatusTable OBJECT-TYPE
    SYNTAX SEQUENCE OF ACPMStatus
    MAX-ACCESS not-accessible
    STATUS current
    DESCRIPTION
        "AC power monitor status table"
    ::= { acPowerMonitorStatus 1 }
    --1.3.6.1.4.1.3052.14.1.8.1

acpmStatusEntry OBJECT-TYPE
    SYNTAX ACPMStatus
    MAX-ACCESS not-accessible
    STATUS current
    DESCRIPTION
        "AC power monitor status table entry"
    INDEX { acpmsIndex }
    ::= { acpmStatusTable 1 }
    --1.3.6.1.4.1.3052.14.1.8.1.1

acpmsIndex OBJECT-TYPE
    SYNTAX Integer32 (1..6)
    MAX-ACCESS read-only
    STATUS current
    DESCRIPTION
        "Index for AC power monitors"
    ::= { acpmStatusEntry 1 }
    --1.3.6.1.4.1.3052.14.1.8.1.1.1

acpmsName OBJECT-TYPE
    SYNTAX DisplayString
    MAX-ACCESS read-only
    STATUS current
    DESCRIPTION
        "Name for the AC power monitor device."
    ::= { acpmStatusEntry 2 }
    --1.3.6.1.4.1.3052.14.1.8.1.1.2

acpmsAvgVoltageValueStr OBJECT-TYPE
    SYNTAX DisplayString
    MAX-ACCESS read-only
    STATUS current
    DESCRIPTION
        "Average voltage, in volts. This is calculated using the formula
        (register * PT ratio * 0.1). This could be either the average of
        the phase voltages, or the sum of the phase voltages, depending
        on device configuration."
    ::= { acpmStatusEntry 3 }
    --1.3.6.1.4.1.3052.14.1.8.1.1.3

acpmsAvgVoltageMinStr OBJECT-TYPE
    SYNTAX DisplayString
    MAX-ACCESS read-only
    STATUS current
    DESCRIPTION
        "Minimum average voltage value since last reset, in volts."
    ::= { acpmStatusEntry 4 }
    --1.3.6.1.4.1.3052.14.1.8.1.1.4

acpmsAvgVoltageMaxStr OBJECT-TYPE
    SYNTAX DisplayString
    MAX-ACCESS read-only
    STATUS current
    DESCRIPTION
        "Maximum average voltage value since last reset, in volts."
    ::= { acpmStatusEntry 5 }
    --1.3.6.1.4.1.3052.14.1.8.1.1.5

acpmsAvgVoltageAvgStr OBJECT-TYPE
    SYNTAX DisplayString
    MAX-ACCESS read-only
    STATUS current
    DESCRIPTION
        "Average average voltage value since last reset, in volts.  This is
        the unit's average of its measurements of the average voltage
        reported by the AC power monitor device."
    ::= { acpmStatusEntry 6 }
    --1.3.6.1.4.1.3052.14.1.8.1.1.6

acpmsAvgVoltageInEventState OBJECT-TYPE
    SYNTAX DisplayString
    MAX-ACCESS read-only
    STATUS current
    DESCRIPTION
        "Event state of this AC power monitor voltage (Low, Normal, High, etc.)."
    ::= { acpmStatusEntry 7 }
    --1.3.6.1.4.1.3052.14.1.8.1.1.7

acpmsVoltagePhaseAValueStr OBJECT-TYPE
    SYNTAX DisplayString
    MAX-ACCESS read-only
    STATUS current
    DESCRIPTION
        "Phase A voltage, in volts. This is calculated using the formula
        (register * PT ratio * 0.1)."
    ::= { acpmStatusEntry 8 }
    --1.3.6.1.4.1.3052.14.1.8.1.1.8

acpmsVoltagePhaseBValueStr OBJECT-TYPE
    SYNTAX DisplayString
    MAX-ACCESS read-only
    STATUS current
    DESCRIPTION
        "Phase B voltage, in volts. This is calculated using the formula
        (register * PT ratio * 0.1)."
    ::= { acpmStatusEntry 9 }
    --1.3.6.1.4.1.3052.14.1.8.1.1.9

acpmsVoltagePhaseCValueStr OBJECT-TYPE
    SYNTAX DisplayString
    MAX-ACCESS read-only
    STATUS current
    DESCRIPTION
        "Phase C voltage, in volts. This is calculated using the formula
        (register * PT ratio * 0.1)."
    ::= { acpmStatusEntry 10 }
    --1.3.6.1.4.1.3052.14.1.8.1.1.10

acpmsAvgCurrentValueStr OBJECT-TYPE
    SYNTAX DisplayString
    MAX-ACCESS read-only
    STATUS current
    DESCRIPTION
        "Average current, in amps. This is calculated using the formula
        (register * CT ratio * 0.001). This could be either the average of
        the phase currents, or the sum of the phase currents, depending on
        device configuration."
    ::= { acpmStatusEntry 11 }
    --1.3.6.1.4.1.3052.14.1.8.1.1.11

acpmsAvgCurrentMinStr OBJECT-TYPE
    SYNTAX DisplayString
    MAX-ACCESS read-only
    STATUS current
    DESCRIPTION
        "Minimum average current value since last reset, in amps."
    ::= { acpmStatusEntry 12 }
    --1.3.6.1.4.1.3052.14.1.8.1.1.12

acpmsAvgCurrentMaxStr OBJECT-TYPE
    SYNTAX DisplayString
    MAX-ACCESS read-only
    STATUS current
    DESCRIPTION
        "Maximum average current value since last reset, in amps."
    ::= { acpmStatusEntry 13 }
    --1.3.6.1.4.1.3052.14.1.8.1.1.13

acpmsAvgCurrentAvgStr OBJECT-TYPE
    SYNTAX DisplayString
    MAX-ACCESS read-only
    STATUS current
    DESCRIPTION
        "Average average current value since last reset, in amps.  This is
        the unit's average of its measurements of the average current reported
        by the AC power monitor device."
    ::= { acpmStatusEntry 14 }
    --1.3.6.1.4.1.3052.14.1.8.1.1.14

acpmsAvgCurrentInEventState OBJECT-TYPE
    SYNTAX DisplayString
    MAX-ACCESS read-only
    STATUS current
    DESCRIPTION
        "Event state of this AC power monitor current (Low, Normal, High, etc.)."
    ::= { acpmStatusEntry 15 }
    --1.3.6.1.4.1.3052.14.1.8.1.1.15

acpmsCurrentPhaseAValueStr OBJECT-TYPE
    SYNTAX DisplayString
    MAX-ACCESS read-only
    STATUS current
    DESCRIPTION
        "Phase A current, in amps. This is calculated using the formula
        (register * CT ratio * 0.001)."
    ::= { acpmStatusEntry 16 }
    --1.3.6.1.4.1.3052.14.1.8.1.1.16

acpmsCurrentPhaseBValueStr OBJECT-TYPE
    SYNTAX DisplayString
    MAX-ACCESS read-only
    STATUS current
    DESCRIPTION
        "Phase B current, in amps. This is calculated using the formula
        (register * CT ratio * 0.001)."
    ::= { acpmStatusEntry 17 }
    --1.3.6.1.4.1.3052.14.1.8.1.1.17

acpmsCurrentPhaseCValueStr OBJECT-TYPE
    SYNTAX DisplayString
    MAX-ACCESS read-only
    STATUS current
    DESCRIPTION
        "Phase C current, in amps. This is calculated using the formula
        (register * CT ratio * 0.001)."
    ::= { acpmStatusEntry 18 }
    --1.3.6.1.4.1.3052.14.1.8.1.1.18

acpmsAvgFreqValueStr OBJECT-TYPE
    SYNTAX DisplayString
    MAX-ACCESS read-only
    STATUS current
    DESCRIPTION
        "Frequency, in hertz. On the YD2010, this is calculated using the
        formula (register * 0.00106813). On the WattsOn, this is calculated
        using the formula (register * 0.1)."
    ::= { acpmStatusEntry 19 }
    --1.3.6.1.4.1.3052.14.1.8.1.1.19

acpmsAvgFreqMinStr OBJECT-TYPE
    SYNTAX DisplayString
    MAX-ACCESS read-only
    STATUS current
    DESCRIPTION
        "Minimum frequency value since last reset, in hertz."
    ::= { acpmStatusEntry 20 }
    --1.3.6.1.4.1.3052.14.1.8.1.1.20

acpmsAvgFreqMaxStr OBJECT-TYPE
    SYNTAX DisplayString
    MAX-ACCESS read-only
    STATUS current
    DESCRIPTION
        "Maximum frequency value since last reset, in hertz."
    ::= { acpmStatusEntry 21 }
    --1.3.6.1.4.1.3052.14.1.8.1.1.21

acpmsAvgFreqAvgStr OBJECT-TYPE
    SYNTAX DisplayString
    MAX-ACCESS read-only
    STATUS current
    DESCRIPTION
        "Average frequency value since last reset, in hertz.  This is the
        unit's average of its measurements of the average frequency reported
        by the AC power monitor device."
    ::= { acpmStatusEntry 22 }
    --1.3.6.1.4.1.3052.14.1.8.1.1.22

acpmsAvgFreqInEventState OBJECT-TYPE
    SYNTAX DisplayString
    MAX-ACCESS read-only
    STATUS current
    DESCRIPTION
        "Event state of this AC power monitor frequency (Low, Normal, High, etc.)."
    ::= { acpmStatusEntry 23 }
    --1.3.6.1.4.1.3052.14.1.8.1.1.23

acpmsTRPValueStr OBJECT-TYPE
    SYNTAX DisplayString
    MAX-ACCESS read-only
    STATUS current
    DESCRIPTION
        "Total real power, in watts. On the YD2010, this is calculated using
        the formula (register * PT ratio * CT ratio * Urg * 0.4), where Urg is
        the voltage range taken from register 0x30A. On the WattsOn models,
        this is calculated using the formula (register * PT * CT)."
    ::= { acpmStatusEntry 24 }
    --1.3.6.1.4.1.3052.14.1.8.1.1.24

acpmsTRPMinStr OBJECT-TYPE
    SYNTAX DisplayString
    MAX-ACCESS read-only
    STATUS current
    DESCRIPTION
        "Minimum total real power value since last reset, in watts."
    ::= { acpmStatusEntry 25 }
    --1.3.6.1.4.1.3052.14.1.8.1.1.25

acpmsTRPMaxStr OBJECT-TYPE
    SYNTAX DisplayString
    MAX-ACCESS read-only
    STATUS current
    DESCRIPTION
        "Maximum total real power value since last reset, in watts."
    ::= { acpmStatusEntry 26 }
    --1.3.6.1.4.1.3052.14.1.8.1.1.26

acpmsTRPAvgStr OBJECT-TYPE
    SYNTAX DisplayString
    MAX-ACCESS read-only
    STATUS current
    DESCRIPTION
        "Average total real power value since last reset, in watts.  This is
        the unit's average of its measurements of the average total real power
        reported by the AC power monitor device."
    ::= { acpmStatusEntry 27 }
    --1.3.6.1.4.1.3052.14.1.8.1.1.27

acpmsTRPInEventState OBJECT-TYPE
    SYNTAX DisplayString
    MAX-ACCESS read-only
    STATUS current
    DESCRIPTION
        "Event state of this AC power monitor total real power (Low, Normal,
        High, etc.)."
    ::= { acpmStatusEntry 28 }
    --1.3.6.1.4.1.3052.14.1.8.1.1.28

acpmsRPPhaseAValueStr OBJECT-TYPE
    SYNTAX DisplayString
    MAX-ACCESS read-only
    STATUS current
    DESCRIPTION
        "Phase A real power, in watts. On the YD2010, this is calculated using
        the formula (register * PT ratio * CT ratio * Urg * 0.4), where Urg is
        the voltage range taken from register 0x30A. On the WattsOn, this is
        calculated using the formula (register * PT * CT)."
    ::= { acpmStatusEntry 29 }
    --1.3.6.1.4.1.3052.14.1.8.1.1.29

acpmsRPPhaseBValueStr OBJECT-TYPE
    SYNTAX DisplayString
    MAX-ACCESS read-only
    STATUS current
    DESCRIPTION
        "Phase B real power, in watts. On the YD2010, this is calculated using
        the formula (register * PT ratio * CT ratio * Urg * 0.4), where Urg is
        the voltage range taken from register 0x30A. On the WattsOn, this is
        calculated using the formula (register * PT * CT)."
    ::= { acpmStatusEntry 30 }
    --1.3.6.1.4.1.3052.14.1.8.1.1.30

acpmsRPPhaseCValueStr OBJECT-TYPE
    SYNTAX DisplayString
    MAX-ACCESS read-only
    STATUS current
    DESCRIPTION
        "Phase C real power, in watts. On the YD2010, this is calculated using
        the formula (register * PT ratio * CT ratio * Urg * 0.4), where Urg is
        the voltage range taken from register 0x30A. On the WattsOn, this is
        calculated using the formula (register * PT * CT)."
    ::= { acpmStatusEntry 31 }
    --1.3.6.1.4.1.3052.14.1.8.1.1.31

acpmsCombined OBJECT-TYPE
    SYNTAX DisplayString
    MAX-ACCESS read-only
    STATUS current
    DESCRIPTION
        "Combined status string intended to be parsed by NMS:
        name`deviceState`deviceStateColorCode`voltage`current`frequency`power~voltageEventState`voltageColorCode`currentEventState`currentColorCode`frequencyEventState`freuencyColorCode`powerEventState`powerColorCode"
    ::= { acpmStatusEntry 32 }
    --1.3.6.1.4.1.3052.14.1.8.1.1.32

acpmsTPFValueStr OBJECT-TYPE
    SYNTAX DisplayString
    MAX-ACCESS read-only
    STATUS current
    DESCRIPTION
        "Total power factor."
    ::= { acpmStatusEntry 33 }
    --1.3.6.1.4.1.3052.14.1.8.1.1.33

acpmsTPFMinStr OBJECT-TYPE
    SYNTAX DisplayString
    MAX-ACCESS read-only
    STATUS current
    DESCRIPTION
        "Total power factor minimum value since last reset."
    ::= { acpmStatusEntry 34 }
    --1.3.6.1.4.1.3052.14.1.8.1.1.34

acpmsTPFMaxStr OBJECT-TYPE
    SYNTAX DisplayString
    MAX-ACCESS read-only
    STATUS current
    DESCRIPTION
        "Total power factor maximum value since last reset."
    ::= { acpmStatusEntry 35 }
    --1.3.6.1.4.1.3052.14.1.8.1.1.35

acpmsTPFAvgStr OBJECT-TYPE
    SYNTAX DisplayString
    MAX-ACCESS read-only
    STATUS current
    DESCRIPTION
        "Total power factor average value since last reset."
    ::= { acpmStatusEntry 36 }
    --1.3.6.1.4.1.3052.14.1.8.1.1.36

acpmsTPFInEventState OBJECT-TYPE
    SYNTAX DisplayString
    MAX-ACCESS read-only
    STATUS current
    DESCRIPTION
        "Total power factor event state."
    ::= { acpmStatusEntry 37 }
    --1.3.6.1.4.1.3052.14.1.8.1.1.37

acpmsPFPhaseAValueStr OBJECT-TYPE
    SYNTAX DisplayString
    MAX-ACCESS read-only
    STATUS current
    DESCRIPTION
        "Phase A power factor."
    ::= { acpmStatusEntry 38 }
    --1.3.6.1.4.1.3052.14.1.8.1.1.38

acpmsPFPhaseBValueStr OBJECT-TYPE
    SYNTAX DisplayString
    MAX-ACCESS read-only
    STATUS current
    DESCRIPTION
        "Phase B power factor."
    ::= { acpmStatusEntry 39 }
    --1.3.6.1.4.1.3052.14.1.8.1.1.39

acpmsPFPhaseCValueStr OBJECT-TYPE
    SYNTAX DisplayString
    MAX-ACCESS read-only
    STATUS current
    DESCRIPTION
        "Phase C power factor."
    ::= { acpmStatusEntry 40 }
    --1.3.6.1.4.1.3052.14.1.8.1.1.40

acpmsTRcPValueStr OBJECT-TYPE
    SYNTAX DisplayString
    MAX-ACCESS read-only
    STATUS current
    DESCRIPTION
        "Total reactive power, in VAR."
    ::= { acpmStatusEntry 41 }
    --1.3.6.1.4.1.3052.14.1.8.1.1.41

acpmsTRcPMinStr OBJECT-TYPE
    SYNTAX DisplayString
    MAX-ACCESS read-only
    STATUS current
    DESCRIPTION
        "Total reactive power minimum value since last reset, in VAR."
    ::= { acpmStatusEntry 42 }
    --1.3.6.1.4.1.3052.14.1.8.1.1.42

acpmsTRcPMaxStr OBJECT-TYPE
    SYNTAX DisplayString
    MAX-ACCESS read-only
    STATUS current
    DESCRIPTION
        "Total reactive power maximum value since last reset, in VAR."
    ::= { acpmStatusEntry 43 }
    --1.3.6.1.4.1.3052.14.1.8.1.1.43

acpmsTRcPAvgStr OBJECT-TYPE
    SYNTAX DisplayString
    MAX-ACCESS read-only
    STATUS current
    DESCRIPTION
        "Total reactive power average value since last reset, in VAR."
    ::= { acpmStatusEntry 44 }
    --1.3.6.1.4.1.3052.14.1.8.1.1.44

acpmsRcPPhaseAValueStr OBJECT-TYPE
    SYNTAX DisplayString
    MAX-ACCESS read-only
    STATUS current
    DESCRIPTION
        "Phase A reactive power, in VAR."
    ::= { acpmStatusEntry 45 }
    --1.3.6.1.4.1.3052.14.1.8.1.1.45

acpmsRcPPhaseBValueStr OBJECT-TYPE
    SYNTAX DisplayString
    MAX-ACCESS read-only
    STATUS current
    DESCRIPTION
        "Phase B reactive power, in VAR."
    ::= { acpmStatusEntry 46 }
    --1.3.6.1.4.1.3052.14.1.8.1.1.46

acpmsRcPPhaseCValueStr OBJECT-TYPE
    SYNTAX DisplayString
    MAX-ACCESS read-only
    STATUS current
    DESCRIPTION
        "Phase C reactive power, in VAR."
    ::= { acpmStatusEntry 47 }
    --1.3.6.1.4.1.3052.14.1.8.1.1.47

acpmsTAPValueStr OBJECT-TYPE
    SYNTAX DisplayString
    MAX-ACCESS read-only
    STATUS current
    DESCRIPTION
        "Total apparent power, in VA."
    ::= { acpmStatusEntry 48 }
    --1.3.6.1.4.1.3052.14.1.8.1.1.48

acpmsTAPMinStr OBJECT-TYPE
    SYNTAX DisplayString
    MAX-ACCESS read-only
    STATUS current
    DESCRIPTION
        "Total apparent power minimum value since last reset, in VA."
    ::= { acpmStatusEntry 49 }
    --1.3.6.1.4.1.3052.14.1.8.1.1.49

acpmsTAPMaxStr OBJECT-TYPE
    SYNTAX DisplayString
    MAX-ACCESS read-only
    STATUS current
    DESCRIPTION
        "Total apparent power maximum value since last reset, in VA."
    ::= { acpmStatusEntry 50 }
    --1.3.6.1.4.1.3052.14.1.8.1.1.50

acpmsTAPAvgStr OBJECT-TYPE
    SYNTAX DisplayString
    MAX-ACCESS read-only
    STATUS current
    DESCRIPTION
        "Total apparent power average value since last reset, in VA."
    ::= { acpmStatusEntry 51 }
    --1.3.6.1.4.1.3052.14.1.8.1.1.51

acpmsAPPhaseAValueStr OBJECT-TYPE
    SYNTAX DisplayString
    MAX-ACCESS read-only
    STATUS current
    DESCRIPTION
        "Phase A apparent power, in VA."
    ::= { acpmStatusEntry 52 }
    --1.3.6.1.4.1.3052.14.1.8.1.1.52

acpmsAPPhaseBValueStr OBJECT-TYPE
    SYNTAX DisplayString
    MAX-ACCESS read-only
    STATUS current
    DESCRIPTION
        "Phase B apparent power, in VA."
    ::= { acpmStatusEntry 53 }
    --1.3.6.1.4.1.3052.14.1.8.1.1.53

acpmsAPPhaseCValueStr OBJECT-TYPE
    SYNTAX DisplayString
    MAX-ACCESS read-only
    STATUS current
    DESCRIPTION
        "Phase C apparent power, in VA."
    ::= { acpmStatusEntry 54 }
    --1.3.6.1.4.1.3052.14.1.8.1.1.54

acpmsTotalEnergyWh OBJECT-TYPE
    SYNTAX Integer32
    MAX-ACCESS read-only
    STATUS current
    DESCRIPTION
        "Total energy, in Wh."
    ::= { acpmStatusEntry 55 }
    --1.3.6.1.4.1.3052.14.1.8.1.1.55

acpmsTotalEnergyVAR OBJECT-TYPE
    SYNTAX Integer32
    MAX-ACCESS read-only
    STATUS current
    DESCRIPTION
        "Total reactive energy, in VAR."
    ::= { acpmStatusEntry 56 }
    --1.3.6.1.4.1.3052.14.1.8.1.1.56

acpmsTotalEnergyVA OBJECT-TYPE
    SYNTAX Integer32
    MAX-ACCESS read-only
    STATUS current
    DESCRIPTION
        "Total apparent energy, in VA."
    ::= { acpmStatusEntry 57 }
    --1.3.6.1.4.1.3052.14.1.8.1.1.57



--***************************************************************************************
--AISG Status Section  1.9
--***************************************************************************************

aisgsPower OBJECT-TYPE
    SYNTAX DisplayString
    MAX-ACCESS read-only
    STATUS current
    DESCRIPTION
        "AISG power state"
    ::= { aisgStatus 1 }
    --1.3.6.1.4.1.3052.14.1.9.1

aisgsBaseStationID OBJECT-TYPE
    SYNTAX DisplayString
    MAX-ACCESS read-only
    STATUS current
    DESCRIPTION
        "AISG base station ID"
    ::= { aisgStatus 2 }
    --1.3.6.1.4.1.3052.14.1.9.2

aisgsALDTable OBJECT-TYPE
    SYNTAX SEQUENCE OF AISGALD
    MAX-ACCESS not-accessible
    STATUS current
    DESCRIPTION
        "The table of what AISG ALDs (Antenna Line Devices) are attached to the unit."
    ::= { aisgStatus 3 }
    --1.3.6.1.4.1.3052.14.1.9.3

aisgsALDEntry OBJECT-TYPE
    SYNTAX AISGALD
    MAX-ACCESS not-accessible
    STATUS current
    DESCRIPTION
        "Table entry for AISG ALD table"
    INDEX { aisgsALDIndex }
    ::= { aisgsALDTable 1 }
    --1.3.6.1.4.1.3052.14.1.9.3.1

aisgsALDIndex OBJECT-TYPE
    SYNTAX Integer32 (1..18)
    MAX-ACCESS read-only
    STATUS current
    DESCRIPTION
        "This number refers to an ALD; it is the ALD # as shown
        in the web UI and CLI."
    ::= { aisgsALDEntry 1 }
    --1.3.6.1.4.1.3052.14.1.9.3.1.1

aisgsALDSectorID OBJECT-TYPE
    SYNTAX DisplayString
    MAX-ACCESS read-only
    STATUS current
    DESCRIPTION
        "The sector ID of this ALD."
    ::= { aisgsALDEntry 2 }
    --1.3.6.1.4.1.3052.14.1.9.3.1.2

aisgsALDType OBJECT-TYPE
    SYNTAX DisplayString
    MAX-ACCESS read-only
    STATUS current
    DESCRIPTION
        "The type of ALD (SR or MR)."
    ::= { aisgsALDEntry 3 }
    --1.3.6.1.4.1.3052.14.1.9.3.1.3

aisgsALDDescription OBJECT-TYPE
    SYNTAX DisplayString
    MAX-ACCESS read-only
    STATUS current
    DESCRIPTION
        "User-defined description for this ALD."
    ::= { aisgsALDEntry 4 }
    --1.3.6.1.4.1.3052.14.1.9.3.1.4

aisgsALDStatus OBJECT-TYPE
    SYNTAX DisplayString
    MAX-ACCESS read-only
    STATUS current
    DESCRIPTION
        "Status of this ALD (i.e., OFF, OK, UNRSP, ALARM)."
    ::= { aisgsALDEntry 5 }
    --1.3.6.1.4.1.3052.14.1.9.3.1.5

aisgsALDID OBJECT-TYPE
    SYNTAX DisplayString
    MAX-ACCESS read-only
    STATUS current
    DESCRIPTION
        "The ID/serial number of this ALD."
    ::= { aisgsALDEntry 6 }
    --1.3.6.1.4.1.3052.14.1.9.3.1.6

aisgsALDTilt OBJECT-TYPE
    SYNTAX DisplayString
    MAX-ACCESS read-only
    STATUS current
    DESCRIPTION
        "The current tilt value of this ALD."
    ::= { aisgsALDEntry 7 }
    --1.3.6.1.4.1.3052.14.1.9.3.1.7

aisgsALDHwVersion OBJECT-TYPE
    SYNTAX DisplayString
    MAX-ACCESS read-only
    STATUS current
    DESCRIPTION
        "The hardware version of this ALD."
    ::= { aisgsALDEntry 8 }
    --1.3.6.1.4.1.3052.14.1.9.3.1.8

aisgsALDSwVersion OBJECT-TYPE
    SYNTAX DisplayString
    MAX-ACCESS read-only
    STATUS current
    DESCRIPTION
        "The software version of this ALD."
    ::= { aisgsALDEntry 9 }
    --1.3.6.1.4.1.3052.14.1.9.3.1.9

aisgsALDModel OBJECT-TYPE
    SYNTAX DisplayString
    MAX-ACCESS read-only
    STATUS current
    DESCRIPTION
        "The model number of this ALD."
    ::= { aisgsALDEntry 10 }
    --1.3.6.1.4.1.3052.14.1.9.3.1.10

aisgsALDAntennaModel OBJECT-TYPE
    SYNTAX DisplayString
    MAX-ACCESS read-only
    STATUS current
    DESCRIPTION
        "The model number of the antenna associated with this ALD.
        Note that not all ALDs have this."
    ::= { aisgsALDEntry 11 }
    --1.3.6.1.4.1.3052.14.1.9.3.1.11

aisgsALDMinTilt OBJECT-TYPE
    SYNTAX DisplayString
    MAX-ACCESS read-only
    STATUS current
    DESCRIPTION
        "The minimum tilt value of this ALD, as determined by the ALD's
        loaded configuration file.  A nonsensical value here indicates
        that the ALD is not configured."
    ::= { aisgsALDEntry 12 }
    --1.3.6.1.4.1.3052.14.1.9.3.1.12

aisgsALDMaxTilt OBJECT-TYPE
    SYNTAX DisplayString
    MAX-ACCESS read-only
    STATUS current
    DESCRIPTION
        "The maximum tilt value of this ALD, as determined by the ALD's
        loaded configuration file.  A nonsensical value here indicates
        that the ALD is not configured."
    ::= { aisgsALDEntry 13 }
    --1.3.6.1.4.1.3052.14.1.9.3.1.13

aisgsALDAISGVersion OBJECT-TYPE
    SYNTAX DisplayString
    MAX-ACCESS read-only
    STATUS current
    DESCRIPTION
        "The AISG version of this ALD.  E.g., 1.1, 2.0."
    ::= { aisgsALDEntry 14 }
    --1.3.6.1.4.1.3052.14.1.9.3.1.14

aisgsFileTable OBJECT-TYPE
    SYNTAX SEQUENCE OF AISGFile
    MAX-ACCESS not-accessible
    STATUS current
    DESCRIPTION
        "The table of what AISG files are currently loaded on the unit."
    ::= { aisgStatus 4 }
    --1.3.6.1.4.1.3052.14.1.9.4

aisgsFileEntry OBJECT-TYPE
    SYNTAX AISGFile
    MAX-ACCESS not-accessible
    STATUS current
    DESCRIPTION
        "Table entry for AISG File table"
    INDEX { aisgsFileIndex }
    ::= { aisgsFileTable 1 }
    --1.3.6.1.4.1.3052.14.1.9.4.1

aisgsFileIndex OBJECT-TYPE
    SYNTAX Integer32 (1..10)
    MAX-ACCESS read-only
    STATUS current
    DESCRIPTION
        "Index for AISG File table.  This defines the local store (local to
        the unit) of files residing on the unit that are available to be
        loaded onto ALDs."
    ::= { aisgsFileEntry 1 }
    --1.3.6.1.4.1.3052.14.1.9.4.1.1

aisgsFileName OBJECT-TYPE
    SYNTAX DisplayString
    MAX-ACCESS read-only
    STATUS current
    DESCRIPTION
        "Name of AISG file (specified by user)."
    ::= { aisgsFileEntry 2 }
    --1.3.6.1.4.1.3052.14.1.9.4.1.2

aisgsFileType OBJECT-TYPE
    SYNTAX DisplayString
    MAX-ACCESS read-only
    STATUS current
    DESCRIPTION
        "Type of AISG file (e.g., SOFTWARE or CONFIG)"
    ::= { aisgsFileEntry 3 }
    --1.3.6.1.4.1.3052.14.1.9.4.1.3

aisgsFileVersion OBJECT-TYPE
    SYNTAX DisplayString
    MAX-ACCESS read-only
    STATUS current
    DESCRIPTION
        "Version of AISG file as reported by the ALD running this software.
        This is for SOFTWARE files, so that the unit can know when (during
        auto config) it does not need to load software onto an ALD (i.e.,
        if the ALD already has this software version loaded)."
    ::= { aisgsFileEntry 4 }
    --1.3.6.1.4.1.3052.14.1.9.4.1.4

aisgsAutoTable OBJECT-TYPE
    SYNTAX SEQUENCE OF AISGAuto
    MAX-ACCESS not-accessible
    STATUS current
    DESCRIPTION
        "The table of AISG automatic configuration slots on the unit.  These
        slots describe what the unit should do automatically (load software,
        load config, calibrate, tilt) upon finding the ALD during a scan, on
        the specific basis of any ALD matching the vendor and ALD model defined
        in a row of this table."
    ::= { aisgStatus 5 }
    --1.3.6.1.4.1.3052.14.1.9.5

aisgsAutoEntry OBJECT-TYPE
    SYNTAX AISGAuto
    MAX-ACCESS not-accessible
    STATUS current
    DESCRIPTION
        "Table entry for AISG Auto table"
    INDEX { aisgsAutoIndex }
    ::= { aisgsAutoTable 1 }
    --1.3.6.1.4.1.3052.14.1.9.5.1

aisgsAutoIndex OBJECT-TYPE
    SYNTAX Integer32 (1..10)
    MAX-ACCESS read-only
    STATUS current
    DESCRIPTION
        "Index for AISG Auto table."
    ::= { aisgsAutoEntry 1 }
    --1.3.6.1.4.1.3052.14.1.9.5.1.1

aisgsAutoVendor OBJECT-TYPE
    SYNTAX DisplayString
    MAX-ACCESS read-only
    STATUS current
    DESCRIPTION
        "The two-letter vendor code for this automatic configuration table row."
    ::= { aisgsAutoEntry 2 }
    --1.3.6.1.4.1.3052.14.1.9.5.1.2

aisgsAutoALDModel OBJECT-TYPE
    SYNTAX DisplayString
    MAX-ACCESS read-only
    STATUS current
    DESCRIPTION
        "The ALD model number this automatic configuration table row."
    ::= { aisgsAutoEntry 3 }
    --1.3.6.1.4.1.3052.14.1.9.5.1.3

aisgsAutoSoftware OBJECT-TYPE
    SYNTAX DisplayString
    MAX-ACCESS read-only
    STATUS current
    DESCRIPTION
        "The software file name of this automatic configuration table row."
    ::= { aisgsAutoEntry 4 }
    --1.3.6.1.4.1.3052.14.1.9.5.1.4

aisgsAutoConfig OBJECT-TYPE
    SYNTAX DisplayString
    MAX-ACCESS read-only
    STATUS current
    DESCRIPTION
        "The configuration file name of this automatic configuration table row."
    ::= { aisgsAutoEntry 5 }
    --1.3.6.1.4.1.3052.14.1.9.5.1.5

aisgsAutoTilt OBJECT-TYPE
    SYNTAX DisplayString
    MAX-ACCESS read-only
    STATUS current
    DESCRIPTION
        "The tilt value for this automatic configuration table row.  Any ALD not
        already auto-configured by the unit will be tilted to this value, if its
        vendor and model number match the vendor and ALD model number of this
        table row."
    ::= { aisgsAutoEntry 6 }
    --1.3.6.1.4.1.3052.14.1.9.5.1.6


aisgsAAATable OBJECT-TYPE
    SYNTAX SEQUENCE OF AISGAAA
    MAX-ACCESS not-accessible
    STATUS current
    DESCRIPTION
        "The table of AISG antenna-ALD associations slots on the unit.  These
        slots describe what antenna serial number and what sector ID the unit
        should assign to an ALD that is undergoing automatic configuration."
    ::= { aisgStatus 6 }
    --1.3.6.1.4.1.3052.14.1.9.6

aisgsAAAEntry OBJECT-TYPE
    SYNTAX AISGAAA
    MAX-ACCESS not-accessible
    STATUS current
    DESCRIPTION
        "Table entry for AISG AAA table"
    INDEX { aisgsAAAIndex }
    ::= { aisgsAAATable 1 }
    --1.3.6.1.4.1.3052.14.1.9.6.1

aisgsAAAIndex OBJECT-TYPE
    SYNTAX Integer32 (1..10)
    MAX-ACCESS read-only
    STATUS current
    DESCRIPTION
        "Index for AISG AAA table."
    ::= { aisgsAAAEntry 1 }
    --1.3.6.1.4.1.3052.14.1.9.6.1.1

aisgsAAAALDID OBJECT-TYPE
    SYNTAX DisplayString
    MAX-ACCESS read-only
    STATUS current
    DESCRIPTION
        "The ID/serial number of the ALD for this AAA table row."
    ::= { aisgsAAAEntry 2 }
    --1.3.6.1.4.1.3052.14.1.9.6.1.2

aisgsAAAAntennaSN OBJECT-TYPE
    SYNTAX DisplayString
    MAX-ACCESS read-only
    STATUS current
    DESCRIPTION
        "The user-specified antenna serial number for this AAA table row.
        An ALD that the unit finds with this ID/serial number will be
        assigned this antenna serial number.  This happens only during
        auto-configuration of the ALD, which happens only once for an ALD."
    ::= { aisgsAAAEntry 3 }
    --1.3.6.1.4.1.3052.14.1.9.6.1.3

aisgsAAASectorID OBJECT-TYPE
    SYNTAX DisplayString
    MAX-ACCESS read-only
    STATUS current
    DESCRIPTION
        "The user-specified sector ID for this AAA table row.
        An ALD that the unit finds with this ID/serial number will be
        assigned this sector ID.  This happens only during auto-configuration
        of the ALD, which happens only once for an ALD."
    ::= { aisgsAAAEntry 4 }
    --1.3.6.1.4.1.3052.14.1.9.6.1.4


--***************************************************************************************
--EventSensor Basics Section    2.1
--***************************************************************************************

esNumberEventSensors OBJECT-TYPE
    SYNTAX Integer32
    MAX-ACCESS read-only
    STATUS current
    DESCRIPTION
        "The number of EventSensors recognized by the unit,
        including the internal EventSensor.
        Range: 1-17"
    ::= { eventSensorBasics 1 }
    --1.3.6.1.4.1.3052.14.2.1.1

esTable OBJECT-TYPE
    SYNTAX SEQUENCE OF ESExist
    MAX-ACCESS not-accessible
    STATUS current
    DESCRIPTION
        "The table of what EventSensors are attached to the unit,
        including the internal EventSensor"
    ::= { eventSensorBasics 2 }
    --1.3.6.1.4.1.3052.14.2.1.2

esEntry OBJECT-TYPE
    SYNTAX ESExist
    MAX-ACCESS not-accessible
    STATUS current
    DESCRIPTION
        "Table entry for EventSensor table"
    INDEX { esIndex }
    ::= { esTable 1 }
    --1.3.6.1.4.1.3052.14.2.1.2.1

esIndex OBJECT-TYPE
    SYNTAX Integer32 (1..200)
    MAX-ACCESS read-only
    STATUS current
    DESCRIPTION
        "This number refers to an EventSensor; it has the
        same meaning as the esIndexES object (see above),
        except that this object is used only within the
        esTable branch.

        This object's allowable values are 1 through 16,
        and 200.  200 always refers to the EventSensor
        inside the unit.  1 through 16 refer to additional
        attached EventSensors.

        The number corresponding to an EventSensor is
        determined by the user at the initial configuration
        time.  If there is an internal sensor in the unit,
        it will always be the first item in the Sensor
        Events setup menu.

        For example, if a new EventSensor is configured as
        the 2nd entry AFTER the internal EventSensor (if
        one exists) in the Sensor Events Setup Menu, then
        that EventSensor will be known from then on as
        EventSensor 2.  All point indeces with esIndex=2
        will now refer to that particular EventSensor.
        "
    ::= { esEntry 1 }
    --1.3.6.1.4.1.3052.14.2.1.2.1.1

esName  OBJECT-TYPE
    SYNTAX DisplayString
    MAX-ACCESS read-only
    STATUS current
    DESCRIPTION
        "The name of the EventSensor"
    ::= { esEntry 2 }
    --1.3.6.1.4.1.3052.14.2.1.2.1.2

esID    OBJECT-TYPE
    SYNTAX DisplayString
    MAX-ACCESS read-only
    STATUS current
    DESCRIPTION
        "The factory-assigned ID of the EventSensor"
    ::= { esEntry 3 }
    --1.3.6.1.4.1.3052.14.2.1.2.1.3

esNumberTempSensors OBJECT-TYPE
    SYNTAX Integer32
    MAX-ACCESS read-only
    STATUS current
    DESCRIPTION
        "The number of temperature sensors on the EventSensor"
    ::= { esEntry 4 }
    --1.3.6.1.4.1.3052.14.2.1.2.1.4

esTempReportingMode OBJECT-TYPE
    SYNTAX DisplayString
    MAX-ACCESS read-only
    STATUS current
    DESCRIPTION
        "Description of how temperature values should
        be interpreted."
    ::= { esEntry 5 }
    --1.3.6.1.4.1.3052.14.2.1.2.1.5

esNumberCCs OBJECT-TYPE
    SYNTAX Integer32
    MAX-ACCESS read-only
    STATUS current
    DESCRIPTION
        "The number of contact closures on the EventSensor."
    ::= { esEntry 6 }
    --1.3.6.1.4.1.3052.14.2.1.2.1.6

esCCReportingMode OBJECT-TYPE
    SYNTAX DisplayString
    MAX-ACCESS read-only
    STATUS current
    DESCRIPTION
        "Description of how CC values should be interpreted."
    ::= { esEntry 7 }
    --1.3.6.1.4.1.3052.14.2.1.2.1.7

esNumberHumidSensors OBJECT-TYPE
    SYNTAX Integer32
    MAX-ACCESS read-only
    STATUS current
    DESCRIPTION
        "The number of humidity sensors on the EventSensor."
    ::= { esEntry 8 }
    --1.3.6.1.4.1.3052.14.2.1.2.1.8

esHumidReportingMode OBJECT-TYPE
    SYNTAX DisplayString
    MAX-ACCESS read-only
    STATUS current
    DESCRIPTION
        "Description of how humidity sensor values should be
        interpreted."
    ::= { esEntry 9 }
    --1.3.6.1.4.1.3052.14.2.1.2.1.9

esNumberNoiseSensors OBJECT-TYPE
    SYNTAX Integer32
    MAX-ACCESS read-only
    STATUS current
    DESCRIPTION
        "The number of noise sensors on the EventSensor."
    ::= { esEntry 10 }
    --1.3.6.1.4.1.3052.14.2.1.2.1.10

esNoiseReportingMode OBJECT-TYPE
    SYNTAX DisplayString
    MAX-ACCESS read-only
    STATUS current
    DESCRIPTION
        "Description of how noise sensor values should be
        interpreted."
    ::= { esEntry 11 }
    --1.3.6.1.4.1.3052.14.2.1.2.1.11

esNumberAirflowSensors OBJECT-TYPE
    SYNTAX Integer32
    MAX-ACCESS read-only
    STATUS current
    DESCRIPTION
        "The number of airflow sensors on the EventSensor."
    ::= { esEntry 12 }
    --1.3.6.1.4.1.3052.14.2.1.2.1.12

esAirflowReportingMode OBJECT-TYPE
    SYNTAX DisplayString
    MAX-ACCESS read-only
    STATUS current
    DESCRIPTION
        "Description of how airflow sensor values should be
        interpreted."
    ::= { esEntry 13 }
    --1.3.6.1.4.1.3052.14.2.1.2.1.13

esNumberAnalog OBJECT-TYPE
    SYNTAX Integer32
    MAX-ACCESS read-only
    STATUS current
    DESCRIPTION
        "The number of analog inputs on the EventSensor."
    ::= { esEntry 14 }
    --1.3.6.1.4.1.3052.14.2.1.2.1.14

esAnalogReportingMode OBJECT-TYPE
    SYNTAX DisplayString
    MAX-ACCESS read-only
    STATUS current
    DESCRIPTION
        "Description of how analog input values should be
        interpreted."
    ::= { esEntry 15 }
    --1.3.6.1.4.1.3052.14.2.1.2.1.15

esNumberOutputs OBJECT-TYPE
    SYNTAX Integer32
    MAX-ACCESS read-only
    STATUS current
    DESCRIPTION
        "The number of outputs (relay or power) on the EventSensor"
    ::= { esEntry 16 }
    --1.3.6.1.4.1.3052.14.2.1.2.1.16

esOutputReportingMode OBJECT-TYPE
    SYNTAX DisplayString
    MAX-ACCESS read-only
    STATUS current
    DESCRIPTION
        "Description of how output values should be interpreted."
    ::= { esEntry 17 }
    --1.3.6.1.4.1.3052.14.2.1.2.1.17

esTempCombinedStatus OBJECT-TYPE
    SYNTAX DisplayString
    MAX-ACCESS read-only
    STATUS current
    DESCRIPTION
        "Combined status string intended to be parsed by NMS:
        name`value`scale`eventState`eventColorCode"
    ::= { esEntry 18 }
    --1.3.6.1.4.1.3052.14.2.1.2.1.18

esCCCombinedStatusBlock1 OBJECT-TYPE
    SYNTAX DisplayString
    MAX-ACCESS read-only
    STATUS current
    DESCRIPTION
        "Combined status string intended to be parsed by NMS:
        numInBlock~name1`value1`eventColorCode1`alias1~name2`value2`eventColorCode2`alias2~...name8`value8`eventColorCode8`alias8"
    ::= { esEntry 19 }
    --1.3.6.1.4.1.3052.14.2.1.2.1.19

esCCCombinedStatusBlock2 OBJECT-TYPE
    SYNTAX DisplayString
    MAX-ACCESS read-only
    STATUS current
    DESCRIPTION
        "Combined status string intended to be parsed by NMS:
        numInBlock~name9`value9`eventColorCode9`alias9~name10`value10`eventColorCode10`alias10~...name16`value16`eventColorCode16`alias16"
    ::= { esEntry 20 }
    --1.3.6.1.4.1.3052.14.2.1.2.1.20

esCCCombinedStatusBlock3 OBJECT-TYPE
    SYNTAX DisplayString
    MAX-ACCESS read-only
    STATUS current
    DESCRIPTION
        "Combined status string intended to be parsed by NMS:
        numInBlock~name17`value17`eventColorCode17`alias17~name18`value18`eventColorCode18`alias18~...name24`value24`eventColorCode24`alias24"
    ::= { esEntry 21 }
    --1.3.6.1.4.1.3052.14.2.1.2.1.21

esCCCombinedStatusBlock4 OBJECT-TYPE
    SYNTAX DisplayString
    MAX-ACCESS read-only
    STATUS current
    DESCRIPTION
        "Combined status string intended to be parsed by NMS:
        numInBlock~name25`value25`eventColorCode25`alias25~name26`value26`eventColorCode26`alias26~...name32`value32`eventColorCode32`alias32"
    ::= { esEntry 22 }
    --1.3.6.1.4.1.3052.14.2.1.2.1.22

esCCCombinedStatusBlock5 OBJECT-TYPE
    SYNTAX DisplayString
    MAX-ACCESS read-only
    STATUS current
    DESCRIPTION
        "Combined status string intended to be parsed by NMS:
        numInBlock~name33`value33`eventColorCode33`alias33~name34`value34`eventColorCode34`alias35~...name40`value40`eventColorCode40`alias40"
    ::= { esEntry 23 }
    --1.3.6.1.4.1.3052.14.2.1.2.1.23

esCCCombinedStatusBlock6 OBJECT-TYPE
    SYNTAX DisplayString
    MAX-ACCESS read-only
    STATUS current
    DESCRIPTION
        "Combined status string intended to be parsed by NMS:
        numInBlock~name41`value41`eventColorCode41`alias41~name42`value42`eventColorCode42`alias43~...name48`value48`eventColorCode48`alias48"
    ::= { esEntry 24 }
    --1.3.6.1.4.1.3052.14.2.1.2.1.24

esCCCombinedStatusBlock7 OBJECT-TYPE
    SYNTAX DisplayString
    MAX-ACCESS read-only
    STATUS current
    DESCRIPTION
        "Combined status string intended to be parsed by NMS:
        numInBlock~name49`value49`eventColorCode49`alias49~name50`value50`eventColorCode50`alias50~...name56`value56`eventColorCode56`alias56"
    ::= { esEntry 25 }
    --1.3.6.1.4.1.3052.14.2.1.2.1.25

esCCCombinedStatusBlock8 OBJECT-TYPE
    SYNTAX DisplayString
    MAX-ACCESS read-only
    STATUS current
    DESCRIPTION
        "Combined status string intended to be parsed by NMS:
        numInBlock~name57`value57`eventColorCode57`alias57~name57`value57`eventColorCode564`alias57~...name64`value64`eventColorCode64`alias64"
    ::= { esEntry 26 }
    --1.3.6.1.4.1.3052.14.2.1.2.1.26

esHumidCombinedStatus OBJECT-TYPE
    SYNTAX DisplayString
    MAX-ACCESS read-only
    STATUS current
    DESCRIPTION
        "Combined status string intended to be parsed by NMS:
        name`value`eventState`eventColorCode"
    ::= { esEntry 27 }
    --1.3.6.1.4.1.3052.14.2.1.2.1.27

esAnalogCombinedStatusBlock1 OBJECT-TYPE
    SYNTAX DisplayString
    MAX-ACCESS read-only
    STATUS current
    DESCRIPTION
        "Combined status string intended to be parsed by NMS:
        numInBlock~name1`value1`units1`eventState`eventColorCode1~name2`value2`units2`eventState`eventColorCode2~..."
    ::= { esEntry 28 }
    --1.3.6.1.4.1.3052.14.2.1.2.1.28

esAnalogCombinedStatusBlock2 OBJECT-TYPE
    SYNTAX DisplayString
    MAX-ACCESS read-only
    STATUS current
    DESCRIPTION
        "Combined status string intended to be parsed by NMS:
        numInBlock~name9`value9`units9`eventState9`eventColorCode9~..."
    ::= { esEntry 29 }
    --1.3.6.1.4.1.3052.14.2.1.2.1.29

esAnalogCombinedStatusBlock3 OBJECT-TYPE
    SYNTAX DisplayString
    MAX-ACCESS read-only
    STATUS current
    DESCRIPTION
        "Combined status string intended to be parsed by NMS:
        numInBlock~namex`valuex`unitsx`eventStatex`eventColorCodex~..."
    ::= { esEntry 30 }
    --1.3.6.1.4.1.3052.14.2.1.2.1.31

esAnalogCombinedStatusBlock4 OBJECT-TYPE
    SYNTAX DisplayString
    MAX-ACCESS read-only
    STATUS current
    DESCRIPTION
        "Combined status string intended to be parsed by NMS:
        numInBlock~namex`valuex`unitsx`eventStatex`eventColorCodex~..."
    ::= { esEntry 31 }
    --1.3.6.1.4.1.3052.14.2.1.2.1.31

esAnalogCombinedStatusBlock5 OBJECT-TYPE
    SYNTAX DisplayString
    MAX-ACCESS read-only
    STATUS current
    DESCRIPTION
        "Combined status string intended to be parsed by NMS:
        numInBlock~namex`valuex`unitsx`eventStatex`eventColorCodex~..."
    ::= { esEntry 32 }
    --1.3.6.1.4.1.3052.14.2.1.2.1.32

esAnalogCombinedStatusBlock6 OBJECT-TYPE
    SYNTAX DisplayString
    MAX-ACCESS read-only
    STATUS current
    DESCRIPTION
        "Combined status string intended to be parsed by NMS:
        numInBlock~namex`valuex`unitsx`eventStatex`eventColorCodex~..."
    ::= { esEntry 33 }
    --1.3.6.1.4.1.3052.14.2.1.2.1.33

esOutputCombinedStatusBlock1 OBJECT-TYPE
    SYNTAX DisplayString
    MAX-ACCESS read-only
    STATUS current
    DESCRIPTION
        "Combined status string intended to be parsed by NMS:
        numInBlock~namex`valuex`unitsx`eventStatex`eventColorCodex~..."
    ::= { esEntry 34 }
    --1.3.6.1.4.1.3052.14.2.1.2.1.34

esOutputCombinedStatusBlock2 OBJECT-TYPE
    SYNTAX DisplayString
    MAX-ACCESS read-only
    STATUS current
    DESCRIPTION
        "Combined status string intended to be parsed by NMS:
        numInBlock`namex`valuex`aliasx~namey`valuey`aliasy~...namez`valuez`aliasz"
    ::= { esEntry 35 }
    --1.3.6.1.4.1.3052.14.2.1.2.1.35


esNewSensors OBJECT-TYPE
    SYNTAX DisplayString
    MAX-ACCESS read-only
    STATUS current
    DESCRIPTION
        "String representing the number of new (attached but unconfigured) EventSensors"
    ::= { eventSensorBasics 3 }
    --1.3.6.1.4.1.3052.14.2.1.3


--***************************************************************************************
--EventSensor Point Config Section   2.2
--***************************************************************************************



esPointConfigTempTable OBJECT-TYPE
    SYNTAX SEQUENCE OF ESPointConfigTemp
    MAX-ACCESS not-accessible
    STATUS current
    DESCRIPTION
        "This table organizes 3 basic attributes of temperature
        sensor points.  A point is a particular sensor on an
        EventSensor.  The 3 point attributes organizes in this table
        are:
        1. the configuration item (e.g., enable, name, etc.)
        2. the eventsensor on which this point resides
        3. the point number (always 1 for temp sensors)

        Points are referenced by a point config index.  The point
        config index is a string of 2 numbers separated by periods.
        It contains all the information necessary for getting a
        piece of data off an event sensor within the context of this
        emperature point config table ; namely, which EventSensor,
        and which sensor (a.k.a. point) (always 1 for temperature
        sensors).
        "
    ::= { eventSensorPointConfig 1 }
    --1.3.6.1.4.1.3052.14.2.2.1

esPointConfigTempEntry OBJECT-TYPE
    SYNTAX ESPointConfigTemp
    MAX-ACCESS not-accessible
    STATUS current
    DESCRIPTION
        "Entry for EventSensor point config temperature table"
    INDEX { espcTempIndexES, espcTempIndexPoint }
    ::= { esPointConfigTempTable 1 }
    --1.3.6.1.4.1.3052.14.2.2.1.1

espcTempIndexES OBJECT-TYPE
    SYNTAX Integer32 (1..200)
    MAX-ACCESS read-only
    STATUS current
    DESCRIPTION
        "The part of the point index that refers to an
        EventSensor.

        The point config index is a string of 2 numbers separated
        by a period.  It contains all the information
        necessary for getting a piece of data off an event
        sensor within the the context of the eventsensor point
        config temperature table; namely, which EventSensor,
        and which sensor (a.k.a. point).

        This object's allowable values are 1 through 16,
        and 200.  200 always refers to the EventSensor
        inside the unit.  1 through 16 refer to additional
        attached EventSensors.

        The number corresponding to an EventSensor is
        determined by the user at the initial configuration
        time.  If there is an internal sensor in the unit,
        it will always be the first item in the Sensor
        Events setup menu.

        For example, if a new EventSensor is configured as
        the 2nd entry AFTER the internal EventSensor (if
        one exists) in the Sensor Events Setup Menu, then
        that EventSensor will be known from then on as
        EventSensor 2.  All point indeces with esIndexES=2
        will now refer to that particular EventSensor.
        "
    ::= { esPointConfigTempEntry 1 }
    --1.3.6.1.4.1.3052.14.2.2.1.1.1

espcTempIndexPoint OBJECT-TYPE
    SYNTAX Integer32 (1..64)
    MAX-ACCESS read-only
    STATUS current
    DESCRIPTION
        "The part of the point index that delineates which
        sensor on the EventSensor.

        So this combined with espcTempIndexES (which EventSensor)
        uniquely defines each point attached to a unit within the
        context of temperature point configuration."
    ::= { esPointConfigTempEntry 2 }
    --1.3.6.1.4.1.3052.14.2.2.1.1.2

espcTempEnable OBJECT-TYPE
    SYNTAX DisplayString
    MAX-ACCESS read-write
    STATUS current
    DESCRIPTION
        "ON/OFF enable this temperature sensor"
    ::= { esPointConfigTempEntry 3 }
    --1.3.6.1.4.1.3052.14.2.2.1.1.3

espcTempScale OBJECT-TYPE
    SYNTAX DisplayString
    MAX-ACCESS read-write
    STATUS current
    DESCRIPTION
        "Scale (C/F) for this temperature sensor"
    ::= { esPointConfigTempEntry 4 }
    --1.3.6.1.4.1.3052.14.2.2.1.1.4

espcTempDeadband OBJECT-TYPE
    SYNTAX DisplayString
    MAX-ACCESS read-write
    STATUS current
    DESCRIPTION
        "Deadband for this temperature sensor (in floating-point format)"
    ::= { esPointConfigTempEntry 5 }
    --1.3.6.1.4.1.3052.14.2.2.1.1.5

espcTempVHighTemp OBJECT-TYPE
    SYNTAX DisplayString
    MAX-ACCESS read-write
    STATUS current
    DESCRIPTION
        "Very high temperature event threshold for this temperature
        sensor (in floating-point format)"
    ::= { esPointConfigTempEntry 6 }
    --1.3.6.1.4.1.3052.14.2.2.1.1.6

espcTempVHighActions OBJECT-TYPE
    SYNTAX DisplayString
    MAX-ACCESS read-write
    STATUS current
    DESCRIPTION
        "Very high temperature event actions for this temperature
        sensor"
    ::= { esPointConfigTempEntry 7 }
    --1.3.6.1.4.1.3052.14.2.2.1.1.7

espcTempVHighTrapnum OBJECT-TYPE
    SYNTAX Integer32
    MAX-ACCESS read-write
    STATUS current
    DESCRIPTION
        "Very high temperature event trap number for this
        temperature sensor"
    ::= { esPointConfigTempEntry 8 }
    --1.3.6.1.4.1.3052.14.2.2.1.1.8

espcTempVHighClass OBJECT-TYPE
    SYNTAX DisplayString
    MAX-ACCESS read-write
    STATUS current
    DESCRIPTION
        "Very high temperature event class for this temperature
        sensor"
    ::= { esPointConfigTempEntry 9 }
    --1.3.6.1.4.1.3052.14.2.2.1.1.9

espcTempHighTemp OBJECT-TYPE
    SYNTAX DisplayString
    MAX-ACCESS read-write
    STATUS current
    DESCRIPTION
        "High temperature event threshold for this temperature
        sensor (in floating-point format)"
    ::= { esPointConfigTempEntry 10 }
    --1.3.6.1.4.1.3052.14.2.2.1.1.10

espcTempHighActions OBJECT-TYPE
    SYNTAX DisplayString
    MAX-ACCESS read-write
    STATUS current
    DESCRIPTION
        "High temperature event actions for this temperature sensor"
    ::= { esPointConfigTempEntry 11 }
    --1.3.6.1.4.1.3052.14.2.2.1.1.11

espcTempHighTrapnum OBJECT-TYPE
    SYNTAX Integer32
    MAX-ACCESS read-write
    STATUS current
    DESCRIPTION
        "High temperature event trap number for this temperature
        sensor"
    ::= { esPointConfigTempEntry 12 }
    --1.3.6.1.4.1.3052.14.2.2.1.1.12

espcTempHighClass OBJECT-TYPE
    SYNTAX DisplayString
    MAX-ACCESS read-write
    STATUS current
    DESCRIPTION
        "High temperature event class for this temperature sensor"
    ::= { esPointConfigTempEntry 13 }
    --1.3.6.1.4.1.3052.14.2.2.1.1.13

espcTempNormalActions OBJECT-TYPE
    SYNTAX DisplayString
    MAX-ACCESS read-write
    STATUS current
    DESCRIPTION
        "Return-to-normal event actions for this temperature sensor"
    ::= { esPointConfigTempEntry 14 }
    --1.3.6.1.4.1.3052.14.2.2.1.1.14

espcTempNormalTrapnum OBJECT-TYPE
    SYNTAX Integer32
    MAX-ACCESS read-write
    STATUS current
    DESCRIPTION
        "Return-to-normal event trap number for this temperature
        sensor"
    ::= { esPointConfigTempEntry 15 }
    --1.3.6.1.4.1.3052.14.2.2.1.1.15

espcTempNormalClass OBJECT-TYPE
    SYNTAX DisplayString
    MAX-ACCESS read-write
    STATUS current
    DESCRIPTION
        "Return-to-normal event class for this temperature sensor"
    ::= { esPointConfigTempEntry 16 }
    --1.3.6.1.4.1.3052.14.2.2.1.1.16

espcTempLowTemp OBJECT-TYPE
    SYNTAX DisplayString
    MAX-ACCESS read-write
    STATUS current
    DESCRIPTION
        "Low temperature event threshold for this temperature sensor
        (in floating-point format)"
    ::= { esPointConfigTempEntry 17 }
    --1.3.6.1.4.1.3052.14.2.2.1.1.17

espcTempLowActions OBJECT-TYPE
    SYNTAX DisplayString
    MAX-ACCESS read-write
    STATUS current
    DESCRIPTION
        "Low temperature event actions for this temperature sensor"
    ::= { esPointConfigTempEntry 18 }
    --1.3.6.1.4.1.3052.14.2.2.1.1.18

espcTempLowTrapnum OBJECT-TYPE
    SYNTAX Integer32
    MAX-ACCESS read-write
    STATUS current
    DESCRIPTION
        "Low temperature event trap number for this temperature
        sensor"
    ::= { esPointConfigTempEntry 19 }
    --1.3.6.1.4.1.3052.14.2.2.1.1.19

espcTempLowClass OBJECT-TYPE
    SYNTAX DisplayString
    MAX-ACCESS read-write
    STATUS current
    DESCRIPTION
        "Low temperature event class for this temperature sensor"
    ::= { esPointConfigTempEntry 20 }
    --1.3.6.1.4.1.3052.14.2.2.1.1.20

espcTempVLowTemp OBJECT-TYPE
    SYNTAX DisplayString
    MAX-ACCESS read-write
    STATUS current
    DESCRIPTION
        "Very Low temperature event threshold for this temperature
        sensor (in floating-point format)"
    ::= { esPointConfigTempEntry 21 }
    --1.3.6.1.4.1.3052.14.2.2.1.1.21

espcTempVLowActions OBJECT-TYPE
    SYNTAX DisplayString
    MAX-ACCESS read-write
    STATUS current
    DESCRIPTION
        "Very Low temperature event actions for this temperature
        sensor"
    ::= { esPointConfigTempEntry 22 }
    --1.3.6.1.4.1.3052.14.2.2.1.1.22

espcTempVLowTrapnum OBJECT-TYPE
    SYNTAX Integer32
    MAX-ACCESS read-write
    STATUS current
    DESCRIPTION
        "Very Low temperature event trap number for this temperature
        sensor"
    ::= { esPointConfigTempEntry 23 }
    --1.3.6.1.4.1.3052.14.2.2.1.1.23

espcTempVLowClass OBJECT-TYPE
    SYNTAX DisplayString
    MAX-ACCESS read-write
    STATUS current
    DESCRIPTION
        "Very Low temperature event class for this temperature sensor"
    ::= { esPointConfigTempEntry 24 }
    --1.3.6.1.4.1.3052.14.2.2.1.1.24





esPointConfigCCTable OBJECT-TYPE
    SYNTAX SEQUENCE OF ESPointConfigCC
    MAX-ACCESS not-accessible
    STATUS current
    DESCRIPTION
        "This table organizes 3 basic attributes of contact closure
        points.  A point is a particular sensor on an EventSensor.
        The 3 point attributes organizes in this table are:
        1. the configuration item (e.g., enable, name, etc.)
        2. the eventsensor on which this point resides
        3. the point number

        Points are referenced by a point config index.  The point
        config index is a string of 2 numbers separated by a period.
        It contains all the information necessary for getting a piece
        of data off an event sensor within the context of this
        contact closure point config table ; namely, which
        EventSensor and which sensor.
        "
    ::= { eventSensorPointConfig 2 }
    --1.3.6.1.4.1.3052.14.2.2.2

esPointConfigCCEntry OBJECT-TYPE
    SYNTAX ESPointConfigCC
    MAX-ACCESS not-accessible
    STATUS current
    DESCRIPTION
        "Entry for EventSensor point config contact closure table"
    INDEX { espcCCIndexES, espcCCIndexPoint }
    ::= { esPointConfigCCTable 1 }
    --1.3.6.1.4.1.3052.14.2.2.2.1

espcCCIndexES OBJECT-TYPE
    SYNTAX Integer32 (1..200)
    MAX-ACCESS read-only
    STATUS current
    DESCRIPTION
        "The part of the point index that refers to an
        EventSensor.

        The point config index is a string of 2 numbers separated
        by a period.  It contains all the information
        necessary for getting a piece of data off an event
        sensor within the the context of the eventsensor point
        config contact closure table; namely, which EventSensor
        and which sensor (a.k.a. point).

        This object's allowable values are 1 through 16,
        and 200.  200 always refers to the EventSensor
        inside the unit.  1 through 16 refer to additional
        attached EventSensors.
        "
    ::= { esPointConfigCCEntry 1 }
    --1.3.6.1.4.1.3052.14.2.2.2.1.1

espcCCIndexPoint OBJECT-TYPE
    SYNTAX Integer32 (1..64)
    MAX-ACCESS read-only
    STATUS current
    DESCRIPTION
        "The part of the point index that delineates which
        sensor on the EventSensor.

        So this combined with espcCCIndexES (which EventSensor)
        uniquely defines each point attached to a unit within the
        context of contact closure point configuration."
    ::= { esPointConfigCCEntry 2 }
    --1.3.6.1.4.1.3052.14.2.2.2.1.2

espcCCEnable OBJECT-TYPE
    SYNTAX DisplayString
    MAX-ACCESS read-write
    STATUS current
    DESCRIPTION
        "ON/OFF enable for this contact closure"
    ::= { esPointConfigCCEntry 3 }
    --1.3.6.1.4.1.3052.14.2.2.2.1.3

espcCCName OBJECT-TYPE
    SYNTAX DisplayString
    MAX-ACCESS read-write
    STATUS current
    DESCRIPTION
        "Name for this contact closure"
    ::= { esPointConfigCCEntry 4 }
    --1.3.6.1.4.1.3052.14.2.2.2.1.4

espcCCEventState OBJECT-TYPE
    SYNTAX DisplayString
    MAX-ACCESS read-write
    STATUS current
    DESCRIPTION
        "Event state for this contact closure"
    ::= { esPointConfigCCEntry 5 }
    --1.3.6.1.4.1.3052.14.2.2.2.1.5

espcCCThreshold OBJECT-TYPE
    SYNTAX Integer32 (0..65535)
    MAX-ACCESS read-write
    STATUS current
    DESCRIPTION
        "Event threshold (seconds) for this contact closure"
    ::= { esPointConfigCCEntry 6 }
    --1.3.6.1.4.1.3052.14.2.2.2.1.6

espcCCEventActions OBJECT-TYPE
    SYNTAX DisplayString
    MAX-ACCESS read-write
    STATUS current
    DESCRIPTION
        "Event actions for this contact closure"
    ::= { esPointConfigCCEntry 7 }
    --1.3.6.1.4.1.3052.14.2.2.2.1.7

espcCCEventTrapnum OBJECT-TYPE
    SYNTAX Integer32
    MAX-ACCESS read-write
    STATUS current
    DESCRIPTION
        "Event trap number for this contact closure"
    ::= { esPointConfigCCEntry 8 }
    --1.3.6.1.4.1.3052.14.2.2.2.1.8

espcCCEventClass OBJECT-TYPE
    SYNTAX DisplayString
    MAX-ACCESS read-write
    STATUS current
    DESCRIPTION
        "Event class for this contact closure"
    ::= { esPointConfigCCEntry 9 }
    --1.3.6.1.4.1.3052.14.2.2.2.1.9

espcCCNormalActions OBJECT-TYPE
    SYNTAX DisplayString
    MAX-ACCESS read-write
    STATUS current
    DESCRIPTION
        "Return-to-normal actions for this contact closure"
    ::= { esPointConfigCCEntry 10 }
    --1.3.6.1.4.1.3052.14.2.2.2.1.10

espcCCNormalTrapnum OBJECT-TYPE
    SYNTAX Integer32
    MAX-ACCESS read-write
    STATUS current
    DESCRIPTION
        "Return-to-normal trap number for this contact closure"
    ::= { esPointConfigCCEntry 11 }
    --1.3.6.1.4.1.3052.14.2.2.2.1.11

espcCCNormalClass OBJECT-TYPE
    SYNTAX DisplayString
    MAX-ACCESS read-write
    STATUS current
    DESCRIPTION
        "Return-to-normal class for this contact closure"
    ::= { esPointConfigCCEntry 12 }
    --1.3.6.1.4.1.3052.14.2.2.2.1.12

espcCCAlarmAlias OBJECT-TYPE
    SYNTAX DisplayString
    MAX-ACCESS read-write
    STATUS current
    DESCRIPTION
        "Event alias for this contact closure"
    ::= { esPointConfigCCEntry 13 }
    --1.3.6.1.4.1.3052.14.2.2.2.1.13

espcCCNormalAlias OBJECT-TYPE
    SYNTAX DisplayString
    MAX-ACCESS read-write
    STATUS current
    DESCRIPTION
        "Return-to-normal alias for this contact closure"
    ::= { esPointConfigCCEntry 14 }
    --1.3.6.1.4.1.3052.14.2.2.2.1.14

espcCCNormalThreshold OBJECT-TYPE
    SYNTAX Integer32 (0..65535)
    MAX-ACCESS read-write
    STATUS current
    DESCRIPTION
        "Event threshold (seconds) for this contact closure to return to normal"
    ::= { esPointConfigCCEntry 15 }
    --1.3.6.1.4.1.3052.14.2.2.2.1.15

espcCCOverrideGlobalReminder OBJECT-TYPE
    SYNTAX DisplayString
    MAX-ACCESS read-write
    STATUS current
    DESCRIPTION
        "Override global reminder interval (evReminderInterval) for this CC."
    ::= { esPointConfigCCEntry 16 }
    --1.3.6.1.4.1.3052.14.2.2.2.1.16

espcCCReminderInterval OBJECT-TYPE
    SYNTAX Integer32
    MAX-ACCESS read-write
    STATUS current
    DESCRIPTION
        "Individual reminder interval for this CC, applicable when the global
        reminder is overriden."
    ::= { esPointConfigCCEntry 17 }
    --1.3.6.1.4.1.3052.14.2.2.2.1.17


esPointConfigHumidTable OBJECT-TYPE
    SYNTAX SEQUENCE OF ESPointConfigHumid
    MAX-ACCESS not-accessible
    STATUS current
    DESCRIPTION
        "This table organizes 3 basic attributes of humidity points.
        A point is a particular sensor on an EventSensor.  The 3
        point attributes organizes in this table are:
        1. the configuration item (e.g., enable, name, etc.)
        2. the eventsensor on which this point resides
        3. the point number (always 1 for humidity sensors)

        Points are referenced by a point config index.  The point
        config index is a string of 2 numbers separated by a period.
        It contains all the information necessary for getting a piece
        of data off an event sensor within the context of this
        humidity point config table ; namely, which EventSensor and
        which sensor.
        "
    ::= { eventSensorPointConfig 3 }
    --1.3.6.1.4.1.3052.14.2.2.3

esPointConfigHumidEntry OBJECT-TYPE
    SYNTAX ESPointConfigHumid
    MAX-ACCESS not-accessible
    STATUS current
    DESCRIPTION
        "Entry for EventSensor point config humidity table"
    INDEX { espcHumidIndexES, espcHumidIndexPoint }
    ::= { esPointConfigHumidTable 1 }
    --1.3.6.1.4.1.3052.14.2.2.3.1

espcHumidIndexES OBJECT-TYPE
    SYNTAX Integer32 (1..200)
    MAX-ACCESS read-only
    STATUS current
    DESCRIPTION
        "The part of the point index that refers to an
        EventSensor.

        The point config index is a string of 2 numbers separated
        by a period.  It contains all the information
        necessary for getting a piece of data off an event
        sensor within the the context of the eventsensor point
        config contact closure table; namely, which EventSensor
        and which sensor (a.k.a. point).

        This object's allowable values are 1 through 16,
        and 200.  200 always refers to the EventSensor
        inside the unit.  1 through 16 refer to additional
        attached EventSensors.
        "
    ::= { esPointConfigHumidEntry 1 }
    --1.3.6.1.4.1.3052.14.2.2.3.1.1

espcHumidIndexPoint OBJECT-TYPE
    SYNTAX Integer32 (1..64)
    MAX-ACCESS read-only
    STATUS current
    DESCRIPTION
        "The part of the point index that delineates which
        sensor on the EventSensor.

        So this combined with espcHumidIndexES (which EventSensor)
        uniquely defines each point attached to a unit within the
        context of contact closure point configuration."
    ::= { esPointConfigHumidEntry 2 }
    --1.3.6.1.4.1.3052.14.2.2.3.1.2

espcHumidEnable OBJECT-TYPE
    SYNTAX DisplayString
    MAX-ACCESS read-write
    STATUS current
    DESCRIPTION
        "ON/OFF enable for this humidity sensor"
    ::= { esPointConfigHumidEntry 3 }
    --1.3.6.1.4.1.3052.14.2.2.3.1.3

espcHumidDeadband OBJECT-TYPE
    SYNTAX Integer32
    MAX-ACCESS read-write
    STATUS current
    DESCRIPTION
        "Deadband for this humidity sensor"
    ::= { esPointConfigHumidEntry 4 }
    --1.3.6.1.4.1.3052.14.2.2.3.1.4

espcHumidVHighHumid OBJECT-TYPE
    SYNTAX Integer32
    MAX-ACCESS read-write
    STATUS current
    DESCRIPTION
        "Very high event threshold for this humidity sensor"
    ::= { esPointConfigHumidEntry 5 }
    --1.3.6.1.4.1.3052.14.2.2.3.1.5

espcHumidVHighActions OBJECT-TYPE
    SYNTAX DisplayString
    MAX-ACCESS read-write
    STATUS current
    DESCRIPTION
        "Very high event actions for this humidity sensor"
    ::= { esPointConfigHumidEntry 6 }
    --1.3.6.1.4.1.3052.14.2.2.3.1.6

espcHumidVHighTrapnum OBJECT-TYPE
    SYNTAX Integer32
    MAX-ACCESS read-write
    STATUS current
    DESCRIPTION
        "Very high event trap number for this humidity sensor"
    ::= { esPointConfigHumidEntry 7 }
    --1.3.6.1.4.1.3052.14.2.2.3.1.7

espcHumidVHighClass OBJECT-TYPE
    SYNTAX DisplayString
    MAX-ACCESS read-write
    STATUS current
    DESCRIPTION
        "Very high event class for this humidity sensor"
    ::= { esPointConfigHumidEntry 8 }
    --1.3.6.1.4.1.3052.14.2.2.3.1.8

espcHumidHighHumid OBJECT-TYPE
    SYNTAX Integer32
    MAX-ACCESS read-write
    STATUS current
    DESCRIPTION
        "High event threshold for this humidity sensor"
    ::= { esPointConfigHumidEntry 9 }
    --1.3.6.1.4.1.3052.14.2.2.3.1.9

espcHumidHighActions OBJECT-TYPE
    SYNTAX DisplayString
    MAX-ACCESS read-write
    STATUS current
    DESCRIPTION
        "High event actions for this humidity sensor"
    ::= { esPointConfigHumidEntry 10 }
    --1.3.6.1.4.1.3052.14.2.2.3.1.10

espcHumidHighTrapnum OBJECT-TYPE
    SYNTAX Integer32
    MAX-ACCESS read-write
    STATUS current
    DESCRIPTION
        "High event trap number for this humidity sensor"
    ::= { esPointConfigHumidEntry 11 }
    --1.3.6.1.4.1.3052.14.2.2.3.1.11

espcHumidHighClass OBJECT-TYPE
    SYNTAX DisplayString
    MAX-ACCESS read-write
    STATUS current
    DESCRIPTION
        "High event class for this humidity sensor"
    ::= { esPointConfigHumidEntry 12 }
    --1.3.6.1.4.1.3052.14.2.2.3.1.12

espcHumidNormalActions OBJECT-TYPE
    SYNTAX DisplayString
    MAX-ACCESS read-write
    STATUS current
    DESCRIPTION
        "Return-to-normal actions for this humidity sensor"
    ::= { esPointConfigHumidEntry 13 }
    --1.3.6.1.4.1.3052.14.2.2.3.1.13

espcHumidNormalTrapnum OBJECT-TYPE
    SYNTAX Integer32
    MAX-ACCESS read-write
    STATUS current
    DESCRIPTION
        "Return-to-normal trap number for this humidity sensor"
    ::= { esPointConfigHumidEntry 14 }
    --1.3.6.1.4.1.3052.14.2.2.3.1.14

espcHumidNormalClass OBJECT-TYPE
    SYNTAX DisplayString
    MAX-ACCESS read-write
    STATUS current
    DESCRIPTION
        "Return-to-normal class for this humidity sensor"
    ::= { esPointConfigHumidEntry 15 }
    --1.3.6.1.4.1.3052.14.2.2.3.1.15

espcHumidLowHumid OBJECT-TYPE
    SYNTAX Integer32
    MAX-ACCESS read-write
    STATUS current
    DESCRIPTION
        "Low event threshold for this humidity sensor"
    ::= { esPointConfigHumidEntry 16 }
    --1.3.6.1.4.1.3052.14.2.2.3.1.16

espcHumidLowActions OBJECT-TYPE
    SYNTAX DisplayString
    MAX-ACCESS read-write
    STATUS current
    DESCRIPTION
        "Low event actions for this humidity sensor"
    ::= { esPointConfigHumidEntry 17 }
    --1.3.6.1.4.1.3052.14.2.2.3.1.17

espcHumidLowTrapnum OBJECT-TYPE
    SYNTAX Integer32
    MAX-ACCESS read-write
    STATUS current
    DESCRIPTION
        "Low event trap number for this humidity sensor"
    ::= { esPointConfigHumidEntry 18 }
    --1.3.6.1.4.1.3052.14.2.2.3.1.18

espcHumidLowClass OBJECT-TYPE
    SYNTAX DisplayString
    MAX-ACCESS read-write
    STATUS current
    DESCRIPTION
        "Low event class for this humidity sensor"
    ::= { esPointConfigHumidEntry 19 }
    --1.3.6.1.4.1.3052.14.2.2.3.1.19

espcHumidVLowHumid OBJECT-TYPE
    SYNTAX Integer32
    MAX-ACCESS read-write
    STATUS current
    DESCRIPTION
        "Very low event threshold for this humidity sensor"
    ::= { esPointConfigHumidEntry 20 }
    --1.3.6.1.4.1.3052.14.2.2.3.1.20

espcHumidVLowActions OBJECT-TYPE
    SYNTAX DisplayString
    MAX-ACCESS read-write
    STATUS current
    DESCRIPTION
        "Very low event actions for this humidity sensor"
    ::= { esPointConfigHumidEntry 21 }
    --1.3.6.1.4.1.3052.14.2.2.3.1.21

espcHumidVLowTrapnum OBJECT-TYPE
    SYNTAX Integer32
    MAX-ACCESS read-write
    STATUS current
    DESCRIPTION
        "Very low event trap number for this humidity sensor"
    ::= { esPointConfigHumidEntry 22 }
    --1.3.6.1.4.1.3052.14.2.2.3.1.22

espcHumidVLowClass OBJECT-TYPE
    SYNTAX DisplayString
    MAX-ACCESS read-write
    STATUS current
    DESCRIPTION
        "Very low event class for this humidity sensor"
    ::= { esPointConfigHumidEntry 23 }
    --1.3.6.1.4.1.3052.14.2.2.3.1.23


esPointConfigAITable OBJECT-TYPE
    SYNTAX SEQUENCE OF ESPointConfigAnalogInput
    MAX-ACCESS not-accessible
    STATUS current
    DESCRIPTION
        "This table organizes 3 basic attributes of analog input
        points.  A point is a particular sensor on an EventSensor.
        The 3 point attributes organizes in this table are:
        1. the configuration item (e.g., enable, name, etc.)
        2. the eventsensor on which this point resides
        3. the point number

        Points are referenced by a point config index.  The point
        config index is a string of 2 numbers separated by a period.
        It contains all the information necessary for getting a
        piece of data off an event sensor within the context of this
        analog input point config table ; namely, which EventSensor
        and which sensor.
        "
    ::= { eventSensorPointConfig 5 }
    --1.3.6.1.4.1.3052.14.2.2.5

esPointConfigAIEntry OBJECT-TYPE
    SYNTAX ESPointConfigAnalogInput
    MAX-ACCESS not-accessible
    STATUS current
    DESCRIPTION
        "Entry for EventSensor point config analog input table"
    INDEX { espcHumidIndexES, espcHumidIndexPoint }
    ::= { esPointConfigAITable 1 }
    --1.3.6.1.4.1.3052.14.2.2.5.1

espcAIIndexES OBJECT-TYPE
    SYNTAX Integer32 (1..200)
    MAX-ACCESS read-only
    STATUS current
    DESCRIPTION
        "The part of the point index that refers to an
        EventSensor.

        The point config index is a string of 2 numbers separated
        by a period.  It contains all the information
        necessary for getting a piece of data off an event
        sensor within the the context of the eventsensor point
        config contact closure table; namely, which EventSensor
        and which sensor (a.k.a. point).

        This object's allowable values are 1 through 16,
        and 200.  200 always refers to the EventSensor
        inside the unit.  1 through 16 refer to additional
        attached EventSensors.
        "
    ::= { esPointConfigAIEntry 1 }
    --1.3.6.1.4.1.3052.14.2.2.5.1.1

espcAIIndexPoint OBJECT-TYPE
    SYNTAX Integer32 (1..64)
    MAX-ACCESS read-only
    STATUS current
    DESCRIPTION
        "The part of the point index that delineates which
        sensor on the EventSensor.

        So this combined with espcAIIndexES (which EventSensor)
        uniquely defines each point attached to a unit within the
        context of contact closure point configuration."
    ::= { esPointConfigAIEntry 2 }
    --1.3.6.1.4.1.3052.14.2.2.5.1.2

espcAIEnable OBJECT-TYPE
    SYNTAX DisplayString
    MAX-ACCESS read-write
    STATUS current
    DESCRIPTION
        "ON/OFF for this analog input sensor"
    ::= { esPointConfigAIEntry 3 }
    --1.3.6.1.4.1.3052.14.2.2.5.1.3

espcAIDeadband OBJECT-TYPE
    SYNTAX DisplayString
    MAX-ACCESS read-write
    STATUS current
    DESCRIPTION
        "Deadband for this analog input sensor"
    ::= { esPointConfigAIEntry 5 }
    --1.3.6.1.4.1.3052.14.2.2.5.1.5

espcAIVhighValue OBJECT-TYPE
    SYNTAX DisplayString
    MAX-ACCESS read-write
    STATUS current
    DESCRIPTION
        "Very high event threshold (decivolts or tenths of
        milliamps) for this analog input sensor"
    ::= { esPointConfigAIEntry 6 }
    --1.3.6.1.4.1.3052.14.2.2.5.1.6

espcAIVhighActions OBJECT-TYPE
    SYNTAX DisplayString
    MAX-ACCESS read-write
    STATUS current
    DESCRIPTION
        "Very high event actions for this analog input sensor"
    ::= { esPointConfigAIEntry 7 }
    --1.3.6.1.4.1.3052.14.2.2.5.1.7

espcAIVhighTrapnum OBJECT-TYPE
    SYNTAX Integer32
    MAX-ACCESS read-write
    STATUS current
    DESCRIPTION
        "Very high event trap number for this analog input sensor"
    ::= { esPointConfigAIEntry 8 }
    --1.3.6.1.4.1.3052.14.2.2.5.1.8

espcAIVhighClass OBJECT-TYPE
    SYNTAX DisplayString
    MAX-ACCESS read-write
    STATUS current
    DESCRIPTION
        "Very high event class for this analog input sensor"
    ::= { esPointConfigAIEntry 9 }
    --1.3.6.1.4.1.3052.14.2.2.5.1.9

espcAIHighValue OBJECT-TYPE
    SYNTAX DisplayString
    MAX-ACCESS read-write
    STATUS current
    DESCRIPTION
        "High event threshold (decivolts or tenths of milliamps) for
        this analog input sensor"
    ::= { esPointConfigAIEntry 10 }
    --1.3.6.1.4.1.3052.14.2.2.5.1.10

espcAIHighActions OBJECT-TYPE
    SYNTAX DisplayString
    MAX-ACCESS read-write
    STATUS current
    DESCRIPTION
        "High event actions for this analog input sensor"
    ::= { esPointConfigAIEntry 11 }
    --1.3.6.1.4.1.3052.14.2.2.5.1.11

espcAIHighTrapnum OBJECT-TYPE
    SYNTAX Integer32
    MAX-ACCESS read-write
    STATUS current
    DESCRIPTION
        "High event trap number for this analog input sensor"
    ::= { esPointConfigAIEntry 12 }
    --1.3.6.1.4.1.3052.14.2.2.5.1.12

espcAIHighClass OBJECT-TYPE
    SYNTAX DisplayString
    MAX-ACCESS read-write
    STATUS current
    DESCRIPTION
        "High event class for this analog input sensor"
    ::= { esPointConfigAIEntry 13 }
    --1.3.6.1.4.1.3052.14.2.2.5.1.13

espcAINormalActions OBJECT-TYPE
    SYNTAX DisplayString
    MAX-ACCESS read-write
    STATUS current
    DESCRIPTION
        "Return-to-normal actions for this analog input sensor"
    ::= { esPointConfigAIEntry 14 }
    --1.3.6.1.4.1.3052.14.2.2.5.1.14

espcAINormalTrapnum OBJECT-TYPE
    SYNTAX Integer32
    MAX-ACCESS read-write
    STATUS current
    DESCRIPTION
        "Return-to-normal trap number for this analog input sensor"
    ::= { esPointConfigAIEntry 15 }
    --1.3.6.1.4.1.3052.14.2.2.5.1.15

espcAINormalClass OBJECT-TYPE
    SYNTAX DisplayString
    MAX-ACCESS read-write
    STATUS current
    DESCRIPTION
        "Return-to-normal class for this analog input sensor"
    ::= { esPointConfigAIEntry 16 }
    --1.3.6.1.4.1.3052.14.2.2.5.1.16

espcAILowValue OBJECT-TYPE
    SYNTAX DisplayString
    MAX-ACCESS read-write
    STATUS current
    DESCRIPTION
        "Low event threshold (decivolts or tenths of milliamps) for
        this analog input sensor"
    ::= { esPointConfigAIEntry 17 }
    --1.3.6.1.4.1.3052.14.2.2.5.1.17

espcAILowActions OBJECT-TYPE
    SYNTAX DisplayString
    MAX-ACCESS read-write
    STATUS current
    DESCRIPTION
        "Low event actions for this analog input sensor"
    ::= { esPointConfigAIEntry 18 }
    --1.3.6.1.4.1.3052.14.2.2.5.1.18

espcAILowTrapnum OBJECT-TYPE
    SYNTAX Integer32
    MAX-ACCESS read-write
    STATUS current
    DESCRIPTION
        "Low event trap number for this analog input sensor"
    ::= { esPointConfigAIEntry 19 }
    --1.3.6.1.4.1.3052.14.2.2.5.1.19

espcAILowClass OBJECT-TYPE
    SYNTAX DisplayString
    MAX-ACCESS read-write
    STATUS current
    DESCRIPTION
        "Low event class for this analog input sensor"
    ::= { esPointConfigAIEntry 20 }
    --1.3.6.1.4.1.3052.14.2.2.5.1.20

espcAIVlowValue OBJECT-TYPE
    SYNTAX DisplayString
    MAX-ACCESS read-write
    STATUS current
    DESCRIPTION
        "Very low event threshold (decivolts or tenths of milliamps)
        for this analog input sensor"
    ::= { esPointConfigAIEntry 21 }
    --1.3.6.1.4.1.3052.14.2.2.5.1.21

espcAIVlowActions OBJECT-TYPE
    SYNTAX DisplayString
    MAX-ACCESS read-write
    STATUS current
    DESCRIPTION
        "Very low event actions for this analog input sensor"
    ::= { esPointConfigAIEntry 22 }
    --1.3.6.1.4.1.3052.14.2.2.5.1.22

espcAIVlowTrapnum OBJECT-TYPE
    SYNTAX Integer32
    MAX-ACCESS read-write
    STATUS current
    DESCRIPTION
        "Very low event actions for this analog input sensor"
    ::= { esPointConfigAIEntry 23 }
    --1.3.6.1.4.1.3052.14.2.2.5.1.23

espcAIVlowClass OBJECT-TYPE
    SYNTAX DisplayString
    MAX-ACCESS read-write
    STATUS current
    DESCRIPTION
        "Very low event class for this analog input sensor"
    ::= { esPointConfigAIEntry 24 }
    --1.3.6.1.4.1.3052.14.2.2.5.1.24

espcAIConvUnitName OBJECT-TYPE
    SYNTAX DisplayString
    MAX-ACCESS read-write
    STATUS current
    DESCRIPTION
        "Converstion unit name for this analog input sensor"
    ::= { esPointConfigAIEntry 25 }
    --1.3.6.1.4.1.3052.14.2.2.5.1.25

espcAIConvHighValue OBJECT-TYPE
    SYNTAX DisplayString
    MAX-ACCESS read-write
    STATUS current
    DESCRIPTION
        "Conversion high value for this analog input sensor"
    ::= { esPointConfigAIEntry 26 }
    --1.3.6.1.4.1.3052.14.2.2.5.1.26

espcAIConvHighUnit OBJECT-TYPE
    SYNTAX DisplayString
    MAX-ACCESS read-write
    STATUS current
    DESCRIPTION
        "Conversion high unit value for this analog input sensor"
    ::= { esPointConfigAIEntry 27 }
    --1.3.6.1.4.1.3052.14.2.2.5.1.27

espcAIConvLowValue OBJECT-TYPE
    SYNTAX DisplayString
    MAX-ACCESS read-write
    STATUS current
    DESCRIPTION
        "Conversion low value for this analog input sensor"
    ::= { esPointConfigAIEntry 29 }
    --1.3.6.1.4.1.3052.14.2.2.5.1.29

espcAIConvLowUnit OBJECT-TYPE
    SYNTAX DisplayString
    MAX-ACCESS read-write
    STATUS current
    DESCRIPTION
        "Conversion unit low unit value for this analog input sensor"
    ::= { esPointConfigAIEntry 30 }
    --1.3.6.1.4.1.3052.14.2.2.5.1.30

espcAIDisplayFormat OBJECT-TYPE
    SYNTAX DisplayString
    MAX-ACCESS read-write
    STATUS current
    DESCRIPTION
        "Analog input display format"
    ::= { esPointConfigAIEntry 32 }
    --1.3.6.1.4.1.3052.14.2.2.5.1.32

esPointConfigOutputTable OBJECT-TYPE
    SYNTAX SEQUENCE OF ESPointConfigOutput
    MAX-ACCESS not-accessible
    STATUS current
    DESCRIPTION
        "This table organizes configuration items for output
        points.  A point is a particular sensor on an EventSensor.
        The 3 point attributes organized in this table are:
        1. the configuration item (e.g., enable, name, etc.)
        2. the eventsensor on which this point resides
        3. the point number

        Points are referenced by a point config index.  The point
        config index is a string of 2 numbers separated by a period.
        It contains all the information necessary for getting a
        piece of data off an event sensor within the context of this
        output config table ; namely, which EventSensor
        and which sensor.
        "
    ::= { eventSensorPointConfig 6 }
    --1.3.6.1.4.1.3052.14.2.2.6

esPointConfigOutputEntry OBJECT-TYPE
    SYNTAX ESPointConfigOutput
    MAX-ACCESS not-accessible
    STATUS current
    DESCRIPTION
        "Entry for EventSensor point config output table"
    INDEX { espcOutputIndexES, espcOutputIndexPoint }
    ::= { esPointConfigOutputTable 1 }
    --1.3.6.1.4.1.3052.14.2.2.6.1

espcOutputIndexES OBJECT-TYPE
    SYNTAX Integer32 (1..200)
    MAX-ACCESS read-only
    STATUS current
    DESCRIPTION
        "The part of the point index that refers to an
        EventSensor.

        The point config index is a string of 2 numbers separated
        by a period.  It contains all the information
        necessary for getting a piece of data off an event
        sensor within the the context of the eventsensor point
        config contact closure table; namely, which EventSensor
        and which sensor (a.k.a. point).

        This object's allowable values are 1 through 16,
        and 200.  200 always refers to the EventSensor
        inside the unit.  1 through 16 refer to additional
        attached EventSensors.
        "
    ::= { esPointConfigOutputEntry 1 }
    --1.3.6.1.4.1.3052.14.2.2.6.1.1

espcOutputIndexPoint OBJECT-TYPE
    SYNTAX Integer32 (1..64)
    MAX-ACCESS read-only
    STATUS current
    DESCRIPTION
        "The part of the point index that delineates which
        sensor on the EventSensor.

        So this combined with espcOutputIndexES (which EventSensor)
        uniquely defines each point attached to a unit within the
        context of output point configuration."
    ::= { esPointConfigOutputEntry 2 }
    --1.3.6.1.4.1.3052.14.2.2.6.1.2

espcOutputEnable OBJECT-TYPE
    SYNTAX DisplayString
    MAX-ACCESS read-write
    STATUS current
    DESCRIPTION
        "Enables the output event for this output.  This has no effect
        on whether the relay changes state, only on whether a state change
        triggers an event."
    ::= { esPointConfigOutputEntry 3 }
    --1.3.6.1.4.1.3052.14.2.2.6.1.3

espcOutputActiveState OBJECT-TYPE
    SYNTAX DisplayString
    MAX-ACCESS read-write
    STATUS current
    DESCRIPTION
        "Which state is considered the active state: energized/de-energized."
    ::= { esPointConfigOutputEntry 4 }
    --1.3.6.1.4.1.3052.14.2.2.6.1.4

espcOutputType OBJECT-TYPE
    SYNTAX DisplayString
    MAX-ACCESS read-only
    STATUS current
    DESCRIPTION
        "Output type: RELAY, POWER, SSR, TTL."
    ::= { esPointConfigOutputEntry 5 }
    --1.3.6.1.4.1.3052.14.2.2.6.1.5

espcOutputAliasValue OBJECT-TYPE
    SYNTAX DisplayString
    MAX-ACCESS read-only
    STATUS current
    DESCRIPTION
        "Output alias corresponding to its event state."
    ::= { esPointConfigOutputEntry 6 }
    --1.3.6.1.4.1.3052.14.2.2.6.1.6

espcOutputAliasColor OBJECT-TYPE
    SYNTAX DisplayString
    MAX-ACCESS read-only
    STATUS current
    DESCRIPTION
        "Output color corresponding to its event state."
    ::= { esPointConfigOutputEntry 7 }
    --1.3.6.1.4.1.3052.14.2.2.6.1.7

espcOutputActiveAlias OBJECT-TYPE
    SYNTAX DisplayString
    MAX-ACCESS read-write
    STATUS current
    DESCRIPTION
        "Alias for the output active state."
    ::= { esPointConfigOutputEntry 10 }
    --1.3.6.1.4.1.3052.14.2.2.6.1.10

espcOutputActiveColor OBJECT-TYPE
    SYNTAX DisplayString
    MAX-ACCESS read-write
    STATUS current
    DESCRIPTION
        "Output color (as rendered in the web UI, in RGB hex format) corresponding
        to the output active state."
    ::= { esPointConfigOutputEntry 11 }
    --1.3.6.1.4.1.3052.14.2.2.6.1.11

espcOutputActiveActions OBJECT-TYPE
    SYNTAX DisplayString
    MAX-ACCESS read-write
    STATUS current
    DESCRIPTION
        "Actions for the output active event."
    ::= { esPointConfigOutputEntry 12 }
    --1.3.6.1.4.1.3052.14.2.2.6.1.12

espcOutputActiveTrapnum OBJECT-TYPE
    SYNTAX Integer32 (150..1199)
    MAX-ACCESS read-write
    STATUS current
    DESCRIPTION
        "Actions for the output active event."
    ::= { esPointConfigOutputEntry 13 }
    --1.3.6.1.4.1.3052.14.2.2.6.1.13

espcOutputActiveClass OBJECT-TYPE
    SYNTAX DisplayString
    MAX-ACCESS read-write
    STATUS current
    DESCRIPTION
        "Class (severity) for the output active event."
    ::= { esPointConfigOutputEntry 14 }
    --1.3.6.1.4.1.3052.14.2.2.6.1.14

espcOutputInactiveAlias OBJECT-TYPE
    SYNTAX DisplayString
    MAX-ACCESS read-write
    STATUS current
    DESCRIPTION
        "Alias for the output inactive state."
    ::= { esPointConfigOutputEntry 20 }
    --1.3.6.1.4.1.3052.14.2.2.6.1.20

espcOutputInactiveColor OBJECT-TYPE
    SYNTAX DisplayString
    MAX-ACCESS read-write
    STATUS current
    DESCRIPTION
        "Output color (as rendered in the web UI, in RGB hex format) corresponding
        to the output inactive state."
    ::= { esPointConfigOutputEntry 21 }
    --1.3.6.1.4.1.3052.14.2.2.6.1.21

espcOutputInactiveActions OBJECT-TYPE
    SYNTAX DisplayString
    MAX-ACCESS read-write
    STATUS current
    DESCRIPTION
        "Actions for the output inactive event."
    ::= { esPointConfigOutputEntry 22 }
    --1.3.6.1.4.1.3052.14.2.2.6.1.22

espcOutputInactiveTrapnum OBJECT-TYPE
    SYNTAX Integer32 (150..1199)
    MAX-ACCESS read-write
    STATUS current
    DESCRIPTION
        "Actions for the output inactive event."
    ::= { esPointConfigOutputEntry 23 }
    --1.3.6.1.4.1.3052.14.2.2.6.1.23

espcOutputInactiveClass OBJECT-TYPE
    SYNTAX DisplayString
    MAX-ACCESS read-write
    STATUS current
    DESCRIPTION
        "Class (severity) for the output inactive event."
    ::= { esPointConfigOutputEntry 24 }
    --1.3.6.1.4.1.3052.14.2.2.6.1.24


--***************************************************************************************
--Serial Port Section       2.3
--***************************************************************************************

numberPorts OBJECT-TYPE
    SYNTAX Integer32
    MAX-ACCESS read-only
    STATUS current
    DESCRIPTION
        "Number of RS-232 ports found.
        Range: 2 or 4"
    ::= { serialPorts 1 }
    --1.3.6.1.4.1.3052.14.2.3.1

portConfigTable OBJECT-TYPE
    SYNTAX SEQUENCE OF PortConfig
    MAX-ACCESS not-accessible
    STATUS current
    DESCRIPTION
        "Port config table"
    ::= { serialPorts 2 }
    --1.3.6.1.4.1.3052.14.2.3.2

portConfigEntry OBJECT-TYPE
    SYNTAX PortConfig
    MAX-ACCESS not-accessible
    STATUS current
    DESCRIPTION
        "Port config entry"
    INDEX { portConfigIndex }
    ::= { portConfigTable 1 }
    --1.3.6.1.4.1.3052.14.2.3.2.1

portConfigIndex OBJECT-TYPE
    SYNTAX Integer32 (1..16)
    MAX-ACCESS read-only
    STATUS current
    DESCRIPTION
        "Index for ports"
    ::= { portConfigEntry 1 }
    --1.3.6.1.4.1.3052.14.2.3.2.1.1

portConfigBaud OBJECT-TYPE
    SYNTAX Integer32
    MAX-ACCESS read-write
    STATUS current
    DESCRIPTION
        "Baud rate, 19200, 9600, etc."
    ::= { portConfigEntry 2 }
    --1.3.6.1.4.1.3052.14.2.3.2.1.2

portConfigDataFormat OBJECT-TYPE
    SYNTAX Integer32
    MAX-ACCESS read-write
    STATUS current
    DESCRIPTION
        "Value representing word length, parity, and
        stop bits: 0=8N1, 1=7E1, 2=7O1, 3=7N1, 4=8O2"
    ::= { portConfigEntry 3 }
    --1.3.6.1.4.1.3052.14.2.3.2.1.3

portConfigStripPtOutputLfs OBJECT-TYPE
    SYNTAX Integer32
    MAX-ACCESS read-write
    STATUS current
    DESCRIPTION
        "Strip passthrough LFs sent to device on this port:
        1=yes, 0=no."
    ::= { portConfigEntry 4 }
    --1.3.6.1.4.1.3052.14.2.3.2.1.4

portConfigStripPtInputLfs OBJECT-TYPE
    SYNTAX Integer32
    MAX-ACCESS read-write
    STATUS current
    DESCRIPTION
        "Strip passthrough LFs received from device on this
        port: 1=yes, 0=no."
    ::= { portConfigEntry 5 }
    --1.3.6.1.4.1.3052.14.2.3.2.1.5

portConfigMaskEnable OBJECT-TYPE
    SYNTAX Integer32
    MAX-ACCESS read-write
    STATUS current
    DESCRIPTION
        "1=Use the character mask on this port.  0=Do
        not use the mask.  When the mask is enabled,
        the following ASCII characters are ignored
        on the port:
        0, 1, 4-9, 11, 12, 14-31, 128-255.
        When the mask is disabled, all characters are
        accepted on the port."
    ::= { portConfigEntry 7 }
    --1.3.6.1.4.1.3052.14.2.3.2.1.7

portConfigDAEnable OBJECT-TYPE
    SYNTAX Integer32
    MAX-ACCESS read-write
    STATUS current
    DESCRIPTION
        "1=Enable the Data Alarm Evaluator for data
        on this port.  0=Do not evaluate data on this
        port."
    ::= { portConfigEntry 8 }
    --1.3.6.1.4.1.3052.14.2.3.2.1.8

portConfigStoreAlarmsDPT OBJECT-TYPE
    SYNTAX DisplayString
    MAX-ACCESS read-write
    STATUS current
    DESCRIPTION
        "ON/OFF: store alarms received during passthrough"
    ::= { portConfigEntry 9 }
    --1.3.6.1.4.1.3052.14.2.3.2.1.9

portConfigRecordTimeout OBJECT-TYPE
    SYNTAX Integer32
    MAX-ACCESS read-write
    STATUS current
    DESCRIPTION
        "Timeout after last unterminated data received upon
        which data collected so far is stored as a record."
    ::= { portConfigEntry 10 }
    --1.3.6.1.4.1.3052.14.2.3.2.1.10

portConfigDataType OBJECT-TYPE
    SYNTAX DisplayString
    MAX-ACCESS read-write
    STATUS current
    DESCRIPTION
        "How the port interprets incoming data: ASCII/BINARY"
    ::= { portConfigEntry 11 }
    --1.3.6.1.4.1.3052.14.2.3.2.1.11

portConfigEtxToCRLF OBJECT-TYPE
    SYNTAX DisplayString
    MAX-ACCESS read-write
    STATUS current
    DESCRIPTION
        "ON/OFF whether the port translates incoming ETX to CRLF"
    ::= { portConfigEntry 12 }
    --1.3.6.1.4.1.3052.14.2.3.2.1.12

portConfigMLREnable OBJECT-TYPE
    SYNTAX DisplayString
    MAX-ACCESS read-write
    STATUS current
    DESCRIPTION
        "ON/OFF Whether Multiline Records are collected on this port."
    ::= { portConfigEntry 13 }
    --1.3.6.1.4.1.3052.14.2.3.2.1.13

portConfigMLRStartField1Pos OBJECT-TYPE
    SYNTAX Integer32
    MAX-ACCESS read-write
    STATUS current
    DESCRIPTION
        "Position of MLR start field 1"
    ::= { portConfigEntry 14 }
    --1.3.6.1.4.1.3052.14.2.3.2.1.14

portConfigMLRStartField1Text OBJECT-TYPE
    SYNTAX DisplayString
    MAX-ACCESS read-write
    STATUS current
    DESCRIPTION
        "Text to match MLR start field 1"
    ::= { portConfigEntry 15 }
    --1.3.6.1.4.1.3052.14.2.3.2.1.15

portConfigMLRStartField2Pos OBJECT-TYPE
    SYNTAX Integer32
    MAX-ACCESS read-write
    STATUS current
    DESCRIPTION
        "Position of MLR start field 2"
    ::= { portConfigEntry 16 }
    --1.3.6.1.4.1.3052.14.2.3.2.1.16

portConfigMLRStartField2Text OBJECT-TYPE
    SYNTAX DisplayString
    MAX-ACCESS read-write
    STATUS current
    DESCRIPTION
        "Text to match MLR start field 2"
    ::= { portConfigEntry 17 }
    --1.3.6.1.4.1.3052.14.2.3.2.1.17

portConfigMLRNumLinesBefore OBJECT-TYPE
    SYNTAX Integer32
    MAX-ACCESS read-write
    STATUS current
    DESCRIPTION
        "Number of lines before the starting line which should
        be included in the MLR"
    ::= { portConfigEntry 18 }
    --1.3.6.1.4.1.3052.14.2.3.2.1.18

portConfigMLREndDetection OBJECT-TYPE
    SYNTAX DisplayString
    MAX-ACCESS read-write
    STATUS current
    DESCRIPTION
        "How the MLR parser determines what ends an MLR: by FORMULA,
        number of lines received so far (COUNT), or number of blank
        lines received so far (BLANKS)"
    ::= { portConfigEntry 19 }
    --1.3.6.1.4.1.3052.14.2.3.2.1.19

portConfigMLRLineCount OBJECT-TYPE
    SYNTAX Integer32
    MAX-ACCESS read-write
    STATUS current
    DESCRIPTION
        "Number of lines in the MLR (used by the end detection mode)"
    ::= { portConfigEntry 20 }
    --1.3.6.1.4.1.3052.14.2.3.2.1.20

portConfigMLREndField1Pos OBJECT-TYPE
    SYNTAX Integer32
    MAX-ACCESS read-write
    STATUS current
    DESCRIPTION
        "Position of MLR end field 1"
    ::= { portConfigEntry 21 }
    --1.3.6.1.4.1.3052.14.2.3.2.1.21

portConfigMLREndField1Text OBJECT-TYPE
    SYNTAX DisplayString
    MAX-ACCESS read-write
    STATUS current
    DESCRIPTION
        "Text to match MLR end field 1"
    ::= { portConfigEntry 22 }
    --1.3.6.1.4.1.3052.14.2.3.2.1.22

portConfigMLREndField2Pos OBJECT-TYPE
    SYNTAX Integer32
    MAX-ACCESS read-write
    STATUS current
    DESCRIPTION
        "Position of MLR end field 2"
    ::= { portConfigEntry 23 }
    --1.3.6.1.4.1.3052.14.2.3.2.1.23

portConfigMLREndField2Text OBJECT-TYPE
    SYNTAX DisplayString
    MAX-ACCESS read-write
    STATUS current
    DESCRIPTION
        "Text to match MLR end field 2"
    ::= { portConfigEntry 24 }
    --1.3.6.1.4.1.3052.14.2.3.2.1.24

portConfigMLRUseComplexRules OBJECT-TYPE
    SYNTAX DisplayString
    MAX-ACCESS read-write
    STATUS current
    DESCRIPTION
        "ON/OFF MLR parser uses complex rules (field possitions/
        formulas, etc.)"
    ::= { portConfigEntry 25 }
    --1.3.6.1.4.1.3052.14.2.3.2.1.25

portConfigBufferPT OBJECT-TYPE
    SYNTAX DisplayString
    MAX-ACCESS read-write
    STATUS current
    DESCRIPTION
        "ON/OFF records received during passthrough mode are
        buffered/stored in the database"
    ::= { portConfigEntry 26 }
    --1.3.6.1.4.1.3052.14.2.3.2.1.26

portConfigId OBJECT-TYPE
    SYNTAX DisplayString
    MAX-ACCESS read-write
    STATUS current
    DESCRIPTION
        "The text identifer for the port"
    ::= { portConfigEntry 27 }
    --1.3.6.1.4.1.3052.14.2.3.2.1.27

portConfigMode OBJECT-TYPE
    SYNTAX DisplayString
    MAX-ACCESS read-write
    STATUS current
    DESCRIPTION
        "Mode of the serial port."
    ::= { portConfigEntry 28 }
    --1.3.6.1.4.1.3052.14.2.3.2.1.28

portConfigHsk OBJECT-TYPE
    SYNTAX DisplayString
    MAX-ACCESS read-write
    STATUS current
    DESCRIPTION
        "Handshaking mode of the serial port."
    ::= { portConfigEntry 29 }
    --1.3.6.1.4.1.3052.14.2.3.2.1.29

--***************************************************************************************
--Network Section   2.4
--***************************************************************************************

eth1Mode OBJECT-TYPE
    SYNTAX DisplayString
    MAX-ACCESS read-only
    STATUS current
    DESCRIPTION
         "Mode of the Ethernet1 interface: STATIC,DHCP,VLAN"
    ::= { ethernet1 1 }
    --1.3.6.1.4.1.3052.14.2.4.1.1.1.1

eth1Address OBJECT-TYPE
    SYNTAX IpAddress
    MAX-ACCESS read-write
    STATUS current
    DESCRIPTION
        "Ethernet1 IP address"
    ::= { ethernet1 2 }
    --1.3.6.1.4.1.3052.14.2.4.1.1.1.2

eth1SubnetMask OBJECT-TYPE
    SYNTAX IpAddress
    MAX-ACCESS read-write
    STATUS current
    DESCRIPTION
        "Ethernet1 subnet mask"
    ::= { ethernet1 3 }
    --1.3.6.1.4.1.3052.14.2.4.1.1.1.3

eth1Router OBJECT-TYPE
    SYNTAX IpAddress
    MAX-ACCESS read-write
    STATUS current
    DESCRIPTION
        "Ethernet1 router"
    ::= { ethernet1 4 }
    --1.3.6.1.4.1.3052.14.2.4.1.1.1.4

-- Ethernet1 VLAN1

eth1VLAN1ID OBJECT-TYPE
    SYNTAX Integer32
    MAX-ACCESS read-write
    STATUS current
    DESCRIPTION
        "Ethernet1 VLAN1 ID"
    ::= { eth1VLAN1 1 }
    --1.3.6.1.4.1.3052.14.2.4.1.1.1.5.1.1

eth1VLAN1Priority OBJECT-TYPE
    SYNTAX Integer32
    MAX-ACCESS read-write
    STATUS current
    DESCRIPTION
        "Ethernet1 VLAN1 priority"
    ::= { eth1VLAN1 2 }
    --1.3.6.1.4.1.3052.14.2.4.1.1.1.5.1.2

eth1VLAN1Address OBJECT-TYPE
    SYNTAX IpAddress
    MAX-ACCESS read-write
    STATUS current
    DESCRIPTION
        "Ethernet1 VLAN1 IP address"
    ::= { eth1VLAN1 3 }
    --1.3.6.1.4.1.3052.14.2.4.1.1.1.5.1.3

eth1VLAN1SubnetMask OBJECT-TYPE
    SYNTAX IpAddress
    MAX-ACCESS read-write
    STATUS current
    DESCRIPTION
        "Ethernet1 VLAN1 subnet mask"
    ::= { eth1VLAN1 4 }
    --1.3.6.1.4.1.3052.14.2.4.1.1.1.5.1.4

eth1VLAN1Router OBJECT-TYPE
    SYNTAX IpAddress
    MAX-ACCESS read-write
    STATUS current
    DESCRIPTION
        "Ethernet1 VLAN1 router"
    ::= { eth1VLAN1 5 }
    --1.3.6.1.4.1.3052.14.2.4.1.1.1.5.1.5

-- Ethernet1 VLAN2

eth1VLAN2ID OBJECT-TYPE
    SYNTAX Integer32
    MAX-ACCESS read-write
    STATUS current
    DESCRIPTION
        "Ethernet1 VLAN2 ID"
    ::= { eth1VLAN2 1 }
    --1.3.6.1.4.1.3052.14.2.4.1.1.1.5.2.1

eth1VLAN2Priority OBJECT-TYPE
    SYNTAX Integer32
    MAX-ACCESS read-write
    STATUS current
    DESCRIPTION
        "Ethernet1 VLAN2 priority"
    ::= { eth1VLAN2 2 }
    --1.3.6.1.4.1.3052.14.2.4.1.1.1.5.2.2

eth1VLAN2Address OBJECT-TYPE
    SYNTAX IpAddress
    MAX-ACCESS read-write
    STATUS current
    DESCRIPTION
        "Ethernet1 VLAN2 IP address"
    ::= { eth1VLAN2 3 }
    --1.3.6.1.4.1.3052.14.2.4.1.1.1.5.2.3

eth1VLAN2SubnetMask OBJECT-TYPE
    SYNTAX IpAddress
    MAX-ACCESS read-write
    STATUS current
    DESCRIPTION
        "Ethernet1 VLAN2 subnet mask"
    ::= { eth1VLAN2 4 }
    --1.3.6.1.4.1.3052.14.2.4.1.1.1.5.2.4

eth1VLAN2Router OBJECT-TYPE
    SYNTAX IpAddress
    MAX-ACCESS read-write
    STATUS current
    DESCRIPTION
        "Ethernet1 VLAN2 router"
    ::= { eth1VLAN2 5 }
    --1.3.6.1.4.1.3052.14.2.4.1.1.1.5.2.5

-- Ethernet1 VLAN3

eth1VLAN3ID OBJECT-TYPE
    SYNTAX Integer32
    MAX-ACCESS read-write
    STATUS current
    DESCRIPTION
        "Ethernet1 VLAN3 ID"
    ::= { eth1VLAN3 1 }
    --1.3.6.1.4.1.3052.14.2.4.1.1.1.5.3.1

eth1VLAN3Priority OBJECT-TYPE
    SYNTAX Integer32
    MAX-ACCESS read-write
    STATUS current
    DESCRIPTION
        "Ethernet1 VLAN3 priority"
    ::= { eth1VLAN3 2 }
    --1.3.6.1.4.1.3052.14.2.4.1.1.1.5.3.2

eth1VLAN3Address OBJECT-TYPE
    SYNTAX IpAddress
    MAX-ACCESS read-write
    STATUS current
    DESCRIPTION
        "Ethernet1 VLAN3 IP address"
    ::= { eth1VLAN3 3 }
    --1.3.6.1.4.1.3052.14.2.4.1.1.1.5.3.3

eth1VLAN3SubnetMask OBJECT-TYPE
    SYNTAX IpAddress
    MAX-ACCESS read-write
    STATUS current
    DESCRIPTION
        "Ethernet1 VLAN3 subnet mask"
    ::= { eth1VLAN3 4 }
    --1.3.6.1.4.1.3052.14.2.4.1.1.1.5.3.4

eth1VLAN3Router OBJECT-TYPE
    SYNTAX IpAddress
    MAX-ACCESS read-write
    STATUS current
    DESCRIPTION
        "Ethernet1 VLAN3 router"
    ::= { eth1VLAN3 5 }
    --1.3.6.1.4.1.3052.14.2.4.1.1.1.5.3.5

-- Ethernet1 VLAN4

eth1VLAN4ID OBJECT-TYPE
    SYNTAX Integer32
    MAX-ACCESS read-write
    STATUS current
    DESCRIPTION
        "Ethernet1 VLAN4 ID"
    ::= { eth1VLAN4 1 }
    --1.3.6.1.4.1.3052.14.2.4.1.1.1.5.4.1

eth1VLAN4Priority OBJECT-TYPE
    SYNTAX Integer32
    MAX-ACCESS read-write
    STATUS current
    DESCRIPTION
        "Ethernet1 VLAN4 priority"
    ::= { eth1VLAN4 2 }
    --1.3.6.1.4.1.3052.14.2.4.1.1.1.5.4.2

eth1VLAN4Address OBJECT-TYPE
    SYNTAX IpAddress
    MAX-ACCESS read-write
    STATUS current
    DESCRIPTION
        "Ethernet1 VLAN4 IP address"
    ::= { eth1VLAN4 3 }
    --1.3.6.1.4.1.3052.14.2.4.1.1.1.5.4.3

eth1VLAN4SubnetMask OBJECT-TYPE
    SYNTAX IpAddress
    MAX-ACCESS read-write
    STATUS current
    DESCRIPTION
        "Ethernet1 VLAN4 subnet mask"
    ::= { eth1VLAN4 4 }
    --1.3.6.1.4.1.3052.14.2.4.1.1.1.5.4.4

eth1VLAN4Router OBJECT-TYPE
    SYNTAX IpAddress
    MAX-ACCESS read-write
    STATUS current
    DESCRIPTION
        "Ethernet1 VLAN4 router"
    ::= { eth1VLAN4 5 }
    --1.3.6.1.4.1.3052.14.2.4.1.1.1.5.4.5

-- Ethernet1 VLAN5

eth1VLAN5ID OBJECT-TYPE
    SYNTAX Integer32
    MAX-ACCESS read-write
    STATUS current
    DESCRIPTION
        "Ethernet1 VLAN5 ID"
    ::= { eth1VLAN5 1 }
    --1.3.6.1.4.1.3052.14.2.4.1.1.1.5.5.1

eth1VLAN5Priority OBJECT-TYPE
    SYNTAX Integer32
    MAX-ACCESS read-write
    STATUS current
    DESCRIPTION
        "Ethernet1 VLAN5 priority"
    ::= { eth1VLAN5 2 }
    --1.3.6.1.4.1.3052.14.2.4.1.1.1.5.5.2

eth1VLAN5Address OBJECT-TYPE
    SYNTAX IpAddress
    MAX-ACCESS read-write
    STATUS current
    DESCRIPTION
        "Ethernet1 VLAN5 IP address"
    ::= { eth1VLAN5 3 }
    --1.3.6.1.4.1.3052.14.2.4.1.1.1.5.5.3

eth1VLAN5SubnetMask OBJECT-TYPE
    SYNTAX IpAddress
    MAX-ACCESS read-write
    STATUS current
    DESCRIPTION
        "Ethernet1 VLAN5 subnet mask"
    ::= { eth1VLAN5 4 }
    --1.3.6.1.4.1.3052.14.2.4.1.1.1.5.5.4

eth1VLAN5Router OBJECT-TYPE
    SYNTAX IpAddress
    MAX-ACCESS read-write
    STATUS current
    DESCRIPTION
        "Ethernet1 VLAN5 router"
    ::= { eth1VLAN5 5 }
    --1.3.6.1.4.1.3052.14.2.4.1.1.1.5.5.5

-- Ethernet1 VLAN6

eth1VLAN6ID OBJECT-TYPE
    SYNTAX Integer32
    MAX-ACCESS read-write
    STATUS current
    DESCRIPTION
        "Ethernet1 VLAN6 ID"
    ::= { eth1VLAN6 1 }
    --1.3.6.1.4.1.3052.14.2.4.1.1.1.5.6.1

eth1VLAN6Priority OBJECT-TYPE
    SYNTAX Integer32
    MAX-ACCESS read-write
    STATUS current
    DESCRIPTION
        "Ethernet1 VLAN6 priority"
    ::= { eth1VLAN6 2 }
    --1.3.6.1.4.1.3052.14.2.4.1.1.1.5.6.2

eth1VLAN6Address OBJECT-TYPE
    SYNTAX IpAddress
    MAX-ACCESS read-write
    STATUS current
    DESCRIPTION
        "Ethernet1 VLAN6 IP address"
    ::= { eth1VLAN6 3 }
    --1.3.6.1.4.1.3052.14.2.4.1.1.1.5.6.3

eth1VLAN6SubnetMask OBJECT-TYPE
    SYNTAX IpAddress
    MAX-ACCESS read-write
    STATUS current
    DESCRIPTION
        "Ethernet1 VLAN6 subnet mask"
    ::= { eth1VLAN6 4 }
    --1.3.6.1.4.1.3052.14.2.4.1.1.1.5.6.4

eth1VLAN6Router OBJECT-TYPE
    SYNTAX IpAddress
    MAX-ACCESS read-write
    STATUS current
    DESCRIPTION
        "Ethernet1 VLAN6 router"
    ::= { eth1VLAN6 5 }
    --1.3.6.1.4.1.3052.14.2.4.1.1.1.5.6.5

eth1MAC OBJECT-TYPE
    SYNTAX DisplayString
    MAX-ACCESS read-only
    STATUS current
    DESCRIPTION
        "Ethernet1 MAC"
    ::= { ethernet1 6 }
    --1.3.6.1.4.1.3052.14.2.4.1.1.1.6

eth1IPv6Mode OBJECT-TYPE
    SYNTAX DisplayString
    MAX-ACCESS read-write
    STATUS current
    DESCRIPTION
        "Controls IPv6 operation for this Ethernet interface."
    ::= { eth1IPv6 1 }
    --1.3.6.1.4.1.3052.14.2.4.1.1.1.7.1

eth1IPv6StaticAddress OBJECT-TYPE
    SYNTAX DisplayString
    MAX-ACCESS read-write
    STATUS current
    DESCRIPTION
        "he static IPv6 address to use for this interface when in
        operating in STATIC mode."
    ::= { eth1IPv6Static 1 }
    --1.3.6.1.4.1.3052.14.2.4.1.1.1.7.2.1

eth1IPv6StaticRouter OBJECT-TYPE
    SYNTAX DisplayString
    MAX-ACCESS read-write
    STATUS current
    DESCRIPTION
        "The IPv6 router to engage as the default router when this
        interface operates in STATIC mode."
    ::= { eth1IPv6Static 2 }
    --1.3.6.1.4.1.3052.14.2.4.1.1.1.7.2.1

eth1IPv6AutoAddress1 OBJECT-TYPE
    SYNTAX DisplayString
    MAX-ACCESS read-only
    STATUS current
    DESCRIPTION
        "One of the automatically-acquired IPv6 addresses."
    ::= { eth1IPv6Auto 1 }
    --1.3.6.1.4.1.3052.14.2.4.1.1.1.7.3.1

eth1IPv6AutoAddress2 OBJECT-TYPE
    SYNTAX DisplayString
    MAX-ACCESS read-only
    STATUS current
    DESCRIPTION
        "One of the automatically-acquired IPv6 addresses."
    ::= { eth1IPv6Auto 2 }
    --1.3.6.1.4.1.3052.14.2.4.1.1.1.7.3.2

eth1IPv6AutoAddress3 OBJECT-TYPE
    SYNTAX DisplayString
    MAX-ACCESS read-only
    STATUS current
    DESCRIPTION
        "One of the automatically-acquired IPv6 addresses."
    ::= { eth1IPv6Auto 3 }
    --1.3.6.1.4.1.3052.14.2.4.1.1.1.7.3.3

eth1IPv6AutoAddress4 OBJECT-TYPE
    SYNTAX DisplayString
    MAX-ACCESS read-only
    STATUS current
    DESCRIPTION
        "One of the automatically-acquired IPv6 addresses."
    ::= { eth1IPv6Auto 4 }
    --1.3.6.1.4.1.3052.14.2.4.1.1.1.7.3.4

eth1IPv6LinkLocalAddress OBJECT-TYPE
    SYNTAX DisplayString
    MAX-ACCESS read-only
    STATUS current
    DESCRIPTION
        "The link local IPv6 address for this interface. This is
        present when the IPv6 mode is not OFF."
    ::= { eth1IPv6 4 }
    --1.3.6.1.4.1.3052.14.2.4.1.1.1.7.4


eth2Mode OBJECT-TYPE
    SYNTAX DisplayString
    MAX-ACCESS read-only
    STATUS current
    DESCRIPTION
         "Mode of the Ethernet2 interface: STATIC,DHCP,VLAN"
    ::= { ethernet2 1 }
    --1.3.6.1.4.1.3052.14.2.4.1.1.2.1

eth2Address OBJECT-TYPE
    SYNTAX IpAddress
    MAX-ACCESS read-write
    STATUS current
    DESCRIPTION
        "Ethernet2 IP address"
    ::= { ethernet2 2 }
    --1.3.6.1.4.1.3052.14.2.4.1.1.2.2

eth2SubnetMask OBJECT-TYPE
    SYNTAX IpAddress
    MAX-ACCESS read-write
    STATUS current
    DESCRIPTION
        "Ethernet2 subnet mask"
    ::= { ethernet2 3 }
    --1.3.6.1.4.1.3052.14.2.4.1.1.2.3

eth2Router OBJECT-TYPE
    SYNTAX IpAddress
    MAX-ACCESS read-write
    STATUS current
    DESCRIPTION
        "Ethernet2 router"
    ::= { ethernet2 4 }
    --1.3.6.1.4.1.3052.14.2.4.1.1.2.4


-- Ethernet2 VLAN1

eth2VLAN1ID OBJECT-TYPE
    SYNTAX Integer32
    MAX-ACCESS read-write
    STATUS current
    DESCRIPTION
        "Ethernet2 VLAN1 ID"
    ::= { eth2VLAN1 1 }
    --1.3.6.1.4.1.3052.14.2.4.1.1.2.5.1.1

eth2VLAN1Priority OBJECT-TYPE
    SYNTAX Integer32
    MAX-ACCESS read-write
    STATUS current
    DESCRIPTION
        "Ethernet2 VLAN1 priority"
    ::= { eth2VLAN1 2 }
    --1.3.6.1.4.1.3052.14.2.4.1.1.2.5.1.2

eth2VLAN1Address OBJECT-TYPE
    SYNTAX IpAddress
    MAX-ACCESS read-write
    STATUS current
    DESCRIPTION
        "Ethernet2 VLAN1 IP address"
    ::= { eth2VLAN1 3 }
    --1.3.6.1.4.1.3052.14.2.4.1.1.2.5.1.3

eth2VLAN1SubnetMask OBJECT-TYPE
    SYNTAX IpAddress
    MAX-ACCESS read-write
    STATUS current
    DESCRIPTION
        "Ethernet2 VLAN1 subnet mask"
    ::= { eth2VLAN1 4 }
    --1.3.6.1.4.1.3052.14.2.4.1.1.2.5.1.4

eth2VLAN1Router OBJECT-TYPE
    SYNTAX IpAddress
    MAX-ACCESS read-write
    STATUS current
    DESCRIPTION
        "Ethernet2 VLAN1 router"
    ::= { eth2VLAN1 5 }
    --1.3.6.1.4.1.3052.14.2.4.1.1.2.5.1.5

-- Ethernet2 VLAN2

eth2VLAN2ID OBJECT-TYPE
    SYNTAX Integer32
    MAX-ACCESS read-write
    STATUS current
    DESCRIPTION
        "Ethernet2 VLAN2 ID"
    ::= { eth2VLAN2 1 }
    --1.3.6.1.4.1.3052.14.2.4.1.1.2.5.2.1

eth2VLAN2Priority OBJECT-TYPE
    SYNTAX Integer32
    MAX-ACCESS read-write
    STATUS current
    DESCRIPTION
        "Ethernet2 VLAN2 priority"
    ::= { eth2VLAN2 2 }
    --1.3.6.1.4.1.3052.14.2.4.1.1.2.5.2.2

eth2VLAN2Address OBJECT-TYPE
    SYNTAX IpAddress
    MAX-ACCESS read-write
    STATUS current
    DESCRIPTION
        "Ethernet2 VLAN2 IP address"
    ::= { eth2VLAN2 3 }
    --1.3.6.1.4.1.3052.14.2.4.1.1.2.5.2.3

eth2VLAN2SubnetMask OBJECT-TYPE
    SYNTAX IpAddress
    MAX-ACCESS read-write
    STATUS current
    DESCRIPTION
        "Ethernet2 VLAN2 subnet mask"
    ::= { eth2VLAN2 4 }
    --1.3.6.1.4.1.3052.14.2.4.1.1.2.5.2.4

eth2VLAN2Router OBJECT-TYPE
    SYNTAX IpAddress
    MAX-ACCESS read-write
    STATUS current
    DESCRIPTION
        "Ethernet2 VLAN2 router"
    ::= { eth2VLAN2 5 }
    --1.3.6.1.4.1.3052.14.2.4.1.1.2.5.2.5

-- Ethernet2 VLAN3

eth2VLAN3ID OBJECT-TYPE
    SYNTAX Integer32
    MAX-ACCESS read-write
    STATUS current
    DESCRIPTION
        "Ethernet2 VLAN3 ID"
    ::= { eth2VLAN3 1 }
    --1.3.6.1.4.1.3052.14.2.4.1.1.2.5.3.1

eth2VLAN3Priority OBJECT-TYPE
    SYNTAX Integer32
    MAX-ACCESS read-write
    STATUS current
    DESCRIPTION
        "Ethernet2 VLAN3 priority"
    ::= { eth2VLAN3 2 }
    --1.3.6.1.4.1.3052.14.2.4.1.1.2.5.3.2

eth2VLAN3Address OBJECT-TYPE
    SYNTAX IpAddress
    MAX-ACCESS read-write
    STATUS current
    DESCRIPTION
        "Ethernet2 VLAN3 IP address"
    ::= { eth2VLAN3 3 }
    --1.3.6.1.4.1.3052.14.2.4.1.1.2.5.3.3

eth2VLAN3SubnetMask OBJECT-TYPE
    SYNTAX IpAddress
    MAX-ACCESS read-write
    STATUS current
    DESCRIPTION
        "Ethernet2 VLAN3 subnet mask"
    ::= { eth2VLAN3 4 }
    --1.3.6.1.4.1.3052.14.2.4.1.1.2.5.3.4

eth2VLAN3Router OBJECT-TYPE
    SYNTAX IpAddress
    MAX-ACCESS read-write
    STATUS current
    DESCRIPTION
        "Ethernet2 VLAN3 router"
    ::= { eth2VLAN3 5 }
    --1.3.6.1.4.1.3052.14.2.4.1.1.2.5.3.5

-- Ethernet2 VLAN4

eth2VLAN4ID OBJECT-TYPE
    SYNTAX Integer32
    MAX-ACCESS read-write
    STATUS current
    DESCRIPTION
        "Ethernet2 VLAN4 ID"
    ::= { eth2VLAN4 1 }
    --1.3.6.1.4.1.3052.14.2.4.1.1.2.5.4.1

eth2VLAN4Priority OBJECT-TYPE
    SYNTAX Integer32
    MAX-ACCESS read-write
    STATUS current
    DESCRIPTION
        "Ethernet2 VLAN4 priority"
    ::= { eth2VLAN4 2 }
    --1.3.6.1.4.1.3052.14.2.4.1.1.2.5.4.2

eth2VLAN4Address OBJECT-TYPE
    SYNTAX IpAddress
    MAX-ACCESS read-write
    STATUS current
    DESCRIPTION
        "Ethernet2 VLAN4 IP address"
    ::= { eth2VLAN4 3 }
    --1.3.6.1.4.1.3052.14.2.4.1.1.2.5.4.3

eth2VLAN4SubnetMask OBJECT-TYPE
    SYNTAX IpAddress
    MAX-ACCESS read-write
    STATUS current
    DESCRIPTION
        "Ethernet2 VLAN4 subnet mask"
    ::= { eth2VLAN4 4 }
    --1.3.6.1.4.1.3052.14.2.4.1.1.2.5.4.4

eth2VLAN4Router OBJECT-TYPE
    SYNTAX IpAddress
    MAX-ACCESS read-write
    STATUS current
    DESCRIPTION
        "Ethernet2 VLAN4 router"
    ::= { eth2VLAN4 5 }
    --1.3.6.1.4.1.3052.14.2.4.1.1.2.5.4.5

-- Ethernet2 VLAN5

eth2VLAN5ID OBJECT-TYPE
    SYNTAX Integer32
    MAX-ACCESS read-write
    STATUS current
    DESCRIPTION
        "Ethernet2 VLAN5 ID"
    ::= { eth2VLAN5 1 }
    --1.3.6.1.4.1.3052.14.2.4.1.1.2.5.5.1

eth2VLAN5Priority OBJECT-TYPE
    SYNTAX Integer32
    MAX-ACCESS read-write
    STATUS current
    DESCRIPTION
        "Ethernet2 VLAN5 priority"
    ::= { eth2VLAN5 2 }
    --1.3.6.1.4.1.3052.14.2.4.1.1.2.5.5.2

eth2VLAN5Address OBJECT-TYPE
    SYNTAX IpAddress
    MAX-ACCESS read-write
    STATUS current
    DESCRIPTION
        "Ethernet2 VLAN5 IP address"
    ::= { eth2VLAN5 3 }
    --1.3.6.1.4.1.3052.14.2.4.1.1.2.5.5.3

eth2VLAN5SubnetMask OBJECT-TYPE
    SYNTAX IpAddress
    MAX-ACCESS read-write
    STATUS current
    DESCRIPTION
        "Ethernet2 VLAN5 subnet mask"
    ::= { eth2VLAN5 4 }
    --1.3.6.1.4.1.3052.14.2.4.1.1.2.5.5.4

eth2VLAN5Router OBJECT-TYPE
    SYNTAX IpAddress
    MAX-ACCESS read-write
    STATUS current
    DESCRIPTION
        "Ethernet2 VLAN5 router"
    ::= { eth2VLAN5 5 }
    --1.3.6.1.4.1.3052.14.2.4.1.1.2.5.5.5

-- Ethernet2 VLAN6

eth2VLAN6ID OBJECT-TYPE
    SYNTAX Integer32
    MAX-ACCESS read-write
    STATUS current
    DESCRIPTION
        "Ethernet2 VLAN6 ID"
    ::= { eth2VLAN6 1 }
    --1.3.6.1.4.1.3052.14.2.4.1.1.2.5.6.1

eth2VLAN6Priority OBJECT-TYPE
    SYNTAX Integer32
    MAX-ACCESS read-write
    STATUS current
    DESCRIPTION
        "Ethernet2 VLAN6 priority"
    ::= { eth2VLAN6 2 }
    --1.3.6.1.4.1.3052.14.2.4.1.1.2.5.6.2

eth2VLAN6Address OBJECT-TYPE
    SYNTAX IpAddress
    MAX-ACCESS read-write
    STATUS current
    DESCRIPTION
        "Ethernet2 VLAN6 IP address"
    ::= { eth2VLAN6 3 }
    --1.3.6.1.4.1.3052.14.2.4.1.1.2.5.6.3

eth2VLAN6SubnetMask OBJECT-TYPE
    SYNTAX IpAddress
    MAX-ACCESS read-write
    STATUS current
    DESCRIPTION
        "Ethernet2 VLAN6 subnet mask"
    ::= { eth2VLAN6 4 }
    --1.3.6.1.4.1.3052.14.2.4.1.1.2.5.6.4

eth2VLAN6Router OBJECT-TYPE
    SYNTAX IpAddress
    MAX-ACCESS read-write
    STATUS current
    DESCRIPTION
        "Ethernet2 VLAN6 router"
    ::= { eth2VLAN6 5 }
    --1.3.6.1.4.1.3052.14.2.4.1.1.2.5.6.5

eth2MAC OBJECT-TYPE
    SYNTAX DisplayString
    MAX-ACCESS read-only
    STATUS current
    DESCRIPTION
        "Ethernet2 MAC"
    ::= { ethernet2 6 }
    --1.3.6.1.4.1.3052.14.2.4.1.1.2.6

eth2IPv6Mode OBJECT-TYPE
    SYNTAX DisplayString
    MAX-ACCESS read-write
    STATUS current
    DESCRIPTION
        "Controls IPv6 operation for this Ethernet interface."
    ::= { eth2IPv6 1 }
    --1.3.6.1.4.1.3052.14.2.4.1.1.2.7.1

eth2IPv6StaticAddress OBJECT-TYPE
    SYNTAX DisplayString
    MAX-ACCESS read-write
    STATUS current
    DESCRIPTION
        "he static IPv6 address to use for this interface when in
        operating in STATIC mode."
    ::= { eth2IPv6Static 1 }
    --1.3.6.1.4.1.3052.14.2.4.1.1.2.7.2.1

eth2IPv6StaticRouter OBJECT-TYPE
    SYNTAX DisplayString
    MAX-ACCESS read-write
    STATUS current
    DESCRIPTION
        "The IPv6 router to engage as the default router when this
        interface operates in STATIC mode."
    ::= { eth2IPv6Static 2 }
    --1.3.6.1.4.1.3052.14.2.4.1.1.2.7.2.1

eth2IPv6AutoAddress1 OBJECT-TYPE
    SYNTAX DisplayString
    MAX-ACCESS read-only
    STATUS current
    DESCRIPTION
        "One of the automatically-acquired IPv6 addresses."
    ::= { eth2IPv6Auto 1 }
    --1.3.6.1.4.1.3052.14.2.4.1.1.2.7.3.1

eth2IPv6AutoAddress2 OBJECT-TYPE
    SYNTAX DisplayString
    MAX-ACCESS read-only
    STATUS current
    DESCRIPTION
        "One of the automatically-acquired IPv6 addresses."
    ::= { eth2IPv6Auto 2 }
    --1.3.6.1.4.1.3052.14.2.4.1.1.2.7.3.2

eth2IPv6AutoAddress3 OBJECT-TYPE
    SYNTAX DisplayString
    MAX-ACCESS read-only
    STATUS current
    DESCRIPTION
        "One of the automatically-acquired IPv6 addresses."
    ::= { eth2IPv6Auto 3 }
    --1.3.6.1.4.1.3052.14.2.4.1.1.2.7.3.3

eth2IPv6AutoAddress4 OBJECT-TYPE
    SYNTAX DisplayString
    MAX-ACCESS read-only
    STATUS current
    DESCRIPTION
        "One of the automatically-acquired IPv6 addresses."
    ::= { eth2IPv6Auto 4 }
    --1.3.6.1.4.1.3052.14.2.4.1.1.2.7.3.4

eth2IPv6LinkLocalAddress OBJECT-TYPE
    SYNTAX DisplayString
    MAX-ACCESS read-only
    STATUS current
    DESCRIPTION
        "The link local IPv6 address for this interface. This is
        present when the IPv6 mode is not OFF."
    ::= { eth2IPv6 4 }
    --1.3.6.1.4.1.3052.14.2.4.1.1.2.7.4


defaultRouter OBJECT-TYPE
    SYNTAX DisplayString
    MAX-ACCESS read-write
    STATUS current
    DESCRIPTION
        "The default router/gateway"
    ::= { network 2 }
    --1.3.6.1.4.1.3052.14.2.4.2

-- DNS

dnsTable OBJECT-TYPE
    SYNTAX SEQUENCE OF DNSConfig
    MAX-ACCESS not-accessible
    STATUS current
    DESCRIPTION
        "DNS server address table"
    ::= { network 3 }
    --1.3.6.1.4.1.3052.14.2.4.3

dnsEntry OBJECT-TYPE
    SYNTAX DNSConfig
    MAX-ACCESS not-accessible
    STATUS current
    DESCRIPTION
        "DNS server address entry"
    INDEX { dnsIndex }
    ::= { dnsTable 1 }
    --1.3.6.1.4.1.3052.14.2.4.3.1

dnsIndex OBJECT-TYPE
    SYNTAX Integer32 (1..2)
    MAX-ACCESS read-only
    STATUS current
    DESCRIPTION
        "Index for DNS server address"
    ::= { dnsEntry 1 }
    --1.3.6.1.4.1.3052.14.2.4.3.1.1

dnsAddress OBJECT-TYPE
    SYNTAX IpAddress
    MAX-ACCESS read-write
    STATUS current
    DESCRIPTION
        "DNS server address"
    ::= { dnsEntry 2 }
    --1.3.6.1.4.1.3052.14.2.4.3.1.2

hostname OBJECT-TYPE
    SYNTAX DisplayString
    MAX-ACCESS read-write
    STATUS current
    DESCRIPTION
        "The hostname of the unit"
    ::= { network 4 }
    --1.3.6.1.4.1.3052.14.2.4.4

hostTable OBJECT-TYPE
    SYNTAX SEQUENCE OF HostConfig
    MAX-ACCESS not-accessible
    STATUS current
    DESCRIPTION
        "Static host table"
    ::= { network 5 }
    --1.3.6.1.4.1.3052.14.2.4.5

hostEntry OBJECT-TYPE
    SYNTAX HostConfig
    MAX-ACCESS not-accessible
    STATUS current
    DESCRIPTION
        "Static host entry"
    INDEX { hostIndex }
    ::= { hostTable 1 }
    --1.3.6.1.4.1.3052.14.2.4.5.1

hostIndex OBJECT-TYPE
    SYNTAX Integer32 (1..2)
    MAX-ACCESS read-only
    STATUS current
    DESCRIPTION
        "Index for static host"
    ::= { hostEntry 1 }
    --1.3.6.1.4.1.3052.14.2.4.5.1.1

hostDeclaration OBJECT-TYPE
    SYNTAX DisplayString
    MAX-ACCESS read-write
    STATUS current
    DESCRIPTION
        "Static host declaration string (i.e. 'address hostname')"
    ::= { hostEntry 2 }
    --1.3.6.1.4.1.3052.14.2.4.5.1.2

-- Network Command Processor

ncpDuplex OBJECT-TYPE
    SYNTAX Integer32
    MAX-ACCESS read-write
    STATUS current
    DESCRIPTION
        "For network command processor: 1=Input characters are echoed; 0=no echo."
    ::= { network 6 }
    --1.3.6.1.4.1.3052.14.2.4.6

ncpTimeout OBJECT-TYPE
    SYNTAX Integer32
    MAX-ACCESS read-write
    STATUS current
    DESCRIPTION
        "Network command processor inactivity timeout"
    ::= { network 7 }
    --1.3.6.1.4.1.3052.14.2.4.7

-- SNMP

snmpAgentEnable OBJECT-TYPE
    SYNTAX DisplayString
    MAX-ACCESS read-write
    STATUS current
    DESCRIPTION
        "ON/OFF for snmp agent"
    ::= { snmp 1 }
    --1.3.6.1.4.1.3052.14.2.4.8.1

snmpNotificationCaptureEnable OBJECT-TYPE
    SYNTAX DisplayString
    MAX-ACCESS read-write
    STATUS current
    DESCRIPTION
        "ON/OFF unit receives and stores SNMP traps/informs"
    ::= { snmp 5 }
    --1.3.6.1.4.1.3052.14.2.4.8.5

snmpNotificationCaptureFile OBJECT-TYPE
    SYNTAX DisplayString
    MAX-ACCESS read-write
    STATUS current
    DESCRIPTION
        "File to which unit stores received SNMP traps/informs"
    ::= { snmp 6 }
    --1.3.6.1.4.1.3052.14.2.4.8.6

snmpNtfnAttempts OBJECT-TYPE
    SYNTAX Integer32
    MAX-ACCESS read-write
    STATUS current
    DESCRIPTION
        "Maximum of times the unit attempts to send a notification
        (trap/inform) in 1 cycle"
    ::= { snmpNotificationTx 1 }
    --1.3.6.1.4.1.3052.14.2.4.8.7.1

snmpNtfnTimeout OBJECT-TYPE
    SYNTAX Integer32
    MAX-ACCESS read-write
    STATUS current
    DESCRIPTION
        "Number of seconds between retries of sending a notification"
    ::= { snmpNotificationTx 2 }
    --1.3.6.1.4.1.3052.14.2.4.8.7.2

snmpNtfnCycles OBJECT-TYPE
    SYNTAX Integer32
    MAX-ACCESS read-write
    STATUS current
    DESCRIPTION
        "Number of times the unit attempts a group of attempts to send
        a notification (a cycle)"
    ::= { snmpNotificationTx 3 }
    --1.3.6.1.4.1.3052.14.2.4.8.7.3

snmpNtfnSnooze OBJECT-TYPE
    SYNTAX Integer32
    MAX-ACCESS read-write
    STATUS current
    DESCRIPTION
        "Minutes between cycles"
    ::= { snmpNotificationTx 4 }
    --1.3.6.1.4.1.3052.14.2.4.8.7.4


-- SNMP Poll

snmpPMode OBJECT-TYPE
    SYNTAX DisplayString
    MAX-ACCESS read-write
    STATUS current
    DESCRIPTION
        "Mode of poll operation: OFF, POLL ONLY (just make the results
        available to view), or POLL BUFFER (store the results)."
    ::= { snmpPoll 1 }
    --1.3.6.1.4.1.3052.14.2.4.8.9.1

snmpPBufferFile OBJECT-TYPE
    SYNTAX DisplayString
    MAX-ACCESS read-write
    STATUS current
    DESCRIPTION
        "CRDB file in which data is stored."
    ::= { snmpPoll 2 }
    --1.3.6.1.4.1.3052.14.2.4.8.9.2

snmpPBufferAllPeriod OBJECT-TYPE
    SYNTAX Integer32
    MAX-ACCESS read-write
    STATUS current
    DESCRIPTION
        "Period (in seconds) that, if non-zero, all results are buffered
        in the CRDB regardless of the threshold."
    ::= { snmpPoll 3 }
    --1.3.6.1.4.1.3052.14.2.4.8.9.3

snmpPRequestTable OBJECT-TYPE
    SYNTAX SEQUENCE OF SNMPPollRequestConfig
    MAX-ACCESS not-accessible
    STATUS current
    DESCRIPTION
        "Table of SNMP Poll requests."
    ::= { snmpPoll 4 }
    --1.3.6.1.4.1.3052.14.2.4.8.9.4

snmpPRequestEntry OBJECT-TYPE
    SYNTAX SNMPPollRequestConfig
    MAX-ACCESS not-accessible
    STATUS current
    DESCRIPTION
        "Entry for table pf SNMP Poll requests."
    INDEX { snmpPRequestIndex }
    ::= { snmpPRequestTable 1 }
    --1.3.6.1.4.1.3052.14.2.4.8.9.4.1

snmpPRequestIndex OBJECT-TYPE
    SYNTAX Integer32 (1..64)
    MAX-ACCESS read-only
    STATUS current
    DESCRIPTION
        "Index for table of SNMP Poll requests."
    ::= { snmpPRequestEntry 1 }
    --1.3.6.1.4.1.3052.14.2.4.8.9.4.1.1

snmpPRequestDescription OBJECT-TYPE
    SYNTAX DisplayString
    MAX-ACCESS read-write
    STATUS current
    DESCRIPTION
        "A description for this single telemetry request; no functional effect."
    ::= { snmpPRequestEntry 2 }
    --1.3.6.1.4.1.3052.14.2.4.8.9.4.1.2

snmpPRequestAgent OBJECT-TYPE
    SYNTAX DisplayString
    MAX-ACCESS read-write
    STATUS current
    DESCRIPTION
        "SNMP Agent IP address or hostname for this single telemetry request."
    ::= { snmpPRequestEntry 3 }
    --1.3.6.1.4.1.3052.14.2.4.8.9.4.1.3

snmpPRequestReadcom OBJECT-TYPE
    SYNTAX DisplayString
    MAX-ACCESS read-write
    STATUS current
    DESCRIPTION
        "SNMP read community for this single telemetry request."
    ::= { snmpPRequestEntry 4 }
    --1.3.6.1.4.1.3052.14.2.4.8.9.4.1.4

snmpPRequestOID OBJECT-TYPE
    SYNTAX DisplayString
    MAX-ACCESS read-write
    STATUS current
    DESCRIPTION
        "SNMP object identifier for this single telemetry request."
    ::= { snmpPRequestEntry 5 }
    --1.3.6.1.4.1.3052.14.2.4.8.9.4.1.5

snmpPRequestPeriod OBJECT-TYPE
    SYNTAX Integer32 (1..255)
    MAX-ACCESS read-write
    STATUS current
    DESCRIPTION
        "How many seconds between periodic SNMP polls of this
        single telemetry request."
    ::= { snmpPRequestEntry 6 }
    --1.3.6.1.4.1.3052.14.2.4.8.9.4.1.6

snmpPRequestID OBJECT-TYPE
    SYNTAX DisplayString
    MAX-ACCESS read-write
    STATUS current
    DESCRIPTION
        "A textual field that is part of the record containing
        the telemetry result."
    ::= { snmpPRequestEntry 7 }
    --1.3.6.1.4.1.3052.14.2.4.8.9.4.1.7

snmpPRequestThreshold OBJECT-TYPE
    SYNTAX DisplayString
    MAX-ACCESS read-write
    STATUS current
    DESCRIPTION
        "Controls when new data is stored upon a successful
        telemetry request."
    ::= { snmpPRequestEntry 8 }
    --1.3.6.1.4.1.3052.14.2.4.8.9.4.1.8

snmpPRequestResultStatus OBJECT-TYPE
    SYNTAX DisplayString
    MAX-ACCESS read-only
    STATUS current
    DESCRIPTION
        "Status of the last attempt for this telemetry request."
    ::= { snmpPRequestEntry 10 }
    --1.3.6.1.4.1.3052.14.2.4.8.9.4.1.10

snmpPRequestResultValue OBJECT-TYPE
    SYNTAX DisplayString
    MAX-ACCESS read-only
    STATUS current
    DESCRIPTION
        "The telemetry value if the last request was successful."
    ::= { snmpPRequestEntry 11 }
    --1.3.6.1.4.1.3052.14.2.4.8.9.4.1.11

snmpPRequestResultTime OBJECT-TYPE
    SYNTAX DisplayString
    MAX-ACCESS read-only
    STATUS current
    DESCRIPTION
        "The timestamp of the last telemetry request."
    ::= { snmpPRequestEntry 12 }
    --1.3.6.1.4.1.3052.14.2.4.8.9.4.1.12

snmpPRequestResultType OBJECT-TYPE
    SYNTAX DisplayString
    MAX-ACCESS read-only
    STATUS current
    DESCRIPTION
        "The type of the telemetry as reported by the agent."
    ::= { snmpPRequestEntry 13 }
    --1.3.6.1.4.1.3052.14.2.4.8.9.4.1.13


-- FTP

ftpPushEnable OBJECT-TYPE
    SYNTAX DisplayString
    MAX-ACCESS read-write
    STATUS current
    DESCRIPTION
        "Enable FTP push for REGULAR (protocol: FTP) or SECURE (protocol:
        SFTP) operation, or disable it (OFF)"
    ::= { ftpPush 1 }
    --1.3.6.1.4.1.3052.14.2.4.9.1

ftpPushServer OBJECT-TYPE
    SYNTAX DisplayString
    MAX-ACCESS read-write
    STATUS current
    DESCRIPTION
        "FTP server to which data should be pushed"
    ::= { ftpPush 2 }
    --1.3.6.1.4.1.3052.14.2.4.9.2

ftpPushAccount OBJECT-TYPE
    SYNTAX DisplayString
    MAX-ACCESS read-write
    STATUS current
    DESCRIPTION
        "FTP push account"
    ::= { ftpPush 5 }
    --1.3.6.1.4.1.3052.14.2.4.9.5

ftpPushDirectory OBJECT-TYPE
    SYNTAX DisplayString
    MAX-ACCESS read-write
    STATUS current
    DESCRIPTION
        "FTP push directory"
    ::= { ftpPush 6 }
    --1.3.6.1.4.1.3052.14.2.4.9.6

ftpPushperiod OBJECT-TYPE
    SYNTAX Integer32
    MAX-ACCESS read-write
    STATUS current
    DESCRIPTION
        "Minutes between pushes"
    ::= { ftpPush 7 }
    --1.3.6.1.4.1.3052.14.2.4.9.7

ftpPushPushFileTable OBJECT-TYPE
    SYNTAX SEQUENCE OF FTPPushPushFileConfig
    MAX-ACCESS not-accessible
    STATUS current
    DESCRIPTION
        "Table of files to push"
    ::= { ftpPush 8 }
    --1.3.6.1.4.1.3052.14.2.4.9.8

ftpPushPushFileEntry OBJECT-TYPE
    SYNTAX FTPPushPushFileConfig
    MAX-ACCESS not-accessible
    STATUS current
    DESCRIPTION
        "Entry for table of files to push"
    INDEX { ftpPushPushFileIndex }
    ::= { ftpPushPushFileTable 1 }
    --1.3.6.1.4.1.3052.14.2.4.9.8.1

ftpPushPushFileIndex OBJECT-TYPE
    SYNTAX Integer32 (1..16)
    MAX-ACCESS read-only
    STATUS current
    DESCRIPTION
        "Index for table of files to push"
    ::= { ftpPushPushFileEntry 1 }
    --1.3.6.1.4.1.3052.14.2.4.9.8.1.1

ftpPushPushFile OBJECT-TYPE
    SYNTAX DisplayString
    MAX-ACCESS read-write
    STATUS current
    DESCRIPTION
        "ON/OFF push this local FILEx"
    ::= { ftpPushPushFileEntry 2 }
    --1.3.6.1.4.1.3052.14.2.4.9.8.1.2

ftpPushPushAudit OBJECT-TYPE
    SYNTAX DisplayString
    MAX-ACCESS read-write
    STATUS current
    DESCRIPTION
        "ON/OFF push the audit log"
    ::= { ftpPush 9 }
    --1.3.6.1.4.1.3052.14.2.4.9.9

ftpPushPushAlarms OBJECT-TYPE
    SYNTAX DisplayString
    MAX-ACCESS read-write
    STATUS current
    DESCRIPTION
        "ON/OFF push the alarms/events file"
    ::= { ftpPush 10 }
    --1.3.6.1.4.1.3052.14.2.4.9.10

ftpPushRemoteFileTable OBJECT-TYPE
    SYNTAX SEQUENCE OF FTPPushRemoteFileConfig
    MAX-ACCESS not-accessible
    STATUS current
    DESCRIPTION
        "Table of remote names of files to push"
    ::= { ftpPush 11 }
    --1.3.6.1.4.1.3052.14.2.4.9.11

ftpPushRemoteFileEntry OBJECT-TYPE
    SYNTAX FTPPushRemoteFileConfig
    MAX-ACCESS not-accessible
    STATUS current
    DESCRIPTION
        "Entry for table of remote names of files to push"
    INDEX { ftpPushRemoteFileIndex }
    ::= { ftpPushRemoteFileTable 1 }
    --1.3.6.1.4.1.3052.14.2.4.9.11.1

ftpPushRemoteFileIndex OBJECT-TYPE
    SYNTAX Integer32 (1..16)
    MAX-ACCESS read-only
    STATUS current
    DESCRIPTION
        "Index for table of remote names of files to push"
    ::= { ftpPushRemoteFileEntry 1 }
    --1.3.6.1.4.1.3052.14.2.4.9.11.1

ftpPushRemoteFileName OBJECT-TYPE
    SYNTAX DisplayString
    MAX-ACCESS read-write
    STATUS current
    DESCRIPTION
        "remote name of pushed FILEx (name on server)"
    ::= { ftpPushRemoteFileEntry 2 }
    --1.3.6.1.4.1.3052.14.2.4.9.11.2

ftpPushRemoteAlarmName OBJECT-TYPE
    SYNTAX DisplayString
    MAX-ACCESS read-write
    STATUS current
    DESCRIPTION
        "Filename on server for alarms"
    ::= { ftpPush 12 }
    --1.3.6.1.4.1.3052.14.2.4.9.12

ftpPushPassive OBJECT-TYPE
    SYNTAX DisplayString
    MAX-ACCESS read-write
    STATUS current
    DESCRIPTION
        "ON/OFF use ftp passive mode"
    ::= { ftpPush 13 }
    --1.3.6.1.4.1.3052.14.2.4.9.13

ftpPushIncludeDate OBJECT-TYPE
    SYNTAX DisplayString
    MAX-ACCESS read-write
    STATUS current
    DESCRIPTION
        "ON/OFF include the date in the name of the pushed file"
    ::= { ftpPush 14 }
    --1.3.6.1.4.1.3052.14.2.4.9.14

ftpPushIncludeTime OBJECT-TYPE
    SYNTAX DisplayString
    MAX-ACCESS read-write
    STATUS current
    DESCRIPTION
        "ON/OFF include the time in the name of the pushed file"
    ::= { ftpPush 15 }
    --1.3.6.1.4.1.3052.14.2.4.9.15

ftpPushIncludeSeq OBJECT-TYPE
    SYNTAX DisplayString
    MAX-ACCESS read-write
    STATUS current
    DESCRIPTION
        "ON/OFF include a sequence number in the name of the pushed file"
    ::= { ftpPush 16 }
    --1.3.6.1.4.1.3052.14.2.4.9.16

ftpPushPermissions OBJECT-TYPE
    SYNTAX DisplayString
    MAX-ACCESS read-write
    STATUS current
    DESCRIPTION
        "Unix permissions to apply to pushed files (octal notation)."
    ::= { ftpPush 17 }
    --1.3.6.1.4.1.3052.14.2.4.9.17


pppDialEnable OBJECT-TYPE
    SYNTAX DisplayString
    MAX-ACCESS read-write
    STATUS current
    DESCRIPTION
        "ON/OFF PPP dialout enabled"
    ::= { pppDial 1 }
    --1.3.6.1.4.1.3052.14.2.4.10.1.1

pppDialNumber OBJECT-TYPE
    SYNTAX DisplayString
    MAX-ACCESS read-write
    STATUS current
    DESCRIPTION
        "phone number to dial"
    ::= { pppDial 2 }
    --1.3.6.1.4.1.3052.14.2.4.10.1.2

pppDialIdleTimeout OBJECT-TYPE
    SYNTAX Integer32
    MAX-ACCESS read-write
    STATUS current
    DESCRIPTION
        "Seconds of inactivity after which the unit disconnects"
    ::= { pppDial 5 }
    --1.3.6.1.4.1.3052.14.2.4.10.1.5

pppDialRetries OBJECT-TYPE
    SYNTAX Integer32
    MAX-ACCESS read-write
    STATUS current
    DESCRIPTION
        "Number of dialing retries for PPP"
    ::= { pppDial 6 }
    --1.3.6.1.4.1.3052.14.2.4.10.1.6

pppDialCDTimeout OBJECT-TYPE
    SYNTAX Integer32
    MAX-ACCESS read-write
    STATUS current
    DESCRIPTION
        "Number of seconds to wait after dialing for CD before
        giving up"
    ::= { pppDial 7 }
    --1.3.6.1.4.1.3052.14.2.4.10.1.7

pppDialLoginTimeout OBJECT-TYPE
    SYNTAX Integer32
    MAX-ACCESS read-write
    STATUS current
    DESCRIPTION
        "Seconds to wait to negotiate PPP after connecting"
    ::= { pppDial 8 }
    --1.3.6.1.4.1.3052.14.2.4.10.1.8

pppDialMdmInit OBJECT-TYPE
    SYNTAX DisplayString
    MAX-ACCESS read-write
    STATUS current
    DESCRIPTION
        "Modem init string to use when dialing PPP"
    ::= { pppDial 9 }
    --1.3.6.1.4.1.3052.14.2.4.10.1.9

pppDialSuggestIP OBJECT-TYPE
    SYNTAX IpAddress
    MAX-ACCESS read-write
    STATUS current
    DESCRIPTION
        "IP address to suggest as the unit's end (local end) of the
        PPP link"
    ::= { pppDial 10 }
    --1.3.6.1.4.1.3052.14.2.4.10.1.10

pppDialPlainLogin OBJECT-TYPE
    SYNTAX DisplayString
    MAX-ACCESS read-write
    STATUS current
    DESCRIPTION
        "ON/OFF look for login/password prompt before negotiating
        PPP"
    ::= { pppDial 11 }
    --1.3.6.1.4.1.3052.14.2.4.10.1.11

pppHostEnable OBJECT-TYPE
    SYNTAX DisplayString
    MAX-ACCESS read-write
    STATUS current
    DESCRIPTION
        "ON/OFF Unit accepts PPP negotiation"
    ::= { pppHost 1 }
    --1.3.6.1.4.1.3052.14.2.4.10.2.1

pppHostIdleTimeout OBJECT-TYPE
    SYNTAX Integer32
    MAX-ACCESS read-write
    STATUS current
    DESCRIPTION
        "Seconds of inactivity after which PPP-hosted link will
        terminate"
    ::= { pppHost 2 }
    --1.3.6.1.4.1.3052.14.2.4.10.2.2

pppHostLocalIP OBJECT-TYPE
    SYNTAX IpAddress
    MAX-ACCESS read-write
    STATUS current
    DESCRIPTION
        "Local IP address to negotiate"
    ::= { pppHost 3 }
    --1.3.6.1.4.1.3052.14.2.4.10.2.3

pppHostRemoteIP OBJECT-TYPE
    SYNTAX IpAddress
    MAX-ACCESS read-write
    STATUS current
    DESCRIPTION
        "Remote IP address to hand out to PPP peer"
    ::= { pppHost 4 }
    --1.3.6.1.4.1.3052.14.2.4.10.2.4

-- Routing

pppRoutingEnable OBJECT-TYPE
    SYNTAX DisplayString
    MAX-ACCESS read-write
    STATUS current
    DESCRIPTION
        "ON/OFF unit routes IP traffic from PPP/Wireless to Ethernet"
    ::= { routing 1 }
    --1.3.6.1.4.1.3052.14.2.4.11.1

ethRoutingEnable OBJECT-TYPE
    SYNTAX DisplayString
    MAX-ACCESS read-write
    STATUS current
    DESCRIPTION
        "ON/OFF unit routes IP traffic from Ethernet to PPP/Wireless"
    ::= { routing 2 }
    --1.3.6.1.4.1.3052.14.2.4.11.2

ethRoutingNATEnable OBJECT-TYPE
    SYNTAX DisplayString
    MAX-ACCESS read-write
    STATUS current
    DESCRIPTION
        "ON/OFF unit applies NAT on routed IP frames egressing the
        unit on its PPP interface"
    ::= { routing 3 }
    --1.3.6.1.4.1.3052.14.2.4.11.3

routingInterface OBJECT-TYPE
    SYNTAX DisplayString
    MAX-ACCESS read-write
    STATUS current
    DESCRIPTION
        "When Ethernet routing is enabled (routing.1), this is the
        Ethernet interface to which IP frames received on PPP are
        routed"
    ::= { routing 4 }
    --1.3.6.1.4.1.3052.14.2.4.11.4

eth2WanRoutingEnable OBJECT-TYPE
    SYNTAX DisplayString
    MAX-ACCESS read-write
    STATUS current
    DESCRIPTION
        "Make ETH2 operate as a WAN port to route outbound traffic
        arriving on ETH1."
    ::= { routing 5 }
    --1.3.6.1.4.1.3052.14.2.4.11.5

-- IP Restrictions

ipRestrictionTable OBJECT-TYPE
    SYNTAX SEQUENCE OF IPRestrictionConfig
    MAX-ACCESS not-accessible
    STATUS current
    DESCRIPTION
        "Table of IP restrictions"
    ::= { ipRestriction 1 }
    --1.3.6.1.4.1.3052.14.2.4.12.1.1

ipRestrictionEntry OBJECT-TYPE
    SYNTAX IPRestrictionConfig
    MAX-ACCESS not-accessible
    STATUS current
    DESCRIPTION
        "Entry for table of IP restrictions"
    INDEX { ipRestrictionIndex }
    ::= { ipRestrictionTable 1 }
    --1.3.6.1.4.1.3052.14.2.4.12.1.1

ipRestrictionIndex OBJECT-TYPE
    SYNTAX Integer32 (1..8)
    MAX-ACCESS read-only
    STATUS current
    DESCRIPTION
        "Index for table of IP restrictions"
    ::= { ipRestrictionEntry 1 }
    --1.3.6.1.4.1.3052.14.2.4.12.1.1.1.1

ipRestrictionEnable OBJECT-TYPE
    SYNTAX DisplayString
    MAX-ACCESS read-write
    STATUS current
    DESCRIPTION
        "ON/OFF enable this IP restriction"
    ::= { ipRestrictionEntry 2 }
    --1.3.6.1.4.1.3052.14.2.4.12.1.1.1.2

ipRestrictionMask OBJECT-TYPE
    SYNTAX DisplayString
    MAX-ACCESS read-write
    STATUS current
    DESCRIPTION
        "IP restriction mask"
    ::= { ipRestrictionEntry 3 }
    --1.3.6.1.4.1.3052.14.2.4.12.1.1.1.3


-- RTS


rtsFileTable OBJECT-TYPE
    SYNTAX SEQUENCE OF RTSFileConfig
    MAX-ACCESS not-accessible
    STATUS current
    DESCRIPTION
        "Table of RTS files"
    ::= { rts 1 }
    --1.3.6.1.4.1.3052.14.2.4.13.1

rtsFileEntry OBJECT-TYPE
    SYNTAX RTSFileConfig
    MAX-ACCESS not-accessible
    STATUS current
    DESCRIPTION
        "Entry for table of RTS files"
    INDEX { rtsFileIndex }
    ::= { rtsFileTable 1 }
    --1.3.6.1.4.1.3052.14.2.4.13.1

rtsFileIndex OBJECT-TYPE
    SYNTAX Integer32 (1..16)
    MAX-ACCESS read-only
    STATUS current
    DESCRIPTION
        "Index for table of RTS files"
    ::= { rtsFileEntry 1 }
    --1.3.6.1.4.1.3052.14.2.4.13.1.1.1

rtsFileMode OBJECT-TYPE
    SYNTAX DisplayString
    MAX-ACCESS read-write
    STATUS current
    DESCRIPTION
        "RTS mode (OFF,LISTEN,PUSH) for FILEx"
    ::= { rtsFileEntry 2 }
    --1.3.6.1.4.1.3052.14.2.4.13.1.1.2

rtsFileShowAnswer OBJECT-TYPE
    SYNTAX DisplayString
    MAX-ACCESS read-write
    STATUS current
    DESCRIPTION
        "Show answer string upon RTS connect for FILEx"
    ::= { rtsFileEntry 3 }
    --1.3.6.1.4.1.3052.14.2.4.13.1.1.3

rtsFileReqXON OBJECT-TYPE
    SYNTAX DisplayString
    MAX-ACCESS read-write
    STATUS current
    DESCRIPTION
        "ON/OFF require XON to start flow for FILEx"
    ::= { rtsFileEntry 4 }
    --1.3.6.1.4.1.3052.14.2.4.13.1.1.4

rtsFileTimeout OBJECT-TYPE
    SYNTAX Integer32
    MAX-ACCESS read-write
    STATUS current
    DESCRIPTION
        "Idle connection close timer (0 means no timeout) for FILEx"
    ::= { rtsFileEntry 5 }
    --1.3.6.1.4.1.3052.14.2.4.13.1.1.5

rtsFileEmptyClose OBJECT-TYPE
    SYNTAX DisplayString
    MAX-ACCESS read-write
    STATUS current
    DESCRIPTION
        "ON/OFF close the socket when FILEx is empty"
    ::= { rtsFileEntry 6 }
    --1.3.6.1.4.1.3052.14.2.4.13.1.1.6

rtsFilePushHost OBJECT-TYPE
    SYNTAX DisplayString
    MAX-ACCESS read-write
    STATUS current
    DESCRIPTION
        "Host to which FILEx should be pushed via RTS"
    ::= { rtsFileEntry 7 }
    --1.3.6.1.4.1.3052.14.2.4.13.1.1.7

rtsFilePushPort OBJECT-TYPE
    SYNTAX Integer32
    MAX-ACCESS read-write
    STATUS current
    DESCRIPTION
        "TCP port to which FILEx should be pushed via RTS"
    ::= { rtsFileEntry 8 }
    --1.3.6.1.4.1.3052.14.2.4.13.1.1.8

rtsFilePushRetryTimer OBJECT-TYPE
    SYNTAX Integer32
    MAX-ACCESS read-write
    STATUS current
    DESCRIPTION
        "Retry timer (seconds) for retrying failed RTS push connect
        attempts"
    ::= { rtsFileEntry 9 }
    --1.3.6.1.4.1.3052.14.2.4.13.1.1.9

-- RTS Alarms

rtsAlarmsMode OBJECT-TYPE
    SYNTAX DisplayString
    MAX-ACCESS read-write
    STATUS current
    DESCRIPTION
        "RTS mode (OFF,LISTEN,PUSH) for alarms file"
    ::= { rtsAlarms 1 }
    --1.3.6.1.4.1.3052.14.2.4.13.2.1

rtsAlarmsShowAnswer OBJECT-TYPE
    SYNTAX DisplayString
    MAX-ACCESS read-write
    STATUS current
    DESCRIPTION
        "Show answer string upon RTS connect for alarms file"
    ::= { rtsAlarms 2 }
    --1.3.6.1.4.1.3052.14.2.4.13.2.2

rtsAlarmsReqXON OBJECT-TYPE
    SYNTAX DisplayString
    MAX-ACCESS read-write
    STATUS current
    DESCRIPTION
        "ON/OFF require XON to start flow for alarms file"
    ::= { rtsAlarms 3 }
    --1.3.6.1.4.1.3052.14.2.4.13.2.3

rtsAlarmsTimeout OBJECT-TYPE
    SYNTAX Integer32
    MAX-ACCESS read-write
    STATUS current
    DESCRIPTION
        "Idle connection close timer (0 means no timeout) for alarms
        file"
    ::= { rtsAlarms 4 }
    --1.3.6.1.4.1.3052.14.2.4.13.2.4

rtsAlarmsEmptyClose OBJECT-TYPE
    SYNTAX DisplayString
    MAX-ACCESS read-write
    STATUS current
    DESCRIPTION
        "ON/OFF close the socket when this file is empty for alarms
        file"
    ::= { rtsAlarms 5 }
    --1.3.6.1.4.1.3052.14.2.4.13.2.5

rtsAlarmsPushHost OBJECT-TYPE
    SYNTAX DisplayString
    MAX-ACCESS read-write
    STATUS current
    DESCRIPTION
        "Host to which alarms file should be pushed via RTS"
    ::= { rtsAlarms 6 }
    --1.3.6.1.4.1.3052.14.2.4.13.2.6

rtsAlarmsPushPort OBJECT-TYPE
    SYNTAX Integer32
    MAX-ACCESS read-write
    STATUS current
    DESCRIPTION
        "TCP port to which alarms file should be pushed via RTS"
    ::= { rtsAlarms 7 }
    --1.3.6.1.4.1.3052.14.2.4.13.2.7

rtsAlarmsPushRetryTimer OBJECT-TYPE
    SYNTAX Integer32
    MAX-ACCESS read-write
    STATUS current
    DESCRIPTION
        "Retry timer (seconds) for retrying failed RTS push connect
        attempts"
    ::= { rtsAlarms 8 }
    --1.3.6.1.4.1.3052.14.2.4.13.2.8

-- Traps

trapIncludeDateTime OBJECT-TYPE
    SYNTAX DisplayString
    MAX-ACCESS read-write
    STATUS current
    DESCRIPTION
        "ON/OFF include date and time in stock trap message"
    ::= { trapInclude 1 }
    --1.3.6.1.4.1.3052.14.2.4.14.1.1

trapIncludeSiteName OBJECT-TYPE
    SYNTAX DisplayString
    MAX-ACCESS read-write
    STATUS current
    DESCRIPTION
        "ON/OFF include site name in stock trap message"
    ::= { trapInclude 2 }
    --1.3.6.1.4.1.3052.14.2.4.14.1.2

trapIncludeSensorID OBJECT-TYPE
    SYNTAX DisplayString
    MAX-ACCESS read-write
    STATUS current
    DESCRIPTION
        "ON/OFF include sensor ID in stock trap message"
    ::= { trapInclude 3 }
    --1.3.6.1.4.1.3052.14.2.4.14.1.3

trapIncludeUDName OBJECT-TYPE
    SYNTAX DisplayString
    MAX-ACCESS read-write
    STATUS current
    DESCRIPTION
        "ON/OFF include user defined name in stock trap message"
    ::= { trapInclude 4 }
    --1.3.6.1.4.1.3052.14.2.4.14.1.4

trapIncludeUDState OBJECT-TYPE
    SYNTAX DisplayString
    MAX-ACCESS read-write
    STATUS current
    DESCRIPTION
        "ON/OFF include user defined state in stock trap message"
    ::= { trapInclude 5 }
    --1.3.6.1.4.1.3052.14.2.4.14.1.5

trapIncludeSourceAddress OBJECT-TYPE
    SYNTAX IpAddress
    MAX-ACCESS read-write
    STATUS current
    DESCRIPTION
        "ON/OFF include source IP address in stock trap message"
    ::= { trapInclude 6 }
    --1.3.6.1.4.1.3052.14.2.4.14.1.6

trapAuthFailEnable OBJECT-TYPE
    SYNTAX DisplayString
    MAX-ACCESS read-write
    STATUS current
    DESCRIPTION
        "ON/OFF enable trap sent upon SNMP authentication failure"
    ::= { trap 2 }
    --1.3.6.1.4.1.3052.14.2.4.14.2

-- Route testing

routeTestEnable OBJECT-TYPE
    SYNTAX DisplayString
    MAX-ACCESS read-write
    STATUS current
    DESCRIPTION
        "ON/OFF enable route testing"
    ::= { routeTest 1 }
    --1.3.6.1.4.1.3052.14.2.4.15.1


routeTestPeriod OBJECT-TYPE
    SYNTAX Integer32
    MAX-ACCESS read-write
    STATUS current
    DESCRIPTION
        "The period which a route is considered valid"
    ::= { routeTest 2 }
    --1.3.6.1.4.1.3052.14.2.4.15.2

routeTestAddressTable OBJECT-TYPE
    SYNTAX SEQUENCE OF RouteTestConfig
    MAX-ACCESS not-accessible
    STATUS current
    DESCRIPTION
        "Table of route testing addresses"
    ::= { routeTest 3 }
    --1.3.6.1.4.1.3052.14.2.4.15.3

routeTestAddressEntry OBJECT-TYPE
    SYNTAX RouteTestConfig
    MAX-ACCESS not-accessible
    STATUS current
    DESCRIPTION
        "Entry for table of RTS files"
    INDEX { routeTestAddressIndex }
    ::= { routeTestAddressTable 1 }
    --1.3.6.1.4.1.3052.14.2.4.15.3.1

routeTestAddressIndex OBJECT-TYPE
    SYNTAX Integer32 (1..3)
    MAX-ACCESS read-only
    STATUS current
    DESCRIPTION
        "Index for table of RTS files"
    ::= { routeTestAddressEntry 1 }
    --1.3.6.1.4.1.3052.14.2.4.15.3.1.1

routeTestAddress OBJECT-TYPE
    SYNTAX DisplayString
    MAX-ACCESS read-write
    STATUS current
    DESCRIPTION
        "Address to ping to see if the route to it is valid"
    ::= { routeTestAddressEntry 2 }
    --1.3.6.1.4.1.3052.14.2.4.15.3.1.2


-- Wireless


wirelessMode OBJECT-TYPE
    SYNTAX DisplayString
    MAX-ACCESS read-write
    STATUS current
    DESCRIPTION
        "Wireless mode (OFF,PERMANENT-EDGE)"
    ::= { wireless 1 }
    --1.3.6.1.4.1.3052.14.2.4.16.1

wirelessAPN OBJECT-TYPE
    SYNTAX DisplayString
    MAX-ACCESS read-write
    STATUS current
    DESCRIPTION
        "Wireless access point name"
    ::= { wireless 2 }
    --1.3.6.1.4.1.3052.14.2.4.16.2

wirelessIdleTimeout OBJECT-TYPE
    SYNTAX Integer32
    MAX-ACCESS read-write
    STATUS current
    DESCRIPTION
        "Wireless idle timeout"
    ::= { wireless 3 }
    --1.3.6.1.4.1.3052.14.2.4.16.3

wirelessPIN OBJECT-TYPE
    SYNTAX DisplayString
    MAX-ACCESS read-write
    STATUS current
    DESCRIPTION
        "Wireless modem SIM PIN"
    ::= { wireless 5 }
    --1.3.6.1.4.1.3052.14.2.4.16.5

wirelessDRE OBJECT-TYPE
    SYNTAX DisplayString
    MAX-ACCESS read-write
    STATUS current
    DESCRIPTION
        "Default route enable for wireless network interface.
         When this is ON, the wireless link, if up, becomes
         the default route, overriding the default route setting
         (defaultRouter object).  When OFF, the default route
         setting controls the default route and the wireless link
         does not become the default route."
    ::= { wireless 9 }
    --1.3.6.1.4.1.3052.14.2.4.16.9

wirelessPPPUsername OBJECT-TYPE
    SYNTAX DisplayString
    MAX-ACCESS read-write
    STATUS current
    DESCRIPTION
        "Username for PPP-based wireless modem connections."
    ::= { wireless 10 }
    --1.3.6.1.4.1.3052.14.2.4.16.10

wirelessFirewall OBJECT-TYPE
    SYNTAX DisplayString
    MAX-ACCESS read-write
    STATUS current
    DESCRIPTION
        "Enable wireless modem firewall."
    ::= { wireless 11 }
    --1.3.6.1.4.1.3052.14.2.4.16.11

wirelessKeepaliveThreshold OBJECT-TYPE
    SYNTAX Integer32
    MAX-ACCESS read-write
    STATUS current
    DESCRIPTION
        "Minutes of no RX activity before sending keep-alive."
    ::= { wireless 12 }
    --1.3.6.1.4.1.3052.14.2.4.16.12

wirelessPPPDebug OBJECT-TYPE
    SYNTAX DisplayString
    MAX-ACCESS read-write
    STATUS current
    DESCRIPTION
        "Enable wireless modem PPP debug."
    ::= { wireless 13 }
    --1.3.6.1.4.1.3052.14.2.4.16.13

wirelessConnEnable OBJECT-TYPE
    SYNTAX DisplayString
    MAX-ACCESS read-write
    STATUS current
    DESCRIPTION
        "Enable wireless modem connectivity check."
    ::= { wirelessConnectivity 1 }
    --1.3.6.1.4.1.3052.14.2.4.16.20.1

wirelessConnCheckInterval OBJECT-TYPE
    SYNTAX Integer32
    MAX-ACCESS read-write
    STATUS current
    DESCRIPTION
        "Wireless connectivity check interval in minutes."
    ::= { wirelessConnectivity 2 }
    --1.3.6.1.4.1.3052.14.2.4.16.20.2

wirelessConnFailThreshold OBJECT-TYPE
    SYNTAX Integer32
    MAX-ACCESS read-write
    STATUS current
    DESCRIPTION
        "Wireless connectivity fail threshold."
    ::= { wirelessConnectivity 3 }
    --1.3.6.1.4.1.3052.14.2.4.16.20.3

wirelessConnIP1 OBJECT-TYPE
    SYNTAX IpAddress
    MAX-ACCESS read-write
    STATUS current
    DESCRIPTION
        "Wireless connectivity check IP address 1."
    ::= { wirelessConnectivity 10 }
    --1.3.6.1.4.1.3052.14.2.4.16.20.10

wirelessConnIP2 OBJECT-TYPE
    SYNTAX IpAddress
    MAX-ACCESS read-write
    STATUS current
    DESCRIPTION
        "Wireless connectivity check IP address 2."
    ::= { wirelessConnectivity 11 }
    --1.3.6.1.4.1.3052.14.2.4.16.20.11


-- Email


emailServer OBJECT-TYPE
    SYNTAX DisplayString
    MAX-ACCESS read-write
    STATUS current
    DESCRIPTION
        "SMTP server to which the unit sends email"
    ::= { email 1 }
    --1.3.6.1.4.1.3052.14.2.4.17.1

emailDomain OBJECT-TYPE
    SYNTAX DisplayString
    MAX-ACCESS read-write
    STATUS current
    DESCRIPTION
        "Domain to use in recipient address"
    ::= { email 2 }
    --1.3.6.1.4.1.3052.14.2.4.17.2

emailAuthEnable OBJECT-TYPE
    SYNTAX DisplayString
    MAX-ACCESS read-write
    STATUS current
    DESCRIPTION
        "ON/OFF enable SMTP authentication"
    ::= { email 3 }
    --1.3.6.1.4.1.3052.14.2.4.17.3

-- Advanced network config

arpFilter OBJECT-TYPE
    SYNTAX Integer32
    MAX-ACCESS read-write
    STATUS current
    DESCRIPTION
        "ARP filter code"
    ::= { netAdvanced 1 }
    --1.3.6.1.4.1.3052.14.2.4.18.1


-- Web interface

webEnable OBJECT-TYPE
    SYNTAX DisplayString
    MAX-ACCESS read-write
    STATUS current
    DESCRIPTION
        "ON/OFF for the web interface"
    ::= { web 1 }
    --1.3.6.1.4.1.3052.14.2.4.19.1

webPort OBJECT-TYPE
    SYNTAX Integer32
    MAX-ACCESS read-write
    STATUS current
    DESCRIPTION
        "TCP port on which web interface listens"
    ::= { web 2 }
    --1.3.6.1.4.1.3052.14.2.4.19.2

webTimeout OBJECT-TYPE
    SYNTAX Integer32
    MAX-ACCESS read-write
    STATUS current
    DESCRIPTION
        "Web interface session timeout (seconds)"
    ::= { web 3 }
    --1.3.6.1.4.1.3052.14.2.4.19.3



-- IPv6

ipv6DefaultRouter OBJECT-TYPE
    SYNTAX DisplayString
    MAX-ACCESS read-write
    STATUS current
    DESCRIPTION
        "The IPv6 default router in use."
    ::= { ipv6 1 }
    --1.3.6.1.4.1.3052.14.2.4.21.1



-- CPE table

cpeTable OBJECT-TYPE
    SYNTAX SEQUENCE OF CPEConfig
    MAX-ACCESS not-accessible
    STATUS current
    DESCRIPTION
        "Table of CPEs"
    ::= { cpe 1 }
    --1.3.6.1.4.1.3052.14.2.4.22.1

cpeEntry OBJECT-TYPE
    SYNTAX CPEConfig
    MAX-ACCESS not-accessible
    STATUS current
    DESCRIPTION
        "Entry for table of CPEs"
    INDEX { cpeIndex }
    ::= { cpeTable 1 }
    --1.3.6.1.4.1.3052.14.2.4.22.1.1

cpeIndex OBJECT-TYPE
    SYNTAX Integer32 (1..16)
    MAX-ACCESS read-only
    STATUS current
    DESCRIPTION
        "Index for table of CPEs"
    ::= { cpeEntry 1 }
    --1.3.6.1.4.1.3052.14.2.4.22.1.1.1

cpeHost OBJECT-TYPE
    SYNTAX DisplayString
    MAX-ACCESS read-write
    STATUS current
    DESCRIPTION
        "CPE host (IP address or DNS name)"
    ::= { cpeEntry 2 }
    --1.3.6.1.4.1.3052.14.2.4.22.1.1.2

cpeName OBJECT-TYPE
    SYNTAX DisplayString
    MAX-ACCESS read-write
    STATUS current
    DESCRIPTION
        "CPE name, informational only"
    ::= { cpeEntry 3 }
    --1.3.6.1.4.1.3052.14.2.4.22.1.1.3

cpeDescription OBJECT-TYPE
    SYNTAX DisplayString
    MAX-ACCESS read-write
    STATUS current
    DESCRIPTION
        "CPE description, informational only"
    ::= { cpeEntry 4 }
    --1.3.6.1.4.1.3052.14.2.4.22.1.1.4

cpeKeepalive OBJECT-TYPE
    SYNTAX Integer32
    MAX-ACCESS read-write
    STATUS current
    DESCRIPTION
        "Number of seconds between each successful ping request."
    ::= { cpeEntry 5 }
    --1.3.6.1.4.1.3052.14.2.4.22.1.1.5

cpeThreshold OBJECT-TYPE
    SYNTAX Integer32
    MAX-ACCESS read-write
    STATUS current
    DESCRIPTION
        "Number of unsuccessful pings that triggers the CPE event."
    ::= { cpeEntry 6 }
    --1.3.6.1.4.1.3052.14.2.4.22.1.1.6

cpeEventReminderInterval OBJECT-TYPE
    SYNTAX Integer32
    MAX-ACCESS read-write
    STATUS current
    DESCRIPTION
        "CPE event reminder interval (minutes)."
    ::= { cpeEntry 7 }
    --1.3.6.1.4.1.3052.14.2.4.22.1.1.7

cpeKeepaliveTicks OBJECT-TYPE
    SYNTAX Integer32
    MAX-ACCESS read-write
    STATUS current
    DESCRIPTION
        "CPE ping period in 16ths of a second (nonzero overrides keepalive)."
    ::= { cpeEntry 20 }
    --1.3.6.1.4.1.3052.14.2.4.22.1.1.20

cpePingSize OBJECT-TYPE
    SYNTAX Integer32
    MAX-ACCESS read-write
    STATUS current
    DESCRIPTION
        "Number of bytes in CPE ping payload"
    ::= { cpeEntry 21 }
    --1.3.6.1.4.1.3052.14.2.4.22.1.11

cpeInfoReset OBJECT-TYPE
    SYNTAX Integer32
    MAX-ACCESS read-only
    STATUS current
    DESCRIPTION
        "Set any number to reset CPE ping stats."
    ::= { cpeEntry 30 }
    --1.3.6.1.4.1.3052.14.2.4.22.1.1.30

cpeInfoNumReq OBJECT-TYPE
    SYNTAX Integer32
    MAX-ACCESS read-only
    STATUS current
    DESCRIPTION
        "Total number of requests transmitted."
    ::= { cpeEntry 31 }
    --1.3.6.1.4.1.3052.14.2.4.22.1.1.31

cpeInfoNumGoodResp OBJECT-TYPE
    SYNTAX Integer32
    MAX-ACCESS read-only
    STATUS current
    DESCRIPTION
        "Total number of non-corrupt responses."
    ::= { cpeEntry 32 }
    --1.3.6.1.4.1.3052.14.2.4.22.1.1.32

cpeInfoNumBadResp OBJECT-TYPE
    SYNTAX Integer32
    MAX-ACCESS read-only
    STATUS current
    DESCRIPTION
        "Total number of corrupt responses."
    ::= { cpeEntry 33 }
    --1.3.6.1.4.1.3052.14.2.4.22.1.1.33

cpeInfoNumLostResp OBJECT-TYPE
    SYNTAX Integer32
    MAX-ACCESS read-only
    STATUS current
    DESCRIPTION
        "Total number of requests with no response."
    ::= { cpeEntry 34 }
    --1.3.6.1.4.1.3052.14.2.4.22.1.1.34

cpeInfoPercentLoss OBJECT-TYPE
    SYNTAX DisplayString
    MAX-ACCESS read-only
    STATUS current
    DESCRIPTION
        "Percent loss (missing responses / total requests)."
    ::= { cpeEntry 35 }
    --1.3.6.1.4.1.3052.14.2.4.22.1.1.35

cpeInfoPercentBad OBJECT-TYPE
    SYNTAX DisplayString
    MAX-ACCESS read-only
    STATUS current
    DESCRIPTION
        "Percent corrupt (corrupt responses / total requests)."
    ::= { cpeEntry 36 }
    --1.3.6.1.4.1.3052.14.2.4.22.1.1.36

--***************************************************************************************
--Modem Section  2.5
--***************************************************************************************





modemFormat OBJECT-TYPE
    SYNTAX DisplayString
    MAX-ACCESS read-write
    STATUS current
    DESCRIPTION
        "Modem data format (8N1,7E1,7O1,7N1)"
    ::= { modem 1 }
    --1.3.6.1.4.1.3052.14.2.5.1

modemInitString OBJECT-TYPE
    SYNTAX DisplayString
    MAX-ACCESS read-write
    STATUS current
    DESCRIPTION
        "Init string for modem"
    ::= { modem 2 }
    --1.3.6.1.4.1.3052.14.2.5.2


modemCallAttempts OBJECT-TYPE
    SYNTAX Integer32
    MAX-ACCESS read-write
    STATUS current
    DESCRIPTION
        "Max mumber of times the modem should try to call out until
        successful connect"
    ::= { modem 4 }
    --1.3.6.1.4.1.3052.14.2.5.4

modemCallDelay OBJECT-TYPE
    SYNTAX Integer32
    MAX-ACCESS read-write
    STATUS current
    DESCRIPTION
        "Minimum delay (seconds) between callouts"
    ::= { modem 5 }
    --1.3.6.1.4.1.3052.14.2.5.6


modemCmdTimout OBJECT-TYPE
    SYNTAX Integer32
    MAX-ACCESS read-write
    STATUS current
    DESCRIPTION
        "Number of minutes after which an idle command session via
        modem is terminated"
    ::= { modem 6 }
    --1.3.6.1.4.1.3052.14.2.5.6

modemGoto OBJECT-TYPE
    SYNTAX DisplayString
    MAX-ACCESS read-write
    STATUS current
    DESCRIPTION
        "When a user connects, where that user is routed (command
        session, passthrough to port 1, passthrough to port 2, etc.)"
    ::= { modem 7 }
    --1.3.6.1.4.1.3052.14.2.5.7


modemCLIDEnable OBJECT-TYPE
    SYNTAX DisplayString
    MAX-ACCESS read-write
    STATUS current
    DESCRIPTION
        "ON/OFF Calling Line Identification security"
    ::= { modemClid 1 }
    --1.3.6.1.4.1.3052.14.2.5.8.1


modemCLIDNumberTable OBJECT-TYPE
    SYNTAX SEQUENCE OF ModemCLIDNumberConfig
    MAX-ACCESS not-accessible
    STATUS current
    DESCRIPTION
        "Table of authorized callers identified by phone number"
    ::= { modemClid 2 }
    --1.3.6.1.4.1.3052.14.2.5.8.2

modemCLIDNumberEntry OBJECT-TYPE
    SYNTAX ModemCLIDNumberConfig
    MAX-ACCESS not-accessible
    STATUS current
    DESCRIPTION
        "Entry for table of CLID numbers"
    INDEX { modemCLIDNumberIndex }
    ::= { modemCLIDNumberTable 1 }
    --1.3.6.1.4.1.3052.14.2.5.8.2.1

modemCLIDNumberIndex OBJECT-TYPE
    SYNTAX Integer32 (1..20)
    MAX-ACCESS read-only
    STATUS current
    DESCRIPTION
        "Index for table of CLID numbers"
    ::= { modemCLIDNumberEntry 1 }
    --1.3.6.1.4.1.3052.14.2.5.8.2.1.1

modemCLIDNumber OBJECT-TYPE
    SYNTAX DisplayString
    MAX-ACCESS read-write
    STATUS current
    DESCRIPTION
        "auhorized CLID number"
    ::= { modemCLIDNumberEntry 2 }
    --1.3.6.1.4.1.3052.14.2.5.8.2.1.2

modemTAPInitString OBJECT-TYPE
    SYNTAX DisplayString
    MAX-ACCESS read-write
    STATUS current
    DESCRIPTION
        "Init string to use for TAP (pager) connections"
    ::= { modem 9 }
    --1.3.6.1.4.1.3052.14.2.5.9

modemTAP8N1 OBJECT-TYPE
    SYNTAX DisplayString
    MAX-ACCESS read-write
    STATUS current
    DESCRIPTION
        "ON/OFF: use 8N1 data/parity/stop for TAP connections"
    ::= { modem 10 }
    --1.3.6.1.4.1.3052.14.2.5.10


--***************************************************************************************
--Time Section  2.8
--***************************************************************************************

clock OBJECT-TYPE
    SYNTAX DisplayString
    MAX-ACCESS read-write
    STATUS current
    DESCRIPTION
        "Text string for date and time;
        e.g. 'SUN 01/02/98 12:34:27'.  When setting
        this object, only the date and time are
        required; the unit will ignore a specified
        day of week because it is calculated from
        the date and time.  When this object is included
        in a notification as a varbind, it represents
        the time that the triggering event occurred."
    ::= { time 1 }
    --1.3.6.1.4.1.3052.14.2.8.1

--***************************************************************************************
--Console Section  2.10
--***************************************************************************************


consoleDuplex OBJECT-TYPE
    SYNTAX DisplayString
    MAX-ACCESS read-write
    STATUS current
    DESCRIPTION
        "ON/OFF characters echoed on telnet command session"
    ::= { console 1 }
    --1.3.6.1.4.1.3052.14.2.10.1

consoleTimeout OBJECT-TYPE
    SYNTAX Integer32
    MAX-ACCESS read-write
    STATUS current
    DESCRIPTION
        "Minutes of inactivity after which telnet command session is terminated"
    ::= { console 2 }
    --1.3.6.1.4.1.3052.14.2.10.2

consoleBaud OBJECT-TYPE
    SYNTAX Integer32
    MAX-ACCESS read-write
    STATUS current
    DESCRIPTION
        "Console baud rate"
    ::= { console 4 }
    --1.3.6.1.4.1.3052.14.2.10.4

consoleFormat OBJECT-TYPE
    SYNTAX DisplayString
    MAX-ACCESS read-write
    STATUS current
    DESCRIPTION
        "Console data format (8N1,7E1,7O1,7N1,8O2)"
    ::= { console 5 }
    --1.3.6.1.4.1.3052.14.2.10.5

consoleHsk OBJECT-TYPE
    SYNTAX DisplayString
    MAX-ACCESS read-write
    STATUS current
    DESCRIPTION
        "Console handshaking mode"
    ::= { console 6 }
    --1.3.6.1.4.1.3052.14.2.10.6

consoleConfirm OBJECT-TYPE
    SYNTAX DisplayString
    MAX-ACCESS read-write
    STATUS current
    DESCRIPTION
        "ON/OFF Prompt to confirm certain actions"
    ::= { console 7 }
    --1.3.6.1.4.1.3052.14.2.10.7

--***************************************************************************************
--Core Security Section 2.11.1
--***************************************************************************************

scShowPasswordPrompt OBJECT-TYPE
    SYNTAX DisplayString
    MAX-ACCESS read-write
    STATUS current
    DESCRIPTION
        "ON/OFF show password prompt upon login"
    ::= { secCore 1 }
    --1.3.6.1.4.1.3052.14.2.11.1.1

scConsoleLoginRequired  OBJECT-TYPE
    SYNTAX DisplayString
    MAX-ACCESS read-write
    STATUS current
    DESCRIPTION
        "ON/OFF login required upon connecting via console"
    ::= { secCore 2 }
    --1.3.6.1.4.1.3052.14.2.11.1.2

scModemLoginRequired OBJECT-TYPE
    SYNTAX DisplayString
    MAX-ACCESS read-write
    STATUS current
    DESCRIPTION
        "ON/OFF login required upon connecting via modem"
    ::= { secCore 3 }
    --1.3.6.1.4.1.3052.14.2.11.1.3

scTelnetLoginRequired OBJECT-TYPE
    SYNTAX DisplayString
    MAX-ACCESS read-write
    STATUS current
    DESCRIPTION
        "ON/OFF login required upon connecting via Telnet"
    ::= { secCore 4 }
    --1.3.6.1.4.1.3052.14.2.11.1.4

scTelnetPTLoginRequired OBJECT-TYPE
    SYNTAX DisplayString
    MAX-ACCESS read-write
    STATUS current
    DESCRIPTION
        "ON/OFF login required upon connecting via Telnet to pass-
        through ports (TCP ports 210x)"
    ::= { secCore 5 }
    --1.3.6.1.4.1.3052.14.2.11.1.5

scRTSLoginRequired OBJECT-TYPE
    SYNTAX DisplayString
    MAX-ACCESS read-write
    STATUS current
    DESCRIPTION
        "ON/OFF login required upon connecting to RTS (TCP ports 220x)"
    ::= { secCore 6 }
    --1.3.6.1.4.1.3052.14.2.11.1.6

scAuthMode OBJECT-TYPE
    SYNTAX DisplayString
    MAX-ACCESS read-write
    STATUS current
    DESCRIPTION
        "Authentication mode (USERNAME/PW,PW/USERNAME,PASSWORD ONLY)"
    ::= { secCore 7 }
    --1.3.6.1.4.1.3052.14.2.11.1.7

scRightsGroup OBJECT-TYPE
    SYNTAX DisplayString
    MAX-ACCESS read-write
    STATUS current
    DESCRIPTION
        "The set of aliases used for the 8 available rights levels"
    ::= { secCore 8 }
    --1.3.6.1.4.1.3052.14.2.11.1.8

scSecret OBJECT-TYPE
    SYNTAX DisplayString
    MAX-ACCESS read-write
    STATUS current
    DESCRIPTION
        "Shared secret for challenges"
    ::= { secCore 9 }
    --1.3.6.1.4.1.3052.14.2.11.1.9



--***************************************************************************************
--User Security Section 2.11.2
--***************************************************************************************


secUserTable OBJECT-TYPE
    SYNTAX SEQUENCE OF SecUserConfig
    MAX-ACCESS not-accessible
    STATUS current
    DESCRIPTION
        "Table of users"
    ::= { unitSecurity 2 }
    --1.3.6.1.4.1.3052.14.2.11.2

secUserEntry OBJECT-TYPE
    SYNTAX SecUserConfig
    MAX-ACCESS not-accessible
    STATUS current
    DESCRIPTION
        "Entry for table of users"
    INDEX { secUserIndex }
    ::= { secUserTable 1 }
    --1.3.6.1.4.1.3052.14.2.11.2.1

secUserIndex OBJECT-TYPE
    SYNTAX Integer32 (1..12)
    MAX-ACCESS read-only
    STATUS current
    DESCRIPTION
        "Index for table of users"
    ::= { secUserEntry 1 }
    --1.3.6.1.4.1.3052.14.2.11.2.1.1

secUserEnable OBJECT-TYPE
    SYNTAX DisplayString
    MAX-ACCESS read-write
    STATUS current
    DESCRIPTION
        "ON/OFF enable user"
    ::= { secUserEntry 2 }
    --1.3.6.1.4.1.3052.14.2.11.2.1.2

secUserConnectVia OBJECT-TYPE
    SYNTAX DisplayString
    MAX-ACCESS read-write
    STATUS current
    DESCRIPTION
        "Methods by which user is allowed to connect:
        L=local (console)
        T=Telnet
        M=modem
        F=FTP
        R=RTS
        S=SSH
        "
    ::= { secUserEntry 5 }
    --1.3.6.1.4.1.3052.14.2.11.2.1.5

secUserLoginTo OBJECT-TYPE
    SYNTAX DisplayString
    MAX-ACCESS read-write
    STATUS current
    DESCRIPTION
        "The function presented to the user upon login (COMMAND,
        PASSTHROUGH,MENU)"
    ::= { secUserEntry 6 }
    --1.3.6.1.4.1.3052.14.2.11.2.1.6

secUserAccessFile OBJECT-TYPE
    SYNTAX DisplayString
    MAX-ACCESS read-write
    STATUS current
    DESCRIPTION
        "The default access file associated with the user"
    ::= { secUserEntry 7 }
    --1.3.6.1.4.1.3052.14.2.11.2.1.7

secUserPTEscapeTo OBJECT-TYPE
    SYNTAX DisplayString
    MAX-ACCESS read-write
    STATUS current
    DESCRIPTION
        "The function presented to the user upon escaping pass-
        through: currently only MENU"
    ::= { secUserEntry 9 }
    --1.3.6.1.4.1.3052.14.2.11.2.1.9

secUserPPPType OBJECT-TYPE
    SYNTAX DisplayString
    MAX-ACCESS read-write
    STATUS current
    DESCRIPTION
        "The kind of PPP access allowed to this user cannot connect
        via PPP (NONE), can connect but only to the unit (LOCAL), or
        can connect and route to Ethernet (ROUTING)"
    ::= { secUserEntry 10 }
    --1.3.6.1.4.1.3052.14.2.11.2.1.10

secUserRights OBJECT-TYPE
    SYNTAX DisplayString
    MAX-ACCESS read-write
    STATUS current
    DESCRIPTION
        "The rights level granted to this user"
    ::= { secUserEntry 11 }
    --1.3.6.1.4.1.3052.14.2.11.2.1.11

secUserEventsReadAccess OBJECT-TYPE
    SYNTAX DisplayString
    MAX-ACCESS read-write
    STATUS current
    DESCRIPTION
        "DENY/ALLOW user to read the events/alarms file"
    ::= { secUserEntry 13 }
    --1.3.6.1.4.1.3052.14.2.11.2.1.13

secUserAuditReadAccess OBJECT-TYPE
    SYNTAX DisplayString
    MAX-ACCESS read-write
    STATUS current
    DESCRIPTION
        "DENY/ALLOW user to read the audit log"
    ::= { secUserEntry 14 }
    --1.3.6.1.4.1.3052.14.2.11.2.1.14

secUserEventsWriteAccess OBJECT-TYPE
    SYNTAX DisplayString
    MAX-ACCESS read-write
    STATUS current
    DESCRIPTION
        "DENY/ALLOW user to delete the events file"
    ::= { secUserEntry 16 }
    --1.3.6.1.4.1.3052.14.2.11.2.1.16

secUserAuditWriteAccess OBJECT-TYPE
    SYNTAX DisplayString
    MAX-ACCESS read-write
    STATUS current
    DESCRIPTION
        "DENY/ALLOW user to write to the audit log"
    ::= { secUserEntry 17 }
    --1.3.6.1.4.1.3052.14.2.11.2.1.17

secUserExpiration OBJECT-TYPE
    SYNTAX DisplayString
    MAX-ACCESS read-write
    STATUS current
    DESCRIPTION
        "Expiration date/time of this user"
    ::= { secUserEntry 18 }
    --1.3.6.1.4.1.3052.14.2.11.2.1.18

secUserCallbackNumber1 OBJECT-TYPE
    SYNTAX DisplayString
    MAX-ACCESS read-write
    STATUS current
    DESCRIPTION
        "Number slot 1 the unit calls for dialback"
    ::= { secUserEntry 19 }
    --1.3.6.1.4.1.3052.14.2.11.2.1.19

secUserCallbackNumber2 OBJECT-TYPE
    SYNTAX DisplayString
    MAX-ACCESS read-write
    STATUS current
    DESCRIPTION
        "Number slot 2 the unit calls for dialback"
    ::= { secUserEntry 20 }
    --1.3.6.1.4.1.3052.14.2.11.2.1.20

secUserCallbackNumber3 OBJECT-TYPE
    SYNTAX DisplayString
    MAX-ACCESS read-write
    STATUS current
    DESCRIPTION
        "Number slot 3 the unit calls for dialback"
    ::= { secUserEntry 21 }
    --1.3.6.1.4.1.3052.14.2.11.2.1.21

secUserChallengeTelnetMode OBJECT-TYPE
    SYNTAX DisplayString
    MAX-ACCESS read-write
    STATUS current
    DESCRIPTION
        "Telnet challenge mode: when user logs in via telnet, unit
        allows access (OFF), presents a challenge (CHALLENGE), or
        unit sends a one-time-password (SEND PASSWORD) to a
        destination configured by secUserChallengeTelnetSendTo"
    ::= { secUserEntry 22 }
    --1.3.6.1.4.1.3052.14.2.11.2.1.22

secUserChallengeModemMode OBJECT-TYPE
    SYNTAX DisplayString
    MAX-ACCESS read-write
    STATUS current
    DESCRIPTION
        "Modem challenge mode: when user logs in via modem, unit
        allows access (OFF), presents a challenge (CHALLENGE), sends
        a one-time-password (SEND PASSWORD) to a destination
        configured by secUserChallengeTelnetSendTo, or dials a
        number (CALLBACK) configured with secUserCallbackNumberx"
    ::= { secUserEntry 23 }
    --1.3.6.1.4.1.3052.14.2.11.2.1.23

secUserChallengeConsoleMode OBJECT-TYPE
    SYNTAX DisplayString
    MAX-ACCESS read-write
    STATUS current
    DESCRIPTION
        "Console challenge mode: when user logs in via console, unit
        allows access (OFF), or presents a challenge (CHALLENGE)"
    ::= { secUserEntry 24 }
    --1.3.6.1.4.1.3052.14.2.11.2.1.24

secUserChallengeTelnetSendTo OBJECT-TYPE
    SYNTAX DisplayString
    MAX-ACCESS read-write
    STATUS current
    DESCRIPTION
        "Email action used as the destination address for one-time-
        password when a user logs in with a challenge mode of
        SEND PASSWORD"
    ::= { secUserEntry 25 }
    --1.3.6.1.4.1.3052.14.2.11.2.1.25

secUserChallengeModemSendTo OBJECT-TYPE
    SYNTAX DisplayString
    MAX-ACCESS read-write
    STATUS current
    DESCRIPTION
        "Modem action used as the destination phone number for one-
        time-password when a user logs in with a challenge mode of
        SEND PASSWORD"
    ::= { secUserEntry 26 }
    --1.3.6.1.4.1.3052.14.2.11.2.1.26

secUserChallengeExpiration OBJECT-TYPE
    SYNTAX Integer32 (0..180)
    MAX-ACCESS read-write
    STATUS current
    DESCRIPTION
        "Time (in minutes) after which a one-time-password is sent
        that it can be used to log in"
    ::= { secUserEntry 27 }
    --1.3.6.1.4.1.3052.14.2.11.2.1.27


--***************************************************************************************
--Factory Security Section 2.11.3
--***************************************************************************************

sfEnable OBJECT-TYPE
    SYNTAX DisplayString
    MAX-ACCESS read-write
    STATUS current
    DESCRIPTION
        "ON/OFF enable factory access"
    ::= { secFactory 1 }
    --1.3.6.1.4.1.3052.14.2.11.3.1

sfSecret OBJECT-TYPE
    SYNTAX DisplayString
    MAX-ACCESS read-write
    STATUS current
    DESCRIPTION
        "Secret used for factory access"
    ::= { secFactory 2 }
    --1.3.6.1.4.1.3052.14.2.11.3.2


--***************************************************************************************
--SSH Security Section 2.11.3
--***************************************************************************************

--***************************************************************************************
--Event Section   2.12
--***************************************************************************************

--***************************************************************************************
--Event Core Section   2.12.1
--***************************************************************************************


evClassNameTable OBJECT-TYPE
    SYNTAX SEQUENCE OF EventClassConfig
    MAX-ACCESS not-accessible
    STATUS current
    DESCRIPTION
        "Table of classes"
    ::= { evCore 1 }
    --1.3.6.1.4.1.3052.14.2.12.1.1

evClassNameEntry OBJECT-TYPE
    SYNTAX EventClassConfig
    MAX-ACCESS not-accessible
    STATUS current
    DESCRIPTION
        "Entry for table of classes"
    INDEX { evClassNameIndex }
    ::= { evClassNameTable 1 }
    --1.3.6.1.4.1.3052.14.2.12.1.1.1

evClassNameIndex OBJECT-TYPE
    SYNTAX Integer32 (1..12)
    MAX-ACCESS read-only
    STATUS current
    DESCRIPTION
        "Index for table of classes"
    ::= { evClassNameEntry 1 }
    --1.3.6.1.4.1.3052.14.2.12.1.1.1.1

evClassName OBJECT-TYPE
    SYNTAX DisplayString
    MAX-ACCESS read-write
    STATUS current
    DESCRIPTION
        "Class name for this slot"
    ::= { evClassNameEntry 2 }
    --1.3.6.1.4.1.3052.14.2.12.1.1.1.2

evReminderInterval OBJECT-TYPE
    SYNTAX Integer32 (0..65535)
    MAX-ACCESS read-write
    STATUS current
    DESCRIPTION
        "Interval (minutes) between EventSensor reminder events"
    ::= { evCore 2 }
    --1.3.6.1.4.1.3052.14.2.12.1.2

evLogEnable OBJECT-TYPE
    SYNTAX DisplayString
    MAX-ACCESS read-write
    STATUS current
    DESCRIPTION
        "ON/OFF enable event log"
    ::= { evLog 1 }
    --1.3.6.1.4.1.3052.14.2.12.1.3.1

evLogStoreAlarm OBJECT-TYPE
    SYNTAX DisplayString
    MAX-ACCESS read-write
    STATUS current
    DESCRIPTION
        "ON/OFF store data alarms in event log"
    ::= { evLog 2 }
    --1.3.6.1.4.1.3052.14.2.12.1.3.2

evLogMaxSize OBJECT-TYPE
    SYNTAX Integer32
    MAX-ACCESS read-write
    STATUS current
    DESCRIPTION
        "max size (in KB) of event log"
    ::= { evLog 3 }
    --1.3.6.1.4.1.3052.14.2.12.1.3.3

evLogStoreSensor OBJECT-TYPE
    SYNTAX DisplayString
    MAX-ACCESS read-write
    STATUS current
    DESCRIPTION
        "ON/OFF store EventSensor events in event log"
    ::= { evLog 4 }
    --1.3.6.1.4.1.3052.14.2.12.1.3.4

evLogTimeStampAlarms OBJECT-TYPE
    SYNTAX DisplayString
    MAX-ACCESS read-write
    STATUS current
    DESCRIPTION
        "ON/OFF put timestamps on event log entries"
    ::= { evLog 5 }
    --1.3.6.1.4.1.3052.14.2.12.1.3.5

evLogPrependName OBJECT-TYPE
    SYNTAX DisplayString
    MAX-ACCESS read-write
    STATUS current
    DESCRIPTION
        "ON/OFF prepend data event name to data alarm records in event
        log"
    ::= { evLog 6 }
    --1.3.6.1.4.1.3052.14.2.12.1.3.6


evMgmtReprocess OBJECT-TYPE
    SYNTAX DisplayString
    MAX-ACCESS read-write
    STATUS current
    DESCRIPTION
        "Number of sensors that have generated events since reset.
        Write this to reprocess each sensor's last generated event
        since reset.  The value to write determines what kind of
        events should be reprocessed:
                'all': all sensor events
                 'cc': cc events
        'temperature': temperature events
           'humidity': humidity events
             'analog': analog input events"
    ::= { evMgmt 3 }
    --1.3.6.1.4.1.3052.14.2.12.1.4.3






--***************************************************************************************
--Data event section 2.12.2
--***************************************************************************************

evdExitOnTrue OBJECT-TYPE
    SYNTAX DisplayString
    MAX-ACCESS read-write
    STATUS current
    DESCRIPTION
        "ON/OFF: Data alarm evaluator stops checking record against
        alarm equations when it finds an equation that matches"
    ::= { evdCore 1 }
    --1.3.6.1.4.1.3052.14.2.12.2.1.1.1

evdFilterAction OBJECT-TYPE
    SYNTAX DisplayString
    MAX-ACCESS read-write
    STATUS current
    DESCRIPTION
        "What happens to a record that matches an equation:
        REJECT/ACCEPT"
    ::= { evdCore 2 }
    --1.3.6.1.4.1.3052.14.2.12.2.1.1.2

evdWildCardChar OBJECT-TYPE
    SYNTAX Integer32
    MAX-ACCESS read-write
    STATUS current
    DESCRIPTION
        "Character (in decimal ASCII code format) used to indicate
        wildcards in data alarm equation"
    ::= { evdCore 3 }
    --1.3.6.1.4.1.3052.14.2.12.2.1.1.3


evdTable OBJECT-TYPE
    SYNTAX SEQUENCE OF DataEventConfig
    MAX-ACCESS not-accessible
    STATUS current
    DESCRIPTION
        "Table of data events"
    ::= { evData 2 }
    --1.3.6.1.4.1.3052.14.2.12.2.2

evdEntry OBJECT-TYPE
    SYNTAX DataEventConfig
    MAX-ACCESS not-accessible
    STATUS current
    DESCRIPTION
        "Entry for table of data events"
    INDEX { evdIndex }
    ::= { evdTable 1 }
    --1.3.6.1.4.1.3052.14.2.12.2.2.1

evdIndex OBJECT-TYPE
    SYNTAX Integer32 (1..1000)
    MAX-ACCESS read-only
    STATUS current
    DESCRIPTION
        "Index for table of data events"
    ::= { evdEntry 1 }
    --1.3.6.1.4.1.3052.14.2.12.2.2.1.1

evdEnable OBJECT-TYPE
    SYNTAX DisplayString
    MAX-ACCESS read-write
    STATUS current
    DESCRIPTION
        "ON/OFF enable this data event"
    ::= { evdEntry 2 }
    --1.3.6.1.4.1.3052.14.2.12.2.2.1.2

evdName OBJECT-TYPE
    SYNTAX DisplayString
    MAX-ACCESS read-write
    STATUS current
    DESCRIPTION
        "Name for this data event"
    ::= { evdEntry 3 }
    --1.3.6.1.4.1.3052.14.2.12.2.2.1.3

evdEquation OBJECT-TYPE
    SYNTAX DisplayString
    MAX-ACCESS read-write
    STATUS current
    DESCRIPTION
        "Equation for this data event"
    ::= { evdEntry 4 }
    --1.3.6.1.4.1.3052.14.2.12.2.2.1.4

evdThreshold OBJECT-TYPE
    SYNTAX Integer32
    MAX-ACCESS read-write
    STATUS current
    DESCRIPTION
        "Number of equation matches that must happen to trigger this
        data event"
    ::= { evdEntry 5 }
    --1.3.6.1.4.1.3052.14.2.12.2.2.1.5

evdAutoClear OBJECT-TYPE
    SYNTAX DisplayString
    MAX-ACCESS read-write
    STATUS current
    DESCRIPTION
        "ON/OFF this data alarm is automatically cleared (re-armed)
        upon reaching the threshold number of matches"
    ::= { evdEntry 6 }
    --1.3.6.1.4.1.3052.14.2.12.2.2.1.6

evdClearInterval OBJECT-TYPE
    SYNTAX DisplayString
    MAX-ACCESS read-write
    STATUS current
    DESCRIPTION
        "Interval at which this alarm is automatically cleared (no
        bearing with evdAutoClear)"
    ::= { evdEntry 7 }
    --1.3.6.1.4.1.3052.14.2.12.2.2.1.7

evdClearTime OBJECT-TYPE
    SYNTAX DisplayString
    MAX-ACCESS read-write
    STATUS current
    DESCRIPTION
        "Tie of day (HH:MM) at which this data alarm is cleared (no
        bearing with evdAutoClear)"
    ::= { evdEntry 8 }
    --1.3.6.1.4.1.3052.14.2.12.2.2.1.8

evdActions OBJECT-TYPE
    SYNTAX DisplayString
    MAX-ACCESS read-write
    STATUS current
    DESCRIPTION
        "Actions for this data event"
    ::= { evdEntry 9 }
    --1.3.6.1.4.1.3052.14.2.12.2.2.1.9

evdClass OBJECT-TYPE
    SYNTAX DisplayString
    MAX-ACCESS read-write
    STATUS current
    DESCRIPTION
        "Class for this data event"
    ::= { evdEntry 10 }
    --1.3.6.1.4.1.3052.14.2.12.2.2.1.10

evdTrapNum OBJECT-TYPE
    SYNTAX Integer32
    MAX-ACCESS read-write
    STATUS current
    DESCRIPTION
        "Trap number for this event"
    ::= { evdEntry 11 }
    --1.3.6.1.4.1.3052.14.2.12.2.2.1.11

evdMode OBJECT-TYPE
    SYNTAX DisplayString
    MAX-ACCESS read-write
    STATUS current
    DESCRIPTION
        "ALARM/FILTER: what is happens when this data event
        triggers: either generate actions (mode=ALARM) )or
        ACCEPT/REJECT (via evdFilterAction) the record
        (mode=FILTER)"
    ::= { evdEntry 12 }
    --1.3.6.1.4.1.3052.14.2.12.2.2.1.12

evdFieldTable OBJECT-TYPE
    SYNTAX SEQUENCE OF DataEventFieldConfig
    MAX-ACCESS not-accessible
    STATUS current
    DESCRIPTION
        "Table of data event fields"
    ::= { evData 3 }
    --1.3.6.1.4.1.3052.14.2.12.2.3

evdFieldEntry OBJECT-TYPE
    SYNTAX DataEventFieldConfig
    MAX-ACCESS not-accessible
    STATUS current
    DESCRIPTION
        "Entry for table of data event fields"
    INDEX { evdFieldIndex }
    ::= { evdFieldTable 1 }
    --1.3.6.1.4.1.3052.14.2.12.2.3.1

evdFieldIndex OBJECT-TYPE
    SYNTAX Integer32 (1..16)
    MAX-ACCESS read-only
    STATUS current
    DESCRIPTION
        "Index for table of data event fields"
    ::= { evdFieldEntry 1 }
    --1.3.6.1.4.1.3052.14.2.12.2.3.1.1

evdFieldStart OBJECT-TYPE
    SYNTAX Integer32
    MAX-ACCESS read-write
    STATUS current
    DESCRIPTION
        "Start position (1-based) for this data event field"
    ::= { evdFieldEntry 2 }
    --1.3.6.1.4.1.3052.14.2.12.2.3.1.2

evdFieldLength OBJECT-TYPE
    SYNTAX Integer32
    MAX-ACCESS read-write
    STATUS current
    DESCRIPTION
        "Number of characters this data event field occupies"
    ::= { evdFieldEntry 3 }
    --1.3.6.1.4.1.3052.14.2.12.2.3.1.3

evdFieldName OBJECT-TYPE
    SYNTAX DisplayString
    MAX-ACCESS read-write
    STATUS current
    DESCRIPTION
        "Start position (1-based) for this data event field"
    ::= { evdFieldEntry 4 }
    --1.3.6.1.4.1.3052.14.2.12.2.3.1.4

evdFieldLine OBJECT-TYPE
    SYNTAX Integer32
    MAX-ACCESS read-write
    STATUS current
    DESCRIPTION
        "Line number (1-based, for multiline records) for this data
        event field"
    ::= { evdFieldEntry 5 }
    --1.3.6.1.4.1.3052.14.2.12.2.3.1.5

evdFieldType OBJECT-TYPE
    SYNTAX DisplayString
    MAX-ACCESS read-write
    STATUS current
    DESCRIPTION
        "Alpha/Numeric type for this data event field"
    ::= { evdFieldEntry 6 }
    --1.3.6.1.4.1.3052.14.2.12.2.3.1.6

evdMacroTable OBJECT-TYPE
    SYNTAX SEQUENCE OF DataEventMacroConfig
    MAX-ACCESS not-accessible
    STATUS current
    DESCRIPTION
        "Table of data event macros"
    ::= { evData 4 }
    --1.3.6.1.4.1.3052.14.2.12.2.4

evdMacroEntry OBJECT-TYPE
    SYNTAX DataEventMacroConfig
    MAX-ACCESS not-accessible
    STATUS current
    DESCRIPTION
        "Entry for table of data event macros"
    INDEX { evdMacroIndex }
    ::= { evdMacroTable 1 }
    --1.3.6.1.4.1.3052.14.2.12.2.4.1

evdMacroIndex OBJECT-TYPE
    SYNTAX Integer32 (1..100)
    MAX-ACCESS read-only
    STATUS current
    DESCRIPTION
        "Index for table of data event macros"
    ::= { evdMacroEntry 1 }
    --1.3.6.1.4.1.3052.14.2.12.2.4.1.1

evdMacroName OBJECT-TYPE
    SYNTAX DisplayString
    MAX-ACCESS read-write
    STATUS current
    DESCRIPTION
        "Name of this macro for use in data event equations"
    ::= { evdMacroEntry 2 }
    --1.3.6.1.4.1.3052.14.2.12.2.4.1.2

evdMacroEquation OBJECT-TYPE
    SYNTAX DisplayString
    MAX-ACCESS read-write
    STATUS current
    DESCRIPTION
        "Equation for this data event macro"
    ::= { evdMacroEntry 3 }
    --1.3.6.1.4.1.3052.14.2.12.2.4.1.3

--***************************************************************************************
--No data event 1 Section 2.12.3
--***************************************************************************************

evNoData1Enable OBJECT-TYPE
    SYNTAX DisplayString
    MAX-ACCESS read-write
    STATUS current
    DESCRIPTION
        "ON/OFF enable this no data event"
    ::= { evNoData1 1 }
    --1.3.6.1.4.1.3052.14.2.12.3.1

evNoData1Actions OBJECT-TYPE
    SYNTAX DisplayString
    MAX-ACCESS read-write
    STATUS current
    DESCRIPTION
        "Actions for this no data event"
    ::= { evNoData1 2 }
    --1.3.6.1.4.1.3052.14.2.12.3.2

evNoData1Message OBJECT-TYPE
    SYNTAX DisplayString
    MAX-ACCESS read-write
    STATUS current
    DESCRIPTION
        "Message for this no data event"
    ::= { evNoData1 3 }
    --1.3.6.1.4.1.3052.14.2.12.3.3

evNoData1TrapNum OBJECT-TYPE
    SYNTAX Integer32 (0..65535)
    MAX-ACCESS read-write
    STATUS current
    DESCRIPTION
        "Trap number for this no data event"
    ::= { evNoData1 4 }
    --1.3.6.1.4.1.3052.14.2.12.3.4

evNoData1Class OBJECT-TYPE
    SYNTAX DisplayString
    MAX-ACCESS read-write
    STATUS current
    DESCRIPTION
        "Class for this no data event"
    ::= { evNoData1 5 }
    --1.3.6.1.4.1.3052.14.2.12.3.5

evNoData1Sched1Begin OBJECT-TYPE
    SYNTAX DisplayString
    MAX-ACCESS read-write
    STATUS current
    DESCRIPTION
        "Schedule 1 begin time (HH:MM) for this no data event"
    ::= { evNoData1 6 }
    --1.3.6.1.4.1.3052.14.2.12.3.6

evNoData1Sched1End OBJECT-TYPE
    SYNTAX DisplayString
    MAX-ACCESS read-write
    STATUS current
    DESCRIPTION
        "Schedule 1 end time (HH:MM) for this no data event"
    ::= { evNoData1 7 }
    --1.3.6.1.4.1.3052.14.2.12.3.7

evNoData1Sched1Duration OBJECT-TYPE
    SYNTAX Integer32 (0..65535)
    MAX-ACCESS read-write
    STATUS current
    DESCRIPTION
        "Duration (minutes) for schedule 1 of this no data event"
    ::= { evNoData1 8 }
    --1.3.6.1.4.1.3052.14.2.12.3.8

evNoData1Sched2Begin OBJECT-TYPE
    SYNTAX DisplayString
    MAX-ACCESS read-write
    STATUS current
    DESCRIPTION
        "Schedule 2 begin time (HH:MM) for this no data event"
    ::= { evNoData1 9 }
    --1.3.6.1.4.1.3052.14.2.12.3.9

evNoData1Sched2End OBJECT-TYPE
    SYNTAX DisplayString
    MAX-ACCESS read-write
    STATUS current
    DESCRIPTION
        "Schedule 2 end time (HH:MM) for this no data event"
    ::= { evNoData1 10 }
    --1.3.6.1.4.1.3052.14.2.12.3.10

evNoData1Sched2Duration OBJECT-TYPE
    SYNTAX Integer32 (0..65535)
    MAX-ACCESS read-write
    STATUS current
    DESCRIPTION
        "Duration (minutes) for schedule 2 of this no data event"
    ::= { evNoData1 11 }
    --1.3.6.1.4.1.3052.14.2.12.3.11

evNoData1PortEnableTable OBJECT-TYPE
    SYNTAX SEQUENCE OF NoDataEvent1PortEnableConfig
    MAX-ACCESS not-accessible
    STATUS current
    DESCRIPTION
        "Table of no data event 1 port enables"
    ::= { evNoData1 12 }
    --1.3.6.1.4.1.3052.14.2.12.3.12

evNoData1PortEnableEntry OBJECT-TYPE
    SYNTAX NoDataEvent1PortEnableConfig
    MAX-ACCESS not-accessible
    STATUS current
    DESCRIPTION
        "Entry for table of no data event 1 port enables"
    INDEX { evNoData1PortEnableIndex }
    ::= { evNoData1PortEnableTable 1 }
    --1.3.6.1.4.1.3052.14.2.12.3.12.1

evNoData1PortEnableIndex OBJECT-TYPE
    SYNTAX Integer32 (1..16)
    MAX-ACCESS read-only
    STATUS current
    DESCRIPTION
        "Index for table of no data event 1 port enables"
    ::= { evNoData1PortEnableEntry 1 }
    --1.3.6.1.4.1.3052.14.2.12.3.12.1.1

evNoData1PortEnable OBJECT-TYPE
    SYNTAX DisplayString
    MAX-ACCESS read-write
    STATUS current
    DESCRIPTION
        "ON/OFF: no data event 1 observes this port"
    ::= { evNoData1PortEnableEntry 2 }
    --1.3.6.1.4.1.3052.14.2.12.3.12.1.2

evNoData1Exclusions OBJECT-TYPE
    SYNTAX DisplayString
    MAX-ACCESS read-write
    STATUS current
    DESCRIPTION
        "Exclusions (space-separated MM/DD-formatted dates) for this
        no data event"
    ::= { evNoData1 13 }
    --1.3.6.1.4.1.3052.14.2.12.3.13

evNoData1Days OBJECT-TYPE
    SYNTAX DisplayString
    MAX-ACCESS read-write
    STATUS current
    DESCRIPTION
        "Days of the week on which this no event is active"
    ::= { evNoData1 14 }
    --1.3.6.1.4.1.3052.14.2.12.3.14

--***************************************************************************************
--No data event 2 Section 2.12.4
--***************************************************************************************

evNoData2Enable OBJECT-TYPE
    SYNTAX DisplayString
    MAX-ACCESS read-write
    STATUS current
    DESCRIPTION
        "ON/OFF enable this no data event"
    ::= { evNoData2 1 }
    --1.3.6.1.4.1.3052.14.2.12.4.1

evNoData2Actions OBJECT-TYPE
    SYNTAX DisplayString
    MAX-ACCESS read-write
    STATUS current
    DESCRIPTION
        "Actions for this no data event"
    ::= { evNoData2 2 }
    --1.3.6.1.4.1.3052.14.2.12.4.2

evNoData2Message OBJECT-TYPE
    SYNTAX DisplayString
    MAX-ACCESS read-write
    STATUS current
    DESCRIPTION
        "Message for this no data event"
    ::= { evNoData2 3 }
    --1.3.6.1.4.1.3052.14.2.12.4.3

evNoData2TrapNum OBJECT-TYPE
    SYNTAX Integer32 (505..1199)
    MAX-ACCESS read-write
    STATUS current
    DESCRIPTION
        "Trap number for this no data event"
    ::= { evNoData2 4 }
    --1.3.6.1.4.1.3052.14.2.12.4.4

evNoData2Class OBJECT-TYPE
    SYNTAX DisplayString
    MAX-ACCESS read-write
    STATUS current
    DESCRIPTION
        "Class for this no data event"
    ::= { evNoData2 5 }
    --1.3.6.1.4.1.3052.14.2.12.4.5

evNoData2Sched1Begin OBJECT-TYPE
    SYNTAX DisplayString
    MAX-ACCESS read-write
    STATUS current
    DESCRIPTION
        "Schedule 1 begin time (HH:MM) for this no data event"
    ::= { evNoData2 6 }
    --1.3.6.1.4.1.3052.14.2.12.4.6

evNoData2Sched1End OBJECT-TYPE
    SYNTAX DisplayString
    MAX-ACCESS read-write
    STATUS current
    DESCRIPTION
        "Schedule 1 end time (HH:MM) for this no data event"
    ::= { evNoData2 7 }
    --1.3.6.1.4.1.3052.14.2.12.4.7

evNoData2Sched1Duration OBJECT-TYPE
    SYNTAX Integer32 (0..65535)
    MAX-ACCESS read-write
    STATUS current
    DESCRIPTION
        "Duration (minutes) for schedule 1 of this no data event"
    ::= { evNoData2 8 }
    --1.3.6.1.4.1.3052.14.2.12.4.8

evNoData2Sched2Begin OBJECT-TYPE
    SYNTAX DisplayString
    MAX-ACCESS read-write
    STATUS current
    DESCRIPTION
        "Schedule 2 begin time (HH:MM) for this no data event"
    ::= { evNoData2 9 }
    --1.3.6.1.4.1.3052.14.2.12.4.9

evNoData2Sched2End OBJECT-TYPE
    SYNTAX DisplayString
    MAX-ACCESS read-write
    STATUS current
    DESCRIPTION
        "Schedule 2 end time (HH:MM) for this no data event"
    ::= { evNoData2 10 }
    --1.3.6.1.4.1.3052.14.2.12.4.10

evNoData2Sched2Duration OBJECT-TYPE
    SYNTAX Integer32 (0..65535)
    MAX-ACCESS read-write
    STATUS current
    DESCRIPTION
        "Duration (minutes) for schedule 2 of this no data event"
    ::= { evNoData2 11 }
    --1.3.6.1.4.1.3052.14.2.12.4.11

evNoData2PortEnableTable OBJECT-TYPE
    SYNTAX SEQUENCE OF NoDataEvent2PortEnableConfig
    MAX-ACCESS not-accessible
    STATUS current
    DESCRIPTION
        "Table of no data event 2 port enables"
    ::= { evNoData2 12 }
    --1.3.6.1.4.1.3052.14.2.12.4.12

evNoData2PortEnableEntry OBJECT-TYPE
    SYNTAX NoDataEvent2PortEnableConfig
    MAX-ACCESS not-accessible
    STATUS current
    DESCRIPTION
        "Entry for table of no data event 2 port enables"
    INDEX { evNoData2PortEnableIndex }
    ::= { evNoData2PortEnableTable 1 }
    --1.3.6.1.4.1.3052.14.2.12.4.12.1

evNoData2PortEnableIndex OBJECT-TYPE
    SYNTAX Integer32 (1..16)
    MAX-ACCESS read-only
    STATUS current
    DESCRIPTION
        "Index for table of no data event 2 port enables"
    ::= { evNoData2PortEnableEntry 1 }
    --1.3.6.1.4.1.3052.14.2.12.4.12.1.1

evNoData2PortEnable OBJECT-TYPE
    SYNTAX DisplayString
    MAX-ACCESS read-write
    STATUS current
    DESCRIPTION
        "ON/OFF: no data event 2 observes this port"
    ::= { evNoData2PortEnableEntry 2 }
    --1.3.6.1.4.1.3052.14.2.12.4.12.1.2

evNoData2Exclusions OBJECT-TYPE
    SYNTAX DisplayString
    MAX-ACCESS read-write
    STATUS current
    DESCRIPTION
        "Exclusions (space-separated MM/DD-formatted dates) for this
        no data event"
    ::= { evNoData2 13 }
    --1.3.6.1.4.1.3052.14.2.12.4.13

evNoData2Days OBJECT-TYPE
    SYNTAX DisplayString
    MAX-ACCESS read-write
    STATUS current
    DESCRIPTION
        "Days of the week on which this no event is active"
    ::= { evNoData2 14 }
    --1.3.6.1.4.1.3052.14.2.12.4.14

--***************************************************************************************
--Scheduled Event 1 Section 2.12.5
--***************************************************************************************

evSched1Enable OBJECT-TYPE
    SYNTAX DisplayString
    MAX-ACCESS read-write
    STATUS current
    DESCRIPTION
        "ON/OFF enable this scheduled event"
    ::= { evSched1 1 }
    --1.3.6.1.4.1.3052.14.2.12.5.1

evSched1Actions OBJECT-TYPE
    SYNTAX DisplayString
    MAX-ACCESS read-write
    STATUS current
    DESCRIPTION
        "Actions for this scheduled event"
    ::= { evSched1 2 }
    --1.3.6.1.4.1.3052.14.2.12.5.2

evSched1Message OBJECT-TYPE
    SYNTAX DisplayString
    MAX-ACCESS read-write
    STATUS current
    DESCRIPTION
        "Message for this scheduled event"
    ::= { evSched1 3 }
    --1.3.6.1.4.1.3052.14.2.12.5.3

evSched1TrapNum OBJECT-TYPE
    SYNTAX Integer32
    MAX-ACCESS read-write
    STATUS current
    DESCRIPTION
        "Trap number for this scheduled event"
    ::= { evSched1 4 }
    --1.3.6.1.4.1.3052.14.2.12.5.4

evSched1Class OBJECT-TYPE
    SYNTAX DisplayString
    MAX-ACCESS read-write
    STATUS current
    DESCRIPTION
        "Class for this scheduled event"
    ::= { evSched1 5 }
    --1.3.6.1.4.1.3052.14.2.12.5.5

evSched1Sunday OBJECT-TYPE
    SYNTAX DisplayString
    MAX-ACCESS read-write
    STATUS current
    DESCRIPTION
        "Time on Sunday (HH:MM) when this scheduled event triggers"
    ::= { evSched1 6 }
    --1.3.6.1.4.1.3052.14.2.12.5.6

evSched1Monday OBJECT-TYPE
    SYNTAX DisplayString
    MAX-ACCESS read-write
    STATUS current
    DESCRIPTION
        "Time on Monday (HH:MM) when this scheduled event triggers"
    ::= { evSched1 7 }
    --1.3.6.1.4.1.3052.14.2.12.5.7

evSched1Tuesday OBJECT-TYPE
    SYNTAX DisplayString
    MAX-ACCESS read-write
    STATUS current
    DESCRIPTION
        "Time on Tuesday (HH:MM) when this scheduled event triggers"
    ::= { evSched1 8 }
    --1.3.6.1.4.1.3052.14.2.12.5.8

evSched1Wednesday OBJECT-TYPE
    SYNTAX DisplayString
    MAX-ACCESS read-write
    STATUS current
    DESCRIPTION
        "Time on Wednesday (HH:MM) when this scheduled event triggers"
    ::= { evSched1 9 }
    --1.3.6.1.4.1.3052.14.2.12.5.9

evSched1Thursday OBJECT-TYPE
    SYNTAX DisplayString
    MAX-ACCESS read-write
    STATUS current
    DESCRIPTION
        "Time on Thursday (HH:MM) when this scheduled event triggers"
    ::= { evSched1 10 }
    --1.3.6.1.4.1.3052.14.2.12.5.10

evSched1Friday OBJECT-TYPE
    SYNTAX DisplayString
    MAX-ACCESS read-write
    STATUS current
    DESCRIPTION
        "Time on Friday (HH:MM) when this scheduled event triggers"
    ::= { evSched1 11 }
    --1.3.6.1.4.1.3052.14.2.12.5.11

evSched1Saturday OBJECT-TYPE
    SYNTAX DisplayString
    MAX-ACCESS read-write
    STATUS current
    DESCRIPTION
        "Time on Saturday (HH:MM) when this scheduled event triggers"
    ::= { evSched1 12 }
    --1.3.6.1.4.1.3052.14.2.12.5.12

evSched1Exclusions OBJECT-TYPE
    SYNTAX DisplayString
    MAX-ACCESS read-write
    STATUS current
    DESCRIPTION
        "Exclusions (space-separated MM/DD-formatted dates) for this
        scheduled event"
    ::= { evSched1 13 }
    --1.3.6.1.4.1.3052.14.2.12.5.13


--***************************************************************************************
--Scheduled Event 2 Section 2.12.6
--***************************************************************************************

evSched2Enable OBJECT-TYPE
    SYNTAX DisplayString
    MAX-ACCESS read-write
    STATUS current
    DESCRIPTION
        "ON/OFF enable this scheduled event"
    ::= { evSched2 1 }
    --1.3.6.1.4.1.3052.14.2.12.6.1

evSched2Actions OBJECT-TYPE
    SYNTAX DisplayString
    MAX-ACCESS read-write
    STATUS current
    DESCRIPTION
        "Actions for this scheduled event"
    ::= { evSched2 2 }
    --1.3.6.1.4.1.3052.14.2.12.6.2

evSched2Message OBJECT-TYPE
    SYNTAX DisplayString
    MAX-ACCESS read-write
    STATUS current
    DESCRIPTION
        "Message for this scheduled event"
    ::= { evSched2 3 }
    --1.3.6.1.4.1.3052.14.2.12.6.3

evSched2TrapNum OBJECT-TYPE
    SYNTAX Integer32
    MAX-ACCESS read-write
    STATUS current
    DESCRIPTION
        "Trap number for this scheduled event"
    ::= { evSched2 4 }
    --1.3.6.1.4.1.3052.14.2.12.6.4

evSched2Class OBJECT-TYPE
    SYNTAX DisplayString
    MAX-ACCESS read-write
    STATUS current
    DESCRIPTION
        "Class for this scheduled event"
    ::= { evSched2 5 }
    --1.3.6.1.4.1.3052.14.2.12.6.5

evSched2Sunday OBJECT-TYPE
    SYNTAX DisplayString
    MAX-ACCESS read-write
    STATUS current
    DESCRIPTION
        "Time on Sunday (HH:MM) when this scheduled event triggers"
    ::= { evSched2 6 }
    --1.3.6.1.4.1.3052.14.2.12.6.6

evSched2Monday OBJECT-TYPE
    SYNTAX DisplayString
    MAX-ACCESS read-write
    STATUS current
    DESCRIPTION
        "Time on Monday (HH:MM) when this scheduled event triggers"
    ::= { evSched2 7 }
    --1.3.6.1.4.1.3052.14.2.12.6.7

evSched2Tuesday OBJECT-TYPE
    SYNTAX DisplayString
    MAX-ACCESS read-write
    STATUS current
    DESCRIPTION
        "Time on Tuesday (HH:MM) when this scheduled event triggers"
    ::= { evSched2 8 }
    --1.3.6.1.4.1.3052.14.2.12.6.8

evSched2Wednesday OBJECT-TYPE
    SYNTAX DisplayString
    MAX-ACCESS read-write
    STATUS current
    DESCRIPTION
        "Time on Wednesday (HH:MM) when this scheduled event triggers"
    ::= { evSched2 9 }
    --1.3.6.1.4.1.3052.14.2.12.6.9

evSched2Thursday OBJECT-TYPE
    SYNTAX DisplayString
    MAX-ACCESS read-write
    STATUS current
    DESCRIPTION
        "Time on Thursday (HH:MM) when this scheduled event triggers"
    ::= { evSched2 10 }
    --1.3.6.1.4.1.3052.14.2.12.6.10

evSched2Friday OBJECT-TYPE
    SYNTAX DisplayString
    MAX-ACCESS read-write
    STATUS current
    DESCRIPTION
        "Time on Friday (HH:MM) when this scheduled event triggers"
    ::= { evSched2 11 }
    --1.3.6.1.4.1.3052.14.2.12.6.11

evSched2Saturday OBJECT-TYPE
    SYNTAX DisplayString
    MAX-ACCESS read-write
    STATUS current
    DESCRIPTION
        "Time on Saturday (HH:MM) when this scheduled event triggers"
    ::= { evSched2 12 }
    --1.3.6.1.4.1.3052.14.2.12.6.12

evSched2Exclusions OBJECT-TYPE
    SYNTAX DisplayString
    MAX-ACCESS read-write
    STATUS current
    DESCRIPTION
        "Exclusions (space-separated MM/DD-formatted dates) for this
        scheduled event"
    ::= { evSched2 13 }
    --1.3.6.1.4.1.3052.14.2.12.6.13

--***************************************************************************************
--Serial Handshaking Low Section 2.12.7
--***************************************************************************************

evShskLowTable OBJECT-TYPE
    SYNTAX SEQUENCE OF SerialHandshakingLowEventConfig
    MAX-ACCESS not-accessible
    STATUS current
    DESCRIPTION
        "Table of serial handshaking low events"
    ::= { event 7 }
    --1.3.6.1.4.1.3052.14.2.12.7

evShskLowEntry OBJECT-TYPE
    SYNTAX SerialHandshakingLowEventConfig
    MAX-ACCESS not-accessible
    STATUS current
    DESCRIPTION
        "Entry for table of serial handshaking low events"
    INDEX { evShskLowIndex }
    ::= { evShskLowTable 1 }
    --1.3.6.1.4.1.3052.14.2.12.7.1

evShskLowIndex OBJECT-TYPE
    SYNTAX Integer32 (1..16)
    MAX-ACCESS read-only
    STATUS current
    DESCRIPTION
        "Index for table of serial handshaking low events"
    ::= { evShskLowEntry 1 }
    --1.3.6.1.4.1.3052.14.2.12.7.1.1

evShskLowEnable OBJECT-TYPE
    SYNTAX DisplayString
    MAX-ACCESS read-write
    STATUS current
    DESCRIPTION
        "ON/OFF: enable the serial handshaking low event for this port"
    ::= { evShskLowEntry 2 }
    --1.3.6.1.4.1.3052.14.2.12.7.1.2

evShskLowActions OBJECT-TYPE
    SYNTAX DisplayString
    MAX-ACCESS read-write
    STATUS current
    DESCRIPTION
        "Actions for the serial handshaking low event for this port"
    ::= { evShskLowEntry 3 }
    --1.3.6.1.4.1.3052.14.2.12.7.1.3

evShskLowMessage OBJECT-TYPE
    SYNTAX DisplayString
    MAX-ACCESS read-write
    STATUS current
    DESCRIPTION
        "Message for the serial handshaking low event for this port"
    ::= { evShskLowEntry 4 }
    --1.3.6.1.4.1.3052.14.2.12.7.1.4

evShskLowClass OBJECT-TYPE
    SYNTAX DisplayString
    MAX-ACCESS read-write
    STATUS current
    DESCRIPTION
        "Class for the serial handshaking low event for this port"
    ::= { evShskLowEntry 5 }
    --1.3.6.1.4.1.3052.14.2.12.7.1.5

evShskLowTrapNum OBJECT-TYPE
    SYNTAX Integer32
    MAX-ACCESS read-write
    STATUS current
    DESCRIPTION
        "Trap number for the serial handshaking low event for this port"
    ::= { evShskLowEntry 6 }
    --1.3.6.1.4.1.3052.14.2.12.7.1.6


--***************************************************************************************
--Serial Handshaking High Section 2.12.8
--***************************************************************************************

evShskHighTable OBJECT-TYPE
    SYNTAX SEQUENCE OF SerialHandshakingHighEventConfig
    MAX-ACCESS not-accessible
    STATUS current
    DESCRIPTION
        "Table of serial handshaking high events"
    ::= { event 8 }
    --1.3.6.1.4.1.3052.14.2.12.8

evShskHighEntry OBJECT-TYPE
    SYNTAX SerialHandshakingHighEventConfig
    MAX-ACCESS not-accessible
    STATUS current
    DESCRIPTION
        "Entry for table of serial handshaking high events"
    INDEX { evShskHighIndex }
    ::= { evShskHighTable 1 }
    --1.3.6.1.4.1.3052.14.2.12.8.1

evShskHighIndex OBJECT-TYPE
    SYNTAX Integer32 (1..16)
    MAX-ACCESS read-only
    STATUS current
    DESCRIPTION
        "Index for table of serial handshaking high events"
    ::= { evShskHighEntry 1 }
    --1.3.6.1.4.1.3052.14.2.12.8.1.1

evShskHighEnable OBJECT-TYPE
    SYNTAX DisplayString
    MAX-ACCESS read-write
    STATUS current
    DESCRIPTION
        "ON/OFF: enable the serial handshaking high event for this
        port"
    ::= { evShskHighEntry 2 }
    --1.3.6.1.4.1.3052.14.2.12.8.1.2

evShskHighActions OBJECT-TYPE
    SYNTAX DisplayString
    MAX-ACCESS read-write
    STATUS current
    DESCRIPTION
        "Actions for the serial handshaking high event for this port"
    ::= { evShskHighEntry 3 }
    --1.3.6.1.4.1.3052.14.2.12.8.1.3

evShskHighMessage OBJECT-TYPE
    SYNTAX DisplayString
    MAX-ACCESS read-write
    STATUS current
    DESCRIPTION
        "Message for the serial handshaking high event for this port"
    ::= { evShskHighEntry 4 }
    --1.3.6.1.4.1.3052.14.2.12.8.1.4

evShskHighClass OBJECT-TYPE
    SYNTAX DisplayString
    MAX-ACCESS read-write
    STATUS current
    DESCRIPTION
        "Class for the serial handshaking high event for this port"
    ::= { evShskHighEntry 5 }
    --1.3.6.1.4.1.3052.14.2.12.8.1.5

evShskHighTrapNum OBJECT-TYPE
    SYNTAX Integer32
    MAX-ACCESS read-write
    STATUS current
    DESCRIPTION
        "Trap number for the serial handshaking high event for this
        port"
    ::= { evShskHighEntry 6 }
    --1.3.6.1.4.1.3052.14.2.12.8.1.6



--***************************************************************************************
--No Sensor Event Section 2.12.9
--***************************************************************************************

evNoSensorTimeout OBJECT-TYPE
    SYNTAX Integer32
    MAX-ACCESS read-write
    STATUS current
    DESCRIPTION
        "Timeout (seconds) after which an EventSensor becomes
        unresponsive that this event is triggered"
    ::= { evNoSensor 1 }
    --1.3.6.1.4.1.3052.14.2.12.9.1

evNoSensorActions OBJECT-TYPE
    SYNTAX DisplayString
    MAX-ACCESS read-write
    STATUS current
    DESCRIPTION
        "Actions for no sensor event"
    ::= { evNoSensor 2 }
    --1.3.6.1.4.1.3052.14.2.12.9.2

evNoSensorTrapNum OBJECT-TYPE
    SYNTAX Integer32
    MAX-ACCESS read-write
    STATUS current
    DESCRIPTION
        "Trap number for no sensor event"
    ::= { evNoSensor 3 }
    --1.3.6.1.4.1.3052.14.2.12.9.3

evNoSensorClass OBJECT-TYPE
    SYNTAX DisplayString
    MAX-ACCESS read-write
    STATUS current
    DESCRIPTION
        "Class for no sensor event"
    ::= { evNoSensor 4 }
    --1.3.6.1.4.1.3052.14.2.12.9.4



--***************************************************************************************
--Fuel Sensor Config Section       2.12.11
--***************************************************************************************


fuelSensorGeneralTable OBJECT-TYPE
    SYNTAX SEQUENCE OF FuelSensorConfigGeneral
    MAX-ACCESS not-accessible
    STATUS current
    DESCRIPTION
        "This table organizes general fuel sensor attributes."
    ::= { fuelSensor 1 }
    --1.3.6.1.4.1.3052.14.2.12.11.1

fsGenEntry OBJECT-TYPE
    SYNTAX FuelSensorConfigGeneral
    MAX-ACCESS not-accessible
    STATUS current
    DESCRIPTION
        "Entry for fuel sensor general config table."
    INDEX { fsGenIndex }
    ::= { fuelSensorGeneralTable 1 }
    --1.3.6.1.4.1.3052.14.2.12.11.1.1

fsGenIndex OBJECT-TYPE
    SYNTAX Integer32 (1..3)
    MAX-ACCESS read-only
    STATUS current
    DESCRIPTION
        "Which fuel sensor in the fuel sensor general config table."
    ::= { fsGenEntry 1 }
    --1.3.6.1.4.1.3052.14.2.12.11.1.1.1

fsGenName OBJECT-TYPE
    SYNTAX DisplayString
    MAX-ACCESS read-write
    STATUS current
    DESCRIPTION
        "Fuel sensor name."
    ::= { fsGenEntry 2 }
    --1.3.6.1.4.1.3052.14.2.12.11.1.1.2

fsGenSensorType OBJECT-TYPE
    SYNTAX DisplayString
    MAX-ACCESS read-write
    STATUS current
    DESCRIPTION
        "Type of fuel sensor in use; NONE disables the fuel sensor."
    ::= { fsGenEntry 3 }
    --1.3.6.1.4.1.3052.14.2.12.11.1.1.3

fsGenDistanceUnit OBJECT-TYPE
    SYNTAX DisplayString
    MAX-ACCESS read-write
    STATUS current
    DESCRIPTION
        "Distance units in use when setting and indicating tank dimensions."
    ::= { fsGenEntry 4 }
    --1.3.6.1.4.1.3052.14.2.12.11.1.1.4

fsGenRawValueTop OBJECT-TYPE
    SYNTAX DisplayString
    MAX-ACCESS read-write
    STATUS current
    DESCRIPTION
        "Analog input reading corresponding to the SENSOR FULL point."
    ::= { fsGenEntry 5 }
    --1.3.6.1.4.1.3052.14.2.12.11.1.1.5

fsGenTopOffset OBJECT-TYPE
    SYNTAX DisplayString
    MAX-ACCESS read-write
    STATUS current
    DESCRIPTION
        "Distance, in the specified distance unit, between the SENSOR FULL
        point and the TANK FULL point.  The value is positive if the
        SENSOR FULL point is above the TANK FULL point, and negative if it is
        below."
    ::= { fsGenEntry 6 }
    --1.3.6.1.4.1.3052.14.2.12.11.1.1.6

fsGenRawValueBottom OBJECT-TYPE
    SYNTAX DisplayString
    MAX-ACCESS read-write
    STATUS current
    DESCRIPTION
        "Analog input reading corresponding to the minimum fluid height
        measurable by the fuel sensor."
    ::= { fsGenEntry 7 }
    --1.3.6.1.4.1.3052.14.2.12.11.1.1.7

fsGenBottomOffset OBJECT-TYPE
    SYNTAX DisplayString
    MAX-ACCESS read-write
    STATUS current
    DESCRIPTION
        "Distance, in the specified distance unit, between the SENSOR EMPTY
        point and the TANK EMPTY point.  The value is positive if the
        SENSOR EMPTY point is above the TANK EMPTY point, and negative if it
        is below."
    ::= { fsGenEntry 8 }
    --1.3.6.1.4.1.3052.14.2.12.11.1.1.8

fsGenInputES OBJECT-TYPE
    SYNTAX Integer32 (1..200)
    MAX-ACCESS read-write
    STATUS current
    DESCRIPTION
        "Which eventsensor contains the analog input associated with this fuel
        sensor. Allowed values are 200 (for internal ES), or 1-16."
    ::= { fsGenEntry 9 }
    --1.3.6.1.4.1.3052.14.2.12.11.1.1.9

fsGenInputPoint OBJECT-TYPE
    SYNTAX Integer32 (1..16)
    MAX-ACCESS read-write
    STATUS current
    DESCRIPTION
        "Which analog input point, on the specified eventsensor, that is
        associated with the fuel sensor."
    ::= { fsGenEntry 10 }
    --1.3.6.1.4.1.3052.14.2.12.11.1.1.10

fsGenFilterAveraging OBJECT-TYPE
    SYNTAX Integer32
    MAX-ACCESS read-write
    STATUS current
    DESCRIPTION
        "Fuel sensor filter averaging factor."
    ::= { fsGenEntry 11 }
    --1.3.6.1.4.1.3052.14.2.12.11.1.1.11

fsGenSysrepEnable OBJECT-TYPE
    SYNTAX DisplayString
    MAX-ACCESS read-write
    STATUS current
    DESCRIPTION
        "Fuel sensor System Reporting enable."
    ::= { fsGenEntry 12 }
    --1.3.6.1.4.1.3052.14.2.12.11.1.1.12

fsGenSysrepThreshold OBJECT-TYPE
    SYNTAX DisplayString
    MAX-ACCESS read-write
    STATUS current
    DESCRIPTION
        "Fuel sensor System Reporting threshold (floating point value)."
    ::= { fsGenEntry 13 }
    --1.3.6.1.4.1.3052.14.2.12.11.1.1.13

fsGenSysrepLimit OBJECT-TYPE
    SYNTAX Integer32
    MAX-ACCESS read-write
    STATUS current
    DESCRIPTION
        "Fuel sensor System Reporting limit."
    ::= { fsGenEntry 14 }
    --1.3.6.1.4.1.3052.14.2.12.11.1.1.14

fsGenSysrepPackage OBJECT-TYPE
    SYNTAX Integer32 (0..10)
    MAX-ACCESS read-write
    STATUS current
    DESCRIPTION
        "Fuel sensor System Reporting package number."
    ::= { fsGenEntry 15 }
    --1.3.6.1.4.1.3052.14.2.12.11.1.1.15

fsGenSysrepType OBJECT-TYPE
    SYNTAX DisplayString
    MAX-ACCESS read-write
    STATUS current
    DESCRIPTION
        "Fuel sensor ASM profile type."
    ::= { fsGenEntry 16 }
    --1.3.6.1.4.1.3052.14.2.12.11.1.1.16

fsGenEnable OBJECT-TYPE
    SYNTAX DisplayString
    MAX-ACCESS read-write
    STATUS current
    DESCRIPTION
        "Fuel sensor enable."
    ::= { fsGenEntry 17 }
    --1.3.6.1.4.1.3052.14.2.12.11.1.1.17


fuelSensorTankTable OBJECT-TYPE
    SYNTAX SEQUENCE OF FuelSensorConfigTank
    MAX-ACCESS not-accessible
    STATUS current
    DESCRIPTION
        "This table organizes tank-specific fuel sensor attributes."
    ::= { fuelSensor 2 }
    --1.3.6.1.4.1.3052.14.2.12.11.2

fsTankEntry OBJECT-TYPE
    SYNTAX FuelSensorConfigTank
    MAX-ACCESS not-accessible
    STATUS current
    DESCRIPTION
        "Entry for fuel sensor tank config table."
    INDEX { fsTankIndex }
    ::= { fuelSensorTankTable 1 }
    --1.3.6.1.4.1.3052.14.2.12.11.2.1

fsTankIndex OBJECT-TYPE
    SYNTAX Integer32 (1..3)
    MAX-ACCESS read-only
    STATUS current
    DESCRIPTION
        "Which fuel sensor in the fuel sensor tank config table."
    ::= { fsTankEntry 1 }
    --1.3.6.1.4.1.3052.14.2.12.11.2.1.1

fsTankHeight OBJECT-TYPE
    SYNTAX DisplayString
    MAX-ACCESS read-write
    STATUS current
    DESCRIPTION
        "Height of the tank, from the TANK EMPTY point to the TANK FULL point,
        in the specified distance unit (i.e. TANK HEIGHT).  This is a
        floating point value."
    ::= { fsTankEntry 2 }
    --1.3.6.1.4.1.3052.14.2.12.11.2.1.2

fsTankDimA OBJECT-TYPE
    SYNTAX DisplayString
    MAX-ACCESS read-write
    STATUS current
    DESCRIPTION
        "Tank dimension measurement A for certain tank profiles. For
        HORIZ OVAL, this is the length of the straight section.  This is a
        floating point value."
    ::= { fsTankEntry 3 }
    --1.3.6.1.4.1.3052.14.2.12.11.2.1.3

fsTankDimB OBJECT-TYPE
    SYNTAX DisplayString
    MAX-ACCESS read-write
    STATUS current
    DESCRIPTION
        "Tank dimension measurement B for certain tank profiles. For
        HORIZ OVAL, this is the radius of the curved section.  This is a
        floating point value."
    ::= { fsTankEntry 4 }
    --1.3.6.1.4.1.3052.14.2.12.11.2.1.4

fsTankVolume OBJECT-TYPE
    SYNTAX DisplayString
    MAX-ACCESS read-write
    STATUS current
    DESCRIPTION
        "How many volume units the tank contains, when full.  This is a
        floating point value."
    ::= { fsTankEntry 5 }
    --1.3.6.1.4.1.3052.14.2.12.11.2.1.5

fsTankVolumeUnit OBJECT-TYPE
    SYNTAX DisplayString
    MAX-ACCESS read-write
    STATUS current
    DESCRIPTION
        "Name of the unit representing fluid volume in the tank. This is only
        used for display purposes; it does not affect the volume calculation."
    ::= { fsTankEntry 6 }
    --1.3.6.1.4.1.3052.14.2.12.11.2.1.6

fsTankShape OBJECT-TYPE
    SYNTAX DisplayString
    MAX-ACCESS read-write
    STATUS current
    DESCRIPTION
        "The shape of the fuel tank.  A value of LINEAR produces a fluid
        volume reading that is directly proportional to fluid height.  The
        HORIZ CYL and HORIZ OVAL settings use a hard-coded formula to
        calculate the volume.  The CUSTOM setting uses a strapping table that
        must be configured as well (see fuelSensorCustomTankTable)."
    ::= { fsTankEntry 7 }
    --1.3.6.1.4.1.3052.14.2.12.11.2.1.7


fuelSensorCustomTankTable OBJECT-TYPE
    SYNTAX SEQUENCE OF FuelSensorConfigCustomTankStrapping
    MAX-ACCESS not-accessible
    STATUS current
    DESCRIPTION
        "This table organizes the custom tank strapping table.  Each fuel
        sensor has a table of height/volume pairs in service only when the tank
        shape (fsTankShape) in CUSTOM.  This allows the unit to calculate
        volumes for nonstandard tank shapes, to the degree that accurate
        height/volume measurements can be configured.  This SNMP table has two
        indexes: the first for which fuel sensor and the second for which
        height/volume pair."
    ::= { fuelSensor 3 }
    --1.3.6.1.4.1.3052.14.2.12.11.3

fsCustomTankEntry OBJECT-TYPE
    SYNTAX FuelSensorConfigCustomTankStrapping
    MAX-ACCESS not-accessible
    STATUS current
    DESCRIPTION
        "Entry for fuel sensor custom tank config table."
    INDEX { fsCustomTankIndexFS, fsCustomTankIndexDatum }
    ::= { fuelSensorCustomTankTable 1 }
    --1.3.6.1.4.1.3052.14.2.12.11.3.1

fsCustomTankIndexFS OBJECT-TYPE
    SYNTAX Integer32 (1..3)
    MAX-ACCESS read-only
    STATUS current
    DESCRIPTION
        "Which fuel sensor in the fuel sensor tank config table.  This is the
        first of two indexes for this SNMP table."
    ::= { fsCustomTankEntry 1 }
    --1.3.6.1.4.1.3052.14.2.12.11.3.1.1

fsCustomTankIndexDatum OBJECT-TYPE
    SYNTAX Integer32 (1..32)
    MAX-ACCESS read-only
    STATUS current
    DESCRIPTION
        "Which hight/volume pair: there are 32 pairs per fuel sensor.  This is
        the second of two indexes for this SNMP table."
    ::= { fsCustomTankEntry 2 }
    --1.3.6.1.4.1.3052.14.2.12.11.3.1.2

fsCustomTankHeight OBJECT-TYPE
    SYNTAX DisplayString
    MAX-ACCESS read-write
    STATUS current
    DESCRIPTION
        "Height of custom tank height/volume pair.  This is a floating point
        value."
    ::= { fsCustomTankEntry 3 }
    --1.3.6.1.4.1.3052.14.2.12.11.3.1.3

fsCustomTankVolume OBJECT-TYPE
    SYNTAX DisplayString
    MAX-ACCESS read-write
    STATUS current
    DESCRIPTION
        "Volume of custom tank height/volume pair.  This is a floating point
        value."
    ::= { fsCustomTankEntry 4 }
    --1.3.6.1.4.1.3052.14.2.12.11.3.1.4


fuelSensorVolumeTable OBJECT-TYPE
    SYNTAX SEQUENCE OF FuelSensorConfigVolume
    MAX-ACCESS not-accessible
    STATUS current
    DESCRIPTION
        "This table organizes volume-event-specific fuel sensor attributes."
    ::= { fuelSensor 4 }
    --1.3.6.1.4.1.3052.14.2.12.11.4

fsVolumeEntry OBJECT-TYPE
    SYNTAX FuelSensorConfigVolume
    MAX-ACCESS not-accessible
    STATUS current
    DESCRIPTION
        "Entry for fuel sensor volume event config table."
    INDEX { fsVolumeIndex }
    ::= { fuelSensorVolumeTable 1 }
    --1.3.6.1.4.1.3052.14.2.12.11.4.1

fsVolumeIndex OBJECT-TYPE
    SYNTAX Integer32 (1..3)
    MAX-ACCESS read-only
    STATUS current
    DESCRIPTION
        "Which fuel sensor in the fuel sensor volume event config table."
    ::= { fsVolumeEntry 1 }
    --1.3.6.1.4.1.3052.14.2.12.11.4.1.1

fsVolumeEnable OBJECT-TYPE
    SYNTAX DisplayString
    MAX-ACCESS read-write
    STATUS current
    DESCRIPTION
        "Enable fuel sensor volume events."
    ::= { fsVolumeEntry 2 }
    --1.3.6.1.4.1.3052.14.2.12.11.4.1.2

fsVolumeDeadband OBJECT-TYPE
    SYNTAX DisplayString
    MAX-ACCESS read-write
    STATUS current
    DESCRIPTION
        "Fuel sensor deadband (hysteresis).  This is a floating point value."
    ::= { fsVolumeEntry 3 }
    --1.3.6.1.4.1.3052.14.2.12.11.4.1.3

fsVolumeVHighValue OBJECT-TYPE
    SYNTAX DisplayString
    MAX-ACCESS read-write
    STATUS current
    DESCRIPTION
        "Fuel sensor volume very high event threshold value.  This is a
        floating point value."
    ::= { fsVolumeEntry 4 }
    --1.3.6.1.4.1.3052.14.2.12.11.4.1.4

fsVolumeVHighActions OBJECT-TYPE
    SYNTAX DisplayString
    MAX-ACCESS read-write
    STATUS current
    DESCRIPTION
        "Fuel sensor volume very high event threshold actions."
    ::= { fsVolumeEntry 5 }
    --1.3.6.1.4.1.3052.14.2.12.11.4.1.5

fsVolumeVHighTrapNum OBJECT-TYPE
    SYNTAX Integer32 (519..1199)
    MAX-ACCESS read-write
    STATUS current
    DESCRIPTION
        "Fuel sensor volume very high event threshold trap number."
    ::= { fsVolumeEntry 6 }
    --1.3.6.1.4.1.3052.14.2.12.11.4.1.6

fsVolumeVHighClass OBJECT-TYPE
    SYNTAX DisplayString
    MAX-ACCESS read-write
    STATUS current
    DESCRIPTION
        "Fuel sensor volume very high event threshold class (severity)."
    ::= { fsVolumeEntry 7 }
    --1.3.6.1.4.1.3052.14.2.12.11.4.1.7

fsVolumeHighValue OBJECT-TYPE
    SYNTAX DisplayString
    MAX-ACCESS read-write
    STATUS current
    DESCRIPTION
        "Fuel sensor volume high event threshold value.  This is a floating
        point value."
    ::= { fsVolumeEntry 8 }
    --1.3.6.1.4.1.3052.14.2.12.11.4.1.8

fsVolumeHighActions OBJECT-TYPE
    SYNTAX DisplayString
    MAX-ACCESS read-write
    STATUS current
    DESCRIPTION
        "Fuel sensor volume high event threshold actions."
    ::= { fsVolumeEntry 9 }
    --1.3.6.1.4.1.3052.14.2.12.11.4.1.9

fsVolumeHighTrapNum OBJECT-TYPE
    SYNTAX Integer32 (519..1199)
    MAX-ACCESS read-write
    STATUS current
    DESCRIPTION
        "Fuel sensor volume high event threshold trap number."
    ::= { fsVolumeEntry 10 }
    --1.3.6.1.4.1.3052.14.2.12.11.4.1.10

fsVolumeHighClass OBJECT-TYPE
    SYNTAX DisplayString
    MAX-ACCESS read-write
    STATUS current
    DESCRIPTION
        "Fuel sensor volume high event threshold class (severity)."
    ::= { fsVolumeEntry 11 }
    --1.3.6.1.4.1.3052.14.2.12.11.4.1.11

fsVolumeNormalActions OBJECT-TYPE
    SYNTAX DisplayString
    MAX-ACCESS read-write
    STATUS current
    DESCRIPTION
        "Fuel sensor volume return to normal actions."
    ::= { fsVolumeEntry 12 }
    --1.3.6.1.4.1.3052.14.2.12.11.4.1.12

fsVolumeNormalTrapNum OBJECT-TYPE
    SYNTAX Integer32 (519..1199)
    MAX-ACCESS read-write
    STATUS current
    DESCRIPTION
        "Fuel sensor volume return to normal trap number."
    ::= { fsVolumeEntry 13 }
    --1.3.6.1.4.1.3052.14.2.12.11.4.1.13

fsVolumeNormalClass OBJECT-TYPE
    SYNTAX DisplayString
    MAX-ACCESS read-write
    STATUS current
    DESCRIPTION
        "Fuel sensor volume return to normal class (severity)."
    ::= { fsVolumeEntry 14 }
    --1.3.6.1.4.1.3052.14.2.12.11.4.1.14

fsVolumeLowValue OBJECT-TYPE
    SYNTAX DisplayString
    MAX-ACCESS read-write
    STATUS current
    DESCRIPTION
        "Fuel sensor volume low event threshold value.  This is a floating
        point value."
    ::= { fsVolumeEntry 15 }
    --1.3.6.1.4.1.3052.14.2.12.11.4.1.15

fsVolumeLowActions OBJECT-TYPE
    SYNTAX DisplayString
    MAX-ACCESS read-write
    STATUS current
    DESCRIPTION
        "Fuel sensor volume low event threshold actions."
    ::= { fsVolumeEntry 16 }
    --1.3.6.1.4.1.3052.14.2.12.11.4.1.16

fsVolumeLowTrapNum OBJECT-TYPE
    SYNTAX Integer32 (519..1199)
    MAX-ACCESS read-write
    STATUS current
    DESCRIPTION
        "Fuel sensor volume low event threshold trap number."
    ::= { fsVolumeEntry 17 }
    --1.3.6.1.4.1.3052.14.2.12.11.4.1.17

fsVolumeLowClass OBJECT-TYPE
    SYNTAX DisplayString
    MAX-ACCESS read-write
    STATUS current
    DESCRIPTION
        "Fuel sensor volume low event threshold class (severity)."
    ::= { fsVolumeEntry 18 }
    --1.3.6.1.4.1.3052.14.2.12.11.4.1.18

fsVolumeVLowValue OBJECT-TYPE
    SYNTAX DisplayString
    MAX-ACCESS read-write
    STATUS current
    DESCRIPTION
        "Fuel sensor volume very low event threshold value.  This is a
        floating point value."
    ::= { fsVolumeEntry 19 }
    --1.3.6.1.4.1.3052.14.2.12.11.4.1.19

fsVolumeVLowActions OBJECT-TYPE
    SYNTAX DisplayString
    MAX-ACCESS read-write
    STATUS current
    DESCRIPTION
        "Fuel sensor volume very low event threshold actions."
    ::= { fsVolumeEntry 20 }
    --1.3.6.1.4.1.3052.14.2.12.11.4.1.20

fsVolumeVLowTrapNum OBJECT-TYPE
    SYNTAX Integer32 (519..1199)
    MAX-ACCESS read-write
    STATUS current
    DESCRIPTION
        "Fuel sensor volume very low event threshold trap number."
    ::= { fsVolumeEntry 21 }
    --1.3.6.1.4.1.3052.14.2.12.11.4.1.21

fsVolumeVLowClass OBJECT-TYPE
    SYNTAX DisplayString
    MAX-ACCESS read-write
    STATUS current
    DESCRIPTION
        "Fuel sensor volume very low event threshold class (severity)."
    ::= { fsVolumeEntry 22 }
    --1.3.6.1.4.1.3052.14.2.12.11.4.1.22



fuelSensorDisconnectTable OBJECT-TYPE
    SYNTAX SEQUENCE OF FuelSensorConfigDisconnect
    MAX-ACCESS not-accessible
    STATUS current
    DESCRIPTION
        "This table organizes disconnect-event-specific fuel sensor attributes."
    ::= { fuelSensor 5 }
    --1.3.6.1.4.1.3052.14.2.12.11.5

fsDiscEntry OBJECT-TYPE
    SYNTAX FuelSensorConfigDisconnect
    MAX-ACCESS not-accessible
    STATUS current
    DESCRIPTION
        "Entry for fuel sensor disconnect event config table."
    INDEX { fsDiscIndex }
    ::= { fuelSensorDisconnectTable 1 }
    --1.3.6.1.4.1.3052.14.2.12.11.5.1

fsDiscIndex OBJECT-TYPE
    SYNTAX Integer32 (1..3)
    MAX-ACCESS read-only
    STATUS current
    DESCRIPTION
        "Which fuel sensor in the fuel sensor disconnect event config table."
    ::= { fsDiscEntry 1 }
    --1.3.6.1.4.1.3052.14.2.12.11.5.1.1

fsDiscEnable OBJECT-TYPE
    SYNTAX DisplayString
    MAX-ACCESS read-write
    STATUS current
    DESCRIPTION
        "Fuel sensor disconnect event enable."
    ::= { fsDiscEntry 2 }
    --1.3.6.1.4.1.3052.14.2.12.11.5.1.2

fsDiscHighValue OBJECT-TYPE
    SYNTAX DisplayString
    MAX-ACCESS read-write
    STATUS current
    DESCRIPTION
        "High end of input value range when fuel sensor is disconnected.  This
        is in the units of the analog input value."
    ::= { fsDiscEntry 3 }
    --1.3.6.1.4.1.3052.14.2.12.11.5.1.3

fsDiscLowValue OBJECT-TYPE
    SYNTAX DisplayString
    MAX-ACCESS read-write
    STATUS current
    DESCRIPTION
        "Low end of input value range when fuel sensor is disconnected.  This
        is in the units of the analog input value."
    ::= { fsDiscEntry 4 }
    --1.3.6.1.4.1.3052.14.2.12.11.5.1.4

fsDiscActions OBJECT-TYPE
    SYNTAX DisplayString
    MAX-ACCESS read-write
    STATUS current
    DESCRIPTION
        "Fuel sensor disconnect event actions."
    ::= { fsDiscEntry 5 }
    --1.3.6.1.4.1.3052.14.2.12.11.5.1.5

fsDiscTrapNum OBJECT-TYPE
    SYNTAX Integer32 (515..1199)
    MAX-ACCESS read-write
    STATUS current
    DESCRIPTION
        "Fuel sensor disconnect event trap number."
    ::= { fsDiscEntry 6 }
    --1.3.6.1.4.1.3052.14.2.12.11.5.1.6

fsDiscClass OBJECT-TYPE
    SYNTAX DisplayString
    MAX-ACCESS read-write
    STATUS current
    DESCRIPTION
        "Fuel sensor disconnect event class (severity)."
    ::= { fsDiscEntry 7 }
    --1.3.6.1.4.1.3052.14.2.12.11.5.1.7

fsDiscNormalActions OBJECT-TYPE
    SYNTAX DisplayString
    MAX-ACCESS read-write
    STATUS current
    DESCRIPTION
        "Fuel sensor disconnect return to normal actions."
    ::= { fsDiscEntry 8 }
    --1.3.6.1.4.1.3052.14.2.12.11.5.1.8

fsDiscNormalTrapNum OBJECT-TYPE
    SYNTAX Integer32 (515..1199)
    MAX-ACCESS read-write
    STATUS current
    DESCRIPTION
        "Fuel sensor disconnect return to normal trap number."
    ::= { fsDiscEntry 9 }
    --1.3.6.1.4.1.3052.14.2.12.11.5.1.9

fsDiscNormalClass OBJECT-TYPE
    SYNTAX DisplayString
    MAX-ACCESS read-write
    STATUS current
    DESCRIPTION
        "Fuel sensor disconnect return to normal class (severity)."
    ::= { fsDiscEntry 10 }
    --1.3.6.1.4.1.3052.14.2.12.11.5.1.10


--***************************************************************************************
--AC Power Monitor Config Section       2.12.12
--***************************************************************************************

acpmGeneralTable OBJECT-TYPE
    SYNTAX SEQUENCE OF ACPMConfigGeneral
    MAX-ACCESS not-accessible
    STATUS current
    DESCRIPTION
        "This table organizes general AC power monitor attributes."
    ::= { acPowerMonitor 1 }
    --1.3.6.1.4.1.3052.14.2.12.12.1

acpmGenEntry OBJECT-TYPE
    SYNTAX ACPMConfigGeneral
    MAX-ACCESS not-accessible
    STATUS current
    DESCRIPTION
        "Entry for AC power monitor general config table."
    INDEX { acpmGenIndex }
    ::= { acpmGeneralTable 1 }
    --1.3.6.1.4.1.3052.14.2.12.12.1.1

acpmGenIndex OBJECT-TYPE
    SYNTAX Integer32 (1..6)
    MAX-ACCESS read-only
    STATUS current
    DESCRIPTION
        "Which AC power monitor in the AC power monitor general config table."
    ::= { acpmGenEntry 1 }
    --1.3.6.1.4.1.3052.14.2.12.12.1.1.1

acpmGenDevice OBJECT-TYPE
    SYNTAX DisplayString
    MAX-ACCESS read-write
    STATUS current
    DESCRIPTION
        "Model of the AC power monitor device. The unit needs this setting to
        know which registers to poll for the various data items, among other
        things."
    ::= { acpmGenEntry 2 }
    --1.3.6.1.4.1.3052.14.2.12.12.1.1.2

acpmGenName OBJECT-TYPE
    SYNTAX DisplayString
    MAX-ACCESS read-write
    STATUS current
    DESCRIPTION
        "Name for the AC power monitor device."
    ::= { acpmGenEntry 3 }
    --1.3.6.1.4.1.3052.14.2.12.12.1.1.3

acpmGenAddress OBJECT-TYPE
    SYNTAX Integer32 (1..247)
    MAX-ACCESS read-write
    STATUS current
    DESCRIPTION
        "Modbus address of the AC power monitor device."
    ::= { acpmGenEntry 4 }
    --1.3.6.1.4.1.3052.14.2.12.12.1.1.4

acpmGenPtRatio OBJECT-TYPE
    SYNTAX Integer32 (1..10000)
    MAX-ACCESS read-write
    STATUS current
    DESCRIPTION
        "Ratio of secondary turns to primary turns on potential transformers
        (PT)."
    ::= { acpmGenEntry 5 }
    --1.3.6.1.4.1.3052.14.2.12.12.1.1.5

acpmGenCtRatio OBJECT-TYPE
    SYNTAX Integer32 (1..10000)
    MAX-ACCESS read-write
    STATUS current
    DESCRIPTION
        "Ratio of secondary turns to primary turns on current transformers
        (CT)."
    ::= { acpmGenEntry 6 }
    --1.3.6.1.4.1.3052.14.2.12.12.1.1.6

acpmGenPowerType OBJECT-TYPE
    SYNTAX DisplayString
    MAX-ACCESS read-write
    STATUS current
    DESCRIPTION
        "Type of power being monitored."
    ::= { acpmGenEntry 7 }
    --1.3.6.1.4.1.3052.14.2.12.12.1.1.7

acpmGenSysrepPackage OBJECT-TYPE
    SYNTAX Integer32 (0..10)
    MAX-ACCESS read-write
    STATUS current
    DESCRIPTION
        "System reporting package number."
    ::= { acpmGenEntry 8 }
    --1.3.6.1.4.1.3052.14.2.12.12.1.1.8

acpmGenSysrepType OBJECT-TYPE
    SYNTAX DisplayString
    MAX-ACCESS read-write
    STATUS current
    DESCRIPTION
        "ASM profile type."
    ::= { acpmGenEntry 9 }
    --1.3.6.1.4.1.3052.14.2.12.12.1.1.9

acpmGenEnable OBJECT-TYPE
    SYNTAX DisplayString
    MAX-ACCESS read-write
    STATUS current
    DESCRIPTION
        "AC power monitor enable."
    ::= { acpmGenEntry 10 }
    --1.3.6.1.4.1.3052.14.2.12.12.1.1.10


acpmAvgVoltageTable OBJECT-TYPE
    SYNTAX SEQUENCE OF ACPMConfigAvgVoltage
    MAX-ACCESS not-accessible
    STATUS current
    DESCRIPTION
        "This table organizes AC power monitor average voltage attributes."
    ::= { acPowerMonitor 2 }
    --1.3.6.1.4.1.3052.14.2.12.12.2

acpmAvgVoltageEntry OBJECT-TYPE
    SYNTAX ACPMConfigAvgVoltage
    MAX-ACCESS not-accessible
    STATUS current
    DESCRIPTION
        "Entry for AC power monitor average voltage config table."
    INDEX { acpmAvgVoltageIndex }
    ::= { acpmAvgVoltageTable 1 }
    --1.3.6.1.4.1.3052.14.2.12.12.2.1

acpmAvgVoltageIndex OBJECT-TYPE
    SYNTAX Integer32 (1..6)
    MAX-ACCESS read-only
    STATUS current
    DESCRIPTION
        "Which AC power monitor in the AC power monitor average voltage config
        table."
    ::= { acpmAvgVoltageEntry 1 }
    --1.3.6.1.4.1.3052.14.2.12.12.2.1.1

acpmAvgVoltageEnable OBJECT-TYPE
    SYNTAX DisplayString
    MAX-ACCESS read-write
    STATUS current
    DESCRIPTION
        "Enable AC power monitor average voltage events."
    ::= { acpmAvgVoltageEntry 2 }
    --1.3.6.1.4.1.3052.14.2.12.12.2.1.2

acpmAvgVoltageDeadband OBJECT-TYPE
    SYNTAX DisplayString
    MAX-ACCESS read-write
    STATUS current
    DESCRIPTION
        "Deadband (hysteresis) for average voltage event.  This is a floating
        point value."
    ::= { acpmAvgVoltageEntry 3 }
    --1.3.6.1.4.1.3052.14.2.12.12.2.1.3

acpmAvgVoltageVHighValue OBJECT-TYPE
    SYNTAX DisplayString
    MAX-ACCESS read-write
    STATUS current
    DESCRIPTION
        "Very high event threshold.  This is a floating point value."
    ::= { acpmAvgVoltageEntry 4 }
    --1.3.6.1.4.1.3052.14.2.12.12.2.1.4

acpmAvgVoltageVHighActions OBJECT-TYPE
    SYNTAX DisplayString
    MAX-ACCESS read-write
    STATUS current
    DESCRIPTION
        "Very high event actions."
    ::= { acpmAvgVoltageEntry 5 }
    --1.3.6.1.4.1.3052.14.2.12.12.2.1.5

acpmAvgVoltageVHighTrapNum OBJECT-TYPE
    SYNTAX Integer32 (520..1199)
    MAX-ACCESS read-write
    STATUS current
    DESCRIPTION
        "Very high event trap number."
    ::= { acpmAvgVoltageEntry 6 }
    --1.3.6.1.4.1.3052.14.2.12.12.2.1.6

acpmAvgVoltageVHighClass OBJECT-TYPE
    SYNTAX DisplayString
    MAX-ACCESS read-write
    STATUS current
    DESCRIPTION
        "Very high event class."
    ::= { acpmAvgVoltageEntry 7 }
    --1.3.6.1.4.1.3052.14.2.12.12.2.1.7

acpmAvgVoltageHighValue OBJECT-TYPE
    SYNTAX DisplayString
    MAX-ACCESS read-write
    STATUS current
    DESCRIPTION
        "High event threshold.  This is a floating point value."
    ::= { acpmAvgVoltageEntry 8 }
    --1.3.6.1.4.1.3052.14.2.12.12.2.1.8

acpmAvgVoltageHighActions OBJECT-TYPE
    SYNTAX DisplayString
    MAX-ACCESS read-write
    STATUS current
    DESCRIPTION
        "High event actions."
    ::= { acpmAvgVoltageEntry 9 }
    --1.3.6.1.4.1.3052.14.2.12.12.2.1.9

acpmAvgVoltageHighTrapNum OBJECT-TYPE
    SYNTAX Integer32 (520..1199)
    MAX-ACCESS read-write
    STATUS current
    DESCRIPTION
        "High event trap number."
    ::= { acpmAvgVoltageEntry 10 }
    --1.3.6.1.4.1.3052.14.2.12.12.2.1.10

acpmAvgVoltageHighClass OBJECT-TYPE
    SYNTAX DisplayString
    MAX-ACCESS read-write
    STATUS current
    DESCRIPTION
        "High event class."
    ::= { acpmAvgVoltageEntry 11 }
    --1.3.6.1.4.1.3052.14.2.12.12.2.1.11

acpmAvgVoltageNormalActions OBJECT-TYPE
    SYNTAX DisplayString
    MAX-ACCESS read-write
    STATUS current
    DESCRIPTION
        "Return to normal actions."
    ::= { acpmAvgVoltageEntry 12 }
    --1.3.6.1.4.1.3052.14.2.12.12.2.1.12

acpmAvgVoltageNormalTrapNum OBJECT-TYPE
    SYNTAX Integer32 (520..1199)
    MAX-ACCESS read-write
    STATUS current
    DESCRIPTION
        "Return to normal trap number."
    ::= { acpmAvgVoltageEntry 13 }
    --1.3.6.1.4.1.3052.14.2.12.12.2.1.13

acpmAvgVoltageNormalClass OBJECT-TYPE
    SYNTAX DisplayString
    MAX-ACCESS read-write
    STATUS current
    DESCRIPTION
        "Return to normal class."
    ::= { acpmAvgVoltageEntry 14 }
    --1.3.6.1.4.1.3052.14.2.12.12.2.1.14

acpmAvgVoltageLowValue OBJECT-TYPE
    SYNTAX DisplayString
    MAX-ACCESS read-write
    STATUS current
    DESCRIPTION
        "Low event threshold.  This is a floating point value."
    ::= { acpmAvgVoltageEntry 15 }
    --1.3.6.1.4.1.3052.14.2.12.12.2.1.15

acpmAvgVoltageLowActions OBJECT-TYPE
    SYNTAX DisplayString
    MAX-ACCESS read-write
    STATUS current
    DESCRIPTION
        "Low event actions."
    ::= { acpmAvgVoltageEntry 16 }
    --1.3.6.1.4.1.3052.14.2.12.12.2.1.16

acpmAvgVoltageLowTrapNum OBJECT-TYPE
    SYNTAX Integer32 (520..1199)
    MAX-ACCESS read-write
    STATUS current
    DESCRIPTION
        "Low event trap number."
    ::= { acpmAvgVoltageEntry 17 }
    --1.3.6.1.4.1.3052.14.2.12.12.2.1.17

acpmAvgVoltageLowClass OBJECT-TYPE
    SYNTAX DisplayString
    MAX-ACCESS read-write
    STATUS current
    DESCRIPTION
        "Low event class."
    ::= { acpmAvgVoltageEntry 18 }
    --1.3.6.1.4.1.3052.14.2.12.12.2.1.18

acpmAvgVoltageVLowValue OBJECT-TYPE
    SYNTAX DisplayString
    MAX-ACCESS read-write
    STATUS current
    DESCRIPTION
        "Very low event threshold.  This is a floating point value."
    ::= { acpmAvgVoltageEntry 19 }
    --1.3.6.1.4.1.3052.14.2.12.12.2.1.19

acpmAvgVoltageVLowActions OBJECT-TYPE
    SYNTAX DisplayString
    MAX-ACCESS read-write
    STATUS current
    DESCRIPTION
        "Very low event actions."
    ::= { acpmAvgVoltageEntry 20 }
    --1.3.6.1.4.1.3052.14.2.12.12.2.1.20

acpmAvgVoltageVLowTrapNum OBJECT-TYPE
    SYNTAX Integer32 (520..1199)
    MAX-ACCESS read-write
    STATUS current
    DESCRIPTION
        "Very low event trap number."
    ::= { acpmAvgVoltageEntry 21 }
    --1.3.6.1.4.1.3052.14.2.12.12.2.1.21

acpmAvgVoltageVLowClass OBJECT-TYPE
    SYNTAX DisplayString
    MAX-ACCESS read-write
    STATUS current
    DESCRIPTION
        "Very low event class."
    ::= { acpmAvgVoltageEntry 22 }
    --1.3.6.1.4.1.3052.14.2.12.12.2.1.22

acpmAvgVoltageSysrepEnable OBJECT-TYPE
    SYNTAX DisplayString
    MAX-ACCESS read-write
    STATUS current
    DESCRIPTION
        "System reporting enable for average voltage telemetry."
    ::= { acpmAvgVoltageEntry 23 }
    --1.3.6.1.4.1.3052.14.2.12.12.2.1.23

acpmAvgVoltageSysrepThreshold OBJECT-TYPE
    SYNTAX DisplayString
    MAX-ACCESS read-write
    STATUS current
    DESCRIPTION
        "System reporting threshold for average voltage telemetry.  This is
        a floating point value."
    ::= { acpmAvgVoltageEntry 24 }
    --1.3.6.1.4.1.3052.14.2.12.12.2.1.24

acpmAvgVoltageSysrepLimit OBJECT-TYPE
    SYNTAX Integer32
    MAX-ACCESS read-write
    STATUS current
    DESCRIPTION
        "System reporting limit for average voltage telemetry."
    ::= { acpmAvgVoltageEntry 25 }
    --1.3.6.1.4.1.3052.14.2.12.12.2.1.25


acpmAvgCurrentTable OBJECT-TYPE
    SYNTAX SEQUENCE OF ACPMConfigAvgCurrent
    MAX-ACCESS not-accessible
    STATUS current
    DESCRIPTION
        "This table organizes AC power monitor average current attributes."
    ::= { acPowerMonitor 3 }
    --1.3.6.1.4.1.3052.14.2.12.12.3

acpmAvgCurrentEntry OBJECT-TYPE
    SYNTAX ACPMConfigAvgCurrent
    MAX-ACCESS not-accessible
    STATUS current
    DESCRIPTION
        "Entry for AC power monitor average current config table."
    INDEX { acpmAvgCurrentIndex }
    ::= { acpmAvgCurrentTable 1 }
    --1.3.6.1.4.1.3052.14.2.12.12.3.1

acpmAvgCurrentIndex OBJECT-TYPE
    SYNTAX Integer32 (1..6)
    MAX-ACCESS read-only
    STATUS current
    DESCRIPTION
        "Which AC power monitor in the AC power monitor average current
        config table."
    ::= { acpmAvgCurrentEntry 1 }
    --1.3.6.1.4.1.3052.14.2.12.12.3.1.1

acpmAvgCurrentEnable OBJECT-TYPE
    SYNTAX DisplayString
    MAX-ACCESS read-write
    STATUS current
    DESCRIPTION
        "Enable AC power monitor average current events."
    ::= { acpmAvgCurrentEntry 2 }
    --1.3.6.1.4.1.3052.14.2.12.12.3.1.2

acpmAvgCurrentDeadband OBJECT-TYPE
    SYNTAX DisplayString
    MAX-ACCESS read-write
    STATUS current
    DESCRIPTION
        "Deadband (hysteresis) for average current event.  This is a floating
        point value."
    ::= { acpmAvgCurrentEntry 3 }
    --1.3.6.1.4.1.3052.14.2.12.12.3.1.3

acpmAvgCurrentVHighValue OBJECT-TYPE
    SYNTAX DisplayString
    MAX-ACCESS read-write
    STATUS current
    DESCRIPTION
        "Very high event threshold.  This is a floating point value."
    ::= { acpmAvgCurrentEntry 4 }
    --1.3.6.1.4.1.3052.14.2.12.12.3.1.4

acpmAvgCurrentVHighActions OBJECT-TYPE
    SYNTAX DisplayString
    MAX-ACCESS read-write
    STATUS current
    DESCRIPTION
        "Very high event actions."
    ::= { acpmAvgCurrentEntry 5 }
    --1.3.6.1.4.1.3052.14.2.12.12.3.1.5

acpmAvgCurrentVHighTrapNum OBJECT-TYPE
    SYNTAX Integer32 (521..1199)
    MAX-ACCESS read-write
    STATUS current
    DESCRIPTION
        "Very high event trap number."
    ::= { acpmAvgCurrentEntry 6 }
    --1.3.6.1.4.1.3052.14.2.12.12.3.1.6

acpmAvgCurrentVHighClass OBJECT-TYPE
    SYNTAX DisplayString
    MAX-ACCESS read-write
    STATUS current
    DESCRIPTION
        "Very high event class."
    ::= { acpmAvgCurrentEntry 7 }
    --1.3.6.1.4.1.3052.14.2.12.12.3.1.7

acpmAvgCurrentHighValue OBJECT-TYPE
    SYNTAX DisplayString
    MAX-ACCESS read-write
    STATUS current
    DESCRIPTION
        "High event threshold.  This is a floating point value."
    ::= { acpmAvgCurrentEntry 8 }
    --1.3.6.1.4.1.3052.14.2.12.12.3.1.8

acpmAvgCurrentHighActions OBJECT-TYPE
    SYNTAX DisplayString
    MAX-ACCESS read-write
    STATUS current
    DESCRIPTION
        "High event actions."
    ::= { acpmAvgCurrentEntry 9 }
    --1.3.6.1.4.1.3052.14.2.12.12.3.1.9

acpmAvgCurrentHighTrapNum OBJECT-TYPE
    SYNTAX Integer32 (521..1199)
    MAX-ACCESS read-write
    STATUS current
    DESCRIPTION
        "High event trap number."
    ::= { acpmAvgCurrentEntry 10 }
    --1.3.6.1.4.1.3052.14.2.12.12.3.1.10

acpmAvgCurrentHighClass OBJECT-TYPE
    SYNTAX DisplayString
    MAX-ACCESS read-write
    STATUS current
    DESCRIPTION
        "High event class."
    ::= { acpmAvgCurrentEntry 11 }
    --1.3.6.1.4.1.3052.14.2.12.12.3.1.11

acpmAvgCurrentNormalActions OBJECT-TYPE
    SYNTAX DisplayString
    MAX-ACCESS read-write
    STATUS current
    DESCRIPTION
        "Return to normal actions."
    ::= { acpmAvgCurrentEntry 12 }
    --1.3.6.1.4.1.3052.14.2.12.12.3.1.12

acpmAvgCurrentNormalTrapNum OBJECT-TYPE
    SYNTAX Integer32 (521..1199)
    MAX-ACCESS read-write
    STATUS current
    DESCRIPTION
        "Return to normal trap number."
    ::= { acpmAvgCurrentEntry 13 }
    --1.3.6.1.4.1.3052.14.2.12.12.3.1.13

acpmAvgCurrentNormalClass OBJECT-TYPE
    SYNTAX DisplayString
    MAX-ACCESS read-write
    STATUS current
    DESCRIPTION
        "Return to normal class."
    ::= { acpmAvgCurrentEntry 14 }
    --1.3.6.1.4.1.3052.14.2.12.12.3.1.14

acpmAvgCurrentLowValue OBJECT-TYPE
    SYNTAX DisplayString
    MAX-ACCESS read-write
    STATUS current
    DESCRIPTION
        "Low event threshold.  This is a floating point value."
    ::= { acpmAvgCurrentEntry 15 }
    --1.3.6.1.4.1.3052.14.2.12.12.3.1.15

acpmAvgCurrentLowActions OBJECT-TYPE
    SYNTAX DisplayString
    MAX-ACCESS read-write
    STATUS current
    DESCRIPTION
        "Low event actions."
    ::= { acpmAvgCurrentEntry 16 }
    --1.3.6.1.4.1.3052.14.2.12.12.3.1.16

acpmAvgCurrentLowTrapNum OBJECT-TYPE
    SYNTAX Integer32 (521..1199)
    MAX-ACCESS read-write
    STATUS current
    DESCRIPTION
        "Low event trap number."
    ::= { acpmAvgCurrentEntry 17 }
    --1.3.6.1.4.1.3052.14.2.12.12.3.1.17

acpmAvgCurrentLowClass OBJECT-TYPE
    SYNTAX DisplayString
    MAX-ACCESS read-write
    STATUS current
    DESCRIPTION
        "Low event class."
    ::= { acpmAvgCurrentEntry 18 }
    --1.3.6.1.4.1.3052.14.2.12.12.3.1.18

acpmAvgCurrentVLowValue OBJECT-TYPE
    SYNTAX DisplayString
    MAX-ACCESS read-write
    STATUS current
    DESCRIPTION
        "Very low event threshold.  This is a floating point value."
    ::= { acpmAvgCurrentEntry 19 }
    --1.3.6.1.4.1.3052.14.2.12.12.3.1.19

acpmAvgCurrentVLowActions OBJECT-TYPE
    SYNTAX DisplayString
    MAX-ACCESS read-write
    STATUS current
    DESCRIPTION
        "Very low event actions."
    ::= { acpmAvgCurrentEntry 20 }
    --1.3.6.1.4.1.3052.14.2.12.12.3.1.20

acpmAvgCurrentVLowTrapNum OBJECT-TYPE
    SYNTAX Integer32 (521..1199)
    MAX-ACCESS read-write
    STATUS current
    DESCRIPTION
        "Very low event trap number."
    ::= { acpmAvgCurrentEntry 21 }
    --1.3.6.1.4.1.3052.14.2.12.12.3.1.21

acpmAvgCurrentVLowClass OBJECT-TYPE
    SYNTAX DisplayString
    MAX-ACCESS read-write
    STATUS current
    DESCRIPTION
        "Very low event class."
    ::= { acpmAvgCurrentEntry 22 }
    --1.3.6.1.4.1.3052.14.2.12.12.3.1.22

acpmAvgCurrentSysrepEnable OBJECT-TYPE
    SYNTAX DisplayString
    MAX-ACCESS read-write
    STATUS current
    DESCRIPTION
        "System reporting enable for average current telemetry."
    ::= { acpmAvgCurrentEntry 23 }
    --1.3.6.1.4.1.3052.14.2.12.12.3.1.23

acpmAvgCurrentSysrepThreshold OBJECT-TYPE
    SYNTAX DisplayString
    MAX-ACCESS read-write
    STATUS current
    DESCRIPTION
        "System reporting threshold for average current telemetry.  This is a
        floating point value."
    ::= { acpmAvgCurrentEntry 24 }
    --1.3.6.1.4.1.3052.14.2.12.12.3.1.24

acpmAvgCurrentSysrepLimit OBJECT-TYPE
    SYNTAX Integer32
    MAX-ACCESS read-write
    STATUS current
    DESCRIPTION
        "System reporting limit for average current telemetry."
    ::= { acpmAvgCurrentEntry 25 }
    --1.3.6.1.4.1.3052.14.2.12.12.3.1.25


acpmFreqTable OBJECT-TYPE
    SYNTAX SEQUENCE OF ACPMConfigFreq
    MAX-ACCESS not-accessible
    STATUS current
    DESCRIPTION
        "This table organizes AC power monitor frequency attributes."
    ::= { acPowerMonitor 4 }
    --1.3.6.1.4.1.3052.14.2.12.12.4

acpmFreqEntry OBJECT-TYPE
    SYNTAX ACPMConfigFreq
    MAX-ACCESS not-accessible
    STATUS current
    DESCRIPTION
        "Entry for AC power monitor frequency config table."
    INDEX { acpmFreqIndex }
    ::= { acpmFreqTable 1 }
    --1.3.6.1.4.1.3052.14.2.12.12.4.1

acpmFreqIndex OBJECT-TYPE
    SYNTAX Integer32 (1..6)
    MAX-ACCESS read-only
    STATUS current
    DESCRIPTION
        "Which AC power monitor in the AC power monitor frequency config
        table."
    ::= { acpmFreqEntry 1 }
    --1.3.6.1.4.1.3052.14.2.12.12.4.1.1

acpmFreqEnable OBJECT-TYPE
    SYNTAX DisplayString
    MAX-ACCESS read-write
    STATUS current
    DESCRIPTION
        "Enable AC power monitor frequency events."
    ::= { acpmFreqEntry 2 }
    --1.3.6.1.4.1.3052.14.2.12.12.4.1.2

acpmFreqDeadband OBJECT-TYPE
    SYNTAX DisplayString
    MAX-ACCESS read-write
    STATUS current
    DESCRIPTION
        "Deadband (hysteresis) for frequency event.  This is a floating
        point value."
    ::= { acpmFreqEntry 3 }
    --1.3.6.1.4.1.3052.14.2.12.12.4.1.3

acpmFreqVHighValue OBJECT-TYPE
    SYNTAX DisplayString
    MAX-ACCESS read-write
    STATUS current
    DESCRIPTION
        "Very high event threshold.  This is a floating point value."
    ::= { acpmFreqEntry 4 }
    --1.3.6.1.4.1.3052.14.2.12.12.4.1.4

acpmFreqVHighActions OBJECT-TYPE
    SYNTAX DisplayString
    MAX-ACCESS read-write
    STATUS current
    DESCRIPTION
        "Very high event actions."
    ::= { acpmFreqEntry 5 }
    --1.3.6.1.4.1.3052.14.2.12.12.4.1.5

acpmFreqVHighTrapNum OBJECT-TYPE
    SYNTAX Integer32 (522..1199)
    MAX-ACCESS read-write
    STATUS current
    DESCRIPTION
        "Very high event trap number."
    ::= { acpmFreqEntry 6 }
    --1.3.6.1.4.1.3052.14.2.12.12.4.1.6

acpmFreqVHighClass OBJECT-TYPE
    SYNTAX DisplayString
    MAX-ACCESS read-write
    STATUS current
    DESCRIPTION
        "Very high event class."
    ::= { acpmFreqEntry 7 }
    --1.3.6.1.4.1.3052.14.2.12.12.4.1.7

acpmFreqHighValue OBJECT-TYPE
    SYNTAX DisplayString
    MAX-ACCESS read-write
    STATUS current
    DESCRIPTION
        "High event threshold.  This is a floating point value."
    ::= { acpmFreqEntry 8 }
    --1.3.6.1.4.1.3052.14.2.12.12.4.1.8

acpmFreqHighActions OBJECT-TYPE
    SYNTAX DisplayString
    MAX-ACCESS read-write
    STATUS current
    DESCRIPTION
        "High event actions."
    ::= { acpmFreqEntry 9 }
    --1.3.6.1.4.1.3052.14.2.12.12.4.1.9

acpmFreqHighTrapNum OBJECT-TYPE
    SYNTAX Integer32 (522..1199)
    MAX-ACCESS read-write
    STATUS current
    DESCRIPTION
        "High event trap number."
    ::= { acpmFreqEntry 10 }
    --1.3.6.1.4.1.3052.14.2.12.12.4.1.10

acpmFreqHighClass OBJECT-TYPE
    SYNTAX DisplayString
    MAX-ACCESS read-write
    STATUS current
    DESCRIPTION
        "High event class."
    ::= { acpmFreqEntry 11 }
    --1.3.6.1.4.1.3052.14.2.12.12.4.1.11

acpmFreqNormalActions OBJECT-TYPE
    SYNTAX DisplayString
    MAX-ACCESS read-write
    STATUS current
    DESCRIPTION
        "Return to normal actions."
    ::= { acpmFreqEntry 12 }
    --1.3.6.1.4.1.3052.14.2.12.12.4.1.12

acpmFreqNormalTrapNum OBJECT-TYPE
    SYNTAX Integer32 (522..1199)
    MAX-ACCESS read-write
    STATUS current
    DESCRIPTION
        "Return to normal trap number."
    ::= { acpmFreqEntry 13 }
    --1.3.6.1.4.1.3052.14.2.12.12.4.1.13

acpmFreqNormalClass OBJECT-TYPE
    SYNTAX DisplayString
    MAX-ACCESS read-write
    STATUS current
    DESCRIPTION
        "Return to normal class."
    ::= { acpmFreqEntry 14 }
    --1.3.6.1.4.1.3052.14.2.12.12.4.1.14

acpmFreqLowValue OBJECT-TYPE
    SYNTAX DisplayString
    MAX-ACCESS read-write
    STATUS current
    DESCRIPTION
        "Low event threshold.  This is a floating point value."
    ::= { acpmFreqEntry 15 }
    --1.3.6.1.4.1.3052.14.2.12.12.4.1.15

acpmFreqLowActions OBJECT-TYPE
    SYNTAX DisplayString
    MAX-ACCESS read-write
    STATUS current
    DESCRIPTION
        "Low event actions."
    ::= { acpmFreqEntry 16 }
    --1.3.6.1.4.1.3052.14.2.12.12.4.1.16

acpmFreqLowTrapNum OBJECT-TYPE
    SYNTAX Integer32 (522..1199)
    MAX-ACCESS read-write
    STATUS current
    DESCRIPTION
        "Low event trap number."
    ::= { acpmFreqEntry 17 }
    --1.3.6.1.4.1.3052.14.2.12.12.4.1.17

acpmFreqLowClass OBJECT-TYPE
    SYNTAX DisplayString
    MAX-ACCESS read-write
    STATUS current
    DESCRIPTION
        "Low event class."
    ::= { acpmFreqEntry 18 }
    --1.3.6.1.4.1.3052.14.2.12.12.4.1.18

acpmFreqVLowValue OBJECT-TYPE
    SYNTAX DisplayString
    MAX-ACCESS read-write
    STATUS current
    DESCRIPTION
        "Very low event threshold.  This is a floating point value."
    ::= { acpmFreqEntry 19 }
    --1.3.6.1.4.1.3052.14.2.12.12.4.1.19

acpmFreqVLowActions OBJECT-TYPE
    SYNTAX DisplayString
    MAX-ACCESS read-write
    STATUS current
    DESCRIPTION
        "Very low event actions."
    ::= { acpmFreqEntry 20 }
    --1.3.6.1.4.1.3052.14.2.12.12.4.1.20

acpmFreqVLowTrapNum OBJECT-TYPE
    SYNTAX Integer32 (522..1199)
    MAX-ACCESS read-write
    STATUS current
    DESCRIPTION
        "Very low event trap number."
    ::= { acpmFreqEntry 21 }
    --1.3.6.1.4.1.3052.14.2.12.12.4.1.21

acpmFreqVLowClass OBJECT-TYPE
    SYNTAX DisplayString
    MAX-ACCESS read-write
    STATUS current
    DESCRIPTION
        "Very low event class."
    ::= { acpmFreqEntry 22 }
    --1.3.6.1.4.1.3052.14.2.12.12.4.1.22

acpmFreqSysrepEnable OBJECT-TYPE
    SYNTAX DisplayString
    MAX-ACCESS read-write
    STATUS current
    DESCRIPTION
        "System reporting enable for frequency telemetry."
    ::= { acpmFreqEntry 23 }
    --1.3.6.1.4.1.3052.14.2.12.12.4.1.23

acpmFreqSysrepThreshold OBJECT-TYPE
    SYNTAX DisplayString
    MAX-ACCESS read-write
    STATUS current
    DESCRIPTION
        "System reporting threshold for frequency telemetry.  This is a
        floating point value."
    ::= { acpmFreqEntry 24 }
    --1.3.6.1.4.1.3052.14.2.12.12.4.1.24

acpmFreqSysrepLimit OBJECT-TYPE
    SYNTAX Integer32
    MAX-ACCESS read-write
    STATUS current
    DESCRIPTION
        "System reporting limit for frequency telemetry."
    ::= { acpmFreqEntry 25 }
    --1.3.6.1.4.1.3052.14.2.12.12.4.1.25


acpmTotalRealPowerTable OBJECT-TYPE
    SYNTAX SEQUENCE OF ACPMConfigTRP
    MAX-ACCESS not-accessible
    STATUS current
    DESCRIPTION
        "This table organizes AC power monitor total real power attributes."
    ::= { acPowerMonitor 5 }
    --1.3.6.1.4.1.3052.14.2.12.12.5

acpmTRPEntry OBJECT-TYPE
    SYNTAX ACPMConfigTRP
    MAX-ACCESS not-accessible
    STATUS current
    DESCRIPTION
        "Entry for AC power monitor total real power config table."
    INDEX { acpmTRPIndex }
    ::= { acpmTotalRealPowerTable 1 }
    --1.3.6.1.4.1.3052.14.2.12.12.5.1

acpmTRPIndex OBJECT-TYPE
    SYNTAX Integer32 (1..6)
    MAX-ACCESS read-only
    STATUS current
    DESCRIPTION
        "Which AC power monitor in the AC power monitor total real power
        config table."
    ::= { acpmTRPEntry 1 }
    --1.3.6.1.4.1.3052.14.2.12.12.5.1.1

acpmTRPEnable OBJECT-TYPE
    SYNTAX DisplayString
    MAX-ACCESS read-write
    STATUS current
    DESCRIPTION
        "Enable AC power monitor total real power events."
    ::= { acpmTRPEntry 2 }
    --1.3.6.1.4.1.3052.14.2.12.12.5.1.2

acpmTRPDeadband OBJECT-TYPE
    SYNTAX DisplayString
    MAX-ACCESS read-write
    STATUS current
    DESCRIPTION
        "Deadband (hysteresis) for total real power event.  This is a floating
        point value."
    ::= { acpmTRPEntry 3 }
    --1.3.6.1.4.1.3052.14.2.12.12.5.1.3

acpmTRPVHighValue OBJECT-TYPE
    SYNTAX DisplayString
    MAX-ACCESS read-write
    STATUS current
    DESCRIPTION
        "Very high event threshold.  This is a floating point value."
    ::= { acpmTRPEntry 4 }
    --1.3.6.1.4.1.3052.14.2.12.12.5.1.4

acpmTRPVHighActions OBJECT-TYPE
    SYNTAX DisplayString
    MAX-ACCESS read-write
    STATUS current
    DESCRIPTION
        "Very high event actions."
    ::= { acpmTRPEntry 5 }
    --1.3.6.1.4.1.3052.14.2.12.12.5.1.5

acpmTRPVHighTrapNum OBJECT-TYPE
    SYNTAX Integer32 (523..1199)
    MAX-ACCESS read-write
    STATUS current
    DESCRIPTION
        "Very high event trap number."
    ::= { acpmTRPEntry 6 }
    --1.3.6.1.4.1.3052.14.2.12.12.5.1.6

acpmTRPVHighClass OBJECT-TYPE
    SYNTAX DisplayString
    MAX-ACCESS read-write
    STATUS current
    DESCRIPTION
        "Very high event class."
    ::= { acpmTRPEntry 7 }
    --1.3.6.1.4.1.3052.14.2.12.12.5.1.7

acpmTRPHighValue OBJECT-TYPE
    SYNTAX DisplayString
    MAX-ACCESS read-write
    STATUS current
    DESCRIPTION
        "High event threshold.  This is a floating point value."
    ::= { acpmTRPEntry 8 }
    --1.3.6.1.4.1.3052.14.2.12.12.5.1.8

acpmTRPHighActions OBJECT-TYPE
    SYNTAX DisplayString
    MAX-ACCESS read-write
    STATUS current
    DESCRIPTION
        "High event actions."
    ::= { acpmTRPEntry 9 }
    --1.3.6.1.4.1.3052.14.2.12.12.5.1.9

acpmTRPHighTrapNum OBJECT-TYPE
    SYNTAX Integer32 (523..1199)
    MAX-ACCESS read-write
    STATUS current
    DESCRIPTION
        "High event trap number."
    ::= { acpmTRPEntry 10 }
    --1.3.6.1.4.1.3052.14.2.12.12.5.1.10

acpmTRPHighClass OBJECT-TYPE
    SYNTAX DisplayString
    MAX-ACCESS read-write
    STATUS current
    DESCRIPTION
        "High event class."
    ::= { acpmTRPEntry 11 }
    --1.3.6.1.4.1.3052.14.2.12.12.5.1.11

acpmTRPNormalActions OBJECT-TYPE
    SYNTAX DisplayString
    MAX-ACCESS read-write
    STATUS current
    DESCRIPTION
        "Return to normal actions."
    ::= { acpmTRPEntry 12 }
    --1.3.6.1.4.1.3052.14.2.12.12.5.1.12

acpmTRPNormalTrapNum OBJECT-TYPE
    SYNTAX Integer32 (523..1199)
    MAX-ACCESS read-write
    STATUS current
    DESCRIPTION
        "Return to normal trap number."
    ::= { acpmTRPEntry 13 }
    --1.3.6.1.4.1.3052.14.2.12.12.5.1.13

acpmTRPNormalClass OBJECT-TYPE
    SYNTAX DisplayString
    MAX-ACCESS read-write
    STATUS current
    DESCRIPTION
        "Return to normal class."
    ::= { acpmTRPEntry 14 }
    --1.3.6.1.4.1.3052.14.2.12.12.5.1.14

acpmTRPLowValue OBJECT-TYPE
    SYNTAX DisplayString
    MAX-ACCESS read-write
    STATUS current
    DESCRIPTION
        "Low event threshold.  This is a floating point value."
    ::= { acpmTRPEntry 15 }
    --1.3.6.1.4.1.3052.14.2.12.12.5.1.15

acpmTRPLowActions OBJECT-TYPE
    SYNTAX DisplayString
    MAX-ACCESS read-write
    STATUS current
    DESCRIPTION
        "Low event actions."
    ::= { acpmTRPEntry 16 }
    --1.3.6.1.4.1.3052.14.2.12.12.5.1.16

acpmTRPLowTrapNum OBJECT-TYPE
    SYNTAX Integer32 (523..1199)
    MAX-ACCESS read-write
    STATUS current
    DESCRIPTION
        "Low event trap number."
    ::= { acpmTRPEntry 17 }
    --1.3.6.1.4.1.3052.14.2.12.12.5.1.17

acpmTRPLowClass OBJECT-TYPE
    SYNTAX DisplayString
    MAX-ACCESS read-write
    STATUS current
    DESCRIPTION
        "Low event class."
    ::= { acpmTRPEntry 18 }
    --1.3.6.1.4.1.3052.14.2.12.12.5.1.18

acpmTRPVLowValue OBJECT-TYPE
    SYNTAX DisplayString
    MAX-ACCESS read-write
    STATUS current
    DESCRIPTION
        "Very low event threshold.  This is a floating point value."
    ::= { acpmTRPEntry 19 }
    --1.3.6.1.4.1.3052.14.2.12.12.5.1.19

acpmTRPVLowActions OBJECT-TYPE
    SYNTAX DisplayString
    MAX-ACCESS read-write
    STATUS current
    DESCRIPTION
        "Very low event actions."
    ::= { acpmTRPEntry 20 }
    --1.3.6.1.4.1.3052.14.2.12.12.5.1.20

acpmTRPVLowTrapNum OBJECT-TYPE
    SYNTAX Integer32 (523..1199)
    MAX-ACCESS read-write
    STATUS current
    DESCRIPTION
        "Very low event trap number."
    ::= { acpmTRPEntry 21 }
    --1.3.6.1.4.1.3052.14.2.12.12.5.1.21

acpmTRPVLowClass OBJECT-TYPE
    SYNTAX DisplayString
    MAX-ACCESS read-write
    STATUS current
    DESCRIPTION
        "Very low event class."
    ::= { acpmTRPEntry 22 }
    --1.3.6.1.4.1.3052.14.2.12.12.5.1.22

acpmTRPSysrepEnable OBJECT-TYPE
    SYNTAX DisplayString
    MAX-ACCESS read-write
    STATUS current
    DESCRIPTION
        "System reporting enable for total real power telemetry."
    ::= { acpmTRPEntry 23 }
    --1.3.6.1.4.1.3052.14.2.12.12.5.1.23

acpmTRPSysrepThreshold OBJECT-TYPE
    SYNTAX DisplayString
    MAX-ACCESS read-write
    STATUS current
    DESCRIPTION
        "System reporting threshold for total real power telemetry.  This is a
        floating point value."
    ::= { acpmTRPEntry 24 }
    --1.3.6.1.4.1.3052.14.2.12.12.5.1.24

acpmTRPSysrepLimit OBJECT-TYPE
    SYNTAX Integer32
    MAX-ACCESS read-write
    STATUS current
    DESCRIPTION
        "System reporting limit for total real power telemetry."
    ::= { acpmTRPEntry 25 }
    --1.3.6.1.4.1.3052.14.2.12.12.5.1.25


acpmDisconnectTable OBJECT-TYPE
    SYNTAX SEQUENCE OF ACPMConfigDisconnect
    MAX-ACCESS not-accessible
    STATUS current
    DESCRIPTION
        "This table organizes AC power monitor device disconnect event
        attributes."
    ::= { acPowerMonitor 6 }
    --1.3.6.1.4.1.3052.14.2.12.12.6

acpmDisconnectEntry OBJECT-TYPE
    SYNTAX ACPMConfigDisconnect
    MAX-ACCESS not-accessible
    STATUS current
    DESCRIPTION
        "Entry for AC power monitor device disconnect event config table."
    INDEX { acpmDisconnectIndex }
    ::= { acpmDisconnectTable 1 }
    --1.3.6.1.4.1.3052.14.2.12.12.6.1

acpmDisconnectIndex OBJECT-TYPE
    SYNTAX Integer32 (1..6)
    MAX-ACCESS read-only
    STATUS current
    DESCRIPTION
        "Which AC power monitor in the AC power monitor device disconnect
        event config table."
    ::= { acpmDisconnectEntry 1 }
    --1.3.6.1.4.1.3052.14.2.12.12.6.1.1

acpmDisconnectEnable OBJECT-TYPE
    SYNTAX DisplayString
    MAX-ACCESS read-write
    STATUS current
    DESCRIPTION
        "Enable AC power monitor device disconnect event."
    ::= { acpmDisconnectEntry 2 }
    --1.3.6.1.4.1.3052.14.2.12.12.6.1.2

acpmDisconnectActions OBJECT-TYPE
    SYNTAX DisplayString
    MAX-ACCESS read-write
    STATUS current
    DESCRIPTION
        "Actions for disconnect event."
    ::= { acpmDisconnectEntry 3 }
    --1.3.6.1.4.1.3052.14.2.12.12.6.1.3

acpmDisconnectTrapNum OBJECT-TYPE
    SYNTAX Integer32 (524..1199)
    MAX-ACCESS read-write
    STATUS current
    DESCRIPTION
        "Trap number for disconnect event."
    ::= { acpmDisconnectEntry 4 }
    --1.3.6.1.4.1.3052.14.2.12.12.6.1.4

acpmDisconnectClass OBJECT-TYPE
    SYNTAX DisplayString
    MAX-ACCESS read-write
    STATUS current
    DESCRIPTION
        "Class for disconnect event."
    ::= { acpmDisconnectEntry 5 }
    --1.3.6.1.4.1.3052.14.2.12.12.6.1.5

acpmDisconnectNormalActions OBJECT-TYPE
    SYNTAX DisplayString
    MAX-ACCESS read-write
    STATUS current
    DESCRIPTION
        "Actions for disconnect return to normal event."
    ::= { acpmDisconnectEntry 6 }
    --1.3.6.1.4.1.3052.14.2.12.12.6.1.6

acpmDisconnectNormalTrapNum OBJECT-TYPE
    SYNTAX Integer32 (524..1199)
    MAX-ACCESS read-write
    STATUS current
    DESCRIPTION
        "Trap number for disconnect return to normal event."
    ::= { acpmDisconnectEntry 7 }
    --1.3.6.1.4.1.3052.14.2.12.12.6.1.7

acpmDisconnectNormalClass OBJECT-TYPE
    SYNTAX DisplayString
    MAX-ACCESS read-write
    STATUS current
    DESCRIPTION
        "Class for disconnect return to normal event."
    ::= { acpmDisconnectEntry 8 }
    --1.3.6.1.4.1.3052.14.2.12.12.6.1.8

acpmTotalPowerFactorTable OBJECT-TYPE
    SYNTAX SEQUENCE OF ACPMConfigTotalPowerFactor
    MAX-ACCESS not-accessible
    STATUS current
    DESCRIPTION
        "This table organizes AC power monitor device total power factor
        event attributes."
    ::= { acPowerMonitor 7 }
    --1.3.6.1.4.1.3052.14.2.12.12.7

acpmTPFEntry OBJECT-TYPE
    SYNTAX ACPMConfigTotalPowerFactor
    MAX-ACCESS not-accessible
    STATUS current
    DESCRIPTION
        "Entry for AC power monitor device total power factor event config
        table."
    INDEX { acpmTPFIndex }
    ::= { acpmTotalPowerFactorTable 1 }
    --1.3.6.1.4.1.3052.14.2.12.12.7.1

acpmTPFIndex OBJECT-TYPE
    SYNTAX Integer32 (1..6)
    MAX-ACCESS read-only
    STATUS current
    DESCRIPTION
        "Which AC power monitor in the AC power monitor device disconnect
        event config table."
    ::= { acpmTPFEntry 1 }
    --1.3.6.1.4.1.3052.14.2.12.12.7.1.1

acpmTPFEnable OBJECT-TYPE
    SYNTAX DisplayString
    MAX-ACCESS read-write
    STATUS current
    DESCRIPTION
        "Enable AC power monitor device disconnect event."
    ::= { acpmTPFEntry 2 }
    --1.3.6.1.4.1.3052.14.2.12.12.7.1.2

acpmTPFDeadband OBJECT-TYPE
    SYNTAX DisplayString
    MAX-ACCESS read-write
    STATUS current
    DESCRIPTION
        "Deadband (hysteresis)."
    ::= { acpmTPFEntry 3 }
    --1.3.6.1.4.1.3052.14.2.12.12.7.1.3

acpmTPFNormalActions OBJECT-TYPE
    SYNTAX DisplayString
    MAX-ACCESS read-write
    STATUS current
    DESCRIPTION
        "Normal actions."
    ::= { acpmTPFEntry 4 }
    --1.3.6.1.4.1.3052.14.2.12.12.7.1.4

acpmTPFNormalTrapNum OBJECT-TYPE
    SYNTAX Integer32
    MAX-ACCESS read-write
    STATUS current
    DESCRIPTION
        "Normal trap number."
    ::= { acpmTPFEntry 5 }
    --1.3.6.1.4.1.3052.14.2.12.12.7.1.5

acpmTPFNormalClass OBJECT-TYPE
    SYNTAX DisplayString
    MAX-ACCESS read-write
    STATUS current
    DESCRIPTION
        "Normal class."
    ::= { acpmTPFEntry 6 }
    --1.3.6.1.4.1.3052.14.2.12.12.7.1.6

acpmTPFLowValue OBJECT-TYPE
    SYNTAX DisplayString
    MAX-ACCESS read-write
    STATUS current
    DESCRIPTION
        "Low threshold."
    ::= { acpmTPFEntry 7 }
    --1.3.6.1.4.1.3052.14.2.12.12.7.1.7

acpmTPFLowActions OBJECT-TYPE
    SYNTAX DisplayString
    MAX-ACCESS read-write
    STATUS current
    DESCRIPTION
        "Low actions."
    ::= { acpmTPFEntry 8 }
    --1.3.6.1.4.1.3052.14.2.12.12.7.1.8

acpmTPFLowTrapNum OBJECT-TYPE
    SYNTAX Integer32
    MAX-ACCESS read-write
    STATUS current
    DESCRIPTION
        "Low trap number."
    ::= { acpmTPFEntry 9 }
    --1.3.6.1.4.1.3052.14.2.12.12.7.1.9

acpmTPFLowClass OBJECT-TYPE
    SYNTAX DisplayString
    MAX-ACCESS read-write
    STATUS current
    DESCRIPTION
        "Low class."
    ::= { acpmTPFEntry 10 }
    --1.3.6.1.4.1.3052.14.2.12.12.7.1.10

acpmTPFVLowValue OBJECT-TYPE
    SYNTAX DisplayString
    MAX-ACCESS read-write
    STATUS current
    DESCRIPTION
        "Very Low threshold."
    ::= { acpmTPFEntry 11 }
    --1.3.6.1.4.1.3052.14.2.12.12.7.1.11

acpmTPFVLowActions OBJECT-TYPE
    SYNTAX DisplayString
    MAX-ACCESS read-write
    STATUS current
    DESCRIPTION
        "Very Low actions."
    ::= { acpmTPFEntry 12 }
    --1.3.6.1.4.1.3052.14.2.12.12.7.1.12

acpmTPFVLowTrapNum OBJECT-TYPE
    SYNTAX Integer32
    MAX-ACCESS read-write
    STATUS current
    DESCRIPTION
        "Very Low trap number."
    ::= { acpmTPFEntry 13 }
    --1.3.6.1.4.1.3052.14.2.12.12.7.1.13

acpmTPFVLowClass OBJECT-TYPE
    SYNTAX DisplayString
    MAX-ACCESS read-write
    STATUS current
    DESCRIPTION
        "Very Low class."
    ::= { acpmTPFEntry 14 }
    --1.3.6.1.4.1.3052.14.2.12.12.7.1.14

acpmTPFSysrepEnable OBJECT-TYPE
    SYNTAX DisplayString
    MAX-ACCESS read-write
    STATUS current
    DESCRIPTION
        "System reporting enable."
    ::= { acpmTPFEntry 15 }
    --1.3.6.1.4.1.3052.14.2.12.12.7.1.15

acpmTPFSysrepThreshold OBJECT-TYPE
    SYNTAX DisplayString
    MAX-ACCESS read-write
    STATUS current
    DESCRIPTION
        "System reporting threshold."
    ::= { acpmTPFEntry 16 }
    --1.3.6.1.4.1.3052.14.2.12.12.7.1.16

acpmTPFSysrepLimit OBJECT-TYPE
    SYNTAX Integer32
    MAX-ACCESS read-write
    STATUS current
    DESCRIPTION
        "System reporting limit."
    ::= { acpmTPFEntry 17 }
    --1.3.6.1.4.1.3052.14.2.12.12.7.1.17



--***************************************************************************************
--Reset Event Section   2.12.16
--***************************************************************************************


evResetEnable OBJECT-TYPE
    SYNTAX DisplayString
    MAX-ACCESS read-write
    STATUS current
    DESCRIPTION
        "Enable/disable reset event.  This event is triggered when the unit
        finishes booting."
    ::= { evReset 1 }
    --1.3.6.1.4.1.3052.14.2.12.16.1

evResetDelay OBJECT-TYPE
    SYNTAX Integer32 (0..3600)
    MAX-ACCESS read-write
    STATUS current
    DESCRIPTION
        "Number of seconds to wait after unit finishes booting before triggering
        the reset event."
    ::= { evReset 2 }
    --1.3.6.1.4.1.3052.14.2.12.16.2

evResetActions OBJECT-TYPE
    SYNTAX DisplayString
    MAX-ACCESS read-write
    STATUS current
    DESCRIPTION
        "Actions for reset event."
    ::= { evReset 3 }
    --1.3.6.1.4.1.3052.14.2.12.16.3

evResetMessage OBJECT-TYPE
    SYNTAX DisplayString
    MAX-ACCESS read-write
    STATUS current
    DESCRIPTION
        "Message for reset event."
    ::= { evReset 4 }
    --1.3.6.1.4.1.3052.14.2.12.16.4

evResetTrapnum OBJECT-TYPE
    SYNTAX Integer32 (543..1199)
    MAX-ACCESS read-write
    STATUS current
    DESCRIPTION
        "Trap number for reset event."
    ::= { evReset 5 }
    --1.3.6.1.4.1.3052.14.2.12.16.5

evResetClass OBJECT-TYPE
    SYNTAX DisplayString
    MAX-ACCESS read-write
    STATUS current
    DESCRIPTION
        "Class (severity) for reset event."
    ::= { evReset 6 }
    --1.3.6.1.4.1.3052.14.2.12.16.6


--***************************************************************************************
--Action Section   2.14
--***************************************************************************************



actionCallNumberTable OBJECT-TYPE
    SYNTAX SEQUENCE OF ActionCallNumberConfig
    MAX-ACCESS not-accessible
    STATUS current
    DESCRIPTION
        "Table of phone numbers to dial for modem actions"
    ::= { action 1 }
    --1.3.6.1.4.1.3052.14.2.14.1

actionCallNumberEntry OBJECT-TYPE
    SYNTAX ActionCallNumberConfig
    MAX-ACCESS not-accessible
    STATUS current
    DESCRIPTION
        "Entry for table of phone numbers to dial for modem actions"
    INDEX { actionCallNumberIndex }
    ::= { actionCallNumberTable 1 }
    --1.3.6.1.4.1.3052.14.2.14.1.1

actionCallNumberIndex OBJECT-TYPE
    SYNTAX Integer32 (1..4)
    MAX-ACCESS read-only
    STATUS current
    DESCRIPTION
        "Index for table of phone numbers to dial for modem actions"
    ::= { actionCallNumberEntry 1 }
    --1.3.6.1.4.1.3052.14.2.14.1.1.1

actionCallNumber OBJECT-TYPE
    SYNTAX DisplayString
    MAX-ACCESS read-write
    STATUS current
    DESCRIPTION
        "The number to dial for this action slot"
    ::= { actionCallNumberEntry 2 }
    --1.3.6.1.4.1.3052.14.2.14.1.1.2

actionPagerTable OBJECT-TYPE
    SYNTAX SEQUENCE OF ActionPagerConfig
    MAX-ACCESS not-accessible
    STATUS current
    DESCRIPTION
        "Table of pager configurations"
    ::= { action 2 }
    --1.3.6.1.4.1.3052.14.2.14.2

actionPagerEntry OBJECT-TYPE
    SYNTAX ActionPagerConfig
    MAX-ACCESS not-accessible
    STATUS current
    DESCRIPTION
        "Entry for table of pager configurations"
    INDEX { actionPagerIndex }
    ::= { actionPagerTable 1 }
    --1.3.6.1.4.1.3052.14.2.14.2.1

actionPagerIndex OBJECT-TYPE
    SYNTAX Integer32 (1..4)
    MAX-ACCESS read-only
    STATUS current
    DESCRIPTION
        "index for table of pager configurations"
    ::= { actionPagerEntry 1 }
    --1.3.6.1.4.1.3052.14.2.14.2.1.1

actionPagerType OBJECT-TYPE
    SYNTAX DisplayString
    MAX-ACCESS read-write
    STATUS current
    DESCRIPTION
        "type of this pager configuration"
    ::= { actionPagerEntry 2 }
    --1.3.6.1.4.1.3052.14.2.14.2.1.2

actionPagerNumber OBJECT-TYPE
    SYNTAX DisplayString
    MAX-ACCESS read-write
    STATUS current
    DESCRIPTION
        "phone number to dial for this pager configuration"
    ::= { actionPagerEntry 3 }
    --1.3.6.1.4.1.3052.14.2.14.2.1.3

actionPagerID OBJECT-TYPE
    SYNTAX DisplayString
    MAX-ACCESS read-write
    STATUS current
    DESCRIPTION
        "ID to use for this pager configuration"
    ::= { actionPagerEntry 4 }
    --1.3.6.1.4.1.3052.14.2.14.2.1.4

actionPagerMessage OBJECT-TYPE
    SYNTAX DisplayString
    MAX-ACCESS read-write
    STATUS current
    DESCRIPTION
        "message to use for this pager configuration"
    ::= { actionPagerEntry 5 }
    --1.3.6.1.4.1.3052.14.2.14.2.1.5

actionPagerPostCalloutDelay OBJECT-TYPE
    SYNTAX Integer32 (0..255)
    MAX-ACCESS read-write
    STATUS current
    DESCRIPTION
        "Seconds to wait after dialing before sending ID"
    ::= { actionPagerEntry 6 }
    --1.3.6.1.4.1.3052.14.2.14.2.1.6

actionPagerPostIDDelay OBJECT-TYPE
    SYNTAX Integer32 (0..255)
    MAX-ACCESS read-write
    STATUS current
    DESCRIPTION
        "Seconds to wait after sending ID to send message"
    ::= { actionPagerEntry 7 }
    --1.3.6.1.4.1.3052.14.2.14.2.1.7

actionSchedEnable OBJECT-TYPE
    SYNTAX DisplayString
    MAX-ACCESS read-write
    STATUS current
    DESCRIPTION
        "ON/OFF enable action schedule"
    ::= { actionSched 1 }
    --1.3.6.1.4.1.3052.14.2.14.3.1

actionSchedBegin OBJECT-TYPE
    SYNTAX DisplayString
    MAX-ACCESS read-write
    STATUS current
    DESCRIPTION
        "action schedule begin time (HH:MM)"
    ::= { actionSched 2 }
    --1.3.6.1.4.1.3052.14.2.14.3.2

actionSchedEnd OBJECT-TYPE
    SYNTAX DisplayString
    MAX-ACCESS read-write
    STATUS current
    DESCRIPTION
        "action schedule end time (HH:MM)"
    ::= { actionSched 3 }
    --1.3.6.1.4.1.3052.14.2.14.3.3

actionSchedWeekdaysOnly OBJECT-TYPE
    SYNTAX DisplayString
    MAX-ACCESS read-write
    STATUS current
    DESCRIPTION
        "ON/OFF whether the action schedule applies to weekdays only
        (ON) or all days (OFF)"
    ::= { actionSched 4 }
    --1.3.6.1.4.1.3052.14.2.14.3.4

actionAsentriaRequireAck OBJECT-TYPE
    SYNTAX DisplayString
    MAX-ACCESS read-write
    STATUS current
    DESCRIPTION
        "ON/OFF Asentria action requires an ack from the receiver"
    ::= { actionAsentria 1 }
    --1.3.6.1.4.1.3052.14.2.14.4.1

actionAsentriaVersion OBJECT-TYPE
    SYNTAX DisplayString
    MAX-ACCESS read-write
    STATUS current
    DESCRIPTION
        "version 1.0 or 1.1"
    ::= { actionAsentria 2 }
    --1.3.6.1.4.1.3052.14.2.14.4.2

actionAsentriaTCPPort OBJECT-TYPE
    SYNTAX Integer32
    MAX-ACCESS read-write
    STATUS current
    DESCRIPTION
        "TCP port used for TCP-based Asentria alarms"
    ::= { actionAsentria 3 }
    --1.3.6.1.4.1.3052.14.2.14.4.3

actionHostTable OBJECT-TYPE
    SYNTAX SEQUENCE OF ActionHostConfig
    MAX-ACCESS not-accessible
    STATUS current
    DESCRIPTION
        "Table of network hosts to use for network-based actions"
    ::= { action 6 }
    --1.3.6.1.4.1.3052.14.2.14.6

actionHostEntry OBJECT-TYPE
    SYNTAX ActionHostConfig
    MAX-ACCESS not-accessible
    STATUS current
    DESCRIPTION
        "Entry for table of network hosts to use for network-based
        actions"
    INDEX { actionHostIndex }
    ::= { actionHostTable 1 }
    --1.3.6.1.4.1.3052.14.2.14.6.1

actionHostIndex OBJECT-TYPE
    SYNTAX Integer32 (1..6)
    MAX-ACCESS read-only
    STATUS current
    DESCRIPTION
        "Index for table of network hosts to use for network-based
        actions"
    ::= { actionHostEntry 1 }
    --1.3.6.1.4.1.3052.14.2.14.6.1.1

actionHost OBJECT-TYPE
    SYNTAX DisplayString
    MAX-ACCESS read-write
    STATUS current
    DESCRIPTION
        "Hostname/IP address used as destination for network-based
        action (e.g., trap)"
    ::= { actionHostEntry 2 }
    --1.3.6.1.4.1.3052.14.2.14.6.1.2

actionEmailTable OBJECT-TYPE
    SYNTAX SEQUENCE OF ActionEmailConfig
    MAX-ACCESS not-accessible
    STATUS current
    DESCRIPTION
        "Table of email addresses to use for email actions"
    ::= { action 7 }
    --1.3.6.1.4.1.3052.14.2.14.7

actionEmailEntry OBJECT-TYPE
    SYNTAX ActionEmailConfig
    MAX-ACCESS not-accessible
    STATUS current
    DESCRIPTION
        "Entry for table of email addresses to use for email actions"
    INDEX { actionEmailIndex }
    ::= { actionEmailTable 1 }
    --1.3.6.1.4.1.3052.14.2.14.7.1

actionEmailIndex OBJECT-TYPE
    SYNTAX Integer32 (1..6)
    MAX-ACCESS read-only
    STATUS current
    DESCRIPTION
        "Index for table of email addresses to use for email actions"
    ::= { actionEmailEntry 1 }
    --1.3.6.1.4.1.3052.14.2.14.7.1.1

actionEmail OBJECT-TYPE
    SYNTAX DisplayString
    MAX-ACCESS read-write
    STATUS current
    DESCRIPTION
        "email address"
    ::= { actionEmailEntry 2 }
    --1.3.6.1.4.1.3052.14.2.14.7.1.2

actionParseError OBJECT-TYPE
    SYNTAX DisplayString
    MAX-ACCESS read-only
    STATUS current
    DESCRIPTION
        "When a user attempts to configure an invalid action setting/
        object, this object says why it was invalid."
    ::= { action 8 }
    --1.3.6.1.4.1.3052.14.2.14.8

--***************************************************************************************
--System Section   2.16
--***************************************************************************************


sysTimeAutoDST OBJECT-TYPE
    SYNTAX DisplayString
    MAX-ACCESS read-write
    STATUS current
    DESCRIPTION
        "ON/OFF automatically adjust for Daylight Savings Time"
    ::= { sysTime 1 }
    --1.3.6.1.4.1.3052.14.2.16.1.1

sysTimeGMTOffset OBJECT-TYPE
    SYNTAX Integer32
    MAX-ACCESS read-write
    STATUS current
    DESCRIPTION
        "Absolute value of offset (hours) from GMT of the timezone"
    ::= { sysTime 2 }
    --1.3.6.1.4.1.3052.14.2.16.1.2

sysTimeGMTDirection OBJECT-TYPE
    SYNTAX DisplayString
    MAX-ACCESS read-write
    STATUS current
    DESCRIPTION
        "Direction (AHEAD/BEHIND) of timezone relative to GMT"
    ::= { sysTime 3 }
    --1.3.6.1.4.1.3052.14.2.16.1.3


sysTimeNetEnable OBJECT-TYPE
    SYNTAX DisplayString
    MAX-ACCESS read-write
    STATUS current
    DESCRIPTION
        "Network time mode"
    ::= { sysTimeNet 1 }
    --1.3.6.1.4.1.3052.14.2.16.1.4.1

sysTimeNetHostTable OBJECT-TYPE
    SYNTAX SEQUENCE OF NetworkTimeHostConfig
    MAX-ACCESS not-accessible
    STATUS current
    DESCRIPTION
        "Table of hosts to use for network time services"
    ::= { sysTimeNet 2 }
    --1.3.6.1.4.1.3052.14.2.16.1.4.2

sysTimeNetHostEntry OBJECT-TYPE
    SYNTAX NetworkTimeHostConfig
    MAX-ACCESS not-accessible
    STATUS current
    DESCRIPTION
        "Entry for table of hosts to use for network time services"
    INDEX { sysTimeNetHostIndex }
    ::= { sysTimeNetHostTable 1 }
    --1.3.6.1.4.1.3052.14.2.16.1.4.2.1

sysTimeNetHostIndex OBJECT-TYPE
    SYNTAX Integer32 (1..6)
    MAX-ACCESS read-only
    STATUS current
    DESCRIPTION
        "Index for table of hosts to use for network time services"
    ::= { sysTimeNetHostEntry 1 }
    --1.3.6.1.4.1.3052.14.2.16.1.4.2.1.1

sysTimeNetHost OBJECT-TYPE
    SYNTAX DisplayString
    MAX-ACCESS read-write
    STATUS current
    DESCRIPTION
        "host to use for network time services"
    ::= { sysTimeNetHostEntry 2 }
    --1.3.6.1.4.1.3052.14.2.16.1.4.2.1.2

sysPTTimeout  OBJECT-TYPE
    SYNTAX Integer32
    MAX-ACCESS read-write
    STATUS current
    DESCRIPTION
        "Timeout (minutes) of inactivity after which a pass-through
        session is terminated (0 means it never terminates)"
    ::= { sysPT 1 }
    --1.3.6.1.4.1.3052.14.2.16.2.1

sysPTEndPause OBJECT-TYPE
    SYNTAX Integer32
    MAX-ACCESS read-write
    STATUS current
    DESCRIPTION
        "number of 16ths of a second between escape characters
        received on pass-through origin IO handle that are reuired
        for the escape characters to register as pass-through escape
        characters in the pass-through escape sequence.  Set to 0 to
        make the escape character register as part of the pass-
        through escape sequence without requiring a pause."
    ::= { sysPT 2 }
    --1.3.6.1.4.1.3052.14.2.16.2.2

sysPTJoinable OBJECT-TYPE
    SYNTAX DisplayString
    MAX-ACCESS read-write
    STATUS current
    DESCRIPTION
        "Enable joinable pass-through sessions."
    ::= { sysPT 3 }
    --1.3.6.1.4.1.3052.14.2.16.2.3

sysMTU OBJECT-TYPE
    SYNTAX Integer32
    MAX-ACCESS read-write
    STATUS current
    DESCRIPTION
        "Maximum transfer unit for ethernet interfaces"
    ::= { sys 3 }
    --1.3.6.1.4.1.3052.14.2.16.3

sysAnswerString OBJECT-TYPE
    SYNTAX DisplayString
    MAX-ACCESS read-write
    STATUS current
    DESCRIPTION
        "String displayed upon login"
    ::= { sys 4 }
    --1.3.6.1.4.1.3052.14.2.16.4

sysEventFileID OBJECT-TYPE
    SYNTAX DisplayString
    MAX-ACCESS read-write
    STATUS current
    DESCRIPTION
        "ID string for events file"
    ::= { sys 6 }
    --1.3.6.1.4.1.3052.14.2.16.6

sysEscapeCharacter OBJECT-TYPE
    SYNTAX Integer32
    MAX-ACCESS read-write
    STATUS current
    DESCRIPTION
        "Decimal ASCII code of the system escape character"
    ::= { sys 7 }
    --1.3.6.1.4.1.3052.14.2.16.7

sysTimeStampTimeFormat OBJECT-TYPE
    SYNTAX DisplayString
    MAX-ACCESS read-write
    STATUS current
    DESCRIPTION
        "Format of time stamp: HH:MM,HH:MM:SS,BLANK"
    ::= { sysTimeStamp 1 }
    --1.3.6.1.4.1.3052.14.2.16.8.1

sysTimeStampDateFormat OBJECT-TYPE
    SYNTAX DisplayString
    MAX-ACCESS read-write
    STATUS current
    DESCRIPTION
        "Format of date stamp: MM/DD,MM/DD/YY,MM/DD/YYYY,BLANK"
    ::= { sysTimeStamp 2 }
    --1.3.6.1.4.1.3052.14.2.16.8.2

sysTimeStampSpaceAfter OBJECT-TYPE
    SYNTAX DisplayString
    MAX-ACCESS read-write
    STATUS current
    DESCRIPTION
        "ON/OFF Inlude a space after timestamp"
    ::= { sysTimeStamp 3 }
    --1.3.6.1.4.1.3052.14.2.16.8.3

sysLogMode OBJECT-TYPE
    SYNTAX DisplayString
    MAX-ACCESS read-write
    STATUS current
    DESCRIPTION
        "Syslog mode: disabled, emit UDP (REMOTE), save in a
        rotating file set (FILE), or emit on a listening socket
        (SERVER)"
    ::= { sysLog 1 }
    --1.3.6.1.4.1.3052.14.2.16.9.1

sysLoghost OBJECT-TYPE
    SYNTAX DisplayString
    MAX-ACCESS read-write
    STATUS current
    DESCRIPTION
        "Syslog host: destination machine when syslog mode is REMOTE"
    ::= { sysLog 2 }
    --1.3.6.1.4.1.3052.14.2.16.9.2

sysLogFilter OBJECT-TYPE
    SYNTAX DisplayString
    MAX-ACCESS read-write
    STATUS current
    DESCRIPTION
        "String describing what functions place data in the syslog"
    ::= { sysLog 3 }
    --1.3.6.1.4.1.3052.14.2.16.9.3

sysLogFileSize OBJECT-TYPE
    SYNTAX Integer32
    MAX-ACCESS read-write
    STATUS current
    DESCRIPTION
        "Size (in KB) of syslog files (when syslog mode is SERVER or
        FILE)"
    ::= { sysLog 4 }
    --1.3.6.1.4.1.3052.14.2.16.9.4

sysLogFileCount OBJECT-TYPE
    SYNTAX Integer32
    MAX-ACCESS read-write
    STATUS current
    DESCRIPTION
        "Number of files in syslog file set (when syslog mode is
        SERVER or FILE)"
    ::= { sysLog 5 }
    --1.3.6.1.4.1.3052.14.2.16.9.5

sysLogListenPort OBJECT-TYPE
    SYNTAX Integer32
    MAX-ACCESS read-write
    STATUS current
    DESCRIPTION
        "TCP port on which the unit listens for a connection on
        which syslog data is dumped (when syslog mode is SERVER)"
    ::= { sysLog 6 }
    --1.3.6.1.4.1.3052.14.2.16.9.6

sysCRDBCapacity OBJECT-TYPE
    SYNTAX Integer32
    MAX-ACCESS read-only
    STATUS current
    DESCRIPTION
        "Capacity of Call Record Database (in KB)"
    ::= { sysCRDB 1 }
    --1.3.6.1.4.1.3052.14.2.16.10.1

sysCRDBPercentFull OBJECT-TYPE
    SYNTAX Integer32
    MAX-ACCESS read-only
    STATUS current
    DESCRIPTION
        "Percent of the CRDB used"
    ::= { sysCRDB 2 }
    --1.3.6.1.4.1.3052.14.2.16.10.2


sysCRDBFileIDTable OBJECT-TYPE
    SYNTAX SEQUENCE OF CRDBFileIDConfig
    MAX-ACCESS not-accessible
    STATUS current
    DESCRIPTION
        "Table of CRDB file IDs"
    ::= { sysCRDB 3 }
    --1.3.6.1.4.1.3052.14.2.16.10.3

sysCRDBFileIDEntry OBJECT-TYPE
    SYNTAX CRDBFileIDConfig
    MAX-ACCESS not-accessible
    STATUS current
    DESCRIPTION
        "Entry for table of CRDB file IDs"
    INDEX { sysCRDBFileIDIndex }
    ::= { sysCRDBFileIDTable 1 }
    --1.3.6.1.4.1.3052.14.2.16.10.3.1

sysCRDBFileIDIndex OBJECT-TYPE
    SYNTAX Integer32 (1..16)
    MAX-ACCESS read-only
    STATUS current
    DESCRIPTION
        "Index for table of CRDB file IDs"
    ::= { sysCRDBFileIDEntry 1 }
    --1.3.6.1.4.1.3052.14.2.16.10.3.1.1

sysCRDBFileID OBJECT-TYPE
    SYNTAX DisplayString
    MAX-ACCESS read-write
    STATUS current
    DESCRIPTION
        "ID of CRDB file for this port-associated file x"
    ::= { sysCRDBFileIDEntry 2 }
    --1.3.6.1.4.1.3052.14.2.16.10.3.1.2

sysCRDBFileEnforceMinTable OBJECT-TYPE
    SYNTAX SEQUENCE OF CRDBFileEnforceMinConfig
    MAX-ACCESS not-accessible
    STATUS current
    DESCRIPTION
        "Table of CRDB file minimum size enforcement settings"
    ::= { sysCRDB 4 }
    --1.3.6.1.4.1.3052.14.2.16.10.4

sysCRDBFileEnforceMinEntry OBJECT-TYPE
    SYNTAX CRDBFileEnforceMinConfig
    MAX-ACCESS not-accessible
    STATUS current
    DESCRIPTION
        "Entry for table of CRDB file minimum size enforcement
        settings"
    INDEX { sysCRDBFileEnforceMinIndex }
    ::= { sysCRDBFileEnforceMinTable 1 }
    --1.3.6.1.4.1.3052.14.2.16.10.4.1

sysCRDBFileEnforceMinIndex OBJECT-TYPE
    SYNTAX Integer32 (1..24)
    MAX-ACCESS read-only
    STATUS current
    DESCRIPTION
        "Index for table of CRDB file minimum size enforcement
        settings"
    ::= { sysCRDBFileEnforceMinEntry 1 }
    --1.3.6.1.4.1.3052.14.2.16.10.4.1.1

sysCRDBFileEnforceMin OBJECT-TYPE
    SYNTAX DisplayString
    MAX-ACCESS read-write
    STATUS current
    DESCRIPTION
        "ON/OFF: enforce minimum size for this CRDB file x"
    ::= { sysCRDBFileEnforceMinEntry 2 }
    --1.3.6.1.4.1.3052.14.2.16.10.4.1.2

sysCharMask OBJECT-TYPE
    SYNTAX OCTET STRING
    MAX-ACCESS read-write
    STATUS current
    DESCRIPTION
        "Character mask used for ignoring certain characters on
        serial ports when assembling data records (when port mode is
        ASCII)"
    ::= { sys 11 }
    --1.3.6.1.4.1.3052.14.2.16.11

sysPrompt OBJECT-TYPE
    SYNTAX DisplayString
    MAX-ACCESS read-write
    STATUS current
    DESCRIPTION
        "Prompt to use in a commnand session"
    ::= { sys 12 }
    --1.3.6.1.4.1.3052.14.2.16.12

sysBootStatus OBJECT-TYPE
    SYNTAX DisplayString
    MAX-ACCESS read-only
    STATUS current
    DESCRIPTION
        "String describing the boot status of the unit (Booted OK/
        still booting"
    ::= { sys 13 }
    --1.3.6.1.4.1.3052.14.2.16.13

sysLocLatitude OBJECT-TYPE
    SYNTAX DisplayString
    MAX-ACCESS read-write
    STATUS current
    DESCRIPTION
        "Latitude portion of geographic coordinates as string"
    ::= { sysLoc 1 }
    --1.3.6.1.4.1.3052.14.2.16.14.1

sysLocLongitude OBJECT-TYPE
    SYNTAX DisplayString
    MAX-ACCESS read-write
    STATUS current
    DESCRIPTION
        "Longitude portion of geographic coordinates as string"
    ::= { sysLoc 2 }
    --1.3.6.1.4.1.3052.14.2.16.14.2

sysLocXOffset OBJECT-TYPE
    SYNTAX DisplayString
    MAX-ACCESS read-write
    STATUS current
    DESCRIPTION
        "X-offset portion of geographic coordinates as string"
    ::= { sysLoc 3 }
    --1.3.6.1.4.1.3052.14.2.16.14.3

sysLocYOffset OBJECT-TYPE
    SYNTAX DisplayString
    MAX-ACCESS read-write
    STATUS current
    DESCRIPTION
        "Y offset portion of geographic coordinates as string"
    ::= { sysLoc 4 }
    --1.3.6.1.4.1.3052.14.2.16.14.4

sysLocAngle OBJECT-TYPE
    SYNTAX DisplayString
    MAX-ACCESS read-write
    STATUS current
    DESCRIPTION
        "Angle portion of geographic coordinates as string"
    ::= { sysLoc 5 }
    --1.3.6.1.4.1.3052.14.2.16.14.5

sysLocAltitude OBJECT-TYPE
    SYNTAX DisplayString
    MAX-ACCESS read-write
    STATUS current
    DESCRIPTION
        "Altitude portion of geographic coordinates as string"
    ::= { sysLoc 6 }
    --1.3.6.1.4.1.3052.14.2.16.14.6

sysAMManufacturer OBJECT-TYPE
    SYNTAX DisplayString
    MAX-ACCESS read-only
    STATUS current
    DESCRIPTION
        "Device manufacturer"
    ::= { sysAssetMgmt 1 }
    --1.3.6.1.4.1.3052.14.2.16.15.1

sysAMProduct OBJECT-TYPE
    SYNTAX DisplayString
    MAX-ACCESS read-only
    STATUS current
    DESCRIPTION
        "Device product description (i.e., model or model number)"
    ::= { sysAssetMgmt 2 }
    --1.3.6.1.4.1.3052.14.2.16.15.2

sysAMSerialNumber OBJECT-TYPE
    SYNTAX DisplayString
    MAX-ACCESS read-only
    STATUS current
    DESCRIPTION
        "Manufacturer serial number for device"
    ::= { sysAssetMgmt 3 }
    --1.3.6.1.4.1.3052.14.2.16.15.3

sysAMHardwareOptions OBJECT-TYPE
    SYNTAX DisplayString
    MAX-ACCESS read-only
    STATUS current
    DESCRIPTION
        "Hardware options currently installed on device"
    ::= { sysAssetMgmt 4 }
    --1.3.6.1.4.1.3052.14.2.16.15.4

sysAMSoftwareVersion OBJECT-TYPE
    SYNTAX DisplayString
    MAX-ACCESS read-only
    STATUS current
    DESCRIPTION
        "Currently-running software version on device"
    ::= { sysAssetMgmt 5 }
    --1.3.6.1.4.1.3052.14.2.16.15.5

sysAMSiteName OBJECT-TYPE
    SYNTAX DisplayString
    MAX-ACCESS read-write
    STATUS current
    DESCRIPTION
        "Site Name of device (user definable, also known as the
        siteName object under the productIds branch."
    ::= { sysAssetMgmt 6 }
    --1.3.6.1.4.1.3052.14.2.16.15.6


--***************************************************************************************
--Sys File Transfer Section 2.16.17
--***************************************************************************************

sysFileTransferStatus OBJECT-TYPE
    SYNTAX DisplayString
    MAX-ACCESS read-write
    STATUS current
    DESCRIPTION
        "Start/cancel file transfer, or check transfer status.  To start, set this object
        to 'start'.  To cancel, set this object to 'cancel'.  To check status, get the
        object"
    ::= { sysFileTransfer 1 }
    --1.3.6.1.4.1.3052.14.2.16.17.1

sysFileTransferURL OBJECT-TYPE
    SYNTAX DisplayString
    MAX-ACCESS read-write
    STATUS current
    DESCRIPTION
        "URL (describing protocol, host, directory, and file) on which file transfer
        function operates."
    ::= { sysFileTransfer 2 }
    --1.3.6.1.4.1.3052.14.2.16.17.2

sysFileTransferUsername OBJECT-TYPE
    SYNTAX DisplayString
    MAX-ACCESS read-write
    STATUS current
    DESCRIPTION
        "Username for user account at the resource specified by sysFileTransferURL."
    ::= { sysFileTransfer 3 }
    --1.3.6.1.4.1.3052.14.2.16.17.3

sysFileTransferPassword OBJECT-TYPE
    SYNTAX DisplayString
    MAX-ACCESS read-write
    STATUS current
    DESCRIPTION
        "Password for user account at the resource specified by sysFileTransferURL."
    ::= { sysFileTransfer 4 }
    --1.3.6.1.4.1.3052.14.2.16.17.4

--***************************************************************************************
--Sys Update Section 2.16.18
--***************************************************************************************

sysUpdateStatus OBJECT-TYPE
    SYNTAX DisplayString
    MAX-ACCESS read-only
    STATUS current
    DESCRIPTION
        "Check time/result of last update attempt."
    ::= { sysUpdate 1 }
    --1.3.6.1.4.1.3052.14.2.16.18.1


--***************************************************************************************
--Audit Log Section   2.17
--***************************************************************************************

auditLogEnable OBJECT-TYPE
    SYNTAX DisplayString
    MAX-ACCESS read-write
    STATUS current
    DESCRIPTION
        "ON/OFF enable audit log"
    ::= { auditLog 1 }
    --1.3.6.1.4.1.3052.14.2.17.1

auditLogStoreResets OBJECT-TYPE
    SYNTAX DisplayString
    MAX-ACCESS read-write
    STATUS current
    DESCRIPTION
        "ON/OFF audit log stores when the unit resets"
    ::= { auditLog 2 }
    --1.3.6.1.4.1.3052.14.2.17.1

auditLogStoreCommands OBJECT-TYPE
    SYNTAX DisplayString
    MAX-ACCESS read-write
    STATUS current
    DESCRIPTION
        "ON/OFF audit log stores commands entered in a command
        session"
    ::= { auditLog 3 }
    --1.3.6.1.4.1.3052.14.2.17.1

auditLogStoreOutputs OBJECT-TYPE
    SYNTAX DisplayString
    MAX-ACCESS read-write
    STATUS current
    DESCRIPTION
        "ON/OFF audit log stores output (relay output and power output)
        activity"
    ::= { auditLog 4 }
    --1.3.6.1.4.1.3052.14.2.17.1

auditLogStoreAlarmActions OBJECT-TYPE
    SYNTAX DisplayString
    MAX-ACCESS read-write
    STATUS current
    DESCRIPTION
        "ON/OFF audit log stores action delivery activity"
    ::= { auditLog 5 }
    --1.3.6.1.4.1.3052.14.2.17.1

auditLogStorePwdFailures OBJECT-TYPE
    SYNTAX DisplayString
    MAX-ACCESS read-write
    STATUS current
    DESCRIPTION
        "ON/OFF audit log stores when user was denied login"
    ::= { auditLog 6 }
    --1.3.6.1.4.1.3052.14.2.17.1

auditLogStoreLogins OBJECT-TYPE
    SYNTAX DisplayString
    MAX-ACCESS read-write
    STATUS current
    DESCRIPTION
        "ON/OFF audit log stores when a user was allowed login"
    ::= { auditLog 7 }
    --1.3.6.1.4.1.3052.14.2.17.1

auditLogStoreSHSK OBJECT-TYPE
    SYNTAX DisplayString
    MAX-ACCESS read-write
    STATUS current
    DESCRIPTION
        "ON/OFF audit log stores serial handshaking status
        (regardless of serial handshaking event)"
    ::= { auditLog 8 }
    --1.3.6.1.4.1.3052.14.2.17.1

auditLogStorePassthrough OBJECT-TYPE
    SYNTAX DisplayString
    MAX-ACCESS read-write
    STATUS current
    DESCRIPTION
        "ON/OFF audit log stores pass-through activity"
    ::= { auditLog 9 }
    --1.3.6.1.4.1.3052.14.2.17.1

auditLogStoreInactivity OBJECT-TYPE
    SYNTAX DisplayString
    MAX-ACCESS read-write
    STATUS current
    DESCRIPTION
        "ON/OFF audit log stores when sessions expire due to
        inactivity"
    ::= { auditLog 10 }
    --1.3.6.1.4.1.3052.14.2.17.1

auditLogStorePolling OBJECT-TYPE
    SYNTAX DisplayString
    MAX-ACCESS read-write
    STATUS current
    DESCRIPTION
        "ON/OFF audit log stores CRDB polling activity"
    ::= { auditLog 11 }
    --1.3.6.1.4.1.3052.14.2.17.1

auditLogMaxSize OBJECT-TYPE
    SYNTAX Integer32
    MAX-ACCESS read-write
    STATUS current
    DESCRIPTION
        "Maximum size (in KB) of audit log"
    ::= { auditLog 12 }
    --1.3.6.1.4.1.3052.14.2.17.1

--***************************************************************************************
--Scripting Section   2.17
--***************************************************************************************

scrGlobalEnable OBJECT-TYPE
    SYNTAX DisplayString
    MAX-ACCESS read-write
    STATUS current
    DESCRIPTION
        "ON/OFF enable scripting"
    ::= { scripting 1 }
    --1.3.6.1.4.1.3052.14.2.18.1

scrDTRCtrlPortEnableTable OBJECT-TYPE
    SYNTAX SEQUENCE OF ScriptingDTRCtrlPortEnableConfig
    MAX-ACCESS not-accessible
    STATUS current
    DESCRIPTION
        "Table of DTR control port enables"
    ::= { scripting 2 }
    --1.3.6.1.4.1.3052.14.2.18.2

scrDTRCtrlPortEnableEntry OBJECT-TYPE
    SYNTAX ScriptingDTRCtrlPortEnableConfig
    MAX-ACCESS not-accessible
    STATUS current
    DESCRIPTION
        "Entry for table of DTR control port enables"
    INDEX { scrDTRCtrlPortEnableIndex }
    ::= { scrDTRCtrlPortEnableTable 1 }
    --1.3.6.1.4.1.3052.14.2.18.2.1

scrDTRCtrlPortEnableIndex OBJECT-TYPE
    SYNTAX Integer32 (1..16)
    MAX-ACCESS read-only
    STATUS current
    DESCRIPTION
        "Index for table of DTR control port enables"
    ::= { scrDTRCtrlPortEnableEntry 1 }
    --1.3.6.1.4.1.3052.14.2.18.2.1.1

scrDTRCtrlPortEnable OBJECT-TYPE
    SYNTAX DisplayString
    MAX-ACCESS read-write
    STATUS current
    DESCRIPTION
        "ON/OFF enable DTR control of scripting for this port"
    ::= { scrDTRCtrlPortEnableEntry 2 }
    --1.3.6.1.4.1.3052.14.2.18.2.1.2


scrTable OBJECT-TYPE
    SYNTAX SEQUENCE OF ScriptingConfig
    MAX-ACCESS not-accessible
    STATUS current
    DESCRIPTION
        "Table of scripts"
    ::= { scripting 3 }
    --1.3.6.1.4.1.3052.14.2.18.3

scrEntry OBJECT-TYPE
    SYNTAX ScriptingConfig
    MAX-ACCESS not-accessible
    STATUS current
    DESCRIPTION
        "Entry for table of scripts"
    INDEX { scrIndex }
    ::= { scrTable 1 }
    --1.3.6.1.4.1.3052.14.2.18.3.1

scrIndex OBJECT-TYPE
    SYNTAX Integer32 (1..20)
    MAX-ACCESS read-only
    STATUS current
    DESCRIPTION
        "Index for table of scripts"
    ::= { scrEntry 1 }
    --1.3.6.1.4.1.3052.14.2.18.3.1.1

scrEnable OBJECT-TYPE
    SYNTAX DisplayString
    MAX-ACCESS read-write
    STATUS current
    DESCRIPTION
        "ON/OFF enable this script"
    ::= { scrEntry 2 }
    --1.3.6.1.4.1.3052.14.2.18.3.1.2

scrName OBJECT-TYPE
    SYNTAX DisplayString
    MAX-ACCESS read-write
    STATUS current
    DESCRIPTION
        "Name of this script"
    ::= { scrEntry 3 }
    --1.3.6.1.4.1.3052.14.2.18.3.1.3

scrFilename OBJECT-TYPE
    SYNTAX DisplayString
    MAX-ACCESS read-write
    STATUS current
    DESCRIPTION
        "Filename for this script"
    ::= { scrEntry 4 }
    --1.3.6.1.4.1.3052.14.2.18.3.1.4

scrRunAlways OBJECT-TYPE
    SYNTAX DisplayString
    MAX-ACCESS read-write
    STATUS current
    DESCRIPTION
        "ON/OFF: this script always runs"
    ::= { scrEntry 5 }
    --1.3.6.1.4.1.3052.14.2.18.3.1.5

scrRunAtStartup OBJECT-TYPE
    SYNTAX DisplayString
    MAX-ACCESS read-write
    STATUS current
    DESCRIPTION
        "ON/OFF: this script runs at startup"
    ::= { scrEntry 6 }
    --1.3.6.1.4.1.3052.14.2.18.3.1.6

scrRunScheduled OBJECT-TYPE
    SYNTAX DisplayString
    MAX-ACCESS read-write
    STATUS current
    DESCRIPTION
        "ON/OFF: this script runs at a certain time of day"
    ::= { scrEntry 7 }
    --1.3.6.1.4.1.3052.14.2.18.3.1.7

scrScheduleTime OBJECT-TYPE
    SYNTAX DisplayString
    MAX-ACCESS read-write
    STATUS current
    DESCRIPTION
        "Time of day (HH:MM) this script is scheduled to run"
    ::= { scrEntry 8 }
    --1.3.6.1.4.1.3052.14.2.18.3.1.8

scrArguments OBJECT-TYPE
    SYNTAX DisplayString
    MAX-ACCESS read-write
    STATUS current
    DESCRIPTION
        "Arguments for this script"
    ::= { scrEntry 9 }
    --1.3.6.1.4.1.3052.14.2.18.3.1.9

scrRepeatInterval OBJECT-TYPE
    SYNTAX Integer32
    MAX-ACCESS read-write
    STATUS current
    DESCRIPTION
        "How often this script runs (minutes)"
    ::= { scrEntry 10 }
    --1.3.6.1.4.1.3052.14.2.18.3.1.10

scrVolatileStringTable OBJECT-TYPE
    SYNTAX SEQUENCE OF ScriptingVolatileString
    MAX-ACCESS not-accessible
    STATUS current
    DESCRIPTION
        "Table of volatile string settings for use in
         scripts."
    ::= { scripting 4 }
    --1.3.6.1.4.1.3052.14.2.18.4

scrVolatileStringEntry OBJECT-TYPE
    SYNTAX ScriptingVolatileString
    MAX-ACCESS not-accessible
    STATUS current
    DESCRIPTION
        "Entry for table of volatile script string
        settings"
    INDEX { scrVolatileStringIndex }
    ::= { scrVolatileStringTable 1 }
    --1.3.6.1.4.1.3052.14.2.18.4.1

scrVolatileStringIndex OBJECT-TYPE
    SYNTAX Integer32 (1..50)
    MAX-ACCESS read-only
    STATUS current
    DESCRIPTION
        "Index for table of volatile script string
        settings"
    ::= { scrVolatileStringEntry 1 }
    --1.3.6.1.4.1.3052.14.2.18.4.1.1

scrVolatileString OBJECT-TYPE
    SYNTAX DisplayString
    MAX-ACCESS read-write
    STATUS current
    DESCRIPTION
        "Volatile string for use in scripts. Use this
         object to cache frequently-changing string values
         or string values that do not need to persist
         through reset.  This object corresponds to the
         scripting.vstring[] setting key branch; use those
         keys in scripts and you can view or change their
         values with this object."
    ::= { scrVolatileStringEntry 2 }
    --1.3.6.1.4.1.3052.14.2.18.4.1.2

scrVolatileIntTable OBJECT-TYPE
    SYNTAX SEQUENCE OF ScriptingVolatileInt
    MAX-ACCESS not-accessible
    STATUS current
    DESCRIPTION
        "Table of volatile integer settings for use in
         scripts."
    ::= { scripting 5 }
    --1.3.6.1.4.1.3052.14.2.18.5

scrVolatileIntEntry OBJECT-TYPE
    SYNTAX ScriptingVolatileInt
    MAX-ACCESS not-accessible
    STATUS current
    DESCRIPTION
        "Entry for table of volatile script integer
        settings"
    INDEX { scrVolatileIntIndex }
    ::= { scrVolatileIntTable 1 }
    --1.3.6.1.4.1.3052.14.2.18.5.1

scrVolatileIntIndex OBJECT-TYPE
    SYNTAX Integer32 (1..50)
    MAX-ACCESS read-only
    STATUS current
    DESCRIPTION
        "Index for table of volatile script integer
        settings"
    ::= { scrVolatileIntEntry 1 }
    --1.3.6.1.4.1.3052.14.2.18.5.1.1

scrVolatileInt OBJECT-TYPE
    SYNTAX Integer32 (0..2147483647)
    MAX-ACCESS read-write
    STATUS current
    DESCRIPTION
        "Volatile integer for use in scripts. Use this
         object to cache frequently-changing integer values
         or integer values that do not need to persist
         through reset.  This object corresponds to the
         scripting.vint[] setting key branch; use those
         keys in scripts and you can view or change their
         values with this object."
    ::= { scrVolatileIntEntry 2 }
    --1.3.6.1.4.1.3052.14.2.18.5.1.2

scrNonVolatileStringTable OBJECT-TYPE
    SYNTAX SEQUENCE OF ScriptingNonVolatileString
    MAX-ACCESS not-accessible
    STATUS current
    DESCRIPTION
        "Table of non-volatile string settings for use in
         scripts."
    ::= { scripting 6 }
    --1.3.6.1.4.1.3052.14.2.18.6

scrNonVolatileStringEntry OBJECT-TYPE
    SYNTAX ScriptingNonVolatileString
    MAX-ACCESS not-accessible
    STATUS current
    DESCRIPTION
        "Entry for table of non-volatile script string
        settings"
    INDEX { scrNonVolatileStringIndex }
    ::= { scrNonVolatileStringTable 1 }
    --1.3.6.1.4.1.3052.14.2.18.6.1

scrNonVolatileStringIndex OBJECT-TYPE
    SYNTAX Integer32 (1..50)
    MAX-ACCESS read-only
    STATUS current
    DESCRIPTION
        "Index for table of non-volatile script string
        settings"
    ::= { scrNonVolatileStringEntry 1 }
    --1.3.6.1.4.1.3052.14.2.18.6.1.1

scrNonVolatileString OBJECT-TYPE
    SYNTAX DisplayString
    MAX-ACCESS read-write
    STATUS current
    DESCRIPTION
        "Non-volatile string for use in scripts. Use this
         object to store values that need to persist
         through reset.  This object corresponds to the
         scripting.nvstring[] setting key branch; use those
         keys in scripts and you can view or change their
         values with this object.  Note: to store frequently-
         changing integers, use the scrVolatileString object,
         otherwise your scripts may cause unnecessary wear of
         the non-volatile storage medium on the unit."
    ::= { scrNonVolatileStringEntry 2 }
    --1.3.6.1.4.1.3052.14.2.18.6.1.2

scrNonVolatileIntTable OBJECT-TYPE
    SYNTAX SEQUENCE OF ScriptingNonVolatileInt
    MAX-ACCESS not-accessible
    STATUS current
    DESCRIPTION
        "Table of non-volatile integer settings for use in
         scripts."
    ::= { scripting 7 }
    --1.3.6.1.4.1.3052.14.2.18.7

scrNonVolatileIntEntry OBJECT-TYPE
    SYNTAX ScriptingNonVolatileInt
    MAX-ACCESS not-accessible
    STATUS current
    DESCRIPTION
        "Entry for table of non-volatile script integer
        settings"
    INDEX { scrNonVolatileIntIndex }
    ::= { scrNonVolatileIntTable 1 }
    --1.3.6.1.4.1.3052.14.2.18.7.1

scrNonVolatileIntIndex OBJECT-TYPE
    SYNTAX Integer32 (1..50)
    MAX-ACCESS read-only
    STATUS current
    DESCRIPTION
        "Index for table of non-volatile script integer
        settings"
    ::= { scrNonVolatileIntEntry 1 }
    --1.3.6.1.4.1.3052.14.2.18.7.1.1

scrNonVolatileInt OBJECT-TYPE
    SYNTAX Integer32 (0..2147483647)
    MAX-ACCESS read-write
    STATUS current
    DESCRIPTION
        "Non-volatile integer for use in scripts. Use this
         object to store integer values that need to persist
         through reset.  This object corresponds to the
         scripting.nvint[] setting key branch; use those
         keys in scripts and you can view or change their
         values with this object.  Note: to store frequently-
         changing integers, use the scrVolatileInt object,
         otherwise your scripts may cause unnecessary wear of
         the non-volatile storage medium on the unit."
    ::= { scrNonVolatileIntEntry 2 }
    --1.3.6.1.4.1.3052.14.2.18.7.1.2

--***************************************************************************************
--Product IDs Section   3
--***************************************************************************************

siteName OBJECT-TYPE
    SYNTAX DisplayString
    MAX-ACCESS read-only
    STATUS current
    DESCRIPTION
        "Site Name string; Max 40 characters."
    ::= { productIds 1 }
    --1.3.6.1.4.1.3052.14.3.1

thisProduct OBJECT-TYPE
    SYNTAX DisplayString
    MAX-ACCESS read-only
    STATUS current
    DESCRIPTION
        "This is a factory configured string for the
        product name."
    ::= { productIds 2 }
    --1.3.6.1.4.1.3052.14.3.2

stockTrapString OBJECT-TYPE
    SYNTAX DisplayString
    MAX-ACCESS read-only
    STATUS current
    DESCRIPTION
        "The message defined for the event that triggers a trap."
    ::= { productIds 3 }
    --1.3.6.1.4.1.3052.14.3.3

trapEventTypeNumber OBJECT-TYPE
    SYNTAX Integer32
    MAX-ACCESS read-only
    STATUS current
    DESCRIPTION
        "The user-defined trap variable for the type of
        event that happened.  Definitions:
           4    Scheduled
           7    Serial Handshaking Low
           8    Serial Handshaking High
           10   Contact Closure Active
           11   Contact Closure Inactive
           12   Temperature High
           13   Temperature Very High
           14   Temperature Low
           15   Temperature Very Low
           16   Temperature Return to Normal
           17   Humidity High
           18   Humidity Very High
           19   Humidity Low
           20   Humidity Very Low
           21   Humidity Return to Normal
           26   Analog High
           27   Analog Very High
           28   Analog Low
           29   Analog Very Low
           30   Analog Normal
           40   EventSensor Unresponsive
           41   Custom
           42   CPE Down
           44   CPE Normal
           47   Power Distribution
           49   Fuel Sensor Disconnect
           50   Fuel Sensor Disconnect Return to Normal
           52   AISG Device Alarm
           53   AISG Device Alarm Return to Normal
           54   AISG Device Unresponsive
           55   AISG Device Unresponsive Return to Normal
           56   Fuel Sensor
           57   AC Power Monitor Average Voltage Very Low
           58   AC Power Monitor Average Voltage Low
           59   AC Power Monitor Average Voltage Return to Normal
           60   AC Power Monitor Average Voltage High
           61   AC Power Monitor Average Voltage Very High
           62   AC Power Monitor Average Current Very Low
           63   AC Power Monitor Average Current Low
           64   AC Power Monitor Average Current Return to Normal
           65   AC Power Monitor Average Current High
           66   AC Power Monitor Average Current Very High
           67   AC Power Monitor Frequency Very Low
           68   AC Power Monitor Frequency Low
           69   AC Power Monitor Frequency Return to Normal
           70   AC Power Monitor Frequency High
           71   AC Power Monitor Frequency Very High
           72   AC Power Monitor Total Real Power Very Low
           73   AC Power Monitor Total Real Power Low
           74   AC Power Monitor Total Real Power Return to Normal
           75   AC Power Monitor Total Real Power High
           76   AC Power Monitor Total Real Power Very High
           77   AC Power Monitor Disconnect
           78   AC Power Monitor Disconnect Return to Normal
           79   Load Shedding Started
           80   Load Shedding Ended
           81   Fuel Sensor Volume Sudden Change
           82   Fuel Sensor Volume Slow Change
           83   CPE Down Reminder
           84   AC Power Monitor Total Power Factor Very Low
           85   AC Power Monitor Total Power Factor Low
           86   AC Power Monitor Total Power Factor Return to Normal
           100  Contact Closure Active Reminder
           101  Temperature High Reminder
           102  Temperature High Very Reminder
           103  Temperature Low Reminder
           104  Temperature Very Low Reminder
           105  Humidity High Reminder
           106  Humidity Very High Reminder
           107  Humidity Low Reminder
           108  Humidity Very Low Reminder
           109  Analog High Reminder
           110  Analog Very High Reminder
           111  Analog Low Reminder
           112  Analog Very Low Reminder
           130  Relay Output Active
           131  Relay Output Inactive
           132  Power Output On
           133  Power Output Off
           164  Reset
           166  Fuel Sensor Levels Auto Adjust
           "
    ::= { productIds 4 }
    --1.3.6.1.4.1.3052.14.3.4

trapEventTypeName OBJECT-TYPE
    SYNTAX DisplayString
    MAX-ACCESS read-only
    STATUS current
    DESCRIPTION
        "The user-defined trap variable for the string
        corresponding to the event type."
    ::= { productIds 5 }
    --1.3.6.1.4.1.3052.14.3.5

trapIncludedValue OBJECT-TYPE
    SYNTAX Integer32 (-2147483648..2147483647)
    MAX-ACCESS read-only
    STATUS current
    DESCRIPTION
        "The user-defined trap variable for the generic
        included value."
    ::= { productIds 6 }
    --1.3.6.1.4.1.3052.14.3.6

trapIncludedString OBJECT-TYPE
    SYNTAX DisplayString
    MAX-ACCESS read-only
    STATUS current
    DESCRIPTION
        "The user-defined trap variable for the generic
        included string."
    ::= { productIds 7 }
    --1.3.6.1.4.1.3052.14.3.7

trapTypeString OBJECT-TYPE
    SYNTAX DisplayString
    MAX-ACCESS read-only
    STATUS current
    DESCRIPTION
        "The cause of the trap, added for DL880 compatibility."
    ::= { productIds 8 }
    --1.3.6.1.4.1.3052.14.3.8

trapEventClassNumber OBJECT-TYPE
    SYNTAX Integer32
    MAX-ACCESS read-only
    STATUS current
    DESCRIPTION
        "The user-defined trap variable for the configurable
        class number associated with the triggering event."
    ::= { productIds 9 }
    --1.3.6.1.4.1.3052.14.3.9

trapEventClassName OBJECT-TYPE
    SYNTAX DisplayString
    MAX-ACCESS read-only
    STATUS current
    DESCRIPTION
        "The user-defined trap variable for the configurable
         class name associated with the class number."
    ::= { productIds 10 }
    --1.3.6.1.4.1.3052.14.3.10


--***************************************************************************************
--Product IDs Section   3
--***************************************************************************************

keyInterface OBJECT-TYPE
    SYNTAX DisplayString
    MAX-ACCESS read-write
    STATUS current
    DESCRIPTION
        "This object represents a setting key interface.  When
        setting this object, the value to set is the 'sk' command
        you would enter on the command line (without the 'sk').  To
        get the result of the operation, read this object after you
        write it.

        For example, to configure EventSensor 1 contact closure 34
        event actions to be an SNMP InformRequest to host foo, set
        this object to:
        'event.sensor[1].cc[34].eventactions=inform(foo)'.  The SNMP
        response is the result of the operation: if setting that key
        to that value was a success then the SNMP response will be a
        success and the response value will be what you had set.  If
        you subsequently read this object then you will see a
        message 'OK: ...'.

        If setting that key to that value failed then the SNMP
        response will be a failure (a badValue response).  If you
        subsequently read this object then the value returned is the
        reason that setting that key to that value failed.

        For another example, to read user 3's pass-through access
        for port 7, set this object to:
        'sec.user[3].port[7].ptaccess'.  The SNMP response is the
        result of the operation: if reading that key is a success
        then the SNMP response will be a success and the response
        value will be what you had SET (i.e., the opertion of
        reading a key, which is just the key itself with no '='
        operator, and this is not the key value you want to read).
        If you subsequently read this object then the value
        returned is the value of the key you want to read.

        If reading that key failed (e.g., if the key is invalid)
        then the SNMP response to your SNMP set operation (the
        value you set being the invalid key to read) will be a
        failure (a badValue response).  If you subsequently read
        this object then the value returned is the reason that
        reading that key failed (i.e., 'invalid key')."
    ::= { s571 4 }
    --1.3.6.1.4.1.3052.14.4


--***************************************************************************************
--TABLE DEFINITIONS
--***************************************************************************************

ESPointConfigTemp ::=
    SEQUENCE {
    espcTempIndexES
            Integer32,
    espcTempIndexPoint
            Integer32,
    espcTempEnable
            DisplayString,
    espcTempScale
            DisplayString,
    espcTempDeadband
            DisplayString,
    espcTempVHighTemp
            DisplayString,
    espcTempVHighActions
            DisplayString,
    espcTempVHighTrapnum
            Integer32,
    espcTempVHighClass
            DisplayString,
    espcTempHighTemp
            DisplayString,
    espcTempHighActions
            DisplayString,
    espcTempHighTrapnum
            Integer32,
    espcTempHighClass
            DisplayString,
    espcTempNormalActions
            DisplayString,
    espcTempNormalTrapnum
            Integer32,
    espcTempNormalClass
            DisplayString,
    espcTempLowTemp
            DisplayString,
    espcTempLowActions
            DisplayString,
    espcTempLowTrapnum
            Integer32,
    espcTempLowClass
            DisplayString,
    espcTempVLowTemp
            DisplayString,
    espcTempVLowActions
            DisplayString,
    espcTempVLowTrapnum
            Integer32,
    espcTempVLowClass
            DisplayString
}


ESPointConfigCC ::=
    SEQUENCE {
        espcCCIndexES
            Integer32,
        espcCCIndexPoint
            Integer32,
        espcCCEnable
            DisplayString,
        espcCCName
            DisplayString,
        espcCCEventState
            DisplayString,
        espcCCThreshold
            Integer32,
        espcCCEventActions
            DisplayString,
        espcCCEventTrapnum
            Integer32,
        espcCCEventClass
            DisplayString,
        espcCCNormalActions
            DisplayString,
        espcCCNormalTrapnum
            Integer32,
        espcCCNormalClass
            DisplayString,
        espcCCAlarmAlias
            DisplayString,
        espcCCNormalAlias
            DisplayString,
        espcCCNormalThreshold
            Integer32,
        espcCCOverrideGlobalReminder
            DisplayString,
        espcCCReminderInterval
            Integer32
}

ESPointConfigHumid ::=
    SEQUENCE {
    espcHumidIndexES
            Integer32,
    espcHumidIndexPoint
            Integer32,
    espcHumidEnable
            DisplayString,
    espcHumidDeadband
            Integer32,
    espcHumidVHighHumid
            Integer32,
    espcHumidVHighActions
            DisplayString,
    espcHumidVHighTrapnum
            Integer32,
    espcHumidVHighClass
            DisplayString,
    espcHumidHighHumid
            Integer32,
    espcHumidHighActions
            DisplayString,
    espcHumidHighTrapnum
            Integer32,
    espcHumidHighClass
            DisplayString,
    espcHumidNormalActions
            DisplayString,
    espcHumidNormalTrapnum
            Integer32,
    espcHumidNormalClass
            DisplayString,
    espcHumidLowHumid
            Integer32,
    espcHumidLowActions
            DisplayString,
    espcHumidLowTrapnum
            Integer32,
    espcHumidLowClass
            DisplayString,
    espcHumidVLowHumid
            Integer32,
    espcHumidVLowActions
            DisplayString,
    espcHumidVLowTrapnum
            Integer32,
    espcHumidVLowClass
            DisplayString
}

ESPointConfigAnalogInput ::=
    SEQUENCE {
    espcAIIndexES
            Integer32,
    espcAIIndexPoint
            Integer32,
    espcAIEnable
            DisplayString,
    espcAIDeadband
            DisplayString,
    espcAIVhighValue
            DisplayString,
    espcAIVhighActions
            DisplayString,
    espcAIVhighTrapnum
            Integer32,
    espcAIVhighClass
            DisplayString,
    espcAIHighValue
            DisplayString,
    espcAIHighActions
            DisplayString,
    espcAIHighTrapnum
            Integer32,
    espcAIHighClass
            DisplayString,
    espcAINormalActions
            DisplayString,
    espcAINormalTrapnum
            Integer32,
    espcAINormalClass
            DisplayString,
    espcAILowValue
            DisplayString,
    espcAILowActions
            DisplayString,
    espcAILowTrapnum
            Integer32,
    espcAILowClass
            DisplayString,
    espcAIVlowValue
            DisplayString,
    espcAIVlowActions
            DisplayString,
    espcAIVlowTrapnum
            Integer32,
    espcAIVlowClass
            DisplayString,
    espcAIConvUnitName
            DisplayString,
    espcAIConvHighValue
            DisplayString,
    espcAIConvHighUnit
            DisplayString,
    espcAIConvLowValue
            DisplayString,
    espcAIConvLowUnit
            DisplayString,
    espcAIDisplayFormat
            DisplayString
}


ActionCallNumberConfig ::=
    SEQUENCE {
        actionCallNumberIndex
            Integer32,
        actionCallNumber
            DisplayString

}

ActionPagerConfig ::=
    SEQUENCE {
        actionPagerIndex
            Integer32,
        actionPagerType
            DisplayString,
        actionPagerNumber
            DisplayString,
        actionPagerID
            DisplayString,
        actionPagerMessage
            DisplayString,
        actionPagerPostCalloutDelay
            Integer32,
        actionPagerPostIDDelay
            Integer32
}

ESPointConfigOutput ::=
    SEQUENCE {
        espcOutputIndexES
            Integer32,
        espcOutputIndexPoint
            Integer32,
        espcOutputEnable
            DisplayString,
        espcOutputActiveState
            DisplayString,
        espcOutputType
            DisplayString,
        espcOutputAliasValue
            DisplayString,
        espcOutputAliasColor
            DisplayString,
        espcOutputActiveAlias
            DisplayString,
        espcOutputActiveColor
            DisplayString,
        espcOutputActiveActions
            DisplayString,
        espcOutputActiveTrapnum
            Integer32,
        espcOutputActiveClass
            DisplayString,
        espcOutputInactiveAlias
            DisplayString,
        espcOutputInactiveColor
            DisplayString,
        espcOutputInactiveActions
            DisplayString,
        espcOutputInactiveTrapnum
            Integer32,
        espcOutputInactiveClass
            DisplayString
}

EventClassConfig ::=
    SEQUENCE {
        evClassNameIndex
            Integer32,
        evClassName
            DisplayString
}

RTSFileConfig ::=
    SEQUENCE {
        rtsFileIndex
            Integer32,
        rtsFileMode
            DisplayString,
        rtsFileShowAnswer
            DisplayString,
        rtsFileReqXON
            DisplayString,
        rtsFileTimeout
            Integer32,
        rtsFileEmptyClose
            DisplayString,
        rtsFilePushHost
            DisplayString,
        rtsFilePushPort
            Integer32,
        rtsFilePushRetryTimer
            Integer32
}


ModemCLIDLogConfig ::=
    SEQUENCE {
        modemCLIDLogIndex
            Integer32,
        modemCLIDLogNumber
            DisplayString
}


PowerDistribOutputCurrent ::=
    SEQUENCE {
        pdOutputCurrentIndex
            Integer32,
        pdOutputCurrentInEventState
            DisplayString,
        pdOutputCurrentValue
            Integer32,
        pdOutputCurrentValueStr
            DisplayString,
        pdOutputCurrentDeadband
            Integer32,
        pdOutputCurrentVHighCurrent
            Integer32,
        pdOutputCurrentHighCurrent
            Integer32,
        pdOutputCurrentLowCurrent
            Integer32,
        pdOutputCurrentVLowCurrent
            Integer32
}

PowerDistribOutputFuse ::=
    SEQUENCE {
        pdOutputFuseIndex
            Integer32,
        pdOutputFuseInEventState
            DisplayString,
        pdOutputFuseValueStr
            DisplayString
}

PowerDistribNextGen ::=
    SEQUENCE {
        pdnIndexPD
            Integer32,
        pdnIndexOutput
            Integer32,
        pdnConfig
            DisplayString,
        pdnMainCurrentInEventState
            DisplayString,
        pdnMainCurrentValue
            Integer32,
        pdnMainCurrentValueStr
            DisplayString,
        pdnMainCurrentDeadband
            Integer32,
        pdnMainCurrentVHighCurrent
            Integer32,
        pdnMainCurrentHighCurrent
            Integer32,
        pdnMainCurrentLowCurrent
            Integer32,
        pdnMainCurrentVLowCurrent
            Integer32,
        pdnMainVoltageInEventState
            DisplayString,
        pdnMainVoltageValue
            Integer32,
        pdnMainVoltageValueStr
            DisplayString,
        pdnMainVoltageDeadband
            Integer32,
        pdnMainVoltageVHighVoltage
            Integer32,
        pdnMainVoltageHighVoltage
            Integer32,
        pdnMainVoltageLowVoltage
            Integer32,
        pdnMainVoltageVLowVoltage
            Integer32,
        pdnMainPowerValue
            Integer32,
        pdnMainPowerValueStr
            DisplayString,
        pdnOutputCurrentInEventState
            DisplayString,
        pdnOutputCurrentValue
            Integer32,
        pdnOutputCurrentValueStr
            DisplayString,
        pdnOutputCurrentDeadband
            Integer32,
        pdnOutputCurrentVHighCurrent
            Integer32,
        pdnOutputCurrentHighCurrent
            Integer32,
        pdnOutputCurrentLowCurrent
            Integer32,
        pdnOutputCurrentVLowCurrent
            Integer32,
        pdnOutputFuseInEventState
            DisplayString,
        pdnOutputFuseValueStr
            DisplayString,
        pdnMainCombinedStatus
            DisplayString,
        pdnOutputCombinedStatusBlock1
            DisplayString,
        pdnOutputCombinedStatusBlock2
            DisplayString,
        pdnDeviceCurrentValue
            Integer32,
        pdnDeviceCurrentValueStr
            DisplayString
}

CPEConfig ::=
    SEQUENCE {
        cpeIndex
            Integer32,
        cpeHost
            DisplayString,
        cpeName
            DisplayString,
        cpeDescription
            DisplayString,
        cpeKeepalive
            Integer32,
        cpeThreshold
            Integer32,
        cpeEventReminderInterval
            Integer32,
        cpeKeepaliveTicks
            Integer32,
        cpePingSize
            Integer32,
        cpeInfoReset
            Integer32,
        cpeInfoNumReq
            Integer32,
        cpeInfoNumGoodResp
            Integer32,
        cpeInfoNumBadResp
            Integer32,
        cpeInfoNumLostResp
            Integer32,
        cpeInfoPercentLoss
            DisplayString,
        cpeInfoPercentBad
            DisplayString
}

ScriptingConfig ::=
    SEQUENCE {
        scrIndex
            Integer32,
        scrEnable
            DisplayString,
        scrName
            DisplayString,
        scrFilename
            DisplayString,
        scrRunAlways
            DisplayString,
        scrRunAtStartup
            DisplayString,
        scrRunScheduled
            DisplayString,
        scrScheduleTime
            DisplayString,
        scrArguments
            DisplayString,
        scrRepeatInterval
            Integer32
}

ScriptingDTRCtrlPortEnableConfig ::=
    SEQUENCE {
        scrDTRCtrlPortEnableIndex
            Integer32,
        scrDTRCtrlPortEnable
            DisplayString

}

ScriptingVolatileString ::=
    SEQUENCE {
        scrVolatileStringIndex
            Integer32,
        scrVolatileString
            DisplayString
}

ScriptingVolatileInt ::=
    SEQUENCE {
        scrVolatileIntIndex
            Integer32,
        scrVolatileInt
            Integer32
}

ScriptingNonVolatileString ::=
    SEQUENCE {
        scrNonVolatileStringIndex
            Integer32,
        scrNonVolatileString
            DisplayString
}

ScriptingNonVolatileInt ::=
    SEQUENCE {
        scrNonVolatileIntIndex
            Integer32,
        scrNonVolatileInt
            Integer32
}

CRDBFileEnforceMinConfig ::=
    SEQUENCE {
        sysCRDBFileEnforceMinIndex
            Integer32,
        sysCRDBFileEnforceMin
            DisplayString
}

CRDBFileIDConfig ::=
    SEQUENCE {
        sysCRDBFileIDIndex
            Integer32,
        sysCRDBFileID
            DisplayString
}

NetworkTimeHostConfig ::=
    SEQUENCE {
        sysTimeNetHostIndex
            Integer32,
        sysTimeNetHost
            DisplayString
}

ActionHostConfig ::=
    SEQUENCE {
        actionHostIndex
            Integer32,
        actionHost
            DisplayString
}

ActionEmailConfig ::=
    SEQUENCE {
        actionEmailIndex
            Integer32,
        actionEmail
            DisplayString
}

FileEnforceMinimumConfig ::=
    SEQUENCE {
        sysCRDBFileEnforceMinIndex
            Integer32,
        sysCRDBFileEnforceMin
            DisplayString
}

SerialHandshakingLowEventConfig ::=
    SEQUENCE {
        evShskLowIndex
            Integer32,
        evShskLowEnable
            DisplayString,
        evShskLowActions
            DisplayString,
        evShskLowMessage
            DisplayString,
        evShskLowClass
            DisplayString,
        evShskLowTrapNum
            Integer32
}

SerialHandshakingHighEventConfig ::=
    SEQUENCE {
        evShskHighIndex
            Integer32,
        evShskHighEnable
            DisplayString,
        evShskHighActions
            DisplayString,
        evShskHighMessage
            DisplayString,
        evShskHighClass
            DisplayString,
        evShskHighTrapNum
            Integer32
}

NoDataEvent1PortEnableConfig ::=
    SEQUENCE {
        evNoData1PortEnableIndex
            Integer32,
        evNoData1PortEnable
            DisplayString
}

NoDataEvent2PortEnableConfig ::=
    SEQUENCE {
        evNoData2PortEnableIndex
            Integer32,
        evNoData2PortEnable
            DisplayString
}

DataEventMacroConfig ::=
    SEQUENCE {
        evdMacroIndex
            Integer32,
        evdMacroName
            DisplayString,
        evdMacroEquation
            DisplayString
}

DataEventFieldConfig ::=
    SEQUENCE {
        evdFieldIndex
            Integer32,
        evdFieldStart
            Integer32,
        evdFieldLength
            Integer32,
        evdFieldName
            DisplayString,
        evdFieldLine
            Integer32,
        evdFieldType
            DisplayString
}

DataEventConfig ::=
    SEQUENCE {
        evdIndex
            Integer32,
        evdEnable
            DisplayString,
        evdName
            DisplayString,
        evdEquation
            DisplayString,
        evdThreshold
            Integer32,
        evdAutoClear
            DisplayString,
        evdClearInterval
            DisplayString,
        evdClearTime
            DisplayString,
        evdActions
            DisplayString,
        evdClass
            DisplayString,
        evdTrapNum
            Integer32,
        evdMode
            DisplayString
}

SecUserConfig ::=
    SEQUENCE {
        secUserIndex
            Integer32,
        secUserEnable
            DisplayString,
        secUserConnectVia
            DisplayString,
        secUserLoginTo
            DisplayString,
        secUserAccessFile
            DisplayString,
        secUserPTEscapeTo
            DisplayString,
        secUserPPPType
            DisplayString,
        secUserRights
            DisplayString,
        secUserEventsReadAccess
            DisplayString,
        secUserAuditReadAccess
            DisplayString,
        secUserEventsWriteAccess
            DisplayString,
        secUserAuditWriteAccess
            DisplayString,
        secUserExpiration
            DisplayString,
        secUserCallbackNumber1
            DisplayString,
        secUserCallbackNumber2
            DisplayString,
        secUserCallbackNumber3
            DisplayString,
        secUserChallengeTelnetMode
            DisplayString,
        secUserChallengeModemMode
            DisplayString,
        secUserChallengeConsoleMode
            DisplayString,
        secUserChallengeTelnetSendTo
            DisplayString,
        secUserChallengeModemSendTo
            DisplayString,
        secUserChallengeExpiration
            Integer32
}




ModemCLIDNumberConfig ::=
    SEQUENCE {
        modemCLIDNumberIndex
            Integer32,
        modemCLIDNumber
            DisplayString
}


RouteTestConfig ::=
    SEQUENCE {
        routeTestAddressIndex
            Integer32,
        routeTestAddress
            DisplayString
}

IPRestrictionConfig ::=
    SEQUENCE {
        ipRestrictionIndex
            Integer32,
        ipRestrictionEnable
            DisplayString,
        ipRestrictionMask
            DisplayString
}

DNSConfig ::=
    SEQUENCE {
        dnsIndex
            Integer32,
        dnsAddress
            IpAddress
}

HostConfig ::=
    SEQUENCE {
        hostIndex
            Integer32,
        hostDeclaration
            DisplayString
}

SNMPPollRequestConfig ::=
    SEQUENCE {
        snmpPRequestIndex
            Integer32,
        snmpPRequestDescription
            DisplayString,
        snmpPRequestAgent
            DisplayString,
        snmpPRequestReadcom
            DisplayString,
        snmpPRequestOID
            DisplayString,
        snmpPRequestPeriod
            Integer32,
        snmpPRequestID
            DisplayString,
        snmpPRequestThreshold
            DisplayString,
        snmpPRequestResultStatus
            DisplayString,
        snmpPRequestResultValue
            DisplayString,
        snmpPRequestResultTime
            DisplayString,
        snmpPRequestResultType
            DisplayString
}

FTPPushPushFileConfig ::=
    SEQUENCE {
        ftpPushPushFileIndex
            Integer32,
        ftpPushPushFile
            DisplayString
}

FTPPushRemoteFileConfig ::=
    SEQUENCE {
        ftpPushRemoteFileIndex
            Integer32,
        ftpPushRemoteFileName
            DisplayString
}

PortConfig ::=
    SEQUENCE {
        portConfigIndex
            Integer32,
        portConfigBaud
            Integer32,
        portConfigDataFormat
            Integer32,
        portConfigStripPtOutputLfs
            Integer32,
        portConfigStripPtInputLfs
            Integer32,
        portConfigMaskEnable
            Integer32,
        portConfigDAEnable
            Integer32,
        portConfigStoreAlarmsDPT
            DisplayString,
        portConfigRecordTimeout
            Integer32,
        portConfigDataType
            DisplayString,
        portConfigEtxToCRLF
            DisplayString,
        portConfigMLREnable
            DisplayString,
        portConfigMLRStartField1Pos
            Integer32,
        portConfigMLRStartField1Text
            DisplayString,
        portConfigMLRStartField2Pos
            Integer32,
        portConfigMLRStartField2Text
            DisplayString,
        portConfigMLRNumLinesBefore
            Integer32,
        portConfigMLREndDetection
            DisplayString,
        portConfigMLRLineCount
            Integer32,
        portConfigMLREndField1Pos
            Integer32,
        portConfigMLREndField1Text
            DisplayString,
        portConfigMLREndField2Pos
            Integer32,
        portConfigMLREndField2Text
            DisplayString,
        portConfigMLRUseComplexRules
            DisplayString,
        portConfigBufferPT
            DisplayString,
        portConfigId
            DisplayString,
        portConfigMode
            DisplayString,
        portConfigHsk
            DisplayString

}

ESPoint ::=
    SEQUENCE {
        esIndexES
            Integer32,
        esIndexPC
            Integer32,
        esIndexPoint
            Integer32,
        esPointName
            DisplayString,
        esPointInEventState
            Integer32,
        esPointValueInt
            Integer32,
        esPointValueStr
            DisplayString,
        esPointTimeLastChange
            DisplayString,
        esPointTimetickLastChange
            TimeTicks
}

ESExist ::=
    SEQUENCE {
        esIndex
            Integer32,
        esName
            DisplayString,
        esID
            DisplayString,
        esNumberTempSensors
            Integer32,
        esTempReportingMode
            DisplayString,
        esNumberCCs
            Integer32,
        esCCReportingMode
            DisplayString,
        esNumberHumidSensors
            Integer32,
        esHumidReportingMode
            DisplayString,
        esNumberNoiseSensors
            Integer32,
        esNoiseReportingMode
            DisplayString,
        esNumberAirflowSensors
            Integer32,
        esAirflowReportingMode
            DisplayString,
        esNumberAnalog
            Integer32,
        esAnalogReportingMode
            DisplayString,
        esNumberOutputs
            Integer32,
        esOutputReportingMode
            DisplayString,
        esTempCombinedStatus
            DisplayString,
        esCCCombinedStatusBlock1
            DisplayString,
        esCCCombinedStatusBlock2
            DisplayString,
        esCCCombinedStatusBlock3
            DisplayString,
        esCCCombinedStatusBlock4
            DisplayString,
        esCCCombinedStatusBlock5
            DisplayString,
        esCCCombinedStatusBlock6
            DisplayString,
        esCCCombinedStatusBlock7
            DisplayString,
        esCCCombinedStatusBlock8
            DisplayString,
        esHumidCombinedStatus
            DisplayString,
        esAnalogCombinedStatusBlock1
            DisplayString,
        esAnalogCombinedStatusBlock2
            DisplayString,
        esAnalogCombinedStatusBlock3
            DisplayString,
        esAnalogCombinedStatusBlock4
            DisplayString,
        esAnalogCombinedStatusBlock5
            DisplayString,
        esAnalogCombinedStatusBlock6
            DisplayString,
        esOutputCombinedStatusBlock1
            DisplayString,
        esOutputCombinedStatusBlock2
            DisplayString
}

DEStatus ::=
    SEQUENCE {
        deStatusIndex
            Integer32,
        deStatusName
            DisplayString,
        deStatusCounter
            Integer32,
        deStatusThreshold
            Integer32
}

AISGALD ::=
    SEQUENCE {
        aisgsALDIndex
            Integer32,
        aisgsALDSectorID
            DisplayString,
        aisgsALDType
            DisplayString,
        aisgsALDDescription
            DisplayString,
        aisgsALDStatus
            DisplayString,
        aisgsALDID
            DisplayString,
        aisgsALDTilt
            DisplayString,
        aisgsALDHwVersion
            DisplayString,
        aisgsALDSwVersion
            DisplayString,
        aisgsALDModel
            DisplayString,
        aisgsALDAntennaModel
            DisplayString,
        aisgsALDMinTilt
            DisplayString,
        aisgsALDMaxTilt
            DisplayString,
        aisgsALDAISGVersion
            DisplayString
}

AISGFile ::=
    SEQUENCE {
        aisgsFileIndex
            Integer32,
        aisgsFileName
            DisplayString,
        aisgsFileType
            DisplayString,
        aisgsFileVersion
            DisplayString
}

AISGAuto ::=
    SEQUENCE {
        aisgsAutoIndex
            Integer32,
        aisgsAutoVendor
            DisplayString,
        aisgsAutoALDModel
            DisplayString,
        aisgsAutoSoftware
            DisplayString,
        aisgsAutoConfig
            DisplayString,
        aisgsAutoTilt
            DisplayString
}

AISGAAA ::=
    SEQUENCE {
        aisgsAAAIndex
            Integer32,
        aisgsAAAALDID
            DisplayString,
        aisgsAAAAntennaSN
            DisplayString,
        aisgsAAASectorID
            DisplayString
}

FSStatus ::=
    SEQUENCE {
        fsStatusIndex
            Integer32,
        fsStatusName
            DisplayString,
        fsStatusDeviceState
            DisplayString,
        fsStatusVolumeValueString
            DisplayString,
        fsStatusVolumePercentLevel
            DisplayString,
        fsStatusVolumeInEventState
            DisplayString,
        fsStatusCombined
            DisplayString
}

ACPMStatus ::=
    SEQUENCE {
        acpmsIndex
            Integer32,
        acpmsName
            DisplayString,
        acpmsAvgVoltageValueStr
            DisplayString,
        acpmsAvgVoltageMinStr
            DisplayString,
        acpmsAvgVoltageMaxStr
            DisplayString,
        acpmsAvgVoltageAvgStr
            DisplayString,
        acpmsAvgVoltageInEventState
            DisplayString,
        acpmsVoltagePhaseAValueStr
            DisplayString,
        acpmsVoltagePhaseBValueStr
            DisplayString,
        acpmsVoltagePhaseCValueStr
            DisplayString,
        acpmsAvgCurrentValueStr
            DisplayString,
        acpmsAvgCurrentMinStr
            DisplayString,
        acpmsAvgCurrentMaxStr
            DisplayString,
        acpmsAvgCurrentAvgStr
            DisplayString,
        acpmsAvgCurrentInEventState
            DisplayString,
        acpmsCurrentPhaseAValueStr
            DisplayString,
        acpmsCurrentPhaseBValueStr
            DisplayString,
        acpmsCurrentPhaseCValueStr
            DisplayString,
        acpmsAvgFreqValueStr
            DisplayString,
        acpmsAvgFreqMinStr
            DisplayString,
        acpmsAvgFreqMaxStr
            DisplayString,
        acpmsAvgFreqAvgStr
            DisplayString,
        acpmsAvgFreqInEventState
            DisplayString,
        acpmsTRPValueStr
            DisplayString,
        acpmsTRPMinStr
            DisplayString,
        acpmsTRPMaxStr
            DisplayString,
        acpmsTRPAvgStr
            DisplayString,
        acpmsTRPInEventState
            DisplayString,
        acpmsRPPhaseAValueStr
            DisplayString,
        acpmsRPPhaseBValueStr
            DisplayString,
        acpmsRPPhaseCValueStr
            DisplayString,
        acpmsCombined
            DisplayString,
        acpmsTPFValueStr
            DisplayString,
        acpmsTPFMinStr
            DisplayString,
        acpmsTPFMaxStr
            DisplayString,
        acpmsTPFAvgStr
            DisplayString,
        acpmsTPFInEventState
            DisplayString,
        acpmsPFPhaseAValueStr
            DisplayString,
        acpmsPFPhaseBValueStr
            DisplayString,
        acpmsPFPhaseCValueStr
            DisplayString,
        acpmsTRcPValueStr
            DisplayString,
        acpmsTRcPMinStr
            DisplayString,
        acpmsTRcPMaxStr
            DisplayString,
        acpmsTRcPAvgStr
            DisplayString,
        acpmsRcPPhaseAValueStr
            DisplayString,
        acpmsRcPPhaseBValueStr
            DisplayString,
        acpmsRcPPhaseCValueStr
            DisplayString,
        acpmsTAPValueStr
            DisplayString,
        acpmsTAPMinStr
            DisplayString,
        acpmsTAPMaxStr
            DisplayString,
        acpmsTAPAvgStr
            DisplayString,
        acpmsAPPhaseAValueStr
            DisplayString,
        acpmsAPPhaseBValueStr
            DisplayString,
        acpmsAPPhaseCValueStr
            DisplayString,
        acpmsTotalEnergyWh
            Integer32,
        acpmsTotalEnergyVAR
            Integer32,
        acpmsTotalEnergyVA
            Integer32
}

FuelSensorConfigGeneral ::=
    SEQUENCE {
        fsGenIndex
            Integer32,
        fsGenName
            DisplayString,
        fsGenSensorType
            DisplayString,
        fsGenDistanceUnit
            DisplayString,
        fsGenRawValueTop
            DisplayString,
        fsGenTopOffset
            DisplayString,
        fsGenRawValueBottom
            DisplayString,
        fsGenBottomOffset
            DisplayString,
        fsGenInputES
            Integer32,
        fsGenInputPoint
            Integer32,
        fsGenFilterAveraging
            Integer32,
        fsGenSysrepEnable
            DisplayString,
        fsGenSysrepThreshold
            DisplayString,
        fsGenSysrepLimit
            Integer32,
        fsGenSysrepPackage
            Integer32,
        fsGenSysrepType
            DisplayString,
        fsGenEnable
            DisplayString
}

FuelSensorConfigTank ::=
    SEQUENCE {
        fsTankIndex
            Integer32,
        fsTankHeight
            DisplayString,
        fsTankDimA
            DisplayString,
        fsTankDimB
            DisplayString,
        fsTankVolume
            DisplayString,
        fsTankVolumeUnit
            DisplayString,
        fsTankShape
            DisplayString
}

FuelSensorConfigCustomTankStrapping ::=
    SEQUENCE {
        fsCustomTankIndexFS
            Integer32,
        fsCustomTankIndexDatum
            Integer32,
        fsCustomTankHeight
            DisplayString,
        fsCustomTankVolume
            DisplayString
}

FuelSensorConfigVolume ::=
    SEQUENCE {
        fsVolumeIndex
            Integer32,
        fsVolumeEnable
            DisplayString,
        fsVolumeDeadband
            DisplayString,
        fsVolumeVHighValue
            DisplayString,
        fsVolumeVHighActions
            DisplayString,
        fsVolumeVHighTrapNum
            Integer32,
        fsVolumeVHighClass
            DisplayString,
        fsVolumeHighValue
            DisplayString,
        fsVolumeHighActions
            DisplayString,
        fsVolumeHighTrapNum
            Integer32,
        fsVolumeHighClass
            DisplayString,
        fsVolumeNormalActions
            DisplayString,
        fsVolumeNormalTrapNum
            Integer32,
        fsVolumeNormalClass
            DisplayString,
        fsVolumeLowValue
            DisplayString,
        fsVolumeLowActions
            DisplayString,
        fsVolumeLowTrapNum
            Integer32,
        fsVolumeLowClass
            DisplayString,
        fsVolumeVLowValue
            DisplayString,
        fsVolumeVLowActions
            DisplayString,
        fsVolumeVLowTrapNum
            Integer32,
        fsVolumeVLowClass
            DisplayString
}

FuelSensorConfigDisconnect ::=
    SEQUENCE {
        fsDiscIndex
            Integer32,
        fsDiscEnable
            DisplayString,
        fsDiscHighValue
            DisplayString,
        fsDiscLowValue
            DisplayString,
        fsDiscActions
            DisplayString,
        fsDiscTrapNum
            Integer32,
        fsDiscClass
            DisplayString,
        fsDiscNormalActions
            DisplayString,
        fsDiscNormalTrapNum
            Integer32,
        fsDiscNormalClass
            DisplayString
}

ACPMConfigGeneral ::=
    SEQUENCE {
        acpmGenIndex
            Integer32,
        acpmGenDevice
            DisplayString,
        acpmGenName
            DisplayString,
        acpmGenAddress
            Integer32,
        acpmGenPtRatio
            Integer32,
        acpmGenCtRatio
            Integer32,
        acpmGenPowerType
            DisplayString,
        acpmGenSysrepPackage
            Integer32,
        acpmGenSysrepType
            DisplayString,
        acpmGenEnable
            DisplayString
}

ACPMConfigAvgVoltage ::=
    SEQUENCE {
        acpmAvgVoltageIndex
            Integer32,
        acpmAvgVoltageEnable
            DisplayString,
        acpmAvgVoltageDeadband
            DisplayString,
        acpmAvgVoltageVHighValue
            DisplayString,
        acpmAvgVoltageVHighActions
            DisplayString,
        acpmAvgVoltageVHighTrapNum
            Integer32,
        acpmAvgVoltageVHighClass
            DisplayString,
        acpmAvgVoltageHighValue
            DisplayString,
        acpmAvgVoltageHighActions
            DisplayString,
        acpmAvgVoltageHighTrapNum
            Integer32,
        acpmAvgVoltageHighClass
            DisplayString,
        acpmAvgVoltageNormalActions
            DisplayString,
        acpmAvgVoltageNormalTrapNum
            Integer32,
        acpmAvgVoltageNormalClass
            DisplayString,
        acpmAvgVoltageLowValue
            DisplayString,
        acpmAvgVoltageLowActions
            DisplayString,
        acpmAvgVoltageLowTrapNum
            Integer32,
        acpmAvgVoltageLowClass
            DisplayString,
        acpmAvgVoltageVLowValue
            DisplayString,
        acpmAvgVoltageVLowActions
            DisplayString,
        acpmAvgVoltageVLowTrapNum
            Integer32,
        acpmAvgVoltageVLowClass
            DisplayString,
        acpmAvgVoltageSysrepEnable
            DisplayString,
        acpmAvgVoltageSysrepThreshold
            DisplayString,
        acpmAvgVoltageSysrepLimit
            Integer32
}

ACPMConfigAvgCurrent ::=
    SEQUENCE {
        acpmAvgCurrentIndex
            Integer32,
        acpmAvgCurrentEnable
            DisplayString,
        acpmAvgCurrentDeadband
            DisplayString,
        acpmAvgCurrentVHighValue
            DisplayString,
        acpmAvgCurrentVHighActions
            DisplayString,
        acpmAvgCurrentVHighTrapNum
            Integer32,
        acpmAvgCurrentVHighClass
            DisplayString,
        acpmAvgCurrentHighValue
            DisplayString,
        acpmAvgCurrentHighActions
            DisplayString,
        acpmAvgCurrentHighTrapNum
            Integer32,
        acpmAvgCurrentHighClass
            DisplayString,
        acpmAvgCurrentNormalActions
            DisplayString,
        acpmAvgCurrentNormalTrapNum
            Integer32,
        acpmAvgCurrentNormalClass
            DisplayString,
        acpmAvgCurrentLowValue
            DisplayString,
        acpmAvgCurrentLowActions
            DisplayString,
        acpmAvgCurrentLowTrapNum
            Integer32,
        acpmAvgCurrentLowClass
            DisplayString,
        acpmAvgCurrentVLowValue
            DisplayString,
        acpmAvgCurrentVLowActions
            DisplayString,
        acpmAvgCurrentVLowTrapNum
            Integer32,
        acpmAvgCurrentVLowClass
            DisplayString,
        acpmAvgCurrentSysrepEnable
            DisplayString,
        acpmAvgCurrentSysrepThreshold
            DisplayString,
        acpmAvgCurrentSysrepLimit
            Integer32
}

ACPMConfigFreq ::=
    SEQUENCE {
        acpmFreqIndex
            Integer32,
        acpmFreqEnable
            DisplayString,
        acpmFreqDeadband
            DisplayString,
        acpmFreqVHighValue
            DisplayString,
        acpmFreqVHighActions
            DisplayString,
        acpmFreqVHighTrapNum
            Integer32,
        acpmFreqVHighClass
            DisplayString,
        acpmFreqHighValue
            DisplayString,
        acpmFreqHighActions
            DisplayString,
        acpmFreqHighTrapNum
            Integer32,
        acpmFreqHighClass
            DisplayString,
        acpmFreqNormalActions
            DisplayString,
        acpmFreqNormalTrapNum
            Integer32,
        acpmFreqNormalClass
            DisplayString,
        acpmFreqLowValue
            DisplayString,
        acpmFreqLowActions
            DisplayString,
        acpmFreqLowTrapNum
            Integer32,
        acpmFreqLowClass
            DisplayString,
        acpmFreqVLowValue
            DisplayString,
        acpmFreqVLowActions
            DisplayString,
        acpmFreqVLowTrapNum
            Integer32,
        acpmFreqVLowClass
            DisplayString,
        acpmFreqSysrepEnable
            DisplayString,
        acpmFreqSysrepThreshold
            DisplayString,
        acpmFreqSysrepLimit
            Integer32
}

ACPMConfigTRP ::=
    SEQUENCE {
        acpmTRPIndex
            Integer32,
        acpmTRPEnable
            DisplayString,
        acpmTRPDeadband
            DisplayString,
        acpmTRPVHighValue
            DisplayString,
        acpmTRPVHighActions
            DisplayString,
        acpmTRPVHighTrapNum
            Integer32,
        acpmTRPVHighClass
            DisplayString,
        acpmTRPHighValue
            DisplayString,
        acpmTRPHighActions
            DisplayString,
        acpmTRPHighTrapNum
            Integer32,
        acpmTRPHighClass
            DisplayString,
        acpmTRPNormalActions
            DisplayString,
        acpmTRPNormalTrapNum
            Integer32,
        acpmTRPNormalClass
            DisplayString,
        acpmTRPLowValue
            DisplayString,
        acpmTRPLowActions
            DisplayString,
        acpmTRPLowTrapNum
            Integer32,
        acpmTRPLowClass
            DisplayString,
        acpmTRPVLowValue
            DisplayString,
        acpmTRPVLowActions
            DisplayString,
        acpmTRPVLowTrapNum
            Integer32,
        acpmTRPVLowClass
            DisplayString,
        acpmTRPSysrepEnable
            DisplayString,
        acpmTRPSysrepThreshold
            DisplayString,
        acpmTRPSysrepLimit
            Integer32
}

ACPMConfigDisconnect ::=
    SEQUENCE {
        acpmDisconnectIndex
            Integer32,
        acpmDisconnectEnable
            DisplayString,
        acpmDisconnectActions
            DisplayString,
        acpmDisconnectTrapNum
            Integer32,
        acpmDisconnectClass
            DisplayString,
        acpmDisconnectNormalActions
            DisplayString,
        acpmDisconnectNormalTrapNum
            Integer32,
        acpmDisconnectNormalClass
            DisplayString
}

ACPMConfigTotalPowerFactor ::=
    SEQUENCE {
        acpmTPFIndex
            Integer32,
        acpmTPFEnable
            DisplayString,
        acpmTPFDeadband
            DisplayString,
        acpmTPFNormalActions
            DisplayString,
        acpmTPFNormalTrapNum
            Integer32,
        acpmTPFNormalClass
            DisplayString,
        acpmTPFLowValue
            DisplayString,
        acpmTPFLowActions
            DisplayString,
        acpmTPFLowTrapNum
            Integer32,
        acpmTPFLowClass
            DisplayString,
        acpmTPFVLowValue
            DisplayString,
        acpmTPFVLowActions
            DisplayString,
        acpmTPFVLowTrapNum
            Integer32,
        acpmTPFVLowClass
            DisplayString,
        acpmTPFSysrepEnable
            DisplayString,
        acpmTPFSysrepThreshold
            DisplayString,
        acpmTPFSysrepLimit
            Integer32
}


--***************************************************************************************
--TRAP DEFINITIONS
--***************************************************************************************

s571StockContactClosureTrap NOTIFICATION-TYPE
    OBJECTS { siteName, stockTrapString, trapTypeString }
    STATUS current
    DESCRIPTION
        "A stock contact closure trap is issued when a contact closure
        event happens."
    ::= { s571 110 }

s571StockTempTrap NOTIFICATION-TYPE
    OBJECTS { siteName, stockTrapString, trapTypeString }
    STATUS current
    DESCRIPTION
        "A stock temperature trap is issued when a temperature event
        happens."
    ::= { s571 120 }

s571StockHumidityTrap NOTIFICATION-TYPE
    OBJECTS { siteName, stockTrapString, trapTypeString }
    STATUS current
    DESCRIPTION
        "A stock humidity trap is issued when a humidity event
        happens."
    ::= { s571 130 }

s571StockAnalogTrap NOTIFICATION-TYPE
    OBJECTS { siteName, stockTrapString, trapTypeString }
    STATUS current
    DESCRIPTION
        "A stock analog trap is issued when an analog sensor event
        happens."
    ::= { s571 140 }

s571StockOutputTrap NOTIFICATION-TYPE
    OBJECTS { siteName, stockTrapString, trapTypeString }
    STATUS current
    DESCRIPTION
        "A stock output trap is issued when an output event
        happens.  That is, depending on the configuration,
        when an output changes state for any reason, this
        trap will be sent."
    ::= { s571 150 }

s571StockPDCurrentTrap NOTIFICATION-TYPE
    OBJECTS { siteName, stockTrapString, trapTypeString }
    STATUS current
    DESCRIPTION
        "A stock analog trap is issued when a power distribution
        current event happens."
    ::= { s571 180 }

s571StockPDVoltageTrap NOTIFICATION-TYPE
    OBJECTS { siteName, stockTrapString, trapTypeString }
    STATUS current
    DESCRIPTION
        "A stock analog trap is issued when a power distribution
        voltage event happens."
    ::= { s571 190 }

s571StockPDFuseTrap NOTIFICATION-TYPE
    OBJECTS { siteName, stockTrapString, trapTypeString }
    STATUS current
    DESCRIPTION
        "A stock analog trap is issued when a power distribution
        fuse event happens."
    ::= { s571 210 }

s571StockDataAlarmTrap NOTIFICATION-TYPE
    OBJECTS { siteName, stockTrapString, trapTypeString }
    STATUS current
    DESCRIPTION
        "The stock data alarm trap is issued when a
        data alarm happens."
    ::= { s571 503 }

s571StockNoDataAlarmTrap NOTIFICATION-TYPE
    OBJECTS { siteName, stockTrapString, trapTypeString }
    STATUS current
    DESCRIPTION
        "The stock no-data alarm trap is issued when
        the unit has received no data for a configured
        interval within a configured schedule."
    ::= { s571 505 }

s571StockSchedTrap NOTIFICATION-TYPE
    OBJECTS { siteName, stockTrapString, trapTypeString }
    STATUS current
    DESCRIPTION
        "The stock scheduled alarm trap is issued
        when the current time reaches the scheduled
        alarm time."
    ::= { s571 506 }

s571StockImmediateTrap NOTIFICATION-TYPE
    OBJECTS { siteName, stockTrapString, trapTypeString }
    STATUS current
    DESCRIPTION
        "The stock immediate alarm trap is issued
        when the user enters the DOTRAP command."
    ::= { s571 507 }

s571StockCTSTrap  NOTIFICATION-TYPE
    OBJECTS { siteName, stockTrapString, trapTypeString }
    STATUS current
    DESCRIPTION
        "A stock CTS trap is issued when an RS-232 CTS event
        happens."
    ::= { s571 510 }

s571CPEDownTrap  NOTIFICATION-TYPE
    OBJECTS { siteName, stockTrapString, trapTypeString }
    STATUS current
    DESCRIPTION
        "A stock CPE Down trap is issued when a CPE Down event
        happens."
    ::= { s571 511 }

s571FuelSensorDisconnectTrap  NOTIFICATION-TYPE
    OBJECTS { siteName, stockTrapString, trapTypeString }
    STATUS current
    DESCRIPTION
        "A stock Fuel Sensor Disconnect trap is issued when a Fuel
        Sensor Disconnect or Connect (Return to Normal) event happens."
    ::= { s571 515 }

s571FuelSensorVolumeTrap  NOTIFICATION-TYPE
    OBJECTS { siteName, stockTrapString, trapTypeString }
    STATUS current
    DESCRIPTION
        "A stock Fuel Sensor Volume trap is issued when a Fuel
        Sensor Volume event happens"
    ::= { s571 519 }

s571ACPowerMonitorAvgVoltageTrap  NOTIFICATION-TYPE
    OBJECTS { siteName, stockTrapString, trapTypeString }
    STATUS current
    DESCRIPTION
        "A stock AC power monitor average voltage trap is issued when an
        AC power monitor average voltage event happens."
    ::= { s571 520 }

s571ACPowerMonitorAvgCurrentTrap  NOTIFICATION-TYPE
    OBJECTS { siteName, stockTrapString, trapTypeString }
    STATUS current
    DESCRIPTION
        "A stock AC power monitor average current trap is issued when an
        AC power monitor average current event happens."
    ::= { s571 521 }

s571ACPowerMonitorFrequencyTrap  NOTIFICATION-TYPE
    OBJECTS { siteName, stockTrapString, trapTypeString }
    STATUS current
    DESCRIPTION
        "A stock AC power monitor frequency trap is issued when an
        AC power monitor frequency event happens."
    ::= { s571 522 }

s571ACPowerMonitorTRPTrap  NOTIFICATION-TYPE
    OBJECTS { siteName, stockTrapString, trapTypeString }
    STATUS current
    DESCRIPTION
        "A stock AC power monitor TRP (total real power) trap is issued
        when an AC power monitor TRP event happens."
    ::= { s571 523 }

s571ACPowerMonitorDisconnectTrap  NOTIFICATION-TYPE
    OBJECTS { siteName, stockTrapString, trapTypeString }
    STATUS current
    DESCRIPTION
        "A stock AC power monitor disconnect trap is issued
        when an AC power monitor disconnect event happens."
    ::= { s571 524 }

s571StockLoadSheddingTrap  NOTIFICATION-TYPE
    OBJECTS { siteName, stockTrapString, trapTypeString }
    STATUS current
    DESCRIPTION
        "A stock Load Shedding trap is issued when a Load Shedding event
        happens."
    ::= { s571 525 }

s571StockScriptTrap  NOTIFICATION-TYPE
    OBJECTS { siteName, stockTrapString, trapTypeString }
    STATUS current
    DESCRIPTION
        "A stock script trap is issued when a script triggers
        an event via a_lib.PostEvent() called with no trap
        number (or this trap number) specified."
    ::= { s571 526 }

s571FuelSensorVolumeSuddenChangeTrap  NOTIFICATION-TYPE
    OBJECTS { siteName, stockTrapString, trapTypeString }
    STATUS current
    DESCRIPTION
        "A stock Fuel Sensor Volume Sudden Change trap is issued
        when a Fuel Sensor Volume Sudden Change event happens"
    ::= { s571 527 }

s571FuelSensorVolumeSlowChangeTrap  NOTIFICATION-TYPE
    OBJECTS { siteName, stockTrapString, trapTypeString }
    STATUS current
    DESCRIPTION
        "A stock Fuel Sensor Volume Slow Change trap is issued
        when a Fuel Sensor Volume Slow Change event happens"
    ::= { s571 528 }

s571ACTotalPowerFactorTrap  NOTIFICATION-TYPE
    OBJECTS { siteName, stockTrapString, trapTypeString }
    STATUS current
    DESCRIPTION
        "A stock AC power monitor total power factor trap is issued
        when an AC power monitor total power factor event happens."
    ::= { s571 540 }

s571ResetTrap  NOTIFICATION-TYPE
    OBJECTS { siteName, stockTrapString, trapTypeString }
    STATUS current
    DESCRIPTION
        "A stock reset trap is issued when a reset event happens."
    ::= { s571 543 }

s571UserTrap1000 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1000."
    ::= { s571 1000 }

s571UserTrap1001 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1001."
    ::= { s571 1001 }

s571UserTrap1002 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1002."
    ::= { s571 1002 }

s571UserTrap1003 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1003."
    ::= { s571 1003 }

s571UserTrap1004 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1004."
    ::= { s571 1004 }

s571UserTrap1005 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1005."
    ::= { s571 1005 }

s571UserTrap1006 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1006."
    ::= { s571 1006 }

s571UserTrap1007 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1007."
    ::= { s571 1007 }

s571UserTrap1008 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1008."
    ::= { s571 1008 }

s571UserTrap1009 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1009."
    ::= { s571 1009 }

s571UserTrap1010 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1010."
    ::= { s571 1010 }

s571UserTrap1011 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1011."
    ::= { s571 1011 }

s571UserTrap1012 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1012."
    ::= { s571 1012 }

s571UserTrap1013 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1013."
    ::= { s571 1013 }

s571UserTrap1014 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1014."
    ::= { s571 1014 }

s571UserTrap1015 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1015."
    ::= { s571 1015 }

s571UserTrap1016 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1016."
    ::= { s571 1016 }

s571UserTrap1017 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1017."
    ::= { s571 1017 }

s571UserTrap1018 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1018."
    ::= { s571 1018 }

s571UserTrap1019 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1019."
    ::= { s571 1019 }

s571UserTrap1020 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1020."
    ::= { s571 1020 }

s571UserTrap1021 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1021."
    ::= { s571 1021 }

s571UserTrap1022 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1022."
    ::= { s571 1022 }

s571UserTrap1023 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1023."
    ::= { s571 1023 }

s571UserTrap1024 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1024."
    ::= { s571 1024 }

s571UserTrap1025 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1025."
    ::= { s571 1025 }

s571UserTrap1026 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1026."
    ::= { s571 1026 }

s571UserTrap1027 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1027."
    ::= { s571 1027 }

s571UserTrap1028 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1028."
    ::= { s571 1028 }

s571UserTrap1029 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1029."
    ::= { s571 1029 }

s571UserTrap1030 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1030."
    ::= { s571 1030 }

s571UserTrap1031 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1031."
    ::= { s571 1031 }

s571UserTrap1032 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1032."
    ::= { s571 1032 }

s571UserTrap1033 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1033."
    ::= { s571 1033 }

s571UserTrap1034 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1034."
    ::= { s571 1034 }

s571UserTrap1035 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1035."
    ::= { s571 1035 }

s571UserTrap1036 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1036."
    ::= { s571 1036 }

s571UserTrap1037 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1037."
    ::= { s571 1037 }

s571UserTrap1038 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1038."
    ::= { s571 1038 }

s571UserTrap1039 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1039."
    ::= { s571 1039 }

s571UserTrap1040 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1040."
    ::= { s571 1040 }

s571UserTrap1041 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1041."
    ::= { s571 1041 }

s571UserTrap1042 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1042."
    ::= { s571 1042 }

s571UserTrap1043 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1043."
    ::= { s571 1043 }

s571UserTrap1044 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1044."
    ::= { s571 1044 }

s571UserTrap1045 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1045."
    ::= { s571 1045 }

s571UserTrap1046 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1046."
    ::= { s571 1046 }

s571UserTrap1047 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1047."
    ::= { s571 1047 }

s571UserTrap1048 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1048."
    ::= { s571 1048 }

s571UserTrap1049 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1049."
    ::= { s571 1049 }

s571UserTrap1050 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1050."
    ::= { s571 1050 }

s571UserTrap1051 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1051."
    ::= { s571 1051 }

s571UserTrap1052 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1052."
    ::= { s571 1052 }

s571UserTrap1053 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1053."
    ::= { s571 1053 }

s571UserTrap1054 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1054."
    ::= { s571 1054 }

s571UserTrap1055 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1055."
    ::= { s571 1055 }

s571UserTrap1056 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1056."
    ::= { s571 1056 }

s571UserTrap1057 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1057."
    ::= { s571 1057 }

s571UserTrap1058 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1058."
    ::= { s571 1058 }

s571UserTrap1059 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1059."
    ::= { s571 1059 }

s571UserTrap1060 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1060."
    ::= { s571 1060 }

s571UserTrap1061 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1061."
    ::= { s571 1061 }

s571UserTrap1062 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1062."
    ::= { s571 1062 }

s571UserTrap1063 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1063."
    ::= { s571 1063 }

s571UserTrap1064 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1064."
    ::= { s571 1064 }

s571UserTrap1065 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1065."
    ::= { s571 1065 }

s571UserTrap1066 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1066."
    ::= { s571 1066 }

s571UserTrap1067 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1067."
    ::= { s571 1067 }

s571UserTrap1068 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1068."
    ::= { s571 1068 }

s571UserTrap1069 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1069."
    ::= { s571 1069 }

s571UserTrap1070 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1070."
    ::= { s571 1070 }

s571UserTrap1071 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1071."
    ::= { s571 1071 }

s571UserTrap1072 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1072."
    ::= { s571 1072 }

s571UserTrap1073 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1073."
    ::= { s571 1073 }

s571UserTrap1074 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1074."
    ::= { s571 1074 }

s571UserTrap1075 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1075."
    ::= { s571 1075 }

s571UserTrap1076 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1076."
    ::= { s571 1076 }

s571UserTrap1077 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1077."
    ::= { s571 1077 }

s571UserTrap1078 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1078."
    ::= { s571 1078 }

s571UserTrap1079 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1079."
    ::= { s571 1079 }

s571UserTrap1080 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1080."
    ::= { s571 1080 }

s571UserTrap1081 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1081."
    ::= { s571 1081 }

s571UserTrap1082 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1082."
    ::= { s571 1082 }

s571UserTrap1083 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1083."
    ::= { s571 1083 }

s571UserTrap1084 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1084."
    ::= { s571 1084 }

s571UserTrap1085 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1085."
    ::= { s571 1085 }

s571UserTrap1086 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1086."
    ::= { s571 1086 }

s571UserTrap1087 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1087."
    ::= { s571 1087 }

s571UserTrap1088 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1088."
    ::= { s571 1088 }

s571UserTrap1089 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1089."
    ::= { s571 1089 }

s571UserTrap1090 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1090."
    ::= { s571 1090 }

s571UserTrap1091 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1091."
    ::= { s571 1091 }

s571UserTrap1092 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1092."
    ::= { s571 1092 }

s571UserTrap1093 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1093."
    ::= { s571 1093 }

s571UserTrap1094 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1094."
    ::= { s571 1094 }

s571UserTrap1095 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1095."
    ::= { s571 1095 }

s571UserTrap1096 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1096."
    ::= { s571 1096 }

s571UserTrap1097 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1097."
    ::= { s571 1097 }

s571UserTrap1098 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1098."
    ::= { s571 1098 }

s571UserTrap1099 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1099."
    ::= { s571 1099 }

s571UserTrap1100 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1100."
    ::= { s571 1100 }

s571UserTrap1101 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1101."
    ::= { s571 1101 }

s571UserTrap1102 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1102."
    ::= { s571 1102 }

s571UserTrap1103 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1103."
    ::= { s571 1103 }

s571UserTrap1104 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1104."
    ::= { s571 1104 }

s571UserTrap1105 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1105."
    ::= { s571 1105 }

s571UserTrap1106 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1106."
    ::= { s571 1106 }

s571UserTrap1107 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1107."
    ::= { s571 1107 }

s571UserTrap1108 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1108."
    ::= { s571 1108 }

s571UserTrap1109 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1109."
    ::= { s571 1109 }

s571UserTrap1110 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1110."
    ::= { s571 1110 }

s571UserTrap1111 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1111."
    ::= { s571 1111 }

s571UserTrap1112 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1112."
    ::= { s571 1112 }

s571UserTrap1113 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1113."
    ::= { s571 1113 }

s571UserTrap1114 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1114."
    ::= { s571 1114 }

s571UserTrap1115 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1115."
    ::= { s571 1115 }

s571UserTrap1116 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1116."
    ::= { s571 1116 }

s571UserTrap1117 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1117."
    ::= { s571 1117 }

s571UserTrap1118 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1118."
    ::= { s571 1118 }

s571UserTrap1119 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1119."
    ::= { s571 1119 }

s571UserTrap1120 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1120."
    ::= { s571 1120 }

s571UserTrap1121 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1121."
    ::= { s571 1121 }

s571UserTrap1122 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1122."
    ::= { s571 1122 }

s571UserTrap1123 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1123."
    ::= { s571 1123 }

s571UserTrap1124 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1124."
    ::= { s571 1124 }

s571UserTrap1125 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1125."
    ::= { s571 1125 }

s571UserTrap1126 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1126."
    ::= { s571 1126 }

s571UserTrap1127 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1127."
    ::= { s571 1127 }

s571UserTrap1128 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1128."
    ::= { s571 1128 }

s571UserTrap1129 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1129."
    ::= { s571 1129 }

s571UserTrap1130 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1130."
    ::= { s571 1130 }

s571UserTrap1131 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1131."
    ::= { s571 1131 }

s571UserTrap1132 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1132."
    ::= { s571 1132 }

s571UserTrap1133 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1133."
    ::= { s571 1133 }

s571UserTrap1134 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1134."
    ::= { s571 1134 }

s571UserTrap1135 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1135."
    ::= { s571 1135 }

s571UserTrap1136 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1136."
    ::= { s571 1136 }

s571UserTrap1137 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1137."
    ::= { s571 1137 }

s571UserTrap1138 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1138."
    ::= { s571 1138 }

s571UserTrap1139 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1139."
    ::= { s571 1139 }

s571UserTrap1140 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1140."
    ::= { s571 1140 }

s571UserTrap1141 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1141."
    ::= { s571 1141 }

s571UserTrap1142 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1142."
    ::= { s571 1142 }

s571UserTrap1143 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1143."
    ::= { s571 1143 }

s571UserTrap1144 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1144."
    ::= { s571 1144 }

s571UserTrap1145 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1145."
    ::= { s571 1145 }

s571UserTrap1146 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1146."
    ::= { s571 1146 }

s571UserTrap1147 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1147."
    ::= { s571 1147 }

s571UserTrap1148 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1148."
    ::= { s571 1148 }

s571UserTrap1149 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1149."
    ::= { s571 1149 }

s571UserTrap1150 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1150."
    ::= { s571 1150 }

s571UserTrap1151 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1151."
    ::= { s571 1151 }

s571UserTrap1152 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1152."
    ::= { s571 1152 }

s571UserTrap1153 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1153."
    ::= { s571 1153 }

s571UserTrap1154 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1154."
    ::= { s571 1154 }

s571UserTrap1155 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1155."
    ::= { s571 1155 }

s571UserTrap1156 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1156."
    ::= { s571 1156 }

s571UserTrap1157 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1157."
    ::= { s571 1157 }

s571UserTrap1158 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1158."
    ::= { s571 1158 }

s571UserTrap1159 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1159."
    ::= { s571 1159 }

s571UserTrap1160 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1160."
    ::= { s571 1160 }

s571UserTrap1161 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1161."
    ::= { s571 1161 }

s571UserTrap1162 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1162."
    ::= { s571 1162 }

s571UserTrap1163 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1163."
    ::= { s571 1163 }

s571UserTrap1164 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1164."
    ::= { s571 1164 }

s571UserTrap1165 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1165."
    ::= { s571 1165 }

s571UserTrap1166 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1166."
    ::= { s571 1166 }

s571UserTrap1167 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1167."
    ::= { s571 1167 }

s571UserTrap1168 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1168."
    ::= { s571 1168 }

s571UserTrap1169 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1169."
    ::= { s571 1169 }

s571UserTrap1170 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1170."
    ::= { s571 1170 }

s571UserTrap1171 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1171."
    ::= { s571 1171 }

s571UserTrap1172 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1172."
    ::= { s571 1172 }

s571UserTrap1173 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1173."
    ::= { s571 1173 }

s571UserTrap1174 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1174."
    ::= { s571 1174 }

s571UserTrap1175 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1175."
    ::= { s571 1175 }

s571UserTrap1176 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1176."
    ::= { s571 1176 }

s571UserTrap1177 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1177."
    ::= { s571 1177 }

s571UserTrap1178 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1178."
    ::= { s571 1178 }

s571UserTrap1179 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1179."
    ::= { s571 1179 }

s571UserTrap1180 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1180."
    ::= { s571 1180 }

s571UserTrap1181 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1181."
    ::= { s571 1181 }

s571UserTrap1182 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1182."
    ::= { s571 1182 }

s571UserTrap1183 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1183."
    ::= { s571 1183 }

s571UserTrap1184 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1184."
    ::= { s571 1184 }

s571UserTrap1185 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1185."
    ::= { s571 1185 }

s571UserTrap1186 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1186."
    ::= { s571 1186 }

s571UserTrap1187 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1187."
    ::= { s571 1187 }

s571UserTrap1188 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1188."
    ::= { s571 1188 }

s571UserTrap1189 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1189."
    ::= { s571 1189 }

s571UserTrap1190 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1190."
    ::= { s571 1190 }

s571UserTrap1191 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1191."
    ::= { s571 1191 }

s571UserTrap1192 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1192."
    ::= { s571 1192 }

s571UserTrap1193 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1193."
    ::= { s571 1193 }

s571UserTrap1194 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1194."
    ::= { s571 1194 }

s571UserTrap1195 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1195."
    ::= { s571 1195 }

s571UserTrap1196 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1196."
    ::= { s571 1196 }

s571UserTrap1197 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1197."
    ::= { s571 1197 }

s571UserTrap1198 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1198."
    ::= { s571 1198 }

s571UserTrap1199 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1199."
    ::= { s571 1199 }

END
