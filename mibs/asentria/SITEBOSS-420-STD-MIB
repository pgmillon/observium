-- SiteBoss 420 MIB

-- v 1.07 06/13/13

-- Copyright (c) 2012 by Asentria Corporation.  All rights reserved.


SITEBOSS-420-STD-MIB DEFINITIONS ::= BEGIN

IMPORTS
 DisplayString
    FROM SNMPv2-TC
 IpAddress, TimeTicks, Integer32,
 MODULE-IDENTITY, NOTIFICATION-TYPE, OBJECT-TYPE
    FROM SNMPv2-SMI
 asentria
    FROM ASENTRIA-ROOT-MIB;

--***************************************************************************************
--MODULE IDENTITY
--***************************************************************************************

  s420 MODULE-IDENTITY
    LAST-UPDATED "201306130107Z"
    ORGANIZATION "Asentria Corporation"
    CONTACT-INFO
     "Phone:  206-344-8800
      Fax:    206-344-2116
      Email:  support@asentria.com"
    DESCRIPTION
      "MIB module for managing Asentria SiteBoss 420"

    REVISION      "201306130107Z"
    DESCRIPTION
      "-v1.07
       -Added missing esPointConfigAITable branch (UTSK-7)."

    REVISION      "201203010105Z"
    DESCRIPTION
      "-v1.05
       -Fixed MIB validation and notification definition errors"

    REVISION      "201203010104Z"
    DESCRIPTION
      "-v1.04
       -Fixed issue with actionEmailIndex"

    REVISION      "200903080900Z"
    DESCRIPTION
      "-v1.03

       -Branched new MIB off of SiteBoss 570 MIB
       -Edited to go with what is actually on the 420
       -fixed reference in traps
       -added thisTrapText for traps"

    ::= { asentria 42 }
    --1.3.6.1.4.1.3052.42


--***************************************************************************************
--MIB View
--***************************************************************************************

--  status                               .1
--    eventSensorStatus                  .1.1
--      esPointTable                     .1.1.1
--        esPointEntry                   .1.1.1.1
--          esIndexES                    .1.1.1.1.1
--          esIndexPC                    .1.1.1.1.2
--          esIndexPoint                 .1.1.1.1.3
--          esPointName                  .1.1.1.1.4
--          esPointInEventState          .1.1.1.1.5
--          esPointValueInt              .1.1.1.1.6
--          esPointValueStr              .1.1.1.1.7

--  config                               .2
--    eventSensorBasics                  .2.1
--    eventSensorPointConfig             .2.2
--      esPointConfigTempTable           .2.2.1
--        esPointConfigTempEntry         .2.2.1.1
--          espcTempIndexES              .2.2.1.1.1
--          espcTempIndexPoint           .2.2.1.1.2
--          espcTempEnable               .2.2.1.1.3
--          espcTempName                 .2.2.1.1.4
--          espcTempScale                .2.2.1.1.5
--          espcTempDeadband             .2.2.1.1.6
--          espcTempVHighTemp            .2.2.1.1.7
--          espcTempVHighClass           .2.2.1.1.9
--          espcTempHighTemp             .2.2.1.1.10
--          espcTempHighClass            .2.2.1.1.13
--          espcTempNormalClass          .2.2.1.1.16
--          espcTempLowTemp              .2.2.1.1.17
--          espcTempLowClass             .2.2.1.1.20
--          espcTempVLowTemp             .2.2.1.1.21
--          espcTempVLowClass            .2.2.1.1.24
--          espcTempActions              .2.2.1.1.25
--      esPointConfigCCTable             .2.2.2
--        esPointConfigCCEntry           .2.2.2.1
--          espcCCIndexES                .2.2.2.1.1
--          espcCCIndexPoint             .2.2.2.1.2
--          espcCCEnable                 .2.2.2.1.3
--          espcCCName                   .2.2.2.1.4
--          espcCCEventState             .2.2.2.1.5
--          espcCCThreshold              .2.2.2.1.6
--          espcCCActions                .2.2.2.1.7
--          espcCCEventClass             .2.2.2.1.9
--          espcCCNormalClass            .2.2.2.1.12
--          espcCCAlarmAlias             .2.2.2.1.13
--          espcCCNormalAlias            .2.2.2.1.14
--      esPointConfigHumidTable          .2.2.3
--        esPointConfigHumidEntry        .2.2.3.1
--          espcHumidIndexES             .2.2.3.1.1
--          espcHumidIndexPoint          .2.2.3.1.2
--          espcHumidEnable              .2.2.3.1.3
--          espcHumidName                .2.2.3.1.4
--          espcHumidDeadband            .2.2.3.1.5
--          espcHumidVHighHumid          .2.2.3.1.6
--          espcHumidVHighClass          .2.2.3.1.8
--          espcHumidHighHumid           .2.2.3.1.9
--          espcHumidHighClass           .2.2.3.1.12
--          espcHumidLowHumid            .2.2.3.1.16
--          espcHumidLowClass            .2.2.3.1.19
--          espcHumidVLowHumid           .2.2.3.1.20
--          espcHumidVLowClass           .2.2.3.1.23
--          espcHumidActions             .2.2.3.1.24
--      esPointConfigAITable             .2.2.5
--        esPointConfigAIEntry           .2.2.5.1
--          espcAIIndexES                .2.2.5.1.1
--          espcAIIndexPoint             .2.2.5.1.2
--          espcAIEnable                 .2.2.5.1.3
--          espcAIName                   .2.2.5.1.4
--          espcAIDeadband               .2.2.5.1.5
--          espcAIVhighValue             .2.2.5.1.6
--          espcAIVhighClass             .2.2.5.1.8
--          espcAIHighValue              .2.2.5.1.9
--          espcAIHighClass              .2.2.5.1.12
--          espcAILowValue               .2.2.5.1.16
--          espcAILowClass               .2.2.5.1.19
--          espcAIVlowValue              .2.2.5.1.20
--          espcAIVlowClass              .2.2.5.1.23
--          espcAIActions                .2.2.5.1.24
--          espcAIConvUnitName           .2.2.5.1.25
--          espcAIConvLowValue           .2.2.5.1.26
--          espcAIConvLowUnit            .2.2.5.1.27
--          espcAIConvHighValue          .2.2.5.1.28
--          espcAIConvHighUnit           .2.2.5.1.29
--      esPointConfigRelayTable          .2.2.6
--        esPointConfigRelayEntry        .2.2.6.1
--          espcRelayIndexES             .2.2.6.1.1
--          espcRelayIndexPoint          .2.2.6.1.2
--          espcRelayEnable              .2.2.6.1.3
--          espcRelayName                .2.2.6.1.4
--    network                            .2.4
--        ethernet                       .2.4.1
--          ipAddress                    .2.4.1.1
--          subnetMask                   .2.4.1.2
--          router                       .2.4.1.3
--      snmp                             .2.4.8
--        snmpReadCommunity              .2.4.8.2
--        snmpWriteCommunity             .2.4.8.3
--        snmpTrapCommunity              .2.4.8.4
--        snmpTable                      .2.4.8.6
--          snmpEntry                    .2.4.8.6.1
--          snmpIndex                    .2.4.8.6.1.1
--          snmpAddress                  .2.4.8.6.1.2
--        snmpTestMail                   .2.4.8.7
--      email                            .2.4.17
--        emailServer                    .2.4.17.1
--        emailDomain                    .2.4.17.2
--        emailAuthEnable                .2.4.17.3
--        emailAuthUsername              .2.4.17.4
--        emailAuthPassword              .2.4.17.5
--        emailTable                     .2.4.17.6
--          emailEntry                   .2.4.17.6.1
--          emailIndex                   .2.4.17.6.1.1
--          emailAddress                 .2.4.17.6.1.2
--        emailTestMail                  .2.4.17.7
--    dateTime                           .2.8
--      date                             .2.8.1
--      time                             .2.8.2
--      autodst                          .2.8.3
--    action                             .2.14
--      actionSystemAlertAction          .2.14.1
--      actionPowerupAlertEnable         .2.14.2
--      actionRTNAlertsEnable            .2.14.3
--      actionAlarmRepeatFrequency       .2.14.4
--    sys                                .2.16
--      sysSerial                        .2.16.1
--      sysVersion                       .2.16.2
--      sysBuild                         .2.16.3
--      sysSitename                      .2.16.4
--      sysProduct                       .2.16.5
--      thisTrapText                     .2.16.6



--***************************************************************************************
--TOP-LEVEL OBJECT IDENTIFIERS
--***************************************************************************************

    notification OBJECT IDENTIFIER ::= { s420 0 }
    --1.3.6.1.4.1.3052.42.0

    status OBJECT IDENTIFIER ::= { s420 1 }
    --1.3.6.1.4.1.3052.42.1

        eventSensorStatus OBJECT IDENTIFIER ::= { status 1 }
        --1.3.6.1.4.1.3052.42.1.1

    config OBJECT IDENTIFIER ::= { s420 2 }
    --1.3.6.1.4.1.3052.42.2

        eventSensorPointConfig OBJECT IDENTIFIER ::= { config 2 }
        --1.3.6.1.4.1.3052.42.2.2

        network OBJECT IDENTIFIER ::= { config 4 }
        --1.3.6.1.4.1.3052.42.2.4

            ethernet OBJECT IDENTIFIER ::= { network 1 }
            --1.3.6.1.4.1.3052.42.2.4.1

            snmp OBJECT IDENTIFIER ::= { network 8 }
            --1.3.6.1.4.1.3052.42.2.4.8

            email OBJECT IDENTIFIER ::= { network 17 }
            --1.3.6.1.4.1.3052.42.2.4.17

        dateTime OBJECT IDENTIFIER ::= { config 8 }
        --1.3.6.1.4.1.3052.42.2.8

        action OBJECT IDENTIFIER ::= { config 14 }
        --1.3.6.1.4.1.3052.42.2.14

        sys OBJECT IDENTIFIER ::= { config 16 }
        --1.3.6.1.4.1.3052.42.2.16


--***************************************************************************************
--OBJECT DEFINITIONS
--***************************************************************************************

--***************************************************************************************
--EventSensor Status Section    1.1
--***************************************************************************************

esPointTable OBJECT-TYPE
    SYNTAX SEQUENCE OF ESPoint
    MAX-ACCESS not-accessible
    STATUS current
    DESCRIPTION
        "
        This table organizes 4 basic attributes of points.  A point
        is a particular sensor on an EventSensor (e.g., temperature,
        humidity, contact closure 2, relay 5, etc.).  The 4 point
        attributes are its name, whether it's in its event state,
        the point's value as a number and its value as a string.

        Points are referenced by a point index.  The point index
        is a string of 3 numbers separated by periods.
        It contains all the information necessary for getting a piece
        of data off an event sensor; namely, which EventSensor,
        point class, and which-sensor-of-that-class (a.k.a. point).
        "
    ::= { eventSensorStatus 1 }
    --1.3.6.1.4.1.3052.42.1.1.1

esPointEntry OBJECT-TYPE
    SYNTAX ESPoint
    MAX-ACCESS not-accessible
    STATUS current
    DESCRIPTION
        "Entry for EventSensor point table"
    INDEX { esIndexES, esIndexPC, esIndexPoint }
    ::= { esPointTable 1 }
    --1.3.6.1.4.1.3052.42.1.1.1.1

esIndexES OBJECT-TYPE
    SYNTAX Integer32 (1..200)
    MAX-ACCESS read-only
    STATUS current
    DESCRIPTION
        "The part of the point index that refers to an
        EventSensor.

        The point index is a string of 3 numbers separated
        by periods.  It contains all the information
        necessary for getting a piece of data off an event
        sensor; namely, which EventSensor, point class,
        and which-sensor-of-that-class (a.k.a. point).

        This object's allowable values are 1 through 16,
        and 200.  200 always refers to the EventSensor
        inside the unit.  1 through 16 refer to additional
        attached EventSensors.

        The number corresponding to an EventSensor is
        determined by the user at the initial configuration
        time.  If there is an internal sensor in the unit,
        it will always be the first item in the Sensor
        Events setup menu.

        For example, if a new EventSensor is configured as
        the 2nd entry AFTER the internal EventSensor (if
        one exists) in the Sensor Events Setup Menu, then
        that EventSensor will be known from then on as
        EventSensor 2.  All point indeces with esIndexES=2
        will now refer to that particular EventSensor.
        "
    ::= { esPointEntry 1 }
    --1.3.6.1.4.1.3052.42.1.1.1.1.1

esIndexPC OBJECT-TYPE
    SYNTAX Integer32 (1..6)
    MAX-ACCESS read-only
    STATUS current
    DESCRIPTION
        "The part of the point index that refers to point class.

        The point index is a string of 3 numbers separated by periods.
        It contains all the information necessary for getting a piece
        of data off an event sensor; namely, which EventSensor,
        point class, and which-sensor-of-that-class (a.k.a. point).

        The values for this object are:
        1=temperature sensor
        2=contact closure
        3=humidity sensor
        4=noise sensor
        5=analog input
        6=relay
        "
    ::= { esPointEntry 2 }
    --1.3.6.1.4.1.3052.42.1.1.1.1.2

esIndexPoint OBJECT-TYPE
    SYNTAX Integer32 (1..64)
    MAX-ACCESS read-only
    STATUS current
    DESCRIPTION
        "The part of the point index that delineates which
        sensor on the EventSensor.

        So this combined with esIndexPC (Point Class or type)
        and esIndexES (which EventSensor) uniquely defines each
        point (sensor or relay) attached to a unit.  For
        example, if esIndexES is 3, esIndexPC is 1 and
        esIndexPoint is 4 then this is the Fourth Temperature
        Sensor on EventSensor number 3."
    ::= { esPointEntry 3 }
    --1.3.6.1.4.1.3052.42.1.1.1.1.3

esPointName OBJECT-TYPE
    SYNTAX DisplayString
    MAX-ACCESS read-write
    STATUS current
    DESCRIPTION
        "The name of the point on an EventSensor. For example,
        'AC temp' (in the case of the temperature sensor on an
        EventSensor).

        There can be multiple points of the same point class on an
        EventSensor (e.g., 8 contact closures) and multiple sensor
        classes on an EventSensor (e.g., temperature, contact closure,
        humidity).

        If the point referenced by a given point index is solitary
        (e.g., temperature sensor, because there can be only one on
        an EventSensor), then this object reads as '<EventSensor
        name>'.  Setting this object for solitary point indices sets
        the EventSensor name only.

        On the other hand, if a given point is among other points of
        the same point class on an EventSensor, then this object reads
        as '<Sensor name>'.  Setting this object for these NON-
        solitary point indices sets the sensor name only - not the
        EventSensor name."
    ::= { esPointEntry 4 }
    --1.3.6.1.4.1.3052.42.1.1.1.1.4

esPointInEventState OBJECT-TYPE
    SYNTAX Integer32
    MAX-ACCESS read-write
    STATUS current
    DESCRIPTION
        "A number referring to the event state of a point
        on an EventSensor.  This number can have different
        meanings depending on the point class.

        If the point class is temperature, humidity, or
        analog input, then the values of this object are:
        1=very low
        2=low
        3=normal
        4=high
        5=very high

        For contact closures the values of this object are:
        1=point in event state
        2=point in normal state

        For relays the values of this object are:
        1=relay energized (active)
        2=relay de-energized (inactive)

        For any point class and any point, if the event
        state is undefined, then the value of this object
        is 0.

        For any point class except relay, this object is
        read-only.  For relays, setting this object to 1
        puts the relay into its active (energized) state.
        Setting it to 2 puts the relay into its inactive
        (de-energized) state.  Setting it to any
        value greater than 2 puts the relay into its
        active state for that many seconds (up to 3600),
        after which time it puts the relay into its
        inactive state.
        "
    ::= { esPointEntry 5 }
    --1.3.6.1.4.1.3052.42.1.1.1.1.5

esPointValueInt OBJECT-TYPE
    SYNTAX Integer32 (-32768..32767)
    MAX-ACCESS read-write
    STATUS current
    DESCRIPTION
        "A read-only number referring to the value of a
        point on an EventSensor.

        If the point class is temperature, then this object
        is the temperature in its configured scale (default
        is Fahrenheit).

        If the point class is contact closure or relay, then
        this object is either 0 (open) or 1 (closed).

        If the point class is humidity, then this object
        is the percent relative humidity.

        If the point class is analog input, then this
        object is the signed input value in tenths of the
        configured units.

        If the point class is relay, then this object is
        either 1 (active a.k.a. energized) or 0
        (inactive a.k.a. de-energized).  This object cannot
        be used to control the relay (use esPointInEventState
        for that).
        "
    ::= { esPointEntry 6 }
    --1.3.6.1.4.1.3052.42.1.1.1.1.6

esPointValueStr OBJECT-TYPE
    SYNTAX DisplayString
    MAX-ACCESS read-only
    STATUS current
    DESCRIPTION
        "A string referring to the value of a point on an
        EventSensor.

        For contact closures this object is either 'Open'
        or 'Closed'.

        For relays this object is either 'Active'
        (energized) or 'Inactive' (de-energized).

        For temperature and humidity point classes, this
        object is the string representation of the
        esPointValueInt object.  For temperature, 'C' or
        'F' is including in the string to indicate scale.

        For analog inputs, this object is the string
        representation of the plus/minus input in the
        configured units appended with the unit name.
        "
    ::= { esPointEntry 7 }
    --1.3.6.1.4.1.3052.42.1.1.1.1.7


--***************************************************************************************
--EventSensor Point Config Section   2.2
--***************************************************************************************


esPointConfigTempTable OBJECT-TYPE
    SYNTAX SEQUENCE OF ESPointConfigTemp
    MAX-ACCESS not-accessible
    STATUS current
    DESCRIPTION
        "This table organizes 3 basic attributes of temperature
        sensor points.  A point is a particular sensor on an
        EventSensor.  The 3 point attributes organizes in this table
        are:
        1. the configuration item (e.g., enable, name, etc.)
        2. the eventsensor on which this point resides
        3. the point number (always 1 for temp sensors)

        Points are referenced by a point config index.  The point
        config index is a string of 2 numbers separated by periods.
        It contains all the information necessary for getting a
        piece of data off an event sensor within the context of this
        emperature point config table ; namely, which EventSensor,
        and which sensor (a.k.a. point) (always 1 for temperature
        sensors).
        "
    ::= { eventSensorPointConfig 1 }
    --1.3.6.1.4.1.3052.42.2.2.1

esPointConfigTempEntry OBJECT-TYPE
    SYNTAX ESPointConfigTemp
    MAX-ACCESS not-accessible
    STATUS current
    DESCRIPTION
        "Entry for EventSensor point config temperature table"
    INDEX { espcTempIndexES, espcTempIndexPoint }
    ::= { esPointConfigTempTable 1 }
    --1.3.6.1.4.1.3052.42.2.2.1.1

espcTempIndexES OBJECT-TYPE
    SYNTAX Integer32 (1..200)
    MAX-ACCESS read-only
    STATUS current
    DESCRIPTION
        "The part of the point index that refers to an
        EventSensor.

        The point config index is a string of 2 numbers separated
        by a period.  It contains all the information
        necessary for getting a piece of data off an event
        sensor within the the context of the eventsensor point
        config temperature table; namely, which EventSensor,
        and which sensor (a.k.a. point).

        This object's allowable values are 1 through 16,
        and 200.  200 always refers to the EventSensor
        inside the unit.  1 through 16 refer to additional
        attached EventSensors.

        The number corresponding to an EventSensor is
        determined by the user at the initial configuration
        time.  If there is an internal sensor in the unit,
        it will always be the first item in the Sensor
        Events setup menu.

        For example, if a new EventSensor is configured as
        the 2nd entry AFTER the internal EventSensor (if
        one exists) in the Sensor Events Setup Menu, then
        that EventSensor will be known from then on as
        EventSensor 2.  All point indeces with esIndexES=2
        will now refer to that particular EventSensor.
        "
    ::= { esPointConfigTempEntry 1 }
    --1.3.6.1.4.1.3052.42.2.2.1.1.1

espcTempIndexPoint OBJECT-TYPE
    SYNTAX Integer32 (1..64)
    MAX-ACCESS read-only
    STATUS current
    DESCRIPTION
        "The part of the point index that delineates which
        sensor on the EventSensor.

        So this combined with espcTempIndexES (which EventSensor)
        uniquely defines each point attached to a unit within the
        context of temperature point configuration."
    ::= { esPointConfigTempEntry 2 }
    --1.3.6.1.4.1.3052.42.2.2.1.1.2

espcTempEnable OBJECT-TYPE
    SYNTAX DisplayString
    MAX-ACCESS read-write
    STATUS current
    DESCRIPTION
        "ON/OFF enable this temperature sensor"
    ::= { esPointConfigTempEntry 3 }
    --1.3.6.1.4.1.3052.42.2.2.1.1.3

espcTempName OBJECT-TYPE
    SYNTAX DisplayString
    MAX-ACCESS read-write
    STATUS current
    DESCRIPTION
        "The name of this temperature sensor"
    ::= { esPointConfigTempEntry 4 }
    --1.3.6.1.4.1.3052.42.2.2.1.1.4

espcTempScale OBJECT-TYPE
    SYNTAX DisplayString
    MAX-ACCESS read-write
    STATUS current
    DESCRIPTION
        "Scale (C/F) for this temperature sensor"
    ::= { esPointConfigTempEntry 5 }
    --1.3.6.1.4.1.3052.42.2.2.1.1.5

espcTempDeadband OBJECT-TYPE
    SYNTAX Integer32
    MAX-ACCESS read-write
    STATUS current
    DESCRIPTION
        "Deadband for this temperature sensor"
    ::= { esPointConfigTempEntry 6 }
    --1.3.6.1.4.1.3052.42.2.2.1.1.6

espcTempVHighTemp OBJECT-TYPE
    SYNTAX Integer32
    MAX-ACCESS read-write
    STATUS current
    DESCRIPTION
        "Very high temperature event threshold for this temperature
        sensor"
    ::= { esPointConfigTempEntry 7 }
    --1.3.6.1.4.1.3052.42.2.2.1.1.7

espcTempVHighClass OBJECT-TYPE
    SYNTAX DisplayString
    MAX-ACCESS read-write
    STATUS current
    DESCRIPTION
        "Very high temperature event class for this temperature
        sensor"
    ::= { esPointConfigTempEntry 9 }
    --1.3.6.1.4.1.3052.42.2.2.1.1.9

espcTempHighTemp OBJECT-TYPE
    SYNTAX Integer32
    MAX-ACCESS read-write
    STATUS current
    DESCRIPTION
        "High temperature event threshold for this temperature
        sensor"
    ::= { esPointConfigTempEntry 10 }
    --1.3.6.1.4.1.3052.42.2.2.1.1.10


espcTempHighClass OBJECT-TYPE
    SYNTAX DisplayString
    MAX-ACCESS read-write
    STATUS current
    DESCRIPTION
        "High temperature event class for this temperature sensor"
    ::= { esPointConfigTempEntry 13 }
    --1.3.6.1.4.1.3052.42.2.2.1.1.13

espcTempLowTemp OBJECT-TYPE
    SYNTAX Integer32
    MAX-ACCESS read-write
    STATUS current
    DESCRIPTION
        "Low temperature event threshold for this temperature sensor"
    ::= { esPointConfigTempEntry 17 }
    --1.3.6.1.4.1.3052.42.2.2.1.1.17

espcTempLowClass OBJECT-TYPE
    SYNTAX DisplayString
    MAX-ACCESS read-write
    STATUS current
    DESCRIPTION
        "Low temperature event class for this temperature sensor"
    ::= { esPointConfigTempEntry 20 }
    --1.3.6.1.4.1.3052.42.2.2.1.1.20

espcTempVLowTemp OBJECT-TYPE
    SYNTAX Integer32
    MAX-ACCESS read-write
    STATUS current
    DESCRIPTION
        "Very Low temperature event threshold for this temperature
        sensor"
    ::= { esPointConfigTempEntry 21 }
    --1.3.6.1.4.1.3052.42.2.2.1.1.21

espcTempVLowClass OBJECT-TYPE
    SYNTAX DisplayString
    MAX-ACCESS read-write
    STATUS current
    DESCRIPTION
        "Very Low temperature event class for this temperature sensor"
    ::= { esPointConfigTempEntry 24 }
    --1.3.6.1.4.1.3052.42.2.2.1.1.24


espcTempActions OBJECT-TYPE
    SYNTAX DisplayString
    MAX-ACCESS read-write
    STATUS current
    DESCRIPTION
        "Temperature event Action"
    ::= { esPointConfigTempEntry 25 }
    --1.3.6.1.4.1.3052.42.2.2.1.1.25


esPointConfigCCTable OBJECT-TYPE
    SYNTAX SEQUENCE OF ESPointConfigCC
    MAX-ACCESS not-accessible
    STATUS current
    DESCRIPTION
        "This table organizes 3 basic attributes of contact closure
        points.  A point is a particular sensor on an EventSensor.
        The 3 point attributes organizes in this table are:
        1. the configuration item (e.g., enable, name, etc.)
        2. the eventsensor on which this point resides
        3. the point number

        Points are referenced by a point config index.  The point
        config index is a string of 2 numbers separated by a period.
        It contains all the information necessary for getting a piece
        of data off an event sensor within the context of this
        contact closure point config table ; namely, which
        EventSensor and which sensor.
        "
    ::= { eventSensorPointConfig 2 }
    --1.3.6.1.4.1.3052.42.2.2.2

esPointConfigCCEntry OBJECT-TYPE
    SYNTAX ESPointConfigCC
    MAX-ACCESS not-accessible
    STATUS current
    DESCRIPTION
        "Entry for EventSensor point config contact closure table"
    INDEX { espcCCIndexES, espcCCIndexPoint }
    ::= { esPointConfigCCTable 1 }
    --1.3.6.1.4.1.3052.42.2.2.2.1

espcCCIndexES OBJECT-TYPE
    SYNTAX Integer32 (1..200)
    MAX-ACCESS read-only
    STATUS current
    DESCRIPTION
        "The part of the point index that refers to an
        EventSensor.

        The point config index is a string of 2 numbers separated
        by a period.  It contains all the information
        necessary for getting a piece of data off an event
        sensor within the the context of the eventsensor point
        config contact closure table; namely, which EventSensor
        and which sensor (a.k.a. point).

        This object's allowable values are 1 through 16,
        and 200.  200 always refers to the EventSensor
        inside the unit.  1 through 16 refer to additional
        attached EventSensors.
        "
    ::= { esPointConfigCCEntry 1 }
    --1.3.6.1.4.1.3052.42.2.2.2.1.1

espcCCIndexPoint OBJECT-TYPE
    SYNTAX Integer32 (1..64)
    MAX-ACCESS read-only
    STATUS current
    DESCRIPTION
        "The part of the point index that delineates which
        sensor on the EventSensor.

        So this combined with espcCCIndexES (which EventSensor)
        uniquely defines each point attached to a unit within the
        context of contact closure point configuration."
    ::= { esPointConfigCCEntry 2 }
    --1.3.6.1.4.1.3052.42.2.2.2.1.2

espcCCEnable OBJECT-TYPE
    SYNTAX DisplayString
    MAX-ACCESS read-write
    STATUS current
    DESCRIPTION
        "ON/OFF enable for this contact closure"
    ::= { esPointConfigCCEntry 3 }
    --1.3.6.1.4.1.3052.42.2.2.2.1.3

espcCCName OBJECT-TYPE
    SYNTAX DisplayString
    MAX-ACCESS read-write
    STATUS current
    DESCRIPTION
        "Name for this contact closure"
    ::= { esPointConfigCCEntry 4 }
    --1.3.6.1.4.1.3052.42.2.2.2.1.4

espcCCEventState OBJECT-TYPE
    SYNTAX DisplayString
    MAX-ACCESS read-write
    STATUS current
    DESCRIPTION
        "Event state for this contact closure"
    ::= { esPointConfigCCEntry 5 }
    --1.3.6.1.4.1.3052.42.2.2.2.1.5

espcCCThreshold OBJECT-TYPE
    SYNTAX Integer32
    MAX-ACCESS read-write
    STATUS current
    DESCRIPTION
        "Threshold (seconds) for this contact closure"
    ::= { esPointConfigCCEntry 6 }
    --1.3.6.1.4.1.3052.42.2.2.2.1.6


espcCCActions OBJECT-TYPE
    SYNTAX DisplayString
    MAX-ACCESS read-write
    STATUS current
    DESCRIPTION
        "Event class for this contact closure"
    ::= { esPointConfigCCEntry 7 }
    --1.3.6.1.4.1.3052.42.2.2.2.1.7

espcCCEventClass OBJECT-TYPE
    SYNTAX DisplayString
    MAX-ACCESS read-write
    STATUS current
    DESCRIPTION
        "Event class for this contact closure"
    ::= { esPointConfigCCEntry 9 }
    --1.3.6.1.4.1.3052.42.2.2.2.1.9

espcCCNormalClass OBJECT-TYPE
    SYNTAX DisplayString
    MAX-ACCESS read-write
    STATUS current
    DESCRIPTION
        "Return-to-normal class for this contact closure"
    ::= { esPointConfigCCEntry 12 }
    --1.3.6.1.4.1.3052.42.2.2.2.1.12

espcCCAlarmAlias OBJECT-TYPE
    SYNTAX DisplayString
    MAX-ACCESS read-write
    STATUS current
    DESCRIPTION
        "Event alias for this contact closure"
    ::= { esPointConfigCCEntry 13 }
    --1.3.6.1.4.1.3052.42.2.2.2.1.13

espcCCNormalAlias OBJECT-TYPE
    SYNTAX DisplayString
    MAX-ACCESS read-write
    STATUS current
    DESCRIPTION
        "Return-to-normal alias for this contact closure"
    ::= { esPointConfigCCEntry 14 }
    --1.3.6.1.4.1.3052.42.2.2.2.1.14



esPointConfigHumidTable OBJECT-TYPE
    SYNTAX SEQUENCE OF ESPointConfigHumid
    MAX-ACCESS not-accessible
    STATUS current
    DESCRIPTION
        "This table organizes 3 basic attributes of humidity points.
        A point is a particular sensor on an EventSensor.  The 3
        point attributes organizes in this table are:
        1. the configuration item (e.g., enable, name, etc.)
        2. the eventsensor on which this point resides
        3. the point number (always 1 for humidity sensors)

        Points are referenced by a point config index.  The point
        config index is a string of 2 numbers separated by a period.
        It contains all the information necessary for getting a piece
        of data off an event sensor within the context of this
        humidity point config table ; namely, which EventSensor and
        which sensor.
        "
    ::= { eventSensorPointConfig 3 }
    --1.3.6.1.4.1.3052.42.2.2.3

esPointConfigHumidEntry OBJECT-TYPE
    SYNTAX ESPointConfigHumid
    MAX-ACCESS not-accessible
    STATUS current
    DESCRIPTION
        "Entry for EventSensor point config humidity table"
    INDEX { espcHumidIndexES, espcHumidIndexPoint }
    ::= { esPointConfigHumidTable 1 }
    --1.3.6.1.4.1.3052.42.2.2.3.1

espcHumidIndexES OBJECT-TYPE
    SYNTAX Integer32 (1..200)
    MAX-ACCESS read-only
    STATUS current
    DESCRIPTION
        "The part of the point index that refers to an
        EventSensor.

        The point config index is a string of 2 numbers separated
        by a period.  It contains all the information
        necessary for getting a piece of data off an event
        sensor within the the context of the eventsensor point
        config contact closure table; namely, which EventSensor
        and which sensor (a.k.a. point).

        This object's allowable values are 1 through 16,
        and 200.  200 always refers to the EventSensor
        inside the unit.  1 through 16 refer to additional
        attached EventSensors.
        "
    ::= { esPointConfigHumidEntry 1 }
    --1.3.6.1.4.1.3052.42.2.2.3.1.1

espcHumidIndexPoint OBJECT-TYPE
    SYNTAX Integer32 (1..64)
    MAX-ACCESS read-only
    STATUS current
    DESCRIPTION
        "The part of the point index that delineates which
        sensor on the EventSensor.

        So this combined with espcHumidIndexES (which EventSensor)
        uniquely defines each point attached to a unit within the
        context of contact closure point configuration."
    ::= { esPointConfigHumidEntry 2 }
    --1.3.6.1.4.1.3052.42.2.2.3.1.2

espcHumidEnable OBJECT-TYPE
    SYNTAX DisplayString
    MAX-ACCESS read-write
    STATUS current
    DESCRIPTION
        "ON/OFF enable for this humidity sensor"
    ::= { esPointConfigHumidEntry 3 }
    --1.3.6.1.4.1.3052.42.2.2.3.1.3

espcHumidName OBJECT-TYPE
    SYNTAX DisplayString
    MAX-ACCESS read-write
    STATUS current
    DESCRIPTION
        "The name for this humidity sensor"
    ::= { esPointConfigHumidEntry 4 }
    --1.3.6.1.4.1.3052.42.2.2.3.1.4

espcHumidDeadband OBJECT-TYPE
    SYNTAX Integer32
    MAX-ACCESS read-write
    STATUS current
    DESCRIPTION
        "Deadband for this humidity sensor"
    ::= { esPointConfigHumidEntry 5 }
    --1.3.6.1.4.1.3052.42.2.2.3.1.5

espcHumidVHighHumid OBJECT-TYPE
    SYNTAX Integer32
    MAX-ACCESS read-write
    STATUS current
    DESCRIPTION
        "Very high event threshold for this humidity sensor"
    ::= { esPointConfigHumidEntry 6 }
    --1.3.6.1.4.1.3052.42.2.2.3.1.6

espcHumidVHighClass OBJECT-TYPE
    SYNTAX DisplayString
    MAX-ACCESS read-write
    STATUS current
    DESCRIPTION
        "Very high event class for this humidity sensor"
    ::= { esPointConfigHumidEntry 8 }
    --1.3.6.1.4.1.3052.42.2.2.3.1.8

espcHumidHighHumid OBJECT-TYPE
    SYNTAX Integer32
    MAX-ACCESS read-write
    STATUS current
    DESCRIPTION
        "High event threshold for this humidity sensor"
    ::= { esPointConfigHumidEntry 9 }
    --1.3.6.1.4.1.3052.42.2.2.3.1.9

espcHumidHighClass OBJECT-TYPE
    SYNTAX DisplayString
    MAX-ACCESS read-write
    STATUS current
    DESCRIPTION
        "High event class for this humidity sensor"
    ::= { esPointConfigHumidEntry 12 }
    --1.3.6.1.4.1.3052.42.2.2.3.1.12

espcHumidLowHumid OBJECT-TYPE
    SYNTAX Integer32
    MAX-ACCESS read-write
    STATUS current
    DESCRIPTION
        "Low event threshold for this humidity sensor"
    ::= { esPointConfigHumidEntry 16 }
    --1.3.6.1.4.1.3052.42.2.2.3.1.16

espcHumidLowClass OBJECT-TYPE
    SYNTAX DisplayString
    MAX-ACCESS read-write
    STATUS current
    DESCRIPTION
        "Low event class for this humidity sensor"
    ::= { esPointConfigHumidEntry 19 }
    --1.3.6.1.4.1.3052.42.2.2.3.1.19

espcHumidVLowHumid OBJECT-TYPE
    SYNTAX Integer32
    MAX-ACCESS read-write
    STATUS current
    DESCRIPTION
        "Very low event threshold for this humidity sensor"
    ::= { esPointConfigHumidEntry 20 }
    --1.3.6.1.4.1.3052.42.2.2.3.1.20

espcHumidVLowClass OBJECT-TYPE
    SYNTAX DisplayString
    MAX-ACCESS read-write
    STATUS current
    DESCRIPTION
        "Very low event class for this humidity sensor"
    ::= { esPointConfigHumidEntry 23 }
    --1.3.6.1.4.1.3052.42.2.2.3.1.23

espcHumidActions OBJECT-TYPE
    SYNTAX DisplayString
    MAX-ACCESS read-write
    STATUS current
    DESCRIPTION
        "Humidity event actions for this humidity sensor"
    ::= { esPointConfigHumidEntry 24 }
    --1.3.6.1.4.1.3052.42.2.2.3.1.24
    
esPointConfigAITable OBJECT-TYPE
    SYNTAX SEQUENCE OF ESPointConfigAnalogInput
    MAX-ACCESS not-accessible
    STATUS current
    DESCRIPTION
        "This table organizes 3 basic attributes of analog input
        points.  A point is a particular sensor on an EventSensor.
        The 3 point attributes organizes in this table are:
        1. the configuration item (e.g., enable, name, etc.)
        2. the eventsensor on which this point resides
        3. the point number

        Points are referenced by a point config index.  The point
        config index is a string of 2 numbers separated by a period.
        It contains all the information necessary for getting a
        piece of data off an event sensor within the context of this
        analog input point config table ; namely, which EventSensor
        and which sensor.
        "
    ::= { eventSensorPointConfig 5 }
    --1.3.6.1.4.1.3052.8.2.2.5

esPointConfigAIEntry OBJECT-TYPE
    SYNTAX ESPointConfigAnalogInput
    MAX-ACCESS not-accessible
    STATUS current
    DESCRIPTION
        "Entry for EventSensor point config analog input table"
    INDEX { espcHumidIndexES, espcHumidIndexPoint }
    ::= { esPointConfigAITable 1 }
    --1.3.6.1.4.1.3052.8.2.2.5.1

espcAIIndexES OBJECT-TYPE
    SYNTAX Integer32 (1..200)
    MAX-ACCESS read-only
    STATUS current
    DESCRIPTION
        "The part of the point index that refers to an
        EventSensor.

        The point config index is a string of 2 numbers separated
        by a period.  It contains all the information
        necessary for getting a piece of data off an event
        sensor within the the context of the eventsensor point
        config contact closure table; namely, which EventSensor
        and which sensor (a.k.a. point).

        This object's allowable values are 1 through 16,
        and 200.  200 always refers to the EventSensor
        inside the unit.  1 through 16 refer to additional
        attached EventSensors.
        "
    ::= { esPointConfigAIEntry 1 }
    --1.3.6.1.4.1.3052.42.2.2.5.1.1

espcAIIndexPoint OBJECT-TYPE
    SYNTAX Integer32 (1..64)
    MAX-ACCESS read-only
    STATUS current
    DESCRIPTION
        "The part of the point index that delineates which
        sensor on the EventSensor.

        So this combined with espcAIIndexES (which EventSensor)
        uniquely defines each point attached to a unit within the
        context of contact closure point configuration."
    ::= { esPointConfigAIEntry 2 }
    --1.3.6.1.4.1.3052.42.2.2.5.1.2

espcAIEnable OBJECT-TYPE
    SYNTAX DisplayString
    MAX-ACCESS read-write
    STATUS current
    DESCRIPTION
        "ON/OFF for this analog input sensor"
    ::= { esPointConfigAIEntry 3 }
    --1.3.6.1.4.1.3052.42.2.2.5.1.3

espcAIName OBJECT-TYPE
    SYNTAX DisplayString
    MAX-ACCESS read-write
    STATUS current
    DESCRIPTION
        "Name for this analog input sensor"
    ::= { esPointConfigAIEntry 4 }
    --1.3.6.1.4.1.3052.42.2.2.5.1.4

espcAIDeadband OBJECT-TYPE
    SYNTAX Integer32
    MAX-ACCESS read-write
    STATUS current
    DESCRIPTION
        "Deadband for this analog input sensor"
    ::= { esPointConfigAIEntry 5 }
    --1.3.6.1.4.1.3052.42.2.2.5.1.5

espcAIVhighValue OBJECT-TYPE
    SYNTAX Integer32
    MAX-ACCESS read-write
    STATUS current
    DESCRIPTION
        "Very high event threshold (decivolts or tenths of
        milliamps) for this analog input sensor"
    ::= { esPointConfigAIEntry 6 }
    --1.3.6.1.4.1.3052.42.2.2.5.1.6

espcAIVhighClass OBJECT-TYPE
    SYNTAX DisplayString
    MAX-ACCESS read-write
    STATUS current
    DESCRIPTION
        "Very high event class for this analog input sensor"
    ::= { esPointConfigAIEntry 8 }
    --1.3.6.1.4.1.3052.42.2.2.5.1.8

espcAIHighValue OBJECT-TYPE
    SYNTAX Integer32
    MAX-ACCESS read-write
    STATUS current
    DESCRIPTION
        "High event threshold (decivolts or tenths of
        milliamps) for this analog input sensor"
    ::= { esPointConfigAIEntry 9 }
    --1.3.6.1.4.1.3052.42.2.2.5.1.9

espcAIHighClass OBJECT-TYPE
    SYNTAX DisplayString
    MAX-ACCESS read-write
    STATUS current
    DESCRIPTION
        "High event class for this analog input sensor"
    ::= { esPointConfigAIEntry 12 }
    --1.3.6.1.4.1.3052.42.2.2.5.1.12

espcAILowValue OBJECT-TYPE
    SYNTAX Integer32
    MAX-ACCESS read-write
    STATUS current
    DESCRIPTION
        "Low event threshold (decivolts or tenths of
        milliamps) for this analog input sensor"
    ::= { esPointConfigAIEntry 16 }
    --1.3.6.1.4.1.3052.42.2.2.5.1.16

espcAILowClass OBJECT-TYPE
    SYNTAX DisplayString
    MAX-ACCESS read-write
    STATUS current
    DESCRIPTION
        "Low event class for this analog input sensor"
    ::= { esPointConfigAIEntry 19 }
    --1.3.6.1.4.1.3052.42.2.2.5.1.19

espcAIVlowValue OBJECT-TYPE
    SYNTAX Integer32
    MAX-ACCESS read-write
    STATUS current
    DESCRIPTION
        "Very low event threshold (decivolts or tenths of
        milliamps) for this analog input sensor"
    ::= { esPointConfigAIEntry 20 }
    --1.3.6.1.4.1.3052.42.2.2.5.1.20

espcAIVlowClass OBJECT-TYPE
    SYNTAX DisplayString
    MAX-ACCESS read-write
    STATUS current
    DESCRIPTION
        "Very low event class for this analog input sensor"
    ::= { esPointConfigAIEntry 23 }
    --1.3.6.1.4.1.3052.42.2.2.5.1.23

espcAIActions OBJECT-TYPE
    SYNTAX DisplayString
    MAX-ACCESS read-write
    STATUS current
    DESCRIPTION
        "Event actions for this analog input sensor"
    ::= { esPointConfigAIEntry 24 }
    --1.3.6.1.4.1.3052.42.2.2.5.1.24

espcAIConvUnitName OBJECT-TYPE
    SYNTAX DisplayString
    MAX-ACCESS read-write
    STATUS current
    DESCRIPTION
        "Conversion unit name for this analog input sensor"
    ::= { esPointConfigAIEntry 25 }
    --1.3.6.1.4.1.3052.42.2.2.5.1.25

espcAIConvLowValue OBJECT-TYPE
    SYNTAX Integer32
    MAX-ACCESS read-write
    STATUS current
    DESCRIPTION
        "Conversion low value for this analog input sensor"
    ::= { esPointConfigAIEntry 26 }
    --1.3.6.1.4.1.3052.42.2.2.5.1.26

espcAIConvLowUnit OBJECT-TYPE
    SYNTAX Integer32
    MAX-ACCESS read-write
    STATUS current
    DESCRIPTION
        "Conversion low unit value for this analog input sensor"
    ::= { esPointConfigAIEntry 27 }
    --1.3.6.1.4.1.3052.42.2.2.5.1.27

espcAIConvHighValue OBJECT-TYPE
    SYNTAX Integer32
    MAX-ACCESS read-write
    STATUS current
    DESCRIPTION
        "Conversion high value for this analog input sensor"
    ::= { esPointConfigAIEntry 28 }
    --1.3.6.1.4.1.3052.42.2.2.5.1.28

espcAIConvHighUnit OBJECT-TYPE
    SYNTAX Integer32
    MAX-ACCESS read-write
    STATUS current
    DESCRIPTION
        "Conversion high unit value for this analog input sensor"
    ::= { esPointConfigAIEntry 29 }
    --1.3.6.1.4.1.3052.42.2.2.5.1.29


esPointConfigRelayTable OBJECT-TYPE
    SYNTAX SEQUENCE OF ESPointConfigRelay
    MAX-ACCESS not-accessible
    STATUS current
    DESCRIPTION
        "This table organizes 3 basic attributes of relay
        points.  A point is a particular sensor on an EventSensor.
        The 3 point attributes organizes in this table are:
        1. the configuration item (e.g., enable, name, etc.)
        2. the eventsensor on which this point resides
        3. the point number

        Points are referenced by a point config index.  The point
        config index is a string of 2 numbers separated by a period.
        It contains all the information necessary for getting a piece
        of data off an event sensor within the context of this
        relay point config table ; namely, which
        EventSensor and which sensor.
        "
    ::= { eventSensorPointConfig 6 }
    --1.3.6.1.4.1.3052.42.2.2.6

esPointConfigRelayEntry OBJECT-TYPE
    SYNTAX ESPointConfigRelay
    MAX-ACCESS not-accessible
    STATUS current
    DESCRIPTION
        "Entry for EventSensor point config relay table"
    INDEX { espcRelayIndexES, espcRelayIndexPoint }
    ::= { esPointConfigRelayTable 1 }
    --1.3.6.1.4.1.3052.42.2.2.6.1

espcRelayIndexES OBJECT-TYPE
    SYNTAX Integer32 (1..200)
    MAX-ACCESS read-only
    STATUS current
    DESCRIPTION
        "The part of the point index that refers to an
        EventSensor.

        The point config index is a string of 2 numbers separated
        by a period.  It contains all the information
        necessary for getting a piece of data off an event
        sensor within the the context of the eventsensor point
        config relay table; namely, which EventSensor
        and which sensor (a.k.a. point).

        This object's allowable values are 1 through 16,
        and 200.  200 always refers to the EventSensor
        inside the unit.  1 through 16 refer to additional
        attached EventSensors.
        "
    ::= { esPointConfigRelayEntry 1 }
    --1.3.6.1.4.1.3052.42.2.2.6.1.1

espcRelayIndexPoint OBJECT-TYPE
    SYNTAX Integer32 (1..64)
    MAX-ACCESS read-only
    STATUS current
    DESCRIPTION
        "The part of the point index that delineates which
        sensor on the EventSensor.

        So this combined with espcRelayIndexES (which EventSensor)
        uniquely defines each point attached to a unit within the
        context of relay point configuration."
    ::= { esPointConfigRelayEntry 2 }
    --1.3.6.1.4.1.3052.42.2.2.6.1.2

espcRelayEnable OBJECT-TYPE
    SYNTAX DisplayString
    MAX-ACCESS read-write
    STATUS current
    DESCRIPTION
        "ON/OFF enable for this relay"
    ::= { esPointConfigRelayEntry 3 }
    --1.3.6.1.4.1.3052.42.2.2.6.1.3

espcRelayName OBJECT-TYPE
    SYNTAX DisplayString
    MAX-ACCESS read-write
    STATUS current
    DESCRIPTION
        "Name for this relay"
    ::= { esPointConfigRelayEntry 4 }
    --1.3.6.1.4.1.3052.42.2.2.6.1.4


--***************************************************************************************
--Network Section   2.4
--***************************************************************************************

ipAddress OBJECT-TYPE
    SYNTAX IpAddress
    MAX-ACCESS read-write
    STATUS current
    DESCRIPTION
        "Ethernet IP address"
    ::= { ethernet 1 }
    --1.3.6.1.4.1.3052.42.2.4.1.1

subnetMask OBJECT-TYPE
    SYNTAX IpAddress
    MAX-ACCESS read-write
    STATUS current
    DESCRIPTION
        "Ethernet subnet mask"
    ::= { ethernet 2 }
    --1.3.6.1.4.1.3052.42.2.4.1.2

router OBJECT-TYPE
    SYNTAX IpAddress
    MAX-ACCESS read-write
    STATUS current
    DESCRIPTION
        "Ethernet router"
    ::= { ethernet 3 }
    --1.3.6.1.4.1.3052.42.2.4.1.3


-- SNMP

snmpReadCommunity OBJECT-TYPE
    SYNTAX DisplayString
    MAX-ACCESS read-write
    STATUS current
    DESCRIPTION
        "SNMP read community"
    ::= { snmp 2 }
    --1.3.6.1.4.1.3052.42.2.4.8.2

snmpWriteCommunity OBJECT-TYPE
    SYNTAX DisplayString
    MAX-ACCESS read-write
    STATUS current
    DESCRIPTION
        "SNMP write community"
    ::= { snmp 3 }
    --1.3.6.1.4.1.3052.42.2.4.8.3

snmpTrapCommunity OBJECT-TYPE
    SYNTAX DisplayString
    MAX-ACCESS read-write
    STATUS current
    DESCRIPTION
        "SNMP trap community"
    ::= { snmp 4 }
    --1.3.6.1.4.1.3052.42.2.4.8.4

snmpServerTable OBJECT-TYPE
    SYNTAX SEQUENCE OF ActionSNMPConfig
    MAX-ACCESS not-accessible
    STATUS current
    DESCRIPTION
        "Table of network hosts to use for network-based actions"
    ::= { snmp 6 }
    --1.3.6.1.4.1.3052.42.2.8.6

snmpServerEntry OBJECT-TYPE
    SYNTAX ActionSNMPConfig
    MAX-ACCESS not-accessible
    STATUS current
    DESCRIPTION
        "Entry for table of network hosts to use for network-based
        actions"
    INDEX { snmpServerIndex }
    ::= { snmpServerTable 1 }
    --1.3.6.1.4.1.3052.42.2.8.6.1

snmpServerIndex OBJECT-TYPE
    SYNTAX Integer32 (1..6)
    MAX-ACCESS read-only
    STATUS current
    DESCRIPTION
        "Index for table of network hosts to use for network-based
        actions"
    ::= { snmpServerEntry 1 }
    --1.3.6.1.4.1.3052.42.2.8.6.1.1

snmpServer OBJECT-TYPE
    SYNTAX IpAddress
    MAX-ACCESS read-write
    STATUS current
    DESCRIPTION
        "Hostname/IP address used as destination for network-based
        action (e.g., trap)"
    ::= { snmpServerEntry 2 }
    --1.3.6.1.4.1.3052.42.2.8.6.1.2

snmpTestTrap OBJECT-TYPE
    SYNTAX DisplayString
    MAX-ACCESS read-write
    STATUS current
    DESCRIPTION
        "SNMP trap community"
    ::= { snmp 7 }
    --1.3.6.1.4.1.3052.42.2.4.8.7

-- Email


emailServer OBJECT-TYPE
    SYNTAX IpAddress
    MAX-ACCESS read-write
    STATUS current
    DESCRIPTION
        "SMTP server to which the unit sends email"
    ::= { email 1 }
    --1.3.6.1.4.1.3052.42.2.4.17.1

emailDomain OBJECT-TYPE
    SYNTAX DisplayString
    MAX-ACCESS read-write
    STATUS current
    DESCRIPTION
        "Domain to use in recipient address"
    ::= { email 2 }
    --1.3.6.1.4.1.3052.42.2.4.17.2

emailAuthEnable OBJECT-TYPE
    SYNTAX DisplayString
    MAX-ACCESS read-write
    STATUS current
    DESCRIPTION
        "ON/OFF enable SMTP authentication"
    ::= { email 3 }
    --1.3.6.1.4.1.3052.42.2.4.17.3

emailAuthUsername OBJECT-TYPE
    SYNTAX DisplayString
    MAX-ACCESS read-write
    STATUS current
    DESCRIPTION
        "Username for SMTP authentication"
    ::= { email 4 }
    --1.3.6.1.4.1.3052.42.2.4.17.4

emailAuthPassword OBJECT-TYPE
    SYNTAX DisplayString
    MAX-ACCESS read-write
    STATUS current
    DESCRIPTION
        "Password for SMTP authentication"
    ::= { email 5 }
    --1.3.6.1.4.1.3052.42.2.4.17.5

emailTable OBJECT-TYPE
    SYNTAX SEQUENCE OF ActionEmailConfig
    MAX-ACCESS not-accessible
    STATUS current
    DESCRIPTION
        "Table of email addresses to use for email actions"
    ::= { email 6 }
    --1.3.6.1.4.1.3052.42.2.4.17.6

emailEntry OBJECT-TYPE
    SYNTAX ActionEmailConfig
    MAX-ACCESS not-accessible
    STATUS current
    DESCRIPTION
        "Entry for table of email addresses to use for email actions"
    INDEX { emailIndex }
    ::= { emailTable 1 }
    --1.3.6.1.4.1.3052.42.2.4.17.6.1

emailIndex OBJECT-TYPE
    SYNTAX Integer32 (1..6)
    MAX-ACCESS read-only
    STATUS current
    DESCRIPTION
        "Index for table of email addresses to use for email actions"
    ::= { emailEntry 1 }
    --1.3.6.1.4.1.3052.42.2.4.17.6.1.1

emailAddress OBJECT-TYPE
    SYNTAX DisplayString
    MAX-ACCESS read-write
    STATUS current
    DESCRIPTION
        "email address"
    ::= { emailEntry 2 }
    --1.3.6.1.4.1.3052.42.2.4.17.6.1.2

emailTestMail OBJECT-TYPE
    SYNTAX DisplayString
    MAX-ACCESS read-write
    STATUS current
    DESCRIPTION
        "Password for SMTP authentication"
    ::= { email 7 }
    --1.3.6.1.4.1.3052.42.2.4.17.7


--***************************************************************************************
--dateTime Section  2.8
--***************************************************************************************

date OBJECT-TYPE
    SYNTAX DisplayString
    MAX-ACCESS read-write
    STATUS current
    DESCRIPTION
        "Text string for date."
    ::= { dateTime 1 }
    --1.3.6.1.4.1.3052.42.2.8.1

time OBJECT-TYPE
    SYNTAX DisplayString
    MAX-ACCESS read-write
    STATUS current
    DESCRIPTION
        "Text string for time."
    ::= { dateTime 2 }
    --1.3.6.1.4.1.3052.42.2.8.2

autodst OBJECT-TYPE
    SYNTAX DisplayString
    MAX-ACCESS read-write
    STATUS current
    DESCRIPTION
        "ON/OFF automatically adjust for Daylight Savings Time"
    ::= { dateTime 3 }
    --1.3.6.1.4.1.3052.42.2.8.3


--***************************************************************************************
--Action Section   2.14
--***************************************************************************************


actionSystemAlertAction OBJECT-TYPE
    SYNTAX DisplayString
    MAX-ACCESS read-write
    STATUS current
    DESCRIPTION
        "System Alert Actions are actions that occur when the system needs to alert
        the user of something.  The only time this occurs currently is a powerup alert."
    ::= { action 1 }
    --1.3.6.1.4.1.3052.42.2.14.1

actionPowerupAlertEnable OBJECT-TYPE
    SYNTAX DisplayString
    MAX-ACCESS read-write
    STATUS current
    DESCRIPTION
        "action Powerup Alert Enable"
    ::= { action 2 }
    --1.3.6.1.4.1.3052.42.2.14.2

actionRTNAlertsEnable OBJECT-TYPE
    SYNTAX DisplayString
    MAX-ACCESS read-write
    STATUS current
    DESCRIPTION
        "Return to Normal Alerts Enabled"
    ::= { action 3 }
    --1.3.6.1.4.1.3052.42.2.14.3

actionAlarmRepeatFrequency OBJECT-TYPE
    SYNTAX Integer32
    MAX-ACCESS read-write
    STATUS current
    DESCRIPTION
        "Frequency in minutes of repeats"
    ::= { action 4 }
    --1.3.6.1.4.1.3052.42.2.14.4

--***************************************************************************************
--System Section   2.16
--***************************************************************************************


sysSerial OBJECT-TYPE
    SYNTAX DisplayString
    MAX-ACCESS read-write
    STATUS current
    DESCRIPTION
        "Serial Number"
    ::= { sys 1 }
    --1.3.6.1.4.1.3052.42.2.16.1

sysVersion OBJECT-TYPE
    SYNTAX DisplayString
    MAX-ACCESS read-write
    STATUS current
    DESCRIPTION
        "Serial Number"
    ::= { sys 2 }
    --1.3.6.1.4.1.3052.42.2.16.2

sysBuild OBJECT-TYPE
    SYNTAX DisplayString
    MAX-ACCESS read-write
    STATUS current
    DESCRIPTION
        "Serial Number"
    ::= { sys 3 }
    --1.3.6.1.4.1.3052.42.2.16.3

sysSitename OBJECT-TYPE
    SYNTAX DisplayString
    MAX-ACCESS read-write
    STATUS current
    DESCRIPTION
        "Serial Number"
    ::= { sys 4 }
    --1.3.6.1.4.1.3052.42.2.16.4

sysProduct OBJECT-TYPE
    SYNTAX DisplayString
    MAX-ACCESS read-write
    STATUS current
    DESCRIPTION
        "Serial Number"
    ::= { sys 5 }
    --1.3.6.1.4.1.3052.42.2.16.5

 thisTrapText OBJECT-TYPE
    SYNTAX DisplayString
    MAX-ACCESS read-write
    STATUS current
    DESCRIPTION
    "A text string included in all traps"
    ::= { sys 6 }
    --1.3.6.1.4.1.3052.42.2.16.6



--***************************************************************************************
--TABLE DEFINITIONS
--***************************************************************************************

ESPointConfigTemp ::=
    SEQUENCE {
    espcTempIndexES
            Integer32,
    espcTempIndexPoint
            Integer32,
    espcTempEnable
            DisplayString,
    espcTempName
            DisplayString,
    espcTempScale
            DisplayString,
    espcTempDeadband
            Integer32,
    espcTempVHighTemp
            Integer32,
    espcTempVHighClass
            DisplayString,
    espcTempHighTemp
            Integer32,
    espcTempHighClass
            DisplayString,
    espcTempLowTemp
            Integer32,
    espcTempLowClass
            DisplayString,
    espcTempVLowTemp
            Integer32,
    espcTempVLowClass
            DisplayString,
    espcTempActions
            DisplayString
}


ESPointConfigCC ::=
    SEQUENCE {
    espcCCIndexES
            Integer32,
    espcCCIndexPoint
            Integer32,
    espcCCEnable
            DisplayString,
    espcCCName
            DisplayString,
    espcCCEventState
            DisplayString,
    espcCCThreshold
            Integer32,
    espcCCActions
            DisplayString,
    espcCCEventClass
            DisplayString,
    espcCCNormalClass
            DisplayString,
    espcCCAlarmAlias
            DisplayString,
    espcCCNormalAlias
            DisplayString
}

ESPointConfigHumid ::=
    SEQUENCE {
    espcHumidIndexES
            Integer32,
    espcHumidIndexPoint
            Integer32,
    espcHumidEnable
            DisplayString,
    espcHumidName
            DisplayString,
    espcHumidDeadband
            Integer32,
    espcHumidVHighHumid
            Integer32,
    espcHumidVHighClass
            DisplayString,
    espcHumidHighHumid
            Integer32,
    espcHumidHighClass
            DisplayString,
    espcHumidLowHumid
            Integer32,
    espcHumidLowClass
            DisplayString,
    espcHumidVLowHumid
            Integer32,
    espcHumidVLowClass
            DisplayString,
    espcHumidActions
            DisplayString
}

ESPointConfigAnalogInput ::=
    SEQUENCE {
    espcAIIndexES
            Integer32,
    espcAIIndexPoint
            Integer32,
    espcAIEnable
            DisplayString,
    espcAIName
            DisplayString,
    espcAIDeadband
            Integer32,
    espcAIVhighValue
            Integer32,
    espcAIVhighClass
            DisplayString,
    espcAIHighValue
            Integer32,
    espcAIHighClass
            DisplayString,
    espcAILowValue
            Integer32,
    espcAILowClass
            DisplayString,
    espcAIVlowValue
            Integer32,
    espcAIVlowClass
            DisplayString,
    espcAIActions
            DisplayString,
    espcAIConvUnitName
            DisplayString,
    espcAIConvLowValue
            Integer32,
    espcAIConvLowUnit
            Integer32,
    espcAIConvHighValue
            Integer32,
    espcAIConvHighUnit
            Integer32
}

ESPointConfigRelay::=
    SEQUENCE {
    espcRelayIndexES
            Integer32,
    espcRelayIndexPoint
            Integer32,
    espcRelayEnable
            DisplayString,
    espcRelayName
            DisplayString
}

ActionEmailConfig ::=
    SEQUENCE {
        emailIndex
            Integer32,
        emailAddress
            DisplayString
}


ESPoint ::=
    SEQUENCE {
        esIndexES
            Integer32,
        esIndexPC
            Integer32,
        esIndexPoint
            Integer32,
        esPointName
            DisplayString,
        esPointInEventState
            Integer32,
        esPointValueInt
            Integer32,
         esPointValueStr
            DisplayString
}

ActionSNMPConfig ::=
    SEQUENCE {
        snmpServerIndex
            Integer32,
        snmpServer
            IpAddress
}

--***************************************************************************************
--TRAP DEFINITIONS
--***************************************************************************************

s420PowerUpTrap  NOTIFICATION-TYPE
    OBJECTS { thisTrapText, sysSitename }
    STATUS current
    DESCRIPTION
      "Sent upon System Alert at power up."
  ::= { s420 20000 }

s420ContactTrap  NOTIFICATION-TYPE
    OBJECTS { thisTrapText, sysSitename }
    STATUS current
    DESCRIPTION
      "Sent to show a contact is in the alarm state."
  ::= { s420 20001 }

s420TempTrap  NOTIFICATION-TYPE
    OBJECTS { thisTrapText, sysSitename }
    STATUS current
    DESCRIPTION
      "Sent to show temperature exceeded threshold."
  ::= { s420 20010 }

s420HumidTrap  NOTIFICATION-TYPE
    OBJECTS { thisTrapText, sysSitename }
    STATUS current
    DESCRIPTION
      "Sent to show humidity exceeded threshold"
  ::= { s420 20020 }

s420TestTrap  NOTIFICATION-TYPE
    OBJECTS { thisTrapText, sysSitename }
    STATUS current
    DESCRIPTION
      "Sent to test IP route(s) for traps."
  ::= { s420 22000 }


END
