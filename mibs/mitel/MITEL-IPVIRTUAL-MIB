-- Copyright 1999 MITEL Corporation
-- All rights reserved.
-- This MITEL SNMP Management Information Base Specification
-- (Specification) embodies MITEL's confidential and
-- proprietary intellectual property. MITEL retains all
-- title and ownership in the Specification, including any
-- revisions.

-- This Specification is supplied "AS IS", and MITEL makes
-- no warranty, either express or implied, as to the use,
-- operation, condition, or performance of the Specification.


MITEL-IPVIRTUAL-MIB
	DEFINITIONS ::= BEGIN

IMPORTS
	MODULE-IDENTITY, OBJECT-TYPE, enterprises,
    Integer32, Counter32, IpAddress
        FROM SNMPv2-SMI
    RowStatus
        FROM SNMPv2-TC;

mitelIpGrpIpVirtualGroup MODULE-IDENTITY
       LAST-UPDATED      "200303240931Z"
       ORGANIZATION      "MITEL Corporation"
       CONTACT-INFO      "Standards Group,
                          Postal:    MITEL Corporation
                          350 Legget Drive, PO Box 13089
                          Kanata, Ontario
                          Canada  K2K 1X3
                          Tel: +1 613 592 2122
                          Fax: +1 613 592 4784
                          E-mail: std@mitel.com"
       DESCRIPTION       "The MITEL IP MIB module."
       REVISION          "200303240931Z"
           DESCRIPTION   "Convert to SMIv2"
       REVISION          "199903010000Z"
           DESCRIPTION   "IP MIB Version 1.0"
::= { mitelRouterIpGroup 4 }

mitel			   OBJECT IDENTIFIER ::= { enterprises 1027}
mitelProprietary 	   OBJECT IDENTIFIER ::= { mitel 4}
mitelPropIpNetworking      OBJECT IDENTIFIER ::= { mitelProprietary 8 }
mitelIpNetRouter           OBJECT IDENTIFIER ::= { mitelPropIpNetworking 1 }
mitelRouterIpGroup 	   OBJECT IDENTIFIER ::= { mitelIpNetRouter 1}

--
--
--     The IP Virtual Port Configuration Table.
--

    mitelIpVGrpPortTable OBJECT-TYPE
        SYNTAX  SEQUENCE OF MitelIpVGrpPortEntry
        MAX-ACCESS  not-accessible
        STATUS  current
        DESCRIPTION
                "This table is used to display and configure IP virtual
                port information. Each logical LAN destination may have
                one or more IP virtuals."
        ::= { mitelIpGrpIpVirtualGroup 1 }


        mitelIpVGrpPortEntry OBJECT-TYPE
            SYNTAX  MitelIpVGrpPortEntry
            MAX-ACCESS  not-accessible
            STATUS  current
            DESCRIPTION
                    "Each entry in this table contains configuration
                    information specific to a single IP interface."
            INDEX   { mitelIpVGrpPortTableNetAddr , mitelIpVGrpPortTableIfIndex }
            ::= { mitelIpVGrpPortTable 1 }


        MitelIpVGrpPortEntry ::=
            SEQUENCE {
                mitelIpVGrpPortTableNetAddr
                    IpAddress,
                mitelIpVGrpPortTableNetMask
                    IpAddress,
                mitelIpVGrpPortTableIfIndex
                   Integer32,
                mitelIpVGrpPortTableStatus
                   RowStatus,
                mitelIpVGrpPortTableCfgMethod
                   INTEGER
            }

        mitelIpVGrpPortTableNetAddr OBJECT-TYPE
            SYNTAX  IpAddress
            MAX-ACCESS  read-only
            STATUS  current
            DESCRIPTION
                    "The IP address that uniquely identifies this entry."
            ::= { mitelIpVGrpPortEntry 1 }


        mitelIpVGrpPortTableNetMask OBJECT-TYPE
            SYNTAX  IpAddress
            MAX-ACCESS  read-write
            STATUS  current
            DESCRIPTION
                    "The subnet mask assigned to this entry."
            ::= { mitelIpVGrpPortEntry 2 }


        mitelIpVGrpPortTableIfIndex OBJECT-TYPE
            SYNTAX Integer32
            MAX-ACCESS  read-only
            STATUS  current
            DESCRIPTION
                    "The interface that this virtual is associated
                    with."
            ::= { mitelIpVGrpPortEntry 11 }


        mitelIpVGrpPortTableStatus OBJECT-TYPE
            SYNTAX  RowStatus
            MAX-ACCESS  read-create
            STATUS  current
            DESCRIPTION
                    "The current status of this entry."
            REFERENCE
                    "Textual Conventions for Version 2 of the
                    Simple Network Management Protocol (RFC 1443)."
            ::= { mitelIpVGrpPortEntry 12 }


        mitelIpVGrpPortTableCfgMethod OBJECT-TYPE
            SYNTAX  INTEGER {
                        static(1),
                        addressless(2),
                        dhcp(3),
                        ipcp(4)
                    }
            MAX-ACCESS  read-write
            STATUS  current
            DESCRIPTION
                    "Determines how this virtual interface is configured.
                    `static' and `addressless' indicate that all information
                    is provided by the SNMP manager, while `dhcp' and `ipcp'
                    indicate that some or all of the information is obtained
                    dynamically. `static' and `dhcp' interfaces connect to
                    multipoint networks, in which case the
                    mitelIpVGrpPortTableNetMask indicates the IP subnet on
                    that network. `addressless' and `ipcp' interfaces connect
                    to point-to-point networks, and in these cases the
                    mitelIpVGrpPortTableNetMask is set to
                    255.255.255.255 and the corresponding IP address is that
                    of the system at the other end of the link."
            ::= { mitelIpVGrpPortEntry 15 }

--
--
--      The IP Virtual Port RIP Table.
--

    mitelIpVGrpRipTable OBJECT-TYPE
        SYNTAX  SEQUENCE OF MitelIpVGrpRipEntry
        MAX-ACCESS  not-accessible
        STATUS  current
        DESCRIPTION
                "This table contains RIP statistics per IP virtual
                interfaces."
        ::= { mitelIpGrpIpVirtualGroup 2 }


        mitelIpVGrpRipEntry OBJECT-TYPE
            SYNTAX  MitelIpVGrpRipEntry
            MAX-ACCESS  not-accessible
            STATUS  current
            DESCRIPTION
                    "Each entry in this table contains RIP statistics
                    specific to a single IP interface."
            INDEX   { mitelIpVGrpTableRipIpAddr }
            ::= { mitelIpVGrpRipTable 1 }


        MitelIpVGrpRipEntry ::=
            SEQUENCE {
				mitelIpVGrpTableRipIpAddr
					IpAddress,
                mitelIpVGrpTableRipRxPkts
                    Counter32,
                mitelIpVGrpTableRipRxBadPkts
                    Counter32,
                mitelIpVGrpTableRipRxBadRtes
                    Counter32,
                mitelIpVGrpTableRipTxUpdates
                    Counter32
            }

		mitelIpVGrpTableRipIpAddr OBJECT-TYPE
			SYNTAX IpAddress
			MAX-ACCESS read-only
			STATUS current
			DESCRIPTION
					"The IP Address that uniquely defines this entry"
			::= { mitelIpVGrpRipEntry 1}


        mitelIpVGrpTableRipRxPkts OBJECT-TYPE
            SYNTAX  Counter32
            MAX-ACCESS  read-only
            STATUS  current
            DESCRIPTION
                    "This object indicates the number of RIP packets
                    regardless of RIP type received on this virtual port."
            ::= { mitelIpVGrpRipEntry 2 }


        mitelIpVGrpTableRipRxBadPkts OBJECT-TYPE
            SYNTAX  Counter32
            MAX-ACCESS  read-only
            STATUS  current
            DESCRIPTION
                    "This object indicates the number of received packets
                    that contained incorrect header/packet definition
                    (ie: unsupported version(0), non-zero must be zero
                    fields)."
            ::= { mitelIpVGrpRipEntry 3 }


        mitelIpVGrpTableRipRxBadRtes OBJECT-TYPE
            SYNTAX  Counter32
            MAX-ACCESS  read-only
            STATUS  current
            DESCRIPTION
                    "This object indicates the number of received packet
                    entries that contained bad route information (ie:
                    unsupported family(AF_INET), bad metric or a
                    bad network address."
            ::= { mitelIpVGrpRipEntry 4 }


        mitelIpVGrpTableRipTxUpdates OBJECT-TYPE
            SYNTAX  Counter32
            MAX-ACCESS  read-only
            STATUS  current
            DESCRIPTION
                    "The number of updates sent on this interface."
            ::= { mitelIpVGrpRipEntry 5 }
END --MITEL-IPVIRTUAL-GROUP
