-- Copyright 1999 MITEL Corporation
-- All rights reserved.
-- This MITEL SNMP Management Information Base Specification
-- (Specification) embodies MITEL's confidential and
-- proprietary intellectual property. MITEL retains all
-- title and ownership in the Specification, including any
-- revisions.

-- This Specification is supplied "AS IS", and MITEL makes
-- no warranty, either express or implied, as to the use,
-- operation, condition, or performance of the Specification.


MITEL-DNSGROUP-MIB DEFINITIONS ::= BEGIN

IMPORTS
	MODULE-IDENTITY, OBJECT-TYPE, enterprises,
    IpAddress, Integer32
        FROM SNMPv2-SMI
    DisplayString, RowStatus
        FROM SNMPv2-TC;

mitelIpGrpDnsGroup MODULE-IDENTITY
	LAST-UPDATED      "200303210318Z"
	ORGANIZATION      "MITEL Corporation"
	CONTACT-INFO      "Standards Group,
	                   Postal:    MITEL Corporation
	                   350 Legget Drive, PO Box 13089
	                   Kanata, Ontario
	                   Canada  K2K 1X3
	                   Tel: +1 613 592 2122
	                   Fax: +1 613 592 4784
	                   E-mail: std@mitel.com"
	DESCRIPTION       "The MITEL DNS MIB module."
	REVISION          "200303210318Z"
	    DESCRIPTION   "Translate to SMIv2"
	REVISION          "199903010000Z"
	    DESCRIPTION   "DNS MIB Version 1.0"
::= { mitelRouterIpGroup 3}

mitel			   OBJECT IDENTIFIER ::= { enterprises 1027}
mitelProprietary 	   OBJECT IDENTIFIER ::= { mitel 4}
mitelPropIpNetworking      OBJECT IDENTIFIER ::= { mitelProprietary 8 }
mitelIpNetRouter           OBJECT IDENTIFIER ::= { mitelPropIpNetworking 1 }
mitelRouterIpGroup	   OBJECT IDENTIFIER ::= { mitelIpNetRouter 1 }

--  DNS MIB Definition
--

mitelDnsGrpDomainName OBJECT-TYPE
     SYNTAX  DisplayString (SIZE (0..255))
     MAX-ACCESS  read-write
     STATUS  current
     DESCRIPTION
	     "The Domain Name for this device."
      ::= { mitelIpGrpDnsGroup 1 }


mitelDnsGrpPrimaryDns OBJECT-TYPE
     SYNTAX  IpAddress
     MAX-ACCESS  read-write
     STATUS  current
     DESCRIPTION
	     "Address of Primary DNS Server."
     ::= { mitelIpGrpDnsGroup 2 }

mitelDnsGrpSecondaryDns OBJECT-TYPE
     SYNTAX  IpAddress
     MAX-ACCESS  read-write
     STATUS  current
     DESCRIPTION
	     "Address of Secondary DNS Server."
     ::= { mitelIpGrpDnsGroup 3 }

mitelDnsGrpQueryOrder OBJECT-TYPE
     SYNTAX INTEGER{
     		local-first(1),
			dns-first(2),
			dns-only(3)
	}
     MAX-ACCESS read-write
     STATUS current
     DESCRIPTION
     	     "Order which DNS is queried."
     ::= { mitelIpGrpDnsGroup 4 }

mitelDnsGrpAnswerTtl OBJECT-TYPE
     SYNTAX Integer32
     MAX-ACCESS read-write
     STATUS current
     DESCRIPTION
     	     "Answer TTL to return in locally generated responses."
     ::= { mitelIpGrpDnsGroup 5 }

mitelDnsGrpDnsPort OBJECT-TYPE
     SYNTAX Integer32
     MAX-ACCESS read-write
     STATUS current
     DESCRIPTION
     	     "Port to listen for DNS requests on."
     ::= { mitelIpGrpDnsGroup 6 }

mitelDnsGrpFilterEnabled OBJECT-TYPE
    SYNTAX INTEGER{
		enabled(1),
		disabled(2)
	}
    MAX-ACCESS read-write
    STATUS current
    DESCRIPTION
	    "DNS Security Filtering Status.  If Enabled, filter DNS quries
	     that are not from localhost."
    ::= { mitelIpGrpDnsGroup 7 }

--
--   DNS Stats Table
--

	mitelDnsGrpDnsStatistics OBJECT IDENTIFIER
	::= { mitelIpGrpDnsGroup 9 }

mitelDnsStatsQueryTotal OBJECT-TYPE
   SYNTAX Integer32
   MAX-ACCESS read-write
   STATUS current
   DESCRIPTION
   	   "Total DNS query count."
   ::= { mitelDnsGrpDnsStatistics 1 }

mitelDnsStatsQueryFiltered OBJECT-TYPE
   SYNTAX Integer32
   MAX-ACCESS read-write
   STATUS current
   DESCRIPTION
   	   "The number of queries filtered and rejected."
   ::= { mitelDnsGrpDnsStatistics 2 }

mitelDnsStatsQueryLocal OBJECT-TYPE
   SYNTAX Integer32
   MAX-ACCESS read-write
   STATUS current
   DESCRIPTION
   	   "The number of queries processed locally."
   ::= { mitelDnsGrpDnsStatistics 3 }

mitelDnsStatsQueryLocalFail OBJECT-TYPE
   SYNTAX Integer32
   MAX-ACCESS read-write
   STATUS current
   DESCRIPTION
   	   "The number of failed queries processed locally."
   ::= { mitelDnsGrpDnsStatistics 4 }

mitelDnsStatsQueryExternal OBJECT-TYPE
   SYNTAX Integer32
   MAX-ACCESS read-write
   STATUS current
   DESCRIPTION
   	   "The number of queries forwarded to an external DNS."
   ::= { mitelDnsGrpDnsStatistics 5 }

mitelDnsStatsQueryExternalFail OBJECT-TYPE
   SYNTAX Integer32
   MAX-ACCESS read-write
   STATUS current
   DESCRIPTION
   	   "The number of queries forwarded to an external DNS that failed."
   ::= { mitelDnsGrpDnsStatistics 6 }

mitelDnsStatsQueryInvalid OBJECT-TYPE
   SYNTAX Integer32
   MAX-ACCESS read-write
   STATUS current
   DESCRIPTION
   	   "The number of invalid queries."
   ::= { mitelDnsGrpDnsStatistics 7 }

--
--   Table of DNS Entries
--

mitelDnsGrpDnsHostTable OBJECT-TYPE
   SYNTAX SEQUENCE OF MitelDnsGrpDnsHostEntry
   MAX-ACCESS not-accessible
   STATUS current
   DESCRIPTION
   	   "This table contains a list of IP addresses and their associated Host Names."
   ::={ mitelIpGrpDnsGroup 10 }

mitelDnsGrpDnsHostEntry OBJECT-TYPE
   SYNTAX MitelDnsGrpDnsHostEntry
   MAX-ACCESS not-accessible
   STATUS current
   DESCRIPTION
          "DNS information"
   INDEX { mitelDnsHostTableIpAddress, mitelDnsHostTableHostName }
   ::={ mitelDnsGrpDnsHostTable 1 }

MitelDnsGrpDnsHostEntry ::= SEQUENCE {
	mitelDnsHostTableIpAddress	IpAddress,
	mitelDnsHostTableHostName DisplayString,
	mitelDnsHostTableRowStatus  RowStatus
}

mitelDnsHostTableIpAddress OBJECT-TYPE
   SYNTAX IpAddress
   MAX-ACCESS read-write
   STATUS current
   DESCRIPTION
           "The IP address to be associated with mitelDnsHostTableHostName"
   ::= { mitelDnsGrpDnsHostEntry 1 }

mitelDnsHostTableHostName OBJECT-TYPE
   SYNTAX DisplayString (SIZE(0..100))
   MAX-ACCESS read-write
   STATUS current
   DESCRIPTION
           "The entry's Host Name"
   ::= { mitelDnsGrpDnsHostEntry 2 }

mitelDnsHostTableRowStatus OBJECT-TYPE
   SYNTAX RowStatus
   MAX-ACCESS read-create
   STATUS current
   DESCRIPTION
           "The current status of this entry"
   ::= { mitelDnsGrpDnsHostEntry 3 }


END -- MITEL-DNSGROUP-MIB
