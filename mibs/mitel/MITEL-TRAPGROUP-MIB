-- Copyright 2002 MITEL Networks Corporation
-- All rights reserved.
-- This MITEL SNMP Management Information Base Specification
-- (Specification) embodies MITEL's confidential and
-- proprietary intellectual property. MITEL retains all
-- title and ownership in the Specification, including any
-- revisions.

-- This Specification is supplied "AS IS", and MITEL makes
-- no warranty, either express or implied, as to the use,
-- operation, condition, or performance of the Specification.


MITEL-TRAPGROUP-MIB
	DEFINITIONS ::= BEGIN

IMPORTS
	MODULE-IDENTITY, OBJECT-TYPE, enterprises,Integer32
        FROM SNMPv2-SMI;

mitelRouterSnmpTrapGroup MODULE-IDENTITY
       LAST-UPDATED      "200303241050Z"
       ORGANIZATION      "MITEL Networks Corporation"
       CONTACT-INFO      "Standards Group,
                          Postal:    MITEL Corporation
                          350 Legget Drive, PO Box 13089
                          Kanata, Ontario
                          Canada  K2K 1X3
                          Tel: +1 613 592 2122
                          Fax: +1 613 592 4784
                          E-mail: std@mitel.com"
       DESCRIPTION       "The Mitel IP Networking Trap MIB."
       REVISION          "200303241050Z"
		DESCRIPTION      "Convert to SMIv2"
       REVISION          "200204020000Z"
		DESCRIPTION      "Mitel IP Networking Trap MIB version 1.0"
::= { mitelIpNetRouter 7 }

mitel			   OBJECT IDENTIFIER ::= { enterprises 1027}
mitelProprietary 	   OBJECT IDENTIFIER ::= { mitel 4}
mitelPropIpNetworking      OBJECT IDENTIFIER ::= { mitelProprietary 8 }
mitelIpNetRouter           OBJECT IDENTIFIER ::= { mitelPropIpNetworking 1 }


-- the Mitel IP Networking Trap Filter Group

mitelSnmpTrapGlobal OBJECT-TYPE
	SYNTAX INTEGER {
			enable(1),
			disable(2)
		}
	MAX-ACCESS  read-write
    STATUS  current
    DESCRIPTION
        "Enable/disable all traps sending traps to remote locations."
    ::= { mitelRouterSnmpTrapGroup 1 }

mitelSnmpTrapControl OBJECT-TYPE
     SYNTAX  Integer32
     MAX-ACCESS  read-write
     STATUS  current
     DESCRIPTION
        "A bit string used to represent the enable/disable state of all traps in
		in the system.

		The bit positions are:
		   1     Cold Start
		   2     Link Down
		   4     Link Up
		   8     Authentication Failure
		   16    New Root (Rfc 1493)
		   32    Topology Change (Rfc 1493)
		   64    Mitel IP Access Restriction
		   128   Mitel Retry Threshold Reached
		   256   Mitel DHCP Client Obtained IP
		   512   Mitel DHCP Client Lease Expired
		   1024  Mitel Call Control Failed to Seize Line
		   2048  Mitel Call Control DDI Mapping Error
		   4096  Mitel Voice Mail Disk Nearly Full
		   8192  Mitel Voice Mail Disk Full
		   16384 DSX1 Line Status
		   32768 Mitel Application Monitor Task Crashed"
    ::= { mitelRouterSnmpTrapGroup 2 }

END -- MITEL-TRAPGROUP-MIB
