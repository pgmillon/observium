-- Copyright 1999 MITEL Corporation
-- All rights reserved.
-- This MITEL SNMP Management Information Base Specification
-- (Specification) embodies MITEL's confidential and
-- proprietary intellectual property. MITEL retains all
-- title and ownership in the Specification, including any
-- revisions.

-- This Specification is supplied "AS IS", and MITEL makes
-- no warranty, either express or implied, as to the use,
-- operation, conWCM_EVENT_STRUCT_tdition, or performance of the Specification.

MITEL-LOGICAL-MIB

DEFINITIONS ::= BEGIN

IMPORTS
	MODULE-IDENTITY, OBJECT-TYPE, enterprises,
    Integer32, NOTIFICATION-TYPE
        FROM SNMPv2-SMI
    NOTIFICATION-GROUP
    	FROM SNMPv2-CONF
    RowStatus, DisplayString
        FROM SNMPv2-TC;

mitelRouterLogicalGroup MODULE-IDENTITY
       LAST-UPDATED      "200303240947Z"
       ORGANIZATION      "MITEL Corporation"
       CONTACT-INFO      "Standards Group,
                          Postal:    MITEL Corporation
                          350 Legget Drive, PO Box 13089
                          Kanata, Ontario
                          Canada  K2K 1X3
                          Tel: +1 613 592 2122
                          Fax: +1 613 592 4784
                          E-mail: std@mitel.com"
       DESCRIPTION       "The MITEL Logical MIB module."
       REVISION          "200303240947Z"
           DESCRIPTION   "Convert to SMIv2"
       REVISION          "199903010000Z"
           DESCRIPTION   "Logical MIB Version 1.0"
::= { mitelIpNetRouter 4 }

mitel			   OBJECT IDENTIFIER ::= { enterprises 1027}
mitelProprietary 	   OBJECT IDENTIFIER ::= { mitel 4}
mitelPropIpNetworking      OBJECT IDENTIFIER ::= { mitelProprietary 8 }
mitelIpNetRouter OBJECT IDENTIFIER::={ mitelPropIpNetworking 1 }

-- NOTIFICATIONS
mitelIdentification 	  OBJECT IDENTIFIER ::= { mitel 1}
mitelIdCallServers 	  OBJECT IDENTIFIER ::= { mitelIdentification 2}
mitelIdCsIpera1000 	  OBJECT IDENTIFIER ::= { mitelIdCallServers 4}


--
--      LAN DESTINATION GROUP OBJECTS
--      =============================
--

	mitelLogGrpLogicalTable OBJECT-TYPE
		SYNTAX  SEQUENCE OF MitelLogGrpLogicalEntry
		MAX-ACCESS  not-accessible
		STATUS  current
		DESCRIPTION
			"A table containing information about logical LAN
			destinations."
		::= { mitelRouterLogicalGroup 1 }


			mitelLogGrpLogicalEntry OBJECT-TYPE
				SYNTAX  MitelLogGrpLogicalEntry
				MAX-ACCESS  not-accessible
				STATUS  current
				DESCRIPTION
					"Each entry of this table contains information about
					a specific logical interface to a local area network.
					Each logical LAN can support routing
					functions, these are considered virtual interfaces.
					The logical LAN can be permanently attached to a
					physical port (LAN or WAN) or it can float among
					available physical resources (WAN's only)."
				INDEX   { mitelLogicalTblIndex }
				::= { mitelLogGrpLogicalTable 1 }


			MitelLogGrpLogicalEntry ::=
				SEQUENCE {
					mitelLogicalTblIndex
						Integer32,
					mitelLogicalTblDestName
						DisplayString,
					mitelLogicalTblType
						INTEGER,
					mitelLogicalTblAdminStatus
						INTEGER
				}

			mitelLogicalTblIndex OBJECT-TYPE
				SYNTAX  Integer32
				MAX-ACCESS  read-only
				STATUS  current
				DESCRIPTION
					"This object identifies the instance of this
					entry in the table."
				::= { mitelLogGrpLogicalEntry 1 }

			mitelLogicalTblDestName OBJECT-TYPE
				SYNTAX  DisplayString (SIZE (1..16))
				MAX-ACCESS  read-write
				STATUS  current
				DESCRIPTION
					"The Ascii string associated with this logical
					destination LAN. Default is Net N (N is
					mitelLogicalTblIndex)."
				::= { mitelLogGrpLogicalEntry 2 }

			mitelLogicalTblType OBJECT-TYPE
				SYNTAX  INTEGER {
					local(1),
					remote(2)
				}
				MAX-ACCESS  read-only
				STATUS  current
				DESCRIPTION
					"This object determines whether this network
					interface is locally connected to a LAN or is
					connected to a LAN via a WAN. If this object
					is set to local(1) then this interface is
					associated with one of the physical LAN interfaces
					via the ifIndex. If this object indicates remote(2)
					then this network is reachable through a wide area
					network (WAN) as described in mitelLogGrpLogicalWanTable."
				::= { mitelLogGrpLogicalEntry 3 }

			mitelLogicalTblAdminStatus OBJECT-TYPE
				SYNTAX  INTEGER {
					up(1),
					down(2)
				}
				MAX-ACCESS  read-write
				STATUS  current
				DESCRIPTION
					"The current desired state of this sub-layer. Default is
					down."
				DEFVAL { 2 }
				::= { mitelLogGrpLogicalEntry 4 }


--
--    The Logical WAN Table.
--

	mitelLogGrpLogicalWanTable OBJECT-TYPE
		SYNTAX  SEQUENCE OF MitelLogGrpLogicalWanEntry
		MAX-ACCESS  not-accessible
		STATUS  current
		DESCRIPTION
			"A table containing configuration parameters for
			wide area network connections to logical LAN destinations
			that are accessible via interfaces. Each entry
			is logically tied to a logical LAN destination entry
			via mitelLogicalTblIndex."
		::= { mitelRouterLogicalGroup 2 }


		mitelLogGrpLogicalWanEntry OBJECT-TYPE
			SYNTAX  MitelLogGrpLogicalWanEntry
			MAX-ACCESS  not-accessible
			STATUS  current
			DESCRIPTION
				"Each entry of this table contains information about
				a specific logical interface to a REMOTELY connected
				local area network. The instance of mitelLogicalTblIndex
				used to	index into this table is the same instance value
				used to index into the grLogicalTable."
			INDEX   { mitelLogicalTblIndex }
			::= { mitelLogGrpLogicalWanTable 1 }


		MitelLogGrpLogicalWanEntry ::=
			SEQUENCE {
				mitelLogWanTblCmprsn
					INTEGER,
				mitelLogWanTblCmprsnStatus
					INTEGER,
				mitelLogWanTblEncryptn
					INTEGER,
				mitelLogWanTblBackupOvrflow
					INTEGER,
				mitelLogWanTblThshld
					INTEGER,
				mitelLogWanTblConnTimer
					INTEGER,
				mitelLogWanTblDiscTimer
					INTEGER,
				mitelLogWanTblProtocolType
					INTEGER
			}


		mitelLogWanTblCmprsn OBJECT-TYPE
			SYNTAX  INTEGER {
				none(1),
				any(2),
				gandalf(3),
				stac(4)
			}
			MAX-ACCESS  read-write
			STATUS  current
			DESCRIPTION
				"This object indicates whether or not this interface
				is to perform data compression. Default is none."
			DEFVAL { 1 }
			::= { mitelLogGrpLogicalWanEntry 1 }


		mitelLogWanTblCmprsnStatus OBJECT-TYPE
			SYNTAX INTEGER {
				none(1),
				fza(2),
				fzap(3),
				concryption(4),
				encryption(5),
				stacNoCheckMode(6),
				stacLCBCheckMode(7),
				stacCRCCheckMode(8),
				stacSeqNumbers(9),
				stacExtendedMode(10),
				stacAscendLCBMode(11)
			}
			MAX-ACCESS  read-only
			STATUS  current
			DESCRIPTION
				"This object describes the type of compression used on
				this destination."
			::= { mitelLogGrpLogicalWanEntry 2}

		mitelLogWanTblEncryptn OBJECT-TYPE
			SYNTAX  INTEGER{
				enabled(1),
				disabled(2)
			}
			MAX-ACCESS  read-write
			STATUS  current
			DESCRIPTION
				"This object describes whether or not PPP encryption is
				proposed to the peer. Default is disabled."
			DEFVAL { 2 }
			::= { mitelLogGrpLogicalWanEntry 3}

		mitelLogWanTblBackupOvrflow OBJECT-TYPE
			SYNTAX  INTEGER {
				disabled(1),
				backup(2),
				overflow(3)
			}
			MAX-ACCESS  read-write
			STATUS  current
			DESCRIPTION
				"This object determines if this interface is to
				attempt to bring up another link to the same
				destination if the traffic over the primary link
				exceeds a pre-determined threshold, in the case of
				overflow(3). Otherwise, if backup(2) is selected
				the interface will bring up an alternate link to
				the same destination in the case that the primary
				link fails. Default is disabled(1)."
			DEFVAL { 1 }
			::= { mitelLogGrpLogicalWanEntry 4 }


		mitelLogWanTblThshld OBJECT-TYPE
			SYNTAX  INTEGER (0..100)
			MAX-ACCESS  read-write
			STATUS  current
			DESCRIPTION
				"This object determines the transmit threshold which
				when exceeded will cause an attempt to bring up another
				path. The returned value of this object has no meaning
				when threshold overflow is not enabled. Default is 80."
			DEFVAL { 80 }
			::= { mitelLogGrpLogicalWanEntry 5 }


		mitelLogWanTblConnTimer OBJECT-TYPE
			SYNTAX  INTEGER (1..3600)
			MAX-ACCESS  read-write
			STATUS  current
			DESCRIPTION
				"When threshold overflow is enabled this object
				determines the amount of time in seconds that
				the average threshold must be exceeded (or below) before another
				link is established (or disconnected). Default is 30."
			DEFVAL { 30 }
			::= { mitelLogGrpLogicalWanEntry 6 }


		mitelLogWanTblDiscTimer OBJECT-TYPE
			SYNTAX  INTEGER (0..3600)
			MAX-ACCESS  read-write
			STATUS  current
			DESCRIPTION
				"The time a non-permanent link will remain connected without traffic. Default is 30."
			DEFVAL { 30 }
			::= { mitelLogGrpLogicalWanEntry 7 }

		mitelLogWanTblProtocolType OBJECT-TYPE
			SYNTAX  INTEGER{
				ppp(1),
				framerelay(2),
				x25(3)
			}
			MAX-ACCESS  read-write
			STATUS  current
			DESCRIPTION
				"The protocol type that this destination is over.
				Default is ppp."
			DEFVAL { 1 }
			::= { mitelLogGrpLogicalWanEntry 8}

--
--
--    The Logical WAN Port Binding table.
--

	mitelLogGrpLogicalWanPortTable OBJECT-TYPE
		SYNTAX  SEQUENCE OF MitelLogGrpLogicalWanPortEntry
		MAX-ACCESS  not-accessible
		STATUS  current
		DESCRIPTION
			"This configuration table identifies the characteristics
			of each potential transportation pipe to a remote
			site.  Each entry in this table is associated with an
			entry in the grLogWanTable via its mitelLogicalTblIndex.
			Multiple entries can be associated with a single entry
			in the mitelLogGrpLogicalWanTable."
		::= { mitelRouterLogicalGroup 3 }


		mitelLogGrpLogicalWanPortEntry OBJECT-TYPE
			SYNTAX  MitelLogGrpLogicalWanPortEntry
			MAX-ACCESS  not-accessible
			STATUS  current
			DESCRIPTION
				"Each entry of this table contains information about
				a single WAN resource used by a logical interface to
				a remote local area network. The instance of
				mitelLogicalTblIndex used to index into this table is
				the same instance value used to index into the
				mitelLogicalTable. Multiple entries in this table
				having the same mitelLogicalTblIndex usually indicates
				backup or multi-linking functionality."
			INDEX   { mitelLogicalTblIndex, mitelLogWanPortTblIndex }
			::= { mitelLogGrpLogicalWanPortTable 1 }


		MitelLogGrpLogicalWanPortEntry ::=
			SEQUENCE {
				mitelLogWanPortTblIndex
					Integer32,
				mitelLogWanPortTblWanType
					INTEGER,
				mitelLogWanPortTblTransType
					INTEGER,
				mitelLogWanPortTblRetry
					INTEGER,
				mitelLogWanPortTblRetryPeriod
					INTEGER,
				mitelLogWanPortTblPrepend
					OCTET STRING,
				mitelLogWanPortTblDestAddr
					DisplayString,
				mitelLogWanPortTblNextDestAddr
					DisplayString,
				mitelLogWanPortTblChId
					INTEGER,
				mitelLogWanPortTblDialback
					INTEGER,
				mitelLogWanPortTblAdminStatus
					INTEGER,
				mitelLogWanPortTblOperStatus
					INTEGER,
				mitelLogWanPortTblStatus
					RowStatus
			}


		mitelLogWanPortTblIndex OBJECT-TYPE
			SYNTAX  Integer32
			MAX-ACCESS  read-only
			STATUS  current
			DESCRIPTION
				"Identifies the port index associated with this
				entry."
			::= { mitelLogGrpLogicalWanPortEntry 1 }


		mitelLogWanPortTblWanType OBJECT-TYPE
			SYNTAX  INTEGER {
				permanent(1),
				ondemand(2),
				incomming(3),
				outgoing(4)
			}
			MAX-ACCESS  read-write
			STATUS  current
			DESCRIPTION
				"Indicates whether or not this link is to be used
				as a  permanent or ondemand link. Default is
				ondemand"
			DEFVAL { 2 }
			::= { mitelLogGrpLogicalWanPortEntry 2 }


		mitelLogWanPortTblTransType OBJECT-TYPE
			SYNTAX  INTEGER{
				hdlc(1),
				modem(2),
				ethernet(3)
			}
			MAX-ACCESS  read-write
			STATUS  current
			DESCRIPTION
				"The transport type that this destination is over.
				Default is HDLC."
			DEFVAL { 1 }
			::= { mitelLogGrpLogicalWanPortEntry 3}


		mitelLogWanPortTblRetry OBJECT-TYPE
			SYNTAX  INTEGER (0..99)
			MAX-ACCESS  read-write
			STATUS  current
			DESCRIPTION
				"Determines the retry count for dial up WAN
				circuits. Default is 10."
			DEFVAL { 10 }
			::= { mitelLogGrpLogicalWanPortEntry 4 }


		mitelLogWanPortTblRetryPeriod OBJECT-TYPE
			SYNTAX  INTEGER (0..99)
			MAX-ACCESS  read-write
			STATUS  current
			DESCRIPTION
				"Determines the retry period in seconds for dial
				up WAN circuits. Default is 10 seconds."
			DEFVAL { 10 }
			::= { mitelLogGrpLogicalWanPortEntry 5 }


		mitelLogWanPortTblPrepend OBJECT-TYPE
			SYNTAX  OCTET STRING (SIZE(3))
			MAX-ACCESS  read-write
			STATUS  current
			DESCRIPTION
				"Indicates in most cases an Ascii string that will
				be prepended to the destination address. Default is
				NULL."
			::= { mitelLogGrpLogicalWanPortEntry 6 }


		mitelLogWanPortTblDestAddr OBJECT-TYPE
			SYNTAX  DisplayString (SIZE (1..20))
			MAX-ACCESS  read-write
			STATUS  current
			DESCRIPTION
				"Indicates the destination address that this
				interface will call (ie: phone number). Default
				is NULL."
			::= { mitelLogGrpLogicalWanPortEntry 7 }


		mitelLogWanPortTblNextDestAddr OBJECT-TYPE
			SYNTAX  DisplayString (SIZE (1..20))
			MAX-ACCESS  read-write
			STATUS  current
			DESCRIPTION
				"Indicates the next destination address that this
				interface will call (ie: phone number). Default is
				NULL."
			::= { mitelLogGrpLogicalWanPortEntry 8 }


		mitelLogWanPortTblChId OBJECT-TYPE
			SYNTAX  INTEGER (0..65535)
			MAX-ACCESS  read-write
			STATUS  current
			DESCRIPTION
				"This object is a unique identifier for this network
				channel.  e.g. DLCI for frame-relay.  The value must be within
				the defined range or if not used the DEFAULT value should be
				0."
			DEFVAL { 0 }
			::= { mitelLogGrpLogicalWanPortEntry 9 }


		mitelLogWanPortTblDialback OBJECT-TYPE
			SYNTAX  INTEGER{
				enable(1),
				disable(2)
			}
			MAX-ACCESS  read-write
			STATUS  current
			DESCRIPTION
				"Enables/disables dialback option.  If enabled the system
				will drop the link and then dial the user back using the
				configured dial string or a dial string reported from an
				authentication server.  Default is disabled."
			DEFVAL { 2 }
			::= { mitelLogGrpLogicalWanPortEntry 10 }


		mitelLogWanPortTblAdminStatus OBJECT-TYPE
			SYNTAX  INTEGER {
				up(1),
				down(2)
			}
			MAX-ACCESS  read-write
			STATUS  current
			DESCRIPTION
				"The current desired state of this sub-layer. Default is
				down."
			DEFVAL { 2 }
			::= { mitelLogGrpLogicalWanPortEntry 11 }


		mitelLogWanPortTblOperStatus OBJECT-TYPE
			SYNTAX  INTEGER {
				connecting(1),
				connected(2),
				disconnecting(3),
				disconnected(4),
				retryExhausted(5)
			}
			MAX-ACCESS  read-only
			STATUS  current
			DESCRIPTION
				"The current active state of this sub-layer."
			::= { mitelLogGrpLogicalWanPortEntry 12 }


		mitelLogWanPortTblStatus OBJECT-TYPE
			SYNTAX  RowStatus
			MAX-ACCESS  read-create
			STATUS  current
			DESCRIPTION
				"The current status of this entry."
			REFERENCE
				"Textual Conventions for Version 2 of the
				Simple Network Management Protocol (RFC 1443)."
			::= { mitelLogGrpLogicalWanPortEntry 13 }

-- NOTIFICATION-TYPE Definitions
	mitelIpera1000Notifications NOTIFICATION-GROUP
        NOTIFICATIONS	{ mitelWanRetryThreshold }
        STATUS            current
        DESCRIPTION       "Notifications for Call Server IPera 1000."
        ::= { mitelIdCsIpera1000 0 }


	mitelWanRetryThreshold NOTIFICATION-TYPE
		OBJECTS {mitelLogWanPortTblStatus}
		STATUS          current
		DESCRIPTION     "The mitelWanRetryThreshold trap is generated by the
			router whenever the maximum number of retries have
			been exhausted when attempting to contact a remote
			site on a specific serial interface. The mitelLogicalTblIndex will
			provided in the variable bindings for this trap type."
		::= { mitelIpera1000Notifications 403 }
END
