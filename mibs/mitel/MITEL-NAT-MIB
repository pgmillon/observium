-- Copyright 1999 MITEL Corporation
-- All rights reserved.
-- This MITEL SNMP Management Information Base Specification
-- (Specification) embodies MITEL's confidential and
-- proprietary intellectual property. MITEL retains all
-- title and ownership in the Specification, including any
-- revisions.

-- This Specification is supplied "AS IS", and MITEL makes
-- no warranty, either express or implied, as to the use,
-- operation, condition, or performance of the Specification.

MITEL-NAT-MIB
DEFINITIONS ::= BEGIN

IMPORTS
	MODULE-IDENTITY, OBJECT-TYPE, enterprises,
    Integer32, IpAddress
        FROM SNMPv2-SMI
    RowStatus
        FROM SNMPv2-TC;
mitelIpGrpNatGroup         MODULE-IDENTITY
       LAST-UPDATED      "200303241001Z"
       ORGANIZATION      "MITEL Corporation"
       CONTACT-INFO      "Standards Group,
                          Postal:    MITEL Corporation
                          350 Legget Drive, PO Box 13089
                          Kanata, Ontario
                          Canada  K2K 1X3
                          Tel: +1 613 592 2122
                          Fax: +1 613 592 4784
                          E-mail: std@mitel.com"
       DESCRIPTION       "The MITEL IP MIB module."
       REVISION          "200303241001Z"
           DESCRIPTION   "Convert to SMIv2"
       REVISION          "199903010000Z"
           DESCRIPTION   "IP MIB Version 1.0"
::= { mitelRouterIpGroup 2}

mitel			   OBJECT IDENTIFIER ::= { enterprises 1027}
mitelProprietary 	   OBJECT IDENTIFIER ::= { mitel 4}
mitelPropIpNetworking      OBJECT IDENTIFIER ::= { mitelProprietary 8 }
mitelIpNetRouter           OBJECT IDENTIFIER ::= { mitelPropIpNetworking 1 }
mitelRouterIpGroup	   OBJECT IDENTIFIER ::= { mitelIpNetRouter 1}

--
--
--
--     IP NAT Interface Objects.
--

    mitelNatGrpIfTable OBJECT-TYPE
        SYNTAX  SEQUENCE OF MitelNatGrpIfEntry
        MAX-ACCESS  not-accessible
        STATUS  current
        DESCRIPTION
                "The IP network address translation configuration table."
        ::= { mitelIpGrpNatGroup 1 }


        mitelNatGrpIfEntry OBJECT-TYPE
            SYNTAX  MitelNatGrpIfEntry
            MAX-ACCESS  not-accessible
            STATUS  current
            DESCRIPTION
                    "Contains information about network address
		    translation on a single IP interface."
            INDEX   { mitelNatGrpIfAddr }
            ::= { mitelNatGrpIfTable 1 }


        MitelNatGrpIfEntry ::=
            SEQUENCE {
               mitelNatGrpIfAddr
                  IpAddress,
               mitelNatGrpIfEnable
                  INTEGER,
               mitelNatGrpIfUdpLifetime
                  Integer32,
               mitelNatGrpIfTcpLifetime
                  Integer32,
               mitelNatGrpIfTcpFinLifetime
                  Integer32,
               mitelNatGrpIfTcpRstLifetime
                  Integer32,
               mitelNatGrpIfPingLifetime
                  Integer32,
			   mitelNatGrpIfStatus
                  RowStatus,
               mitelNatGrpIfIndex
                  Integer32
            }

        mitelNatGrpIfAddr OBJECT-TYPE
            SYNTAX  IpAddress
            MAX-ACCESS  read-only
            STATUS  current
            DESCRIPTION
                    "The IP address of the interface."
            ::= { mitelNatGrpIfEntry 1 }

	mitelNatGrpIfEnable OBJECT-TYPE
	    SYNTAX  INTEGER {
		       enabled(1),
		       disabled(2)
		    }
	    MAX-ACCESS  read-write
	    STATUS  current
	    DESCRIPTION
		    "Configures the router to enable IP NAT on a
		    virtual interface."
	    DEFVAL { 2 }
	    ::= { mitelNatGrpIfEntry 2 }

        mitelNatGrpIfUdpLifetime OBJECT-TYPE
            SYNTAX  Integer32
            MAX-ACCESS  read-write
            STATUS  current
            DESCRIPTION
                    "Specifies timeout in seconds for a NAT UDP session."
	    DEFVAL { 900 }
            ::= { mitelNatGrpIfEntry 3 }


        mitelNatGrpIfTcpLifetime OBJECT-TYPE
            SYNTAX  Integer32
            MAX-ACCESS  read-write
            STATUS  current
            DESCRIPTION
                    "Specifies timeout in seconds for a NAT TCP session."
	    DEFVAL { 900 }
            ::= { mitelNatGrpIfEntry 4 }


        mitelNatGrpIfTcpFinLifetime OBJECT-TYPE
            SYNTAX  Integer32
            MAX-ACCESS  read-write
            STATUS  current
            DESCRIPTION
                    "Specifies timeout in seconds for a NAT TCP session once a FIN was seen."
	    DEFVAL { 120 }
            ::= { mitelNatGrpIfEntry 5 }


        mitelNatGrpIfTcpRstLifetime OBJECT-TYPE
            SYNTAX  Integer32
            MAX-ACCESS  read-write
            STATUS  current
            DESCRIPTION
                    "Specifies timeout in seconds for a NAT TCP session once a RST was seen."
	    DEFVAL { 120 }
            ::= { mitelNatGrpIfEntry 6 }


        mitelNatGrpIfPingLifetime OBJECT-TYPE
            SYNTAX  Integer32
            MAX-ACCESS  read-write
            STATUS  current
            DESCRIPTION
                    "Specifies timeout in seconds for an ICMP echo."
	    DEFVAL { 120 }
            ::= { mitelNatGrpIfEntry 7 }

        mitelNatGrpIfStatus OBJECT-TYPE
            SYNTAX  RowStatus
            MAX-ACCESS  read-create
            STATUS  current
            DESCRIPTION
                    "The current status of this entry."
            REFERENCE
                    "Textual Conventions for Version 2 of the
                    Simple Network Management Protocol (RFC 1443)."
            ::= { mitelNatGrpIfEntry 8 }

        mitelNatGrpIfIndex OBJECT-TYPE
            SYNTAX  Integer32
            MAX-ACCESS  read-only
            STATUS  current
            DESCRIPTION
                    "The current Interface this entry pertains to."
            ::= { mitelNatGrpIfEntry 9 }
--
--
--
--     IP NAT Redirection Objects.
--

    mitelNatGrpRedirTable OBJECT-TYPE
        SYNTAX  SEQUENCE OF MitelNatGrpRedirEntry
        MAX-ACCESS  not-accessible
        STATUS  current
        DESCRIPTION
                "The IP network address translation redirection table."
        ::= { mitelIpGrpNatGroup 2 }


        mitelNatGrpRedirEntry OBJECT-TYPE
            SYNTAX  MitelNatGrpRedirEntry
            MAX-ACCESS  not-accessible
            STATUS  current
            DESCRIPTION
                    "Contains information about network address
		    translation incoming on a single IP interface."
            INDEX   { mitelNatGrpRedirOldAddr, mitelNatGrpRedirProto, mitelNatGrpRedirOldPort }
            ::= { mitelNatGrpRedirTable 1 }


        MitelNatGrpRedirEntry ::=
            SEQUENCE {
               mitelNatGrpRedirOldAddr
                  IpAddress,
               mitelNatGrpRedirProto
                  Integer32,
               mitelNatGrpRedirOldPort
                  Integer32,
               mitelNatGrpRedirNewAddr
                  IpAddress,
               mitelNatGrpRedirNewPort
                  Integer32,
	       mitelNatGrpRedirStatus
                  RowStatus
            }

        mitelNatGrpRedirOldAddr OBJECT-TYPE
            SYNTAX  IpAddress
            MAX-ACCESS  read-only
            STATUS  current
            DESCRIPTION
                    "The IP address of the interface."
            ::= { mitelNatGrpRedirEntry 1 }

	mitelNatGrpRedirProto OBJECT-TYPE
	    SYNTAX  Integer32
	    MAX-ACCESS  read-only
	    STATUS  current
	    DESCRIPTION
		    "Identifies the IP protocol to redirect, 6 or 17."
	    ::= { mitelNatGrpRedirEntry 2 }

	mitelNatGrpRedirOldPort OBJECT-TYPE
	    SYNTAX  Integer32
	    MAX-ACCESS  read-only
	    STATUS  current
	    DESCRIPTION
		    "Identifies the TCP or UDP port to redirect."
	    ::= { mitelNatGrpRedirEntry 3 }

        mitelNatGrpRedirNewAddr OBJECT-TYPE
            SYNTAX  IpAddress
            MAX-ACCESS  read-write
            STATUS  current
            DESCRIPTION
                    "The IP address to which the datagram is to be redirected.  Default is 0.0.0.0 "
            ::= { mitelNatGrpRedirEntry 4 }

	mitelNatGrpRedirNewPort OBJECT-TYPE
	    SYNTAX  Integer32
	    MAX-ACCESS  read-write
	    STATUS  current
	    DESCRIPTION
		    "The TCP or UDP port to which the datagram is to be redirected."
	    DEFVAL { 0 }
	    ::= { mitelNatGrpRedirEntry 5 }

        mitelNatGrpRedirStatus OBJECT-TYPE
            SYNTAX  RowStatus
            MAX-ACCESS  read-create
            STATUS  current
            DESCRIPTION
                    "The current status of this entry."
            REFERENCE
                    "Textual Conventions for Version 2 of the
                    Simple Network Management Protocol (RFC 1443)."
            ::= { mitelNatGrpRedirEntry 6 }

END
