Avaya-46xxIPTelephone-MIB 
DEFINITIONS ::= BEGIN     
IMPORTS
        	enterprises, OBJECT-TYPE, MODULE-IDENTITY, Integer32, IpAddress
                FROM SNMPv2-SMI 
   		DisplayString 
		FROM RFC1213-MIB ;

endpointMIB MODULE-IDENTITY
	     	LAST-UPDATED     "0612052000Z"
    		 ORGANIZATION     "avaya"
        		CONTACT-INFO     "Avaya Customer Services
				Avaya, Inc.
				211 Mt. Airy Road
				Basking Ridge, NJ 07920 USA

    	                        WWW: www.avaya.com

        	                  Tel: +1 908 953 6000"
	      DESCRIPTION "MIB Module for 46xx IP Telephones through Release 2.8
				in accordance with 46xx Common Requirements COMPAS 75441, Issue 2.8.
				Copyright 2006 by Avaya Inc.  All rights reserved."
	            ::= { avayaipEndpointMIBs 1 }

avaya           		OBJECT IDENTIFIER ::= { enterprises 6889 }
avayaProducts  			OBJECT IDENTIFIER ::= { avaya 1 }
avayaMibs            		OBJECT IDENTIFIER ::= { avaya 2 }
avayaipEndpointProd    	OBJECT IDENTIFIER ::= { avayaProducts 69 }
avayaipEndpointMIBs  	OBJECT IDENTIFIER ::= { avayaMibs 69 }

endptID         OBJECT IDENTIFIER ::= { endpointMIB 1 }
endptMARKET     OBJECT-TYPE
                    SYNTAX      DisplayString
                    MAX-ACCESS  read-only
                    STATUS      obsolete
                    DESCRIPTION "ID designation. This variable returns a 
		string specifying 'domestic' or 'export'."
                    ::= { endptID 1 }
endptMODEL      OBJECT-TYPE
                    SYNTAX      DisplayString
                    MAX-ACCESS  read-only
                    STATUS      current
                    DESCRIPTION "Model identifier. This variable returns 
		a string of up to 8 ASCII characters."
                    ::= { endptID 2 }
endptMCIPADD    OBJECT-TYPE                   
                    SYNTAX      DisplayString                   
                    MAX-ACCESS  read-only
                    STATUS      current
                    DESCRIPTION "List of call server addresses.  This 
		variable returns a sequence of IP addresses, in 
		dotted-decimal orDNS format and separated by  
		commas, of call server IP addresses available 
                        for use."
                    ::= { endptID 3 }
endptMCIPINUSE    OBJECT-TYPE
                    SYNTAX      IpAddress
                    MAX-ACCESS  read-only
                    STATUS      current
                    DESCRIPTION "Call server address.  This variable 
                        returns a 4-octet string specifying the IP 
                        address of the call server currently in use."
                    ::= { endptID 4 }
endptMCPORT     OBJECT-TYPE
                    SYNTAX      INTEGER 
                    MAX-ACCESS  read-only
                    STATUS      current
                    DESCRIPTION "Transport layer port number. This 
		variable returns an integer specifying the  
		port number in use by the current call server." 
                    ::= { endptID 5 }
endptPHONESN    OBJECT-TYPE
                    SYNTAX      DisplayString
                    MAX-ACCESS  read-only
                    STATUS      current
                    DESCRIPTION "Housing serial number. This variable 
		returns a string of up to 18 ASCII characters, 
		specifying the serial number on the outside 
                        of the endpoint's housing."
                    ::= { endptID 6 }
endptPWBCC      OBJECT-TYPE
                    SYNTAX      DisplayString
                    MAX-ACCESS  read-only
                    STATUS      current
                    DESCRIPTION "PWB comcode. This variable returns  
                        a string of up to 9 numerical characters, 
                        specifying the comcode or version number of 
                        the printed wiring board of the endpoint."
                    ::= { endptID 7 }
endptPWBSN      OBJECT-TYPE
                    SYNTAX      DisplayString
                    MAX-ACCESS  read-only
                    STATUS      current
                    DESCRIPTION "PWB serial number. This variable 
		returns a string of up to 18 ASCII characters, 
		specifying the serial number on the endpoint's 
		printed wiring board, or N/A if the board has 
                        no serial number."
                    ::= { endptID 8 }
endptETHERADD   OBJECT-TYPE
                    SYNTAX      OCTET STRING
                    MAX-ACCESS  read-only
                    STATUS      current
                    DESCRIPTION "MAC address. This variable returns  
                        a 6-octet string specifying the endpoint's
                        MAC address."
                    ::= { endptID 9 }
endptESPEED     OBJECT-TYPE
                    SYNTAX      DisplayString
                    MAX-ACCESS  read-only
                    STATUS      current
                    DESCRIPTION "Ethernet interface speed. This variable 
		returns a string specifying the endpoint's Ethernet
		interface speed in Mbps: '100', '10', or '0'."
                    ::= { endptID 10 }
endptIPADD      OBJECT-TYPE
                    SYNTAX      IpAddress
                    MAX-ACCESS  read-only
                    STATUS      current
                    DESCRIPTION "IP address. This variable returns a 
		4-octet string specifying the endpoint's current 
                        IP address."
                    ::= { endptID 11 }
endptDHCPLEASETIME      OBJECT-TYPE
                    SYNTAX      Integer32
                    MAX-ACCESS  read-only
                    STATUS      current
                    DESCRIPTION "Duration of IPADD lease. This variable 
                        returns an unsigned integer specifying the length 
                        of time of the IPADD lease, in seconds as received 
                        by DHCP option 51."
                    ::= { endptID 12 }
endptDHCPLEASERENEW     OBJECT-TYPE
                    SYNTAX      Integer32
                    MAX-ACCESS  read-only
                    STATUS      current
                    DESCRIPTION "Renewal time of IPADD lease. This 
                        variable returns an unsigned integer specifying 
                        the length of time at which to renew the IPADD 
				lease, in seconds as received by DHCP option 58."
                    ::= { endptID 13 }
endptDHCPLEASEREBIND     OBJECT-TYPE
                    SYNTAX      Integer32
                    MAX-ACCESS  read-only
                    STATUS      current
                    DESCRIPTION "Rebind time of IPADD lease. This 
                        variable returns an unsigned integer specifying 
                        the length of time at which to rebind the IPADD 
		lease, in seconds as received by DHCP option 59."
                    ::= { endptID 14 }
endptGIPADD     OBJECT-TYPE
                    SYNTAX      DisplayString
                    MAX-ACCESS  read-only
                    STATUS      current
                    DESCRIPTION "List of router addresses.  This variable 
		returns a sequence of IP addresses, in  
		dotted-decimal format and separated by commas, 
                      	of routers available for use."
                    ::= { endptID 15 }
endptGIPINUSE       OBJECT-TYPE
                    SYNTAX      IpAddress
                    MAX-ACCESS  read-only
                    STATUS      current
                    DESCRIPTION "Router address.  This variable returns  
                        a 4-octet string specifying the IP address of 
                        the router currently in use."
                    ::= { endptID 16 }
endptNETMASK        OBJECT-TYPE
                    SYNTAX      IpAddress
                    MAX-ACCESS  read-only
                    STATUS      current
                    DESCRIPTION "Subnet mask. This variable returns a  
                        4-octet string specifying the subnet mask 
                        currently in use."
                    ::= { endptID 17 }
endptTFTPDIR    OBJECT-TYPE
                    SYNTAX      DisplayString
                    MAX-ACCESS  read-only
                    STATUS      current
                    DESCRIPTION "TFTP server path name. This variable 
                        returns a string of 0-127 ASCII characters, 
                        specifying the path name currently prepended 
                        to file names used in TFTP read operations."
                    ::= { endptID 18 }
endptTFTPSRVR   OBJECT-TYPE
                    SYNTAX      DisplayString
                    MAX-ACCESS  read-only
                    STATUS      current
                    DESCRIPTION "List of TFTP server addresses.  This 
		variable returns a sequence of IP addresses, 
		in dotted-decimal orDNS format and separated 
		by commas, of TFTP servers available for use."
                    ::= { endptID 19 }
endptTFTPINUSE      OBJECT-TYPE
                    SYNTAX      IpAddress
                    MAX-ACCESS  read-only
                    STATUS      current
                    DESCRIPTION "TFTP server address.  This variable 
                        returns a 4-octet string specifying the IP 
                        address of the TFTP server currently in use 
		(or all zeroes if no server used successfully 
                        during initialization)."
                    ::= { endptID 20 }
endptBOOTNAME       OBJECT-TYPE
                    SYNTAX      DisplayString
                    MAX-ACCESS  read-only
                    STATUS      current
                    DESCRIPTION "Boot code file ID. This variable 
                        returns a string specifying the boot code 
                        file used to initiate telephone operation."
                    ::= { endptID 21 }
endptAPPNAME    OBJECT-TYPE
                    SYNTAX      DisplayString
                    MAX-ACCESS  read-only
                    STATUS      current
                    DESCRIPTION "Application file ID. This variable 
                        returns a string specifying the system-specific 
                        application file that should be used for
                        telephone operation."
                    ::= { endptID 22 }
endptSSON       OBJECT-TYPE
                    SYNTAX      INTEGER 
                    MAX-ACCESS  read-only
                    STATUS      obsolete
                    DESCRIPTION "Site-specific option number (SSON). This 
                        variable returns an integer between 128 and 254 
                        inclusive, specifying the SSON in use.  The
                        default is 176."
                    ::= { endptID 23 }
endptBBURST     OBJECT-TYPE
                    SYNTAX      INTEGER  
                    MAX-ACCESS  read-only
                    STATUS      obsolete
                    DESCRIPTION "Blackburst flag. This variable returns 0
                        if Blackburst is currently OFF, else 1."
                    ::= { endptID 24 }
endptHUBSTAT    OBJECT-TYPE
                    SYNTAX      INTEGER  
                    MAX-ACCESS  read-only
                    STATUS      obsolete
                    DESCRIPTION "Hub flag. This variable has been superseded 
                        by endptPHY2STAT."
                    ::= { endptID 25 }
endptDSCPAUD    OBJECT-TYPE
                    SYNTAX      INTEGER  
                    MAX-ACCESS  read-only
                    STATUS      current
                    DESCRIPTION "DSCP for audio. This variable specifies the
                        Differentiated Services Code Point for audio 
                        currently in use (between 0 and 63 inclusive)."
                    ::= { endptID 26 }
endptDSCPSIG    OBJECT-TYPE
                    SYNTAX      INTEGER  
                    MAX-ACCESS  read-only
                    STATUS      current
                    DESCRIPTION " DSCP for signaling. This variable specifies 
                        the Differentiated Services Code Point for signaling 
                        currently in use (between 0 and 63 inclusive)."
                    ::= { endptID 27 }
endptL2Q        OBJECT-TYPE
                    SYNTAX      INTEGER  
                    MAX-ACCESS  read-only
                    STATUS      current
                    DESCRIPTION "802.1Q framing flag. This variable returns 0 
		if the Layer 2 802.1Q framing parameter is set to 
		'auto', 1 if it is set to on/enabled, else 2 for
                        off/disabled."
                    ::= { endptID 28 }
endptL2QAUD     OBJECT-TYPE
                    SYNTAX      INTEGER  
                    MAX-ACCESS  read-only
                    STATUS      current
                    DESCRIPTION "Audio priority. This variable returns an 
                        integer between 0 and 7 inclusive specifying the 
                        current Layer 2 802.1Q audio priority value."
                    ::= { endptID 29 }
endptL2QSIG     OBJECT-TYPE
                    SYNTAX      INTEGER  
                    MAX-ACCESS  read-only
                    STATUS      current
                    DESCRIPTION "Signaling priority. This variable returns 
                        an integer between 0 and 7 inclusive specifying the 
                        current Layer 2 802.1Q signaling priority value."
                    ::= { endptID 30 }
endptL2QVLAN    OBJECT-TYPE
                    SYNTAX      INTEGER 
                    MAX-ACCESS  read-only
                    STATUS      current
                    DESCRIPTION "Telephone VLAN Identifier. This variable returns 
                        an integer between 0 and 4094 inclusive specifying the 
                        current Layer 2 802.1Q VLAN Identifier value."
                    ::= { endptID 31 }
endpt46XXUPGR   OBJECT-TYPE
                    SYNTAX      DisplayString
                    MAX-ACCESS  read-only
                    STATUS      current
                    DESCRIPTION "Upgrade script ID. This variable returns
                        a string of up to 16 ASCII characters specifying 
                        the name of the upgrade script retrieved by TFTP 
                        after the most recent power-up or reset."
                    ::= { endptID 32 }
endptDNSSRVR   OBJECT-TYPE
                    SYNTAX      DisplayString
                    MAX-ACCESS  read-only
                    STATUS      current
                    DESCRIPTION "List of DNS server addresses.  This variable 
		returns a sequence of IP addresses, in dotted-decimal 
		format and separated by commas, of DNS servers 
		available for use."
                    ::= { endptID 33 }
endptDNSINUSE  OBJECT-TYPE
                    SYNTAX      IpAddress
                    MAX-ACCESS  read-only
                    STATUS      obsolete
                    DESCRIPTION "DNS server address.  This variable returns a 
                        4-octet string specifying the IP address of the DNS
                        server currently in use."
                    ::= { endptID 34 }
endptDOMAIN    OBJECT-TYPE
                    SYNTAX      DisplayString
                    MAX-ACCESS  read-only
                    STATUS      current
                    DESCRIPTION "List of DNS domain labels.  This variable 
		returns a sequence of labels, separated by periods, for
                        use as the highest-level domain in resolving DNS names
		in system values."
                    ::= { endptID 35 }
endptRTCPMON  OBJECT-TYPE
                    SYNTAX      IpAddress
                    MAX-ACCESS  read-only
                    STATUS      current
                    DESCRIPTION "RTCP Monitor address.  This variable returns a 
                        4-octet string specifying the IP address of the RTCP
                        monitor currently in use."
                    ::= { endptID 36 }
endptPHY2STAT    OBJECT-TYPE
                    SYNTAX      INTEGER  
                    MAX-ACCESS  read-only
                    STATUS      current
                    DESCRIPTION "Secondary Ethernet interface setting.  This 
		variable returns 0 if the endpoint's secondary Ethernet 
		interface is currently NOT enabled (or none exists), 1  
		if the hub is setfor auto-negotiation, 2 for 10Mbps 
		half-duplex, 3 for 10Mbps full-duplex, 4 for 100Mbps 
		half-duplex, and 5 for 100Mbps full-duplex."
                    ::= { endptID 37 }
endptIRSTAT    OBJECT-TYPE
                    SYNTAX      INTEGER  
                    MAX-ACCESS  read-only
                    STATUS      current
                    DESCRIPTION "IR Interface flag. This variable returns 0 
                        if the endpoint's IR interface is currently NOT enabled,
                        else 1."
                    ::= { endptID 38 }
endptSMTPSRVR    OBJECT-TYPE
                    SYNTAX      DisplayString
                    MAX-ACCESS  read-only
                    STATUS      current
                    DESCRIPTION "SMTP server IP addresses.  This variable 
				returns a comma-separated list of SMTP server IP 
				addresses available for use, in dotted-decimal
                        or DNS format."
                    ::= { endptID 39 }

endptDSPVERSION  OBJECT-TYPE
                    SYNTAX      DisplayString
                    MAX-ACCESS  read-only
                    STATUS      current
                    DESCRIPTION "DSP Version.  This variable returns a string 
				of up to 10 characters, that identifies the version of 
				the DSP firmware in the endpoint."
                    ::= { endptID 40 }
endptLOGSRVR   OBJECT-TYPE
                    SYNTAX      DisplayString
                    MAX-ACCESS  read-only
                    STATUS      current
                    DESCRIPTION "Event Log server address.  This variable 
				returns at most one IP address, in dotted-decimal 
				or DNS format, of the server to be used for event 
				logging.  This function is intended for Avaya use,
                        in debugging if necessary."
                    ::= { endptID 41 }
endptLOGSTAT    OBJECT-TYPE
                    SYNTAX      INTEGER  
                    MAX-ACCESS  read-only
                    STATUS      obsolete
                    DESCRIPTION "Event Log flag. This variable returns 0 if   
                        the endpoint's event logging capability is currently 
                        NOT enabled, else 1.  This function is intended for 
		Avaya use, in debugging if necessary."
                    ::= { endptID 42 }
endptAGCHAND   OBJECT-TYPE
                    SYNTAX      INTEGER  
                    MAX-ACCESS  read-only
                    STATUS      current
                    DESCRIPTION "Handset AGC status. This variable returns 1  
                        if the endpoint's handset Automatic Gain Control 
                        capability is currently enabled, else 0."
                    ::= { endptID 43 }
endptAGCHEAD   OBJECT-TYPE
                    SYNTAX      INTEGER  
                    MAX-ACCESS  read-only
                    STATUS      current
                    DESCRIPTION "Headset AGC status. This variable returns 1 
                        if the endpoint's headset Automatic Gain Control 
                        capability is currently enabled, else 0."
                    ::= { endptID 44 }
endptPHY1STAT    OBJECT-TYPE
                    SYNTAX      INTEGER  
                    MAX-ACCESS  read-only
                    STATUS      current
                    DESCRIPTION "Ethernet line interface status.  This 
		variable returns 0 if the endpoint's Ethernet line 
		interface is currently NOT enabled, 1 if the Ethernet 
		line interface is currently for auto-negotiation, 2 for 
		10Mbps half-duplex, 3 for 10Mbps full-duplex, 4 for 
		100Mbps half-duplex, and 5 for 100Mbps full-duplex."
                    ::= { endptID 45 }
endptL2QSTAT     OBJECT-TYPE
                    SYNTAX      INTEGER  
                    MAX-ACCESS  read-only
                    STATUS      current
                    DESCRIPTION "802.1Q tagging flag. This variable returns 0  
                        if the Layer 2 802.1Q tagging parameter is currently
                        OFF, else 1." 
                    ::= { endptID 46 }
endptVLANTEST    OBJECT-TYPE
                    SYNTAX      INTEGER  
                    MAX-ACCESS  read-only
                    STATUS      obsolete
                    DESCRIPTION "VLAN pause parameter. This variable returns 
                        the number of seconds for the endpoint to wait for a 
				DHCPOFFER message when using a non-zero VLAN ID.  Valid 
				values are integers from 0 to 999 inclusive."
                    ::= { endptID 47 }
endptPHONECC     OBJECT-TYPE
                    SYNTAX      DisplayString
                    MAX-ACCESS  read-only
                    STATUS      current
                    DESCRIPTION "Phone comcode. This variable returns a string 
				of up to 9 numerical characters, specifying the comcode
                        of the endpoint itself." 
                    ::= { endptID 48 }
endptVLANLIST    OBJECT-TYPE
                    SYNTAX      DisplayString
                    MAX-ACCESS  read-only
                    STATUS      current
                    DESCRIPTION "VLAN ID list. This variable returns a list of  
                        zero or more VLAN IDs."
                    ::= { endptID 49}
endptAGCSPKR    OBJECT-TYPE
                    SYNTAX      INTEGER  
                    MAX-ACCESS  read-only
                    STATUS      current
                    DESCRIPTION "Speakerphone AGC status. This variable returns 
                        1 if the endpoint's speakerphone Automatic Gain Control 
                        capability is currently enabled, else 0."
                    ::= { endptID 50}
endptHTTPSRVR    OBJECT-TYPE
                    SYNTAX      DisplayString
                    MAX-ACCESS  read-only
                    STATUS      current
                    DESCRIPTION "HTTP server IP addresses.  This variable 
				returns a comma-separated list of HTTP server IP 
				addresses available  for use, in dotted-decimal or 
                        DNS format."
                    ::= { endptID 51}
endptHTTPDIR    OBJECT-TYPE
                    SYNTAX      DisplayString
                    MAX-ACCESS  read-only
                    STATUS      current
                    DESCRIPTION "HTTP server Directory.  This variable returns 
				the path used in formation of the URI for HTTP GET 
                        operations."
                    ::= { endptID 52}
endptHTTPPORT   OBJECT-TYPE
                    SYNTAX      INTEGER  
                    MAX-ACCESS  read-only
                    STATUS      current
                    DESCRIPTION "HTTP TCP port number.  This variable returns  
				the TCP port number used by HTTP during initialization."
                    ::= { endptID 53}
endptHTTPUSED   OBJECT-TYPE
                    SYNTAX      OCTET STRING
                    MAX-ACCESS  read-only
                    STATUS      current
                    DESCRIPTION "HTTP initialization server IP address.  This 
				variable returns a 4-octet IP address for the HTTP server 
				used during initialization (all zeroes if no server 
				successfully used during initialization)."
                    ::= { endptID 54}
endptPROCSTAT   OBJECT-TYPE
                    SYNTAX      INTEGER  
                    MAX-ACCESS  read-only
                    STATUS      current
                    DESCRIPTION "Local Procedure flag. This variable returns 0 if 
                        Local Procedures are currently allowed for this telephone,
                        else 1."
                    ::= { endptID 55 }
endptPROCPSWD   OBJECT-TYPE
                    SYNTAX      INTEGER
                    MAX-ACCESS  read-only
                    STATUS      current
                    DESCRIPTION "Local Procedure Password. This variable returns
                        0 if the Local Procedure Password is null, else 1."
                    ::= { endptID 56 }
endptSIG	OBJECT-TYPE
                    SYNTAX      INTEGER  
                    MAX-ACCESS  read-only
                    STATUS      current
                    DESCRIPTION "Signaling protocol download flag. This variable 
                        returns the integer corresponding to the current
                        signaling protocol."
                    ::= { endptID 57 }
endptGROUP	OBJECT-TYPE
                    SYNTAX      INTEGER  
                    MAX-ACCESS  read-only
                    STATUS      current
                    DESCRIPTION "Group identifier. This variable returns the 
                        integer corresponding to the current group identifier."
                    ::= { endptID 58 }
endptSNMPADD    OBJECT-TYPE
                    SYNTAX      DisplayString
                    MAX-ACCESS  read-only
                    STATUS      current
                    DESCRIPTION "SNMP source addresses. This variable returns 
				one or more allowable source IP addresses for SNMP queries, 
                        in dotted decimal or DNS format."
                    ::= { endptID 59 }
endptCODESRVR    OBJECT-TYPE
                    SYNTAX      DisplayString
                    MAX-ACCESS  read-only
                    STATUS      obsolete
                    DESCRIPTION "HTTP server addresses. This variable returns 
				zero or more HTTP server addresses for software download, 
                        in dotted decimal or DNS format."
                    ::= { endptID 60 }
endptCODEUSED    OBJECT-TYPE
                    SYNTAX      OCTET STRING
                    MAX-ACCESS  read-only
                    STATUS      obsolete
                    DESCRIPTION "HTTP server address used. This variable 
				returns the HTTP server address from CODESRVR used, 
				if any, during initialization, or all zeroes if no HTTP
                        server was used."
                    ::= { endptID 61 }
endptSTATIC	OBJECT-TYPE
                    SYNTAX      INTEGER  
                    MAX-ACCESS  read-only
                    STATUS      current
                    DESCRIPTION "Static programming override flag. This variable 
                        returns the integer corresponding to the current level of
				 override permissions for static programming."
                    ::= { endptID 62 }
endptTLSSRVR    OBJECT-TYPE
                    SYNTAX      DisplayString
                    MAX-ACCESS  read-only
                    STATUS      current
                    DESCRIPTION "TLS server addresses. This variable returns zero 
				or more Transport Layer Security server addresses for
                        software download, in dotted decimal or DNS format."
                    ::= { endptID 63 }
endptTLSUSED    OBJECT-TYPE
                    SYNTAX      OCTET STRING
                    MAX-ACCESS  read-only
                    STATUS      current
                    DESCRIPTION "TLS server address used. This variable returns the
				TLS server address from TLSSRVR used, if any, during 
				initialization, or all zeroes if no TLS server was used."
                    ::= { endptID 64 }
endptCNAPORT    OBJECT-TYPE
                    SYNTAX      INTEGER
                    MAX-ACCESS  read-only
                    STATUS      current
                    DESCRIPTION "Chatter server port. This variable returns the 
				Chatter server registration transport-layer port number 
				(from 0 to 65535; default is 8888)."
                    ::= { endptID 65 }
endptCNASRVR    OBJECT-TYPE
                    SYNTAX      DisplayString
                    MAX-ACCESS  read-only
                    STATUS      current
                    DESCRIPTION "CNA server addresses. This variable returns zero 
				or more Chatter server addresses for network analysis, in 
				dotted decimal or DNS format."
                    ::= { endptID 66 }
endptDSTOFFSET  OBJECT-TYPE
                    SYNTAX      DisplayString
                    MAX-ACCESS  read-only
                    STATUS      current
                    DESCRIPTION "Daylight Savings Time Offset. This variable 
				returns the offset in local time for Daylight Savings Time.  
				Currently used in SIP phones."
                    ::= { endptID 67 }
endptDSTSTART   OBJECT-TYPE
                    SYNTAX      DisplayString
                    MAX-ACCESS  read-only
                    STATUS      current
                    DESCRIPTION "Daylight Savings Time Start. This variable returns 
				the first day or date Daylight Savings Time is effective.  
				Currently used in SIP phones."
                    ::= { endptID 68 }
endptDSTSTOP    OBJECT-TYPE
                    SYNTAX      DisplayString
                    MAX-ACCESS  read-only
                    STATUS      current
                    DESCRIPTION "Daylight Savings Time Stop. This variable returns 
		the first day or date after Daylight Savings Time is over.  
		Currently used in SIP phones."
                    ::= { endptID 69 }
endptGMTOFFSET  OBJECT-TYPE
                    SYNTAX      DisplayString
                    MAX-ACCESS  read-only
                    STATUS      current
                    DESCRIPTION "Greenwich Mean Time Offset. This variable returns 
		the offset in local time for Greenwich Mean Time.  Currently 
		used in SIP phones."
                    ::= { endptID 70 }
endptSNTPSRVR   OBJECT-TYPE
                    SYNTAX      DisplayString
                    MAX-ACCESS  read-only
                    STATUS      current
                    DESCRIPTION "SNTP server addresses. This variable returns zero 
		or more SNTP server addresses for obtaining time data, in 
		dotted decimal or DNS format.  Currently used in SIP phones."
                    ::= { endptID 71 }
endptBAKLIGHTOFF OBJECT-TYPE
                    SYNTAX      INTEGER
                    MAX-ACCESS  read-only
                    STATUS      current
                    DESCRIPTION "Backlight idle timer setting. This variable returns 
		the number of minutes of idle time, after which the 
		telephone backlightis turned off. Range is 0-999, with a 
		default of 120.  Used in phones with backlit displays."                        
                    ::= { endptID 72 }
endptDOT1X      OBJECT-TYPE
                    SYNTAX      INTEGER
                    MAX-ACCESS  read-only
                    STATUS      current
                    DESCRIPTION "Current value for 802.1X handling. This variable returns 
		0 if the telephone supports unicast Supplicant operation only,
                        with PAE multicast pass-through without proxy Logoff, 1 if the 
                        same as 0 but with proxy Logoff, and 2 if Unicast both unicast
                        or Multicast Supplicant operation, without PAE multicast pass-
                        through, is supported.  The default is 0." 
                    ::= { endptID 73 }
endptAUDIOENV    OBJECT-TYPE
                    SYNTAX      INTEGER
                    MAX-ACCESS  read-only
                    STATUS      current
                    DESCRIPTION "Audio environment selection index.  This variable returns 
		the current setting from the audio environment table (from 0 to 107,
		default is 0)."
                    ::= { endptID 74}
endptAUDIOSTHD    OBJECT-TYPE
                    SYNTAX      INTEGER
                    MAX-ACCESS  read-only
                    STATUS      current
                    DESCRIPTION "Audio headset sidetone setting.  This variable returns the 
		current setting (0, 1, or 2; default is 0)."
                    ::= { endptID 75}
endptAUDIOSTHS    OBJECT-TYPE
                    SYNTAX      INTEGER
                    MAX-ACCESS  read-only
                    STATUS      current
                    DESCRIPTION "Audio handset sidetone setting.  This variable returns the 
		current setting (0, 1, or 2; default is 0)."
                    ::= { endptID 76}
endptDHCPINUSE      OBJECT-TYPE
                    SYNTAX      IpAddress
                    MAX-ACCESS  read-only
                    STATUS      current
                    DESCRIPTION "DHCP server address.  This variable returns a 4-octet string 
		specifying the IP address of the DHCP server from which the
		telephone's IP address was obtained (or all zeroes if the telephone
		was statically addressed)."
                    ::= { endptID 77}
endptDHCPLEASEEXP     OBJECT-TYPE
                    SYNTAX      Integer32
                    MAX-ACCESS  read-only
                    STATUS      current
                    DESCRIPTION "Remaining time of IPADD lease. This 
                        	variable returns an unsigned integer specifying 
                        	the length of time in seconds until the expiration of the IP
		address lease, or 0 if the lease has expired."
                    ::= { endptID 78}
endptDHCPSTD    OBJECT-TYPE
                    SYNTAX      INTEGER
                    MAX-ACCESS  read-only
                    STATUS      current
                    DESCRIPTION "DHCP lease violation flag.  This variable returns 
		1 if the telephone is not allowed to use the IP address after
		its lease has expired, or else 0 if the telephone is allowed to
		continue operating after the IP address lease has expired.)."
                    ::= { endptID 79}
endptDHCPT1REM     OBJECT-TYPE
                    SYNTAX      Integer32
                    MAX-ACCESS  read-only
                    STATUS      current
                    DESCRIPTION "Remaining time until IP address lease renewal. This 
                        	variable returns an unsigned integer specifying the length of 
		time in seconds until the start of the IP
		address lease renewal, or 0 if the lease has expired."
                    ::= { endptID 80}
endptDHCPT2REM     OBJECT-TYPE
                    SYNTAX      Integer32
                    MAX-ACCESS  read-only
                    STATUS      current
                    DESCRIPTION "Remaining time until IP address lease renewal. This 
                        	variable returns an unsigned integer specifying the length of 
		time in seconds until the start of the IP address lease 
		rebindingl, or 0 if the lease has expired."
                    ::= { endptID 81}
endptICMPDU    OBJECT-TYPE
                    SYNTAX      INTEGER
                    MAX-ACCESS  read-only
                    STATUS      current
                    DESCRIPTION "ICMP Destination support setting.  This variable returns 
		2 if the telephone transmits Destination Unreachable messages with
		code 2 if the designated transport protocol is not supported AND also
		if the telephone transmits Destination Unreachable messages with
		code 3 if a closed UD/TCP port is designated.

		This variable returns 1 if the telephone only transmits Destination Unreachable 
		messages with code 3 if a closed UD/TCP port is designated.

		This variable returns 0 if the telephone does not transmit Destination 
		Unreachable messages."
                    ::= { endptID 81}
endptICMPRED    OBJECT-TYPE
                    SYNTAX      INTEGER
                    MAX-ACCESS  read-only
                    STATUS      current
                    DESCRIPTION "ICMP Redirect support setting.  This variable returns 1 if the telephone 
		supports received Redirect messages as specified in RFC 1122, Sections
		3.2.2.2 and 3.3.1.2, or 0 if the telephone does not provide this support."
                    ::= { endptID 82}
endptSSONCONTENT    OBJECT-TYPE
                    SYNTAX      DisplayString
                    MAX-ACCESS  read-only
                    STATUS      current
                    DESCRIPTION "Contents of DHCP Site Specific Option Number.  This variable returns
		the data portion of the DHCP SSON as designated by endptNVSSON."
                    ::= { endptID 83}
endptBRURI      OBJECT-TYPE
                    SYNTAX      DisplayString
                    MAX-ACCESS  read-only
                    STATUS      current
                    DESCRIPTION "Backup and restore URI. This variable returns 
		a string specifying the URI used for backup and restore files."      
  	  ::= { endptID 84}

endptNVM        OBJECT IDENTIFIER ::= { endpointMIB 2 }
endptNVMCIPADD  OBJECT-TYPE
                    SYNTAX      DisplayString
                    MAX-ACCESS  read-only
                    STATUS      current
                    DESCRIPTION "IP address of call server stored in Non-Volatile 
                        Memory (NVM). This variable returns a 4-octet string or 
                        DNS string.  Default is AvayaCallServer."
                    ::= { endptNVM 1 }
endptNVMCPORT   OBJECT-TYPE
                    SYNTAX      INTEGER 
                    MAX-ACCESS  read-only
                    STATUS      obsolete
                    DESCRIPTION "NVM Transport layer port number. This variable 
                        returns an integer specifying the call server port number
                        stored in NVM."
                    ::= { endptNVM 2 }
endptNVIPADD    OBJECT-TYPE
                    SYNTAX      DisplayString
                    MAX-ACCESS  read-only
                    STATUS      current
                    DESCRIPTION "NVM IP address. This variable returns a 4-octet
                        string specifying the endpoint's IP address stored in
                        NVM."
                    ::= { endptNVM 3 }
endptNVGIPADD   OBJECT-TYPE
                    SYNTAX      DisplayString
                    MAX-ACCESS  read-only
                    STATUS      current
                    DESCRIPTION "NVM Router address.  This variable returns a 4-
                        octet string specifying the IP address of the router as
                        stored in NVM."
                    ::= { endptNVM 4 }
endptNVNETMASK  OBJECT-TYPE
                    SYNTAX      DisplayString
                    MAX-ACCESS  read-only
                    STATUS      current
                    DESCRIPTION "NVM Subnet mask. This variable returns a 4-octet 
                        string specifying the subnet mask as stored in NVM."
                    ::= { endptNVM 5 }
endptNVTFTPSRVR OBJECT-TYPE
                    SYNTAX      DisplayString
                    MAX-ACCESS  read-only
                    STATUS      obsolete
                    DESCRIPTION "NVM TFTP server address. This variable returns
                        a 4-octet string specifying the IP address of the file 
                        server as stored in NVM.  The default is AvayaTFTPserver."
                    ::= { endptNVM 6 }
endptNVSSON     OBJECT-TYPE
                    SYNTAX      INTEGER 
                    MAX-ACCESS  read-only
                    STATUS      current
                    DESCRIPTION "NVM Site-specific option number. This variable 
                        returns an integer between 128 and 254 inclusive,
                        specifying the SSON stored in NVM.  The default is 176."
                    ::= { endptNVM 7 }
endptNVBBURST   OBJECT-TYPE
                    SYNTAX      INTEGER  
                    MAX-ACCESS  read-only
                    STATUS      obsolete
                    DESCRIPTION "NVM Blackburst flag. This variable returns 0
                         if the Blackburst parameter in NVM is OFF, else 1."
                    ::= { endptNVM 8 }
endptNVHUBSTAT  OBJECT-TYPE
                    SYNTAX      INTEGER  
                    MAX-ACCESS  read-only
                    STATUS      obsolete
                    DESCRIPTION "NVM Hub flag. This variable has been superseded 
                        by endptNVPHY2STAT."
                    ::= { endptNVM 9 }
endptNVDSCPAUD  OBJECT-TYPE
                    SYNTAX      INTEGER  
                    MAX-ACCESS  read-only
                    STATUS      current
                    DESCRIPTION "NVM DSCP for audio. This variable specifies the
                        Differentiated Services Code Point for audio stored 
                        in NVM (integer between 0 and 63 inclusive)."
                    ::= { endptNVM 10 }
endptNVDSCPSIG  OBJECT-TYPE
                    SYNTAX      INTEGER  
                    MAX-ACCESS  read-only
                    STATUS      current
                    DESCRIPTION " NVM DSCP for signaling. This variable specifies 
                        the Differentiated Services Code Point for signaling 
                        stored in NVM (integer between 0 and 63 inclusive)."
                    ::= { endptNVM 11 }
endptNVL2Q      OBJECT-TYPE
                    SYNTAX      INTEGER  
                    MAX-ACCESS  read-only
                    STATUS      current
                    DESCRIPTION "NVM 802.1Q flag. This variable returns 0 if 
				the Layer 2 802.1Q framing parameter in NVM is set to  
				'auto', 1 if it is set to on/enabled, else 2 for
                        off/disabled."
                    ::= { endptNVM 12 }
endptNVL2QAUD   OBJECT-TYPE
                    SYNTAX      INTEGER  
                    MAX-ACCESS  read-only
                    STATUS      current
                    DESCRIPTION "NVM Audio priority. This variable returns an 
                        integer between 0 and 7 inclusive specifying the Layer 2 
                        802.1Q audio priority value stored in NVM."
                    ::= { endptNVM 13 }
endptNVL2QSIG   OBJECT-TYPE
                    SYNTAX      INTEGER  
                    MAX-ACCESS  read-only
                    STATUS      current
                    DESCRIPTION "NVM Signaling priority. This variable returns an 
                        integer between 0 and 7 inclusive specifying the Layer 2
                        802.1Q signaling priority value stored in NVM."
                    ::= { endptNVM 14 }
endptNVL2QVLAN  OBJECT-TYPE
                    SYNTAX      INTEGER  
                    MAX-ACCESS  read-only
                    STATUS      current
                    DESCRIPTION "NVM VLAN Identifier. This variable returns an 
                        integer between 0 and 4094 inclusive specifying the Layer
                        2 802.1Q VLAN Identifier value stored in NVM."
                    ::= { endptNVM 15 }
endptNVPHY2STAT  OBJECT-TYPE
                    SYNTAX      INTEGER  
                    MAX-ACCESS  read-only
                    STATUS      current
                    DESCRIPTION "NVM Secondary Ethernet interface setting.  This 
				variable returns 0 if the endpoint's secondary Ethernet 
				interface in NVM is currently NOT enabled(or none exists), 
				1 if the hub is set for auto-negotiation, 2 for 10Mbps 
				half-duplex, 3 for 10Mbps full-duplex, 4 for 100Mbps
                        half-duplex, and 5 for 100Mbps full-duplex."
                    ::= { endptNVM 16 }
endptNVLOGSTAT    OBJECT-TYPE
                    SYNTAX      INTEGER  
                    MAX-ACCESS  read-only
                    STATUS      current
                    DESCRIPTION "NVM Event Log flag. This variable returns 0 if the 
                        endpoint's event logging capability in NVM is currently 
                        NOT enabled, else 1."
                    ::= { endptNVM 17 }
endptNVAGCHAND   OBJECT-TYPE
                    SYNTAX      INTEGER  
                    MAX-ACCESS  read-only
                    STATUS      current
                    DESCRIPTION "NVM Handset AGC status. This variable returns 1  
                        if the endpoint's handset Automatic Gain Control capability 
				in NVM is currently enabled, else 0."
                    ::= { endptNVM 18}
endptNVAGCHEAD   OBJECT-TYPE
                    SYNTAX      INTEGER  
                    MAX-ACCESS  read-only
                    STATUS      current
                    DESCRIPTION "NVM Headset AGC status. This variable returns 1 
                        if the endpoint's headset Automatic Gain Control capability 
				in NVM is currently enabled, else 0."
                    ::= { endptNVM 19}
endptNVIRSTAT    OBJECT-TYPE
                    SYNTAX      INTEGER  
                    MAX-ACCESS  read-only
                    STATUS      current
                    DESCRIPTION "NVM IR Interface flag. This variable returns 0 
                        if the endpoint's IR interface capability in NVM is 
				currently NOT enabled, else 1."
                    ::= { endptNVM 20}
endptNVPHY1STAT    OBJECT-TYPE
                    SYNTAX      INTEGER  
                    MAX-ACCESS  read-only
                    STATUS      current
                    DESCRIPTION "NVM Ethernet line interface status.  This 
                        variable returns 0 if the endpoint's Ethernet line 
                        interface in NVM iscurrently NOT enabled, 1 if the 
                        Ethernet line interface in NVM is currently for 
                        auto-negotiation, 2 for 10Mbps half-duplex, 3 for 
                        10Mbps full-duplex, 4 for 100Mbps half-duplex, and
                        5 for 100Mbps full-duplex."
                    ::= { endptNVM 21}
endptNVVLANTEST    OBJECT-TYPE
                    SYNTAX      INTEGER  
                    MAX-ACCESS  read-only
                    STATUS      current
                    DESCRIPTION "NVM VLAN pause parameter. This variable returns 
                        the number of seconds stored in NVM for the endppoint to 
                        wait for a DHCPOFFER message when using a non-zero VLAN ID.  
                        Valid values are integers from 0 to 999 inclusive."
                    ::= { endptNVM 22 }
endptNVVLANLIST    OBJECT-TYPE
                    SYNTAX      DisplayString
                    MAX-ACCESS  read-only
                    STATUS      obsolete
                    DESCRIPTION "NVM VLAN ID list. This variable returns a list 
                        of zero or more VLAN IDs in NVM."
                    ::= { endptNVM 23}
endptNVAGCSPKR    OBJECT-TYPE
                    SYNTAX      INTEGER  
                    MAX-ACCESS  read-only
                    STATUS      current
                    DESCRIPTION "Speakerphone AGC status. This variable returns 1 
                        if the endpoint's speakerphone Automatic Gain Control 
                        capability in NVM is currently enabled, else 0."
                    ::= { endptNVM 24}
endptNVHTTPSRVR   OBJECT-TYPE
                    SYNTAX      DisplayString
                    MAX-ACCESS  read-only
                    STATUS      obsolete
                    DESCRIPTION "NVM HTTP server IP addresses.  This variable 
				returns a comma-separated list of HTTP server IP 
				addresses available for use as stored in NVM, in
                        dotted-decimal format."
                    ::= { endptNVM 25}
endptNVAUTH      OBJECT-TYPE
                    SYNTAX      INTEGER  
                    MAX-ACCESS  read-only
                    STATUS      current
                    DESCRIPTION "Script file authentication flag. This variable 
				returns 1 if the endpoint must authenticate script files,
                        else 0."
                    ::= { endptNVM 26}
endptNVFILESRVR OBJECT-TYPE
                    SYNTAX      DisplayString
                    MAX-ACCESS  read-only
                    STATUS      current
                    DESCRIPTION "NVM File server address. This variable returns
                        a 4-octet string specifying the IP address of the file 
                        server as stored in NVM."
                    ::= { endptNVM 27 }
endptNVALERT    OBJECT-TYPE
                    SYNTAX      INTEGER  
                    MAX-ACCESS  read-only
                    STATUS      current
                    DESCRIPTION "Alerting Mode flag. This variable returns 1 if 
				the alerting mode setting in non-volatile memory is 
				enabled, else 0."
                    ::= { endptNVM 28}
endptNVCHADDR    OBJECT-TYPE
                    SYNTAX      Integer32
                    MAX-ACCESS  read-only
                    STATUS      current
                    DESCRIPTION "Manually-entered DHCP chaddr value. This 
				variable returns a manually-entered value for the DHCP 
				chaddr field as stored in non-volatile memory, if any. 
				A Hexadecimal value with range of 0 (the default) to
                        999999."
                    ::= { endptNVM 29}
endptNVCONTRAST    OBJECT-TYPE
                    SYNTAX      INTEGER  
                    MAX-ACCESS  read-only
                    STATUS      current
                    DESCRIPTION "Display Contrast setting. This variable returns 
				the value of the display contrast setting in non-volatile 
				memory.  Range is 0-15, with 8 the default."
                    ::= { endptNVM 30}


endptMaintenance        OBJECT IDENTIFIER ::= { endpointMIB 3 }
endptUPGRADESCRIPT      OBJECT-TYPE 
                    SYNTAX      INTEGER  
                    MAX-ACCESS  read-only
                    STATUS      current
                    DESCRIPTION "Script loading status flag. This variable
                        returns '0' if the upgrade script (endpt46XXUPGR)
                        was successfully obtained and interpreted since the
                        last power-up or reset. This variable returns '1' if
                        the upgrade script was successfully obtained and but
                        NOT successfully interpreted since the last power-up
                        or reset. This variable returns '2' if the upgrade
                        script was NOT successfully obtained since the last
                        power-up or reset."
                    ::= { endptMaintenance 1 }
endptAPPINUSE    OBJECT-TYPE 
                    SYNTAX      DisplayString 
                    MAX-ACCESS  read-only
                    STATUS      current
                    DESCRIPTION "Application file name.  This variable returns
                        the name of the application file in the endpoint."
                    ::= { endptMaintenance 2 }
endptAPPSTAT    OBJECT-TYPE 
                    SYNTAX      INTEGER  
                    MAX-ACCESS  read-only
                    STATUS      current
                    DESCRIPTION "Application download flag. This variable
				returns '0' if the most recent attempt to download
				and store an application file was successful. This
				variable returns '1' if the most recent attempt to
				download an application file was successful but the
				file was not successfully stored in NVM.  This variable
				returns '2' if the most recent attempt to download an
				application file was NOT successful."
		    ::= { endptMaintenance 3 }
endptRecentLog	OBJECT-TYPE
			  SYNTAX SEQUENCE OF EndptRecentLogEntry
		 	  MAX-ACCESS	not-accessible
			  STATUS		current
			  DESCRIPTION	"Each entry is one of up to 75 syslog event 
				messages added since last reset or power-up, each of 
				which has severity code less than the value of NVLOGLOCAL.  
				Entries are in chronological order, oldest first."
			  ::= { endptMaintenance 4 }
endptRecentLogEntry	OBJECT-TYPE
			  SYNTAX EndptRecentLogEntry
			  MAX-ACCESS	not-accessible
			  STATUS		current
			  DESCRIPTION	"Each entry is one of up to 75 syslog event 
				messages added since last reset or power-up, each of 
				which has severity code less than the value of NVLOGLOCAL. 
				Entries are in chronological order, oldest first."
			  INDEX		{ endptRecentLogText }
			  ::= { endptRecentLog 1 }
EndptRecentLogEntry	    ::= 
				SEQUENCE {
			  		endptRecentLogText
			  			DisplayString
				}
endptRecentLogText	OBJECT-TYPE
			  SYNTAX		DisplayString
			  MAX-ACCESS	read-only
			  STATUS		current
			  DESCRIPTION	"Syslog event message."
			  ::= { endptRecentLogEntry 1 }	
endptResetLog	OBJECT-TYPE
			  SYNTAX SEQUENCE OF EndptResetLogEntry
		 	  MAX-ACCESS	not-accessible
			  STATUS		current
			  DESCRIPTION	"Each entry is one of up to 75 syslog event 
				messages added before the last reset or power-up, each of 
				which has severity code less than the value of NVLOGLOCAL.  
				Entries are in chronological order, oldest first."
			  ::= { endptMaintenance 5 }
endptResetLogEntry	OBJECT-TYPE
			  SYNTAX EndptResetLogEntry
			  MAX-ACCESS	not-accessible
			  STATUS		current
			  DESCRIPTION	"Each entry is one of up to 75 syslog event 
				messages added before the last reset or power-up, each of 
				which has severity code less than the value of NVLOGLOCAL.  
				Entries are in chronological order, oldest first."
			  INDEX		{ endptResetLogText }
			  ::= { endptResetLog 1 }
EndptResetLogEntry	    ::= 
				SEQUENCE {
			  		endptResetLogText
			  			DisplayString
				}
endptResetLogText	OBJECT-TYPE
			  SYNTAX		DisplayString
			  MAX-ACCESS	read-only
			  STATUS		current
			  DESCRIPTION	"Syslog event message."
			  ::= { endptResetLogEntry 1 }	



endptDEFINITY   OBJECT IDENTIFIER ::= { endpointMIB 4 }
endptPORTAUD    OBJECT-TYPE
                    SYNTAX      INTEGER 
                    MAX-ACCESS  read-only
                    STATUS      current
                    DESCRIPTION "Transport-layer audio port. This variable returns
                        the endpoint's transport layer port number for audio, 
                        currently in use."
                    ::= { endptDEFINITY 1 }
endptPORTSIG    OBJECT-TYPE
                    SYNTAX      INTEGER 
                    MAX-ACCESS  read-only
                    STATUS      current
                    DESCRIPTION "Transport-layer signaling port. This variable 
                        returns the endpoint's transport layer port number for 
                        signaling, currently in use."
                    ::= { endptDEFINITY 2 }
endptFEIPADD    OBJECT-TYPE
                    SYNTAX      OCTET STRING
                    MAX-ACCESS  read-only
                    STATUS      current
                    DESCRIPTION "Audio endpoint address. This variable returns
                        a 4-octet string specifying the address of the far-end 
                        audio endpoint currently in use."
                    ::= { endptDEFINITY 3 }
endptFEPORT     OBJECT-TYPE
                    SYNTAX      INTEGER 
                    MAX-ACCESS  read-only
                    STATUS      current
                    DESCRIPTION "Audio endpoint port number. This variable returns
                        the far-end endpoint's transport layer port number for 
                        audio, currently in use."
                    ::= { endptDEFINITY 4 }
endptCODECR     OBJECT-TYPE
                    SYNTAX      DisplayString
                    MAX-ACCESS  read-only
                    STATUS      current
                    DESCRIPTION "Receive codec. This variable returns the 
                        designation of the Receive codec currently in use."
                    ::= { endptDEFINITY 5 }
endptCODECT     OBJECT-TYPE
                    SYNTAX      DisplayString
                    MAX-ACCESS  read-only
                    STATUS      current
                    DESCRIPTION "Transmit codec. This variable returns the 
                        designation of the Transmit codec currently in use."
                    ::= { endptDEFINITY 6 }
endptJCPC       OBJECT-TYPE
                    SYNTAX      INTEGER 
                    MAX-ACCESS  read-only
                    STATUS      current
                    DESCRIPTION "Jitter compensation packet count. This variable 
                        returns the Jitter compensation packet count currently
                        in use (between 0 and 20, inclusive)."
                    ::= { endptDEFINITY 7 }
endptTMSEC      OBJECT-TYPE
                    SYNTAX      INTEGER 
                    MAX-ACCESS  read-only
                    STATUS      current
                    DESCRIPTION "Transmit buffer fill level. This variable returns 
                        the transmit buffer minimum fill level, in msec, currently
                        in use."
                    ::= { endptDEFINITY 8 }
endptNVPHONEXT      OBJECT-TYPE
                    SYNTAX      DisplayString
                    MAX-ACCESS  read-only
                    STATUS      current
                    DESCRIPTION "Endpoint's phone extension.  This variable 
				returns a text string identifying the endpoint's extension, 
				in free text format.  The default value is NULL. "
                    ::= { endptDEFINITY 9 }
endptL2QBBE     OBJECT-TYPE
                    SYNTAX      INTEGER 
                    MAX-ACCESS  read-only
                    STATUS      obsolete
                    DESCRIPTION "802.1Q BBE priority value. This variable returns
                        an integer between 0 and 7 inclusive specifying the 
                        far-end endpoint's Layer 2 Better than Best Effort audio 
                        priority value."
                    ::= { endptDEFINITY 10 }
endptDSCPBBE    OBJECT-TYPE
                    SYNTAX      INTEGER 
                    MAX-ACCESS  read-only
                    STATUS      current
                    DESCRIPTION "DSCP BBE priority value. This variable returns
                        an integer between 0 and 7 inclusive specifying the 
                        far-end endpoint's DiffServ Better than Best Effort audio 
                        priority value."
                    ::= { endptDEFINITY 11 }
endptRTCPCONT   OBJECT-TYPE
                    SYNTAX      INTEGER 
                    MAX-ACCESS  read-only
                    STATUS      current
                    DESCRIPTION "RTCP Control flag. This variable returns
                        0 if the RTCP control status is off/disabled, else 1."
                    ::= { endptDEFINITY 12 }
endptRTCPFLOW   OBJECT-TYPE
                    SYNTAX      INTEGER 
                    MAX-ACCESS  read-only
                    STATUS      current
                    DESCRIPTION "RTCP Flowrate. This variable returns
                        an integer between 0 and 65335 inclusive specifying the
                        RTCP flowrate in milliseconds."
                    ::= { endptDEFINITY 13 }
endptRSVPCONT   OBJECT-TYPE
                    SYNTAX      INTEGER 
                    MAX-ACCESS  read-only
                    STATUS      current
                    DESCRIPTION "RSVP Control flag. This variable returns
                        0 if the RSVP control status is off/disabled, else 1."
                    ::= { endptDEFINITY 14 }
endptRSVPRFRSH   OBJECT-TYPE
                    SYNTAX      INTEGER 
                    MAX-ACCESS  read-only
                    STATUS      current
                    DESCRIPTION "RSVP Refresh rate. This variable returns
                        an integer between 0 and 65335 inclusive specifying the
                        RSVP refresh rate in milliseconds."
                    ::= { endptDEFINITY 15 }
endptRSVPRTRY   OBJECT-TYPE
                    SYNTAX      INTEGER 
                    MAX-ACCESS  read-only
                    STATUS      current
                    DESCRIPTION "RSVP Failed Retry flag. This variable returns
                        0 if the RSVP Failed Retry Reservation control status is 
                        off/disabled, else 1."
                    ::= { endptDEFINITY 16 }
endptRSVPPROF   OBJECT-TYPE
                    SYNTAX      INTEGER 
                    MAX-ACCESS  read-only
                    STATUS      current
                    DESCRIPTION "RSVP profile flag. This variable returns
                        0 if the RSVP profile is guaranteed, else 1 for controlled
                        load."
                    ::= { endptDEFINITY 17 }
endptPHNCC      OBJECT-TYPE
                    SYNTAX      INTEGER 
                    MAX-ACCESS  read-only
                    STATUS      current
                    DESCRIPTION "Telephone country code. This variable returns
                        1-3 digits; the administered international country code
                        for the location of the serving call server."
                    ::= { endptDEFINITY 18 }
endptPHNDPLENGTH OBJECT-TYPE
                    SYNTAX      INTEGER 
                    MAX-ACCESS  read-only
                    STATUS      current
                    DESCRIPTION "Telephone dial plan length. This variable returns
                        1 or 2 digits (3-10); the length of the administered dial 
                        plan for the serving call server."
                    ::= { endptDEFINITY 19 }
endptPHNIC      OBJECT-TYPE
                    SYNTAX      INTEGER 
                    MAX-ACCESS  read-only
                    STATUS      current
                    DESCRIPTION "Telephone international access code. This variable
                        returns 1-4 digits; the digits dialed to access public 
                        network international trunks from the serving call server."
                    ::= { endptDEFINITY 20 }
endptPHNLD      OBJECT-TYPE
                    SYNTAX      INTEGER 
                    MAX-ACCESS  read-only
                    STATUS      current
                    DESCRIPTION "Telephone long distance access code. This variable
                        returns 1 digit or Null; the digit dialed to access public 
                        network long distance trunks from the serving call server."
                    ::= { endptDEFINITY 21 }
endptPHNLDLENGTH OBJECT-TYPE
                    SYNTAX      INTEGER 
                    MAX-ACCESS  read-only
                    STATUS      current
                    DESCRIPTION "Length of national telephone number. This 
                        variable returns 1 or 2 digits (5-15); the number of digits 
                        in the longest possible national telephone number for the 
                        location of the serving call server."
                    ::= { endptDEFINITY 22 }
endptPHNOL      OBJECT-TYPE
                    SYNTAX      INTEGER 
                    MAX-ACCESS  read-only
                    STATUS      current
                    DESCRIPTION "Outside line access code. This variable returns
                        1 or 2 digits or Null; the digit(s) dialed to access public
                        network local trunks from the serving call server."
                    ::= { endptDEFINITY 23 }
endptNTWKAUDIO  OBJECT-TYPE
                    SYNTAX      INTEGER 
                    MAX-ACCESS  read-only
                    STATUS      current
                    DESCRIPTION "Network audio quality display flag. This variable 
                        returns 0 if the Network audio quality display status is 
                        off/disabled, else 1. This flag does not apply to the 4610, 
				4620, or 4630 IP Telephones."
                    ::= { endptDEFINITY 24 }
endptENHDIALSTAT OBJECT-TYPE
                    SYNTAX      INTEGER 
                    MAX-ACCESS  read-only
                    STATUS      current
                    DESCRIPTION "Enhanced Local Dialing status.  This variable 
				returns 0 if the Enhanced Local Dialing status is
                        off/disabled, else 1."                     
                    ::= { endptDEFINITY 25 }
endptRESTORESTAT OBJECT-TYPE
                    SYNTAX      INTEGER 
                    MAX-ACCESS  read-only
                    STATUS      current
                    DESCRIPTION "FTP Backup/restore status.  This variable returns 
				0 if the automatic FTP backup and restore feature status is 
				off/disabled, else 1."                     
                    ::= { endptDEFINITY 26 }
endptFTPUSERSTAT OBJECT-TYPE
                    SYNTAX      INTEGER 
                    MAX-ACCESS  read-only
                    STATUS      current
                    DESCRIPTION "FTP User permissions status.  This variable returns 
				0 if the user may not change previously-administered FTP 
				server and Directory data, 1 if the user may change or 
				create both FTP server and Directory data, and 2 if the user 
                        may only change or create FTP Directory data."                     
                    ::= { endptDEFINITY 27 }
endptRASGkList	OBJECT-TYPE
			  SYNTAX SEQUENCE OF EndptRASGkEntry
		 	  MAX-ACCESS	not-accessible
			  STATUS		current
			  DESCRIPTION	"Each entry is one of up to 30 gatekeeper 
				addresses in dotted-decimal or DNS format, as downloaded from 
				the call server during RAS.  Entries are listed in the order
                        received."
			  ::= { endptDEFINITY 28 }
endptRASGkEntry   OBJECT-TYPE
			  SYNTAX EndptRASGkEntry
			  MAX-ACCESS	not-accessible
			  STATUS		current
			  DESCRIPTION	"Each entry is one of up to 30 gatekeeper 
				addresses in dotted-decimal or DNS format, as downloaded from
				the call server during RAS.  Entries are listed in the order
                        received."
			  INDEX		{ endptRASGkEntryData}
			  ::= { endptRASGkList 1 }
EndptRASGkEntry	  ::= 
				SEQUENCE {
			  		endptRASGkEntryData
			  			DisplayString
				}
endptRASGkEntryData OBJECT-TYPE
			  SYNTAX		DisplayString
			  MAX-ACCESS	read-only
			  STATUS		current
			  DESCRIPTION	"Data for an individual RAS-provided Gatekeeper."
			  ::= { endptRASGkEntry 1 }


endptAdvApps    OBJECT IDENTIFIER ::= { endpointMIB 5 }
endptCIBURL     OBJECT-TYPE
                    SYNTAX      DisplayString 
                    MAX-ACCESS  read-only
                    STATUS      obsolete
                    DESCRIPTION "Documentation URL. This variable returns
                        a URL of the directory in which the web-based Customer
                        Information Booklet web pages are located."
                    ::= { endptAdvApps 1 }
endptDIRSRVR     OBJECT-TYPE
                    SYNTAX      OCTET STRING 
                    MAX-ACCESS  read-only
                    STATUS      current
                    DESCRIPTION "LDAP Server address. This variable returns
                        a  the IP address of the LDAP server to be used for 
                        the phone's Directoryapplication, in dotted decimal 
                        or DNS format."
                    ::= { endptAdvApps 2 }
endptDIRTOPDN     OBJECT-TYPE
                    SYNTAX      DisplayString 
                    MAX-ACCESS  read-only
                    STATUS      current
                    DESCRIPTION "Directory Top Name. This variable returns
                        a string specifying the Topmost Distinguished Name in the 
                        LDAP Directory to be used for the 4630's Directory 
                        application."
                    ::= { endptAdvApps 3 }
endptDIRFULLNAME  OBJECT-TYPE
                    SYNTAX      DisplayString 
                    MAX-ACCESS  read-only
                    STATUS      current
                    DESCRIPTION "Directory FullName Label. This variable returns
                        a string specifying the LDAP Directory's Full Name Field
                        Label, to be used for the 4630's Directory application."
                    ::= { endptAdvApps 4 }
endptDIRTELNUM  OBJECT-TYPE
                    SYNTAX      DisplayString 
                    MAX-ACCESS  read-only
                    STATUS      current
                    DESCRIPTION "Directory Phone Number Label. This variable returns
                        a string specifying the LDAP Directory's Telephone Number 
                        Field Label, to be used for the 4630's Directory application."
                    ::= { endptAdvApps 5 }
endptDIRSRCHTIME  OBJECT-TYPE
                    SYNTAX      INTEGER
                    MAX-ACCESS  read-only
                    STATUS      current
                    DESCRIPTION "Directory Search Duration. This variable returns
                        an integer specifying the maximum number of seconds the LDAP
                        Directory should be searched before reporting completion or
                        failure of the search."
                    ::= { endptAdvApps 6 }
endptDIRSRVRPWD   OBJECT-TYPE
                    SYNTAX      DisplayString 
                    MAX-ACCESS  read-only
                    STATUS      current
                    DESCRIPTION "Directory Access Password. This variable returns
                        a string specifying the password used for accessing the LDAP
                        Directory.  The null string is returned if no password has
                        been specified."
                    ::= { endptAdvApps 7 }
endptDIRUSERID   OBJECT-TYPE
                    SYNTAX      DisplayString 
                    MAX-ACCESS  read-only
                    STATUS      current
                    DESCRIPTION "Directory Access User ID. This variable returns
                        a string specifying the User identity used for accessing 
                        the LDAP Directory.  The null strong is returned if no 
                        user ID has been specified."
                    ::= { endptAdvApps 8 }
endptDIRCODING  OBJECT-TYPE
                    SYNTAX      DisplayString 
                    MAX-ACCESS  read-only
                    STATUS      current
                    DESCRIPTION "Directory Coding Scheme. This variable returns
                        a string specifying the character coding scheme (e.g. ASCII
                        or Latin-1) to be used for LDAP Directory queries."
                    ::= { endptAdvApps 9 }
endptDIRSTAT    OBJECT-TYPE
                    SYNTAX      INTEGER
                    MAX-ACCESS  read-only
                    STATUS      current
                    DESCRIPTION "Directory Connection Status. This variable returns
                        an integer specifying the result code for the most recent
                        Bind Request sent by the 4630 to the LDAP server."
                    ::= { endptAdvApps 10 }
endptFTPSRVR    OBJECT-TYPE
                    SYNTAX      OCTET STRING
                    MAX-ACCESS  read-only
                    STATUS      current
                    DESCRIPTION "FTP Server address. This variable returns
                        the IP address of the FTP server to be used for the phone's 
				file storage and retrieval, in dotted decimal or DNS format."
                    ::= { endptAdvApps 11 }
endptFTPDIR     OBJECT-TYPE
                    SYNTAX      DisplayString 
                    MAX-ACCESS  read-only
                    STATUS      current
                    DESCRIPTION "FTP Server directory. This variable returns
                        a path name of the directory on the FTP server 
                        to be used for the phone's file storage and retrieval."
                    ::= { endptAdvApps 12 }
endptPHNEMERGNUM  OBJECT-TYPE
                    SYNTAX      DisplayString 
                    MAX-ACCESS  read-only
                    STATUS      current
                    DESCRIPTION "Emergency number. This variable returns
                        a string specifying the emergency number to be outpulsed 
                        when the user presses the optional Emergency button in
                        the 4630 Speed Dial application."
                    ::= { endptAdvApps 13 }
endptPHNNUMOFCA   OBJECT-TYPE
                    SYNTAX      INTEGER
                    MAX-ACCESS  read-only
                    STATUS      current
                    DESCRIPTION "Number of Call Appearances. This variable returns
                        the number of Call Appearances downloaded from the DEFINITY
                        during registration to the 4630, 462x and 4610SW."
                    ::= { endptAdvApps 14 }
endptPHNNUMOFFB   OBJECT-TYPE
                    SYNTAX      INTEGER
                    MAX-ACCESS  read-only
                    STATUS      current
                    DESCRIPTION "Number of Feature Buttons. This variable returns
                        the number of administered Feature Buttons downloaded from 
                        the switch during registration to the 4630, 462x and 4610SW."
                    ::= { endptAdvApps 15 }
endptWEBCODING  OBJECT-TYPE
                    SYNTAX      DisplayString 
                    MAX-ACCESS  read-only
                    STATUS      current
                    DESCRIPTION "Web Coding Scheme. This variable returns
                        a string specifying the character coding scheme (e.g. ASCII
                        or Latin-1) to be used for characters entered on forms on 
                        web pages. Used by the 4630 Web application."
                    ::= { endptAdvApps 16 }
endptWEBEXCEPT  OBJECT-TYPE
                    SYNTAX      DisplayString 
                    MAX-ACCESS  read-only
                    STATUS      current
                    DESCRIPTION "Web Proxy Server Exception List. This variable 
                        returns a string specifying a list of one or more HTTP  
                        proxy server Exception domains, separated by commas with 
                        no intervening spaces, up to 127 total characters.  Used 
				by the 4630 Web application."
                    ::= { endptAdvApps 17 }
endptWEBHOME    OBJECT-TYPE
                    SYNTAX      DisplayString 
                    MAX-ACCESS  read-only
                    STATUS      current
                    DESCRIPTION "Web application URL. This variable returns
                        a URL of the Home page for the 4630 Web application."
                    ::= { endptAdvApps 18 }
endptWEBPORT    OBJECT-TYPE
                    SYNTAX      INTEGER
                    MAX-ACCESS  read-only
                    STATUS      current
                    DESCRIPTION "Web application TCP port. This variable returns
                        an integer specifying the TCP port most recently used for 
                        the HTTP proxy server.  Used by the 4630 Web application."
                    ::= { endptAdvApps 19 }
endptWEBPROXY   OBJECT-TYPE
                    SYNTAX      OCTET STRING 
                    MAX-ACCESS  read-only
                    STATUS      current
                    DESCRIPTION "Web Proxy Server. This variable returns
                        an IP addresses, in dotted-decimal or DNS format, of an  
                        HTTP proxy server.  Used by the 4630 Web application."
                    ::= { endptAdvApps 20 }
endptDIRLDAPPORT OBJECT-TYPE
                    SYNTAX      INTEGER
                    MAX-ACCESS  read-only
                    STATUS      current
                    DESCRIPTION "LDAP Directory Port. This variable returns
                        the port number for LDAP messages, and has a default value
                        of 389."
                    ::= { endptAdvApps 21 }
endptVMLCODING OBJECT-TYPE
                      SYNTAX      DisplayString 
                    MAX-ACCESS  read-only
                    STATUS      current
                    DESCRIPTION "Voice Mail Coding Scheme. This variable returns
                        a string specifying the character coding scheme (e.g. ASCII
                        or Latin-1) to be used for characters entered on forms on 
                        the 4630 Voice Mail application."
                    ::= { endptAdvApps 22 }
endptVMLHOME    OBJECT-TYPE
                    SYNTAX      DisplayString 
                    MAX-ACCESS  read-only
                    STATUS      current
                    DESCRIPTION "Voice Mail application URL. This variable returns
                        a URL of the Home page for the 4630 Voice Mail application."
                    ::= { endptAdvApps 23 }
endptCLACTIVE    OBJECT-TYPE
                    SYNTAX      INTEGER 
                    MAX-ACCESS  read-only
                    STATUS      obsolete
                    DESCRIPTION "Call Log activation flag. This variable returns
                        0 if the call log status is off/disabled, else 1."
                    ::= { endptAdvApps 24 }
endptWMLCODING  OBJECT-TYPE
                    SYNTAX      DisplayString 
                    MAX-ACCESS  read-only
                    STATUS      obsolete
                    DESCRIPTION "4610SW/2x Web Coding Scheme. This variable returns
                        a string specifying the character coding scheme (e.g. ASCII
                        or Latin-1) to be used for characters entered on forms on 
                        web pages. Used by the 4610SW/462x Web application."
                    ::= { endptAdvApps 25 }
endptWMLEXCEPT  OBJECT-TYPE
                    SYNTAX      DisplayString 
                    MAX-ACCESS  read-only
                    STATUS      current
                    DESCRIPTION "4610SW/2x Web Proxy Server Exception List. This 
                        variable returns a string specifying a list of one or 
                        more HTTP proxy server Exception domains, separated by 
                        commas with no intervening spaces, up to 127 total  
				characters. Used by the 4610SW/462x Web application."
                    ::= { endptAdvApps 26 }
endptWMLHOME    OBJECT-TYPE
                    SYNTAX      DisplayString 
                    MAX-ACCESS  read-only
                    STATUS      current
                    DESCRIPTION "4610SW/2x Web application URL. This variable returns
                        a URL of the Home page for the 4610SW/462x Web application."
                    ::= { endptAdvApps 27 }
endptWMLPORT    OBJECT-TYPE
                    SYNTAX      INTEGER
                    MAX-ACCESS  read-only
                    STATUS      current
                    DESCRIPTION "4610SW/2x Web application TCP port. This variable 
                        returns an integer specifying the TCP port most recently 
                        used for the HTTP proxy server.  Used by the 4610SW/462x
                        Web application."
                    ::= { endptAdvApps 28 }
endptWMLPROXY   OBJECT-TYPE
                    SYNTAX      OCTET STRING 
                    MAX-ACCESS  read-only
                    STATUS      current
                    DESCRIPTION "4610SW/2x Web Proxy Server. This variable returns
                        an IP addresses, in dotted-decimal or DNS format, of an  
                        HTTP proxy server.  Used by the 4610SW/2x Web application."
                    ::= { endptAdvApps 29 }
endptCTISTAT    OBJECT-TYPE
                    SYNTAX      INTEGER
                    MAX-ACCESS  read-only
                    STATUS      current
                    DESCRIPTION "CTI flag. This variable returns
                        0 if the CTI application is set to off, else 1."
                    ::= { endptAdvApps 30 }
endptCTIUDPPORT OBJECT-TYPE
                    SYNTAX      INTEGER
                    MAX-ACCESS  read-only
                    STATUS      current
                    DESCRIPTION "CTI application UDP port. This variable returns
                        an integer specifying the UDP port most recently used for 
                        the UDP listener to receive broadcast messages."
                    ::= { endptAdvApps 31 }
endptSTKSTAT    OBJECT-TYPE
                    SYNTAX      INTEGER
                    MAX-ACCESS  read-only
                    STATUS      current
                    DESCRIPTION "Stock Ticker flag. This variable returns
                        0 if the 4630 Stock Ticker application is set to off,
                        else 1."
                    ::= { endptAdvApps 32 }
endptSUBSCRIBELIST    OBJECT-TYPE
                    SYNTAX      DisplayString 
                    MAX-ACCESS  read-only
                    STATUS      current
                    DESCRIPTION "4610SW/2x Web push subscription list. This 
                        variable returns a string containing one or more fully 
                        qualified URLs to which the phone's Web application 
                        subscribes for potential pushed content."
                    ::= { endptAdvApps 33 }
endptTPSLIST    OBJECT-TYPE
                    SYNTAX      DisplayString 
                    MAX-ACCESS  read-only
                    STATUS      current
                    DESCRIPTION "4610SW/2x Web Trusted Push Server list. This 
                        variable returns a string containing one or more domains 
                        and paths in DNS format, used to determine for 
                        validation of push requests."
                    ::= { endptAdvApps 34 }
endptWMLIDLETIME    OBJECT-TYPE
                    SYNTAX      INTEGER
                    MAX-ACCESS  read-only
                    STATUS      current
                    DESCRIPTION "Web Idle Timer. This variable returns the number
                        of minutes, from 1 to 60 inclusive, of idle activity on the
                        telephone before the Web Idle Timer URI is displayed."
                    ::= { endptAdvApps 35 }
endptWMLIDLEURI    OBJECT-TYPE
                    SYNTAX      DisplayString
                    MAX-ACCESS  read-only
                    STATUS      current
                    DESCRIPTION "Web Idle Timer URI. This variable returns the
                        URI of the WML page displayed after the 4610SW/462x Web 
                        Idle Timer expires."
                    ::= { endptAdvApps 36 }


endptAdjuncts   OBJECT IDENTIFIER ::= { endpointMIB 6 }
endptFKEU       OBJECT-TYPE
                    SYNTAX      INTEGER
                    MAX-ACCESS  read-only
                    STATUS      current
                    DESCRIPTION "FKEU flag. This variable returns
                        0 if the Feature Key Expansion Unit is off, disabled, 
				or not present, else 1."
                    ::= { endptAdjuncts 1}
endptFKEUHEALTH OBJECT-TYPE
                    SYNTAX      INTEGER
                    MAX-ACCESS  read-only
                    STATUS      current
                    DESCRIPTION "FKEU flag. This variable returns
                        1 if the most recent self-test of the Feature Key Expansion 
				Unit or the 4620 failed, else 0."
                    ::= { endptAdjuncts 2}


endptSIP   OBJECT IDENTIFIER ::= { endpointMIB 7 }
endptCALLFWDSTAT OBJECT-TYPE
                    SYNTAX      INTEGER
                    MAX-ACCESS  read-only
                    STATUS      current
                    DESCRIPTION "Call Forwarding setting. This variable returns
                        the sum of all Call Forwarding permissions.  Range is 0
                        to 7, with 0 as the default."
                    ::= { endptSIP 1}
endptCOVERAGEADDR OBJECT-TYPE
                    SYNTAX      DisplayString
                    MAX-ACCESS  read-only
                    STATUS      current
                    DESCRIPTION "Call Coverage Server address. This variable returns
                        the URI to which call coverage is sent; up to 255 characters."
                    ::= { endptSIP 2}
endptDATETIMEFORMAT OBJECT-TYPE
                    SYNTAX      INTEGER
                    MAX-ACCESS  read-only
                    STATUS      current
                    DESCRIPTION "Date and Time format specification. This variable 
                        returns a parameter indicating the desired format for display 
				of date and time.  Range is 0 to 3, with 0 as the default."
                    ::= { endptSIP 3}
endptMUSICSRVR     OBJECT-TYPE
                    SYNTAX      DisplayString
                    MAX-ACCESS  read-only
                    STATUS      current
                    DESCRIPTION "List of music server addresses.  This variable 
				returns a sequence of IP addresses, in dotted-decimal format
				and separated by commas, of music servers available for use."
                    ::= { endptSIP 4}
endptMUSICSRVRINUSE     OBJECT-TYPE
                    SYNTAX      IpAddress
                    MAX-ACCESS  read-only
                    STATUS      current
                    DESCRIPTION "Music server address.  This variable returns a 
                        4-octet string specifying the IP address of the music server 
                        most recently used."
                    ::= { endptSIP 5}
endptMWISRVR    OBJECT-TYPE
                    SYNTAX      DisplayString
                    MAX-ACCESS  read-only
                    STATUS      current
                    DESCRIPTION "List of message waiting indicator server addresses.  
				This variable returns a sequence of IP addresses, in 
				dotted-decimal format and separated by commas, of message 
				waiting indicator servers available for use."
                    ::= { endptSIP 6}
endptMWISRVRINUSE   OBJECT-TYPE
                    SYNTAX      IpAddress
                    MAX-ACCESS  read-only
                    STATUS      current
                    DESCRIPTION "Message waiting indicator server address.  This 
                        variable returns a 4-octet string specifying the IP address 
                        of the message waiting indicator server most recently used."
                    ::= { endptSIP 7}
endptREGISTERWAIT OBJECT-TYPE
                    SYNTAX      INTEGER
                    MAX-ACCESS  read-only
                    STATUS      current
                    DESCRIPTION "Registration wait interval. This variable returns 
                        the number of seconds between attempts to re-register with 
				the current server.  Range is 0 to 65535, with 3600 as the
                        default."
                    ::= { endptSIP 8}
endptSIPPROXYSRVR    OBJECT-TYPE
                    SYNTAX      DisplayString
                    MAX-ACCESS  read-only
                    STATUS      current
                    DESCRIPTION "List of SIP Proxy server addresses.  This variable 
				returns a sequence of IP addresses, in dotted-decimal format 
				and separated by commas, of SIP Proxy servers available for use."
                    ::= { endptSIP 9}
endptSIPPROXYSRVRINUSE   OBJECT-TYPE
                    SYNTAX      IpAddress
                    MAX-ACCESS  read-only
                    STATUS      current
                    DESCRIPTION "SIP Proxy server address.  This variable returns a
                        4-octet string specifying the IP address of the SIP Proxy 
				server most recently used."
                    ::= { endptSIP 10}
endptSIPREGISTRAR    OBJECT-TYPE
                    SYNTAX      DisplayString
                    MAX-ACCESS  read-only
                    STATUS      current
                    DESCRIPTION "List of SIP registrar addresses.  This variable 
				returns a sequence of IP addresses, in dotted-decimal format 
				and separated by commas, of SIP registrars available for use."
                    ::= { endptSIP 11}
endptSIPREGISTRARINUSE   OBJECT-TYPE
                    SYNTAX      IpAddress
                    MAX-ACCESS  read-only
                    STATUS      current
                    DESCRIPTION "SIP registrar address.  This variable returns a 4-octet
                        string specifying the IP address of the SIP registrar most 
				recently used."
                    ::= { endptSIP 12}
endptSPEAKERSTAT OBJECT-TYPE
                    SYNTAX      INTEGER
                    MAX-ACCESS  read-only
                    STATUS      current
                    DESCRIPTION "Speaker setting. This variable returns a parameter
                        indicating the allowed level of speakerphone functionality.  
				Range is 0 to 2, with 2 as the default."
                    ::= { endptSIP 13}
endptSIPPORT    OBJECT-TYPE
                    SYNTAX      INTEGER 
                    MAX-ACCESS  read-only
                    STATUS      current
                    DESCRIPTION "TCP/UDP port used for SIP messages.  This variable 
                        returns the current port number used for SIP messaging.  The
                        default is 5060."
			  ::= { endptSIP 14}
endptSIPDOMAIN  OBJECT-TYPE
                    SYNTAX      DisplayString
                    MAX-ACCESS  read-only
                    STATUS      current
                    DESCRIPTION "SIP registration domain name.  This text is used in the 
                        Contact header field as part of SIP registration."
			  ::= { endptSIP 15}
endptPHNNUMOFSA OBJECT-TYPE
                    SYNTAX      INTEGER
                    MAX-ACCESS  read-only
                    STATUS      current
                    DESCRIPTION "Number of Session Appearances. This variable returns
                        the number of Session Appearances administered for the SIP 
                        phone."
                    ::= { endptSIP 16 }
endptDIALWAIT   OBJECT-TYPE
                    SYNTAX      INTEGER 
                    MAX-ACCESS  read-only
                    STATUS      current
                    DESCRIPTION "Dialing timeout interval.  This variable returns the 
                        number of seconds after the user stops dialing, that the 
                        telephone waits before automatically dialing the number enterered 
                        so far. The range is 0 to 10, and zero seconds means the 
                        telephone will wait forever, or until the user presses Send."
			  ::= { endptSIP 17}
endptDIALPLAN   OBJECT-TYPE
                    SYNTAX      DisplayString
                    MAX-ACCESS  read-only
                    STATUS      current
                    DESCRIPTION "SIP dial plan.  This variable returns the administered
                        dial plan, used during manual dialing to allow a call to be 			      initiated without the use of a Send button and without waiting 
                        for the expiration of a timeout interval; up to 1000 characters."
			  ::= { endptSIP 18}
endptCALLFWDADDR OBJECT-TYPE
                    SYNTAX      DisplayString
                    MAX-ACCESS  read-only
                    STATUS      current
                    DESCRIPTION "Call Forwarding address. This variable returns
                        the URI to which calls are forwarded; up to 255 characters."
                    ::= { endptSIP 19}
endptCALLFWDDELAY OBJECT-TYPE
                    SYNTAX      INTEGER 
                    MAX-ACCESS  read-only
                    STATUS      current
                    DESCRIPTION "Call Forwarding delay. This variable returns the number 
                        of times the telephone will ring before a call is forwarded, if 
                        Call Forwarding on No Answer is selected."
			  ::= { endptSIP 20}
END
