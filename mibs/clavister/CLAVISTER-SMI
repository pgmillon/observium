CLAVISTER-SMI DEFINITIONS ::= BEGIN

IMPORTS
    MODULE-IDENTITY, enterprises
        FROM SNMPv2-SMI;

clavisterSmiMibModule MODULE-IDENTITY
    LAST-UPDATED "200605190900Z"
    ORGANIZATION 
        "Clavister AB"
    CONTACT-INFO 
        "Clavister Support
         
         Box 393
         SE-891 28 ORNSKOLDSVIK
         SWEDEN
         
         Tel: +46-660-299200
         E-mail: support@clavister.com
         http://www.clavister.com"
    DESCRIPTION 
        "Smi Mib"
    REVISION    "200605190900Z"
    DESCRIPTION 
        "Initial version."
    ::= { clavister 0 }


clavister OBJECT IDENTIFIER ::= { enterprises 5089 }

clavisterOS OBJECT IDENTIFIER ::= { clavister 1 }

clavisterOSTrap OBJECT IDENTIFIER ::= { clavisterOS 0 }

clavisterOSTrapInfo OBJECT IDENTIFIER ::= { clavisterOS 1 }

clavisterOSStats OBJECT IDENTIFIER ::= { clavisterOS 2 }

clavisterReg OBJECT IDENTIFIER ::= { clavister 2 }

clavisterMibModules OBJECT IDENTIFIER ::= { clavisterReg  1 }

clavisterMibConfs OBJECT IDENTIFIER ::= { clavisterReg 2 }

clavisterMibObjectGroups OBJECT IDENTIFIER ::= { clavisterReg 3 }

END -- end of module CLAVISTER-SMI.
