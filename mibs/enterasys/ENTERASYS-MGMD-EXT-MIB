ENTERASYS-MGMD-EXT-MIB DEFINITIONS ::= BEGIN

--  enterasys-mgmd-ext-mib.txt
--
--  Part Number:
--
--

--  This module provides authoritative definitions for Enterasys 
--  Networks' MGMD Extension MIB.

--
--  This module will be extended, as needed.

--  Enterasys Networks reserves the right to make changes in this
--  specification and other information contained in this document
--  without prior notice.  The reader should consult Enterasys Networks
--  to determine whether any such changes have been made.
--
--  In no event shall Enterasys Networks be liable for any incidental,
--  indirect, special, or consequential damages whatsoever (including
--  but not limited to lost profits) arising out of or related to this
--  document or the information contained in it, even if Enterasys
--  Networks has been advised of, known, or should have known, the
--  possibility of such damages.
--
--  Enterasys Networks grants vendors, end-users, and other interested
--  parties a non-exclusive license to use this Specification in 
--  connection with the management of Enterasys Networks products.

--  Copyright <February, 2010> Enterasys Networks, Inc.

IMPORTS
    MODULE-IDENTITY, OBJECT-TYPE, Integer32, Counter32, TimeTicks
        FROM SNMPv2-SMI
    TEXTUAL-CONVENTION, RowStatus, TruthValue
        FROM SNMPv2-TC
    MODULE-COMPLIANCE, OBJECT-GROUP
        FROM SNMPv2-CONF
    SnmpAdminString
        FROM SNMP-FRAMEWORK-MIB
    InetAddressType, InetAddress 
        FROM INET-ADDRESS-MIB
    InterfaceIndex, ifIndex
        FROM IF-MIB
    dot1dBasePort
        FROM BRIDGE-MIB
    PortList
        FROM Q-BRIDGE-MIB
    EnabledStatus
        FROM P-BRIDGE-MIB
    etsysModules 
        FROM ENTERASYS-MIB-NAMES;

etsysMgmdExtMIB MODULE-IDENTITY
    LAST-UPDATED "201002081408Z"  -- Mon Feb  8 14:08 UTC 2010
    ORGANIZATION "Enterasys Networks, Inc"
    CONTACT-INFO
        "Postal:  Enterasys Networks
                  50 Minuteman Rd.
                  Andover, MA 01810-1008
                  USA
         Phone:   +1 978 684 1000
         E-mail:  support@enterasys.com
         WWW:     http://www.enterasys.com"
   
    DESCRIPTION
        "This MIB module defines a portion of the SNMP MIB under
         the Enterasys Networks enterprise OID pertaining to 
         IGMP operation on a device.

         This MIB contains Enterasys proprietary MGMD information that
         goes above and beyond any IETF multicast MIBs. It is intended 
         to cover any Enterasys value added features and configurations."

    REVISION    "201002081408Z"  -- Mon Feb  8 14:08 UTC 2010
    DESCRIPTION "The initial version of this MIB module"

    ::= { etsysModules 71 } 



-- Textual Conventions
    MGMDNumGroupsTc ::=  TEXTUAL-CONVENTION
        STATUS  current
        DESCRIPTION
            " This textual convention describes the available MGMD
              number of groups size selection. None means no flows are
              currently supported. The rest of the settings are
              dependent on which hardware platform you are running on.
              Please see the users manual for your device to see what 
              these values mean."
        SYNTAX  INTEGER  {
                            none(1),
                            minimum(2),
                            default(3),
                            maximum(4)
                          }

    MGMDPortModeTc  ::=  TEXTUAL-CONVENTION
        STATUS  current
        DESCRIPTION
            "This textual convention maps out possible MGMD port modes."
        SYNTAX  INTEGER {
                            reporter(1),
                            source(2)
                        }

    MGMDDiscoveredRouterModeTc  ::= TEXTUAL-CONVENTION
        STATUS  current
        DESCRIPTION
            "This textual convention maps the possible ways a router may
              be discovered by the device."
        SYNTAX  INTEGER {
                            querier(1),
                            routingProtocol(2),
                            multicastRouterDiscovery(3),
                            staticallyConfigured(4)
                        }

    MGMDProtocolClassTc  ::=  TEXTUAL-CONVENTION
        STATUS current
        DESCRIPTION
            "This textual convention describes the possible ways
            IGMP/MLD can classify received frames."
        SYNTAX  INTEGER {
                            multicastData(1),
                            routingProtocol(2),
                            ignore(3)
                        }

    MGMDProtocolIdTc ::= TEXTUAL-CONVENTION
        STATUS current
        DESCRIPTION
            "Bit definitions for each of the IP protocol numbers assigned by
            IANA."
        SYNTAX BITS {
            hopopt       (0), -- IPv6 Hop-by-Hop Option            [RFC1883]
            icmp         (1), -- Internet Control Message           [RFC792]
            igmp         (2), -- Internet Group Management         [RFC1112]
            ggp          (3), -- Gateway-to-Gateway                 [RFC823]
            ip           (4), -- IP in IP (encapsulation)          [RFC2003]
            st           (5), -- Stream                    [RFC1190,RFC1819]
            tcp          (6), -- Transmission Control               [RFC793]
            cbt          (7), -- CBT                             [Ballardie]
            egp          (8), -- Exterior Gateway Protocol     [RFC888,DLM1]
            igp          (9), -- any private interior gateway         [IANA]
                              -- (used by Cisco for their IGRP)
            bbnRccMon   (10), -- BBN RCC Monitoring                    [SGC]
            nvpII       (11), -- Network Voice Protocol         [RFC741,SC3]
            pup         (12), -- PUP                             [PUP,XEROX]
            argus       (13), -- ARGUS                                [RWS4]
            emcon       (14), -- EMCON                                 [BN7]
            xnet        (15), -- Cross Net Debugger            [IEN158,JFH2]
            chaos       (16), -- Chaos                                 [NC3]
            udp         (17), -- User Datagram                  [RFC768,JBP]
            mux         (18), -- Multiplexing                    [IEN90,JBP]
            dcnMeas     (19), -- DCN Measurement Subsystems           [DLM1]
            hmp         (20), -- Host Monitoring                [RFC869,RH6]
            prm         (21), -- Packet Radio Measurement              [ZSU]
            xnsIdp      (22), -- XEROX NS IDP               [ETHERNET,XEROX]
            trunk1      (23), -- Trunk-1                              [BWB6]
            trunk2      (24), -- Trunk-2                              [BWB6]
            leaf1       (25), -- Leaf-1                               [BWB6]
            leaf2       (26), -- Leaf-2                               [BWB6]
            rdp         (27), -- Reliable Data Protocol         [RFC908,RH6]
            irtp        (28), -- Internet Reliable Transaction  [RFC938,TXM]
            isoTp4      (29), -- ISO Transport Protocol Class 4 [RFC905,RC77]
            netblt      (30), -- Bulk Data Transfer Protocol    [RFC969,DDC1]
            mfeNsp      (31), -- MFE Network Services Protocol  [MFENET,BCH2]
            meritInp    (32), -- MERIT Internodal Protocol             [HWB]
            sep         (33), -- Sequential Exchange Protocol        [JC120]
            x3pc        (34), -- Third Party Connect Protocol         [SAF3]
            idpr        (35), -- Inter-Domain Policy Routing Protocol [MXS1] 
            xtp         (36), -- XTP                                   [GXC]
            ddp         (37), -- Datagram Delivery Protocol            [WXC]
            idprCmtp    (38), -- IDPR Control Message Transport Proto [MXS1]
            tpPlusPlus  (39), -- TP++ Transport Protocol               [DXF]
            il          (40), -- IL Transport Protocol            [Presotto]
            ipv6        (41), -- Ipv6                              [Deering]    
            sdrp        (42), -- Source Demand Routing Protocol       [DXE1]
            ipv6Route   (43), -- Routing Header for IPv6           [Deering]
            ipv6Frag    (44), -- Fragment Header for IPv6          [Deering]
            idrp        (45), -- Inter-Domain Routing Protocol   [Sue Hares]
            rsvp        (46), -- Reservation Protocol           [Bob Braden]
            gre         (47), -- General Routing Encapsulation     [Tony Li]
            mhrp        (48), -- Mobile Host Routing Protocol[David Johnson]
            bna         (49), -- BNA                          [Gary Salamon]
            esp         (50), -- Encap Security Payload            [RFC2406]
            ah          (51), -- Authentication Header             [RFC2402]
            inlsp       (52), -- Integrated Net Layer Security  TUBA [GLENN]
            swipe       (53), -- IP with Encryption                    [JI6]
            narp        (54), -- NBMA Address Resolution Protocol  [RFC1735]
            mobile      (55), -- IP Mobility                       [Perkins]
            tlsp        (56), -- Transport Layer Security Protocol   [Oberg]
                              -- using Kryptonet key management
            skip        (57), -- SKIP                              [Markson]
            ipv6Icmp    (58), -- ICMP for IPv6                     [RFC1883]
            ipv6NoNxt   (59), -- No Next Header for IPv6           [RFC1883]
            ipv6Opts    (60), -- Destination Options for IPv6      [RFC1883]
            ipProt61    (61), -- any host internal protocol           [IANA]
            cftp        (62), -- CFTP                            [CFTP,HCF2]
            ipProt63    (63), -- any local network                    [IANA]
            satExpak    (64), -- SATNET and Backroom EXPAK             [SHB]
            kryptolan   (65), -- Kryptolan                            [PXL1]
            rvd         (66), -- MIT Remote Virtual Disk Protocol      [MBG]
            ippc        (67), -- Internet Pluribus Packet Core         [SHB]
            ipProt64    (68), -- any distributed file system          [IANA]
            satMon      (69), -- SATNET Monitoring                     [SHB]
            visa        (70), -- VISA Protocol                        [GXT1]
            ipcv        (71), -- Internet Packet Core Utility          [SHB]
            cpnx        (72), -- Computer Protocol Network Executive  [DXM2]
            cphb        (73), -- Computer Protocol Heart Beat         [DXM2]
            wsn         (74), -- Wang Span Network                     [VXD]
            pvp         (75), -- Packet Video Protocol                 [SC3]
            brSatMon    (76), -- Backroom SATNET Monitoring            [SHB]
            sunNd       (77), -- SUN ND PROTOCOL-Temporary             [WM3]
            wbMon       (78), -- WIDEBAND Monitoring                   [SHB]
            wbExpak     (79), -- WIDEBAND EXPAK                        [SHB]
            isoIp       (80), -- ISO Internet Protocol                 [MTR]
            vmtp        (81), -- VMTP                                 [DRC3]
            secureVmtp  (82), -- SECURE-VMTP                          [DRC3]
            vines       (83), -- VINES                                 [BXH]
            ttp         (84), -- TTP                                   [JXS]
            nsfnetIgp   (85), -- NSFNET-IGP                            [HWB]
            dgp         (86), -- Dissimilar Gateway Protocol     [DGP,ML109]
            tcf         (87), -- TCF                                  [GAL5]
            eigrp       (88), -- EIGRP                           [CISCO,GXS]
            ospfIgp     (89), -- OSPFIGP                      [RFC1583,JTM4]
            spriteRpc   (90), -- Sprite RPC Protocol            [SPRITE,BXW]
            larp        (91), -- Locus Address Resolution Protocol     [BXH]
            mtp         (92), -- Multicast Transport Protocol          [SXA]
            ax25        (93), -- AX.25 Frames                         [BK29]
            ipip        (94), -- IP-within-IP Encapsulation Protocol   [JI6]
            micp        (95), -- Mobile Internetworking Control Pro.   [JI6]
            sccSp       (96), -- Semaphore Communications Sec. Pro.    [HXH]
            etherIp     (97), -- Ethernet-within-IP Encapsulation  [RFC3378]
            encap       (98), -- Encapsulation Header         [RFC1241,RXB3]
            ipProt99    (99), -- any private encryption scheme        [IANA]
            gmtp       (100), -- GMTP                                 [RXB5]
            ifmp       (101), -- Ipsilon Flow Management Protocol   [Hinden]
            pnni       (102), -- PNNI over IP                       [Callon]
            pim        (103), -- Protocol Independent Multicast  [Farinacci]
            aris       (104), -- ARIS                              [Feldman]
            scps       (105), -- SCPS                                [Durst]
            qnx        (106), -- QNX                                [Hunter]
            an         (107), -- Active Networks                    [Braden]
            ipComp     (108), -- IP Payload Compression Protocol   [RFC2393]
            snp        (109), -- Sitara Networks Protocol          [Sridhar]
            compaqPeer (110), -- Compaq Peer Protocol                [Volpe]
            ipxInIp    (111), -- IPX in IP                             [Lee]
            vrrp       (112), -- Virtual Router Redundancy Protocol [RFC3768]
            pgm        (113), -- PGM Reliable Transport Protocol  [Speakman]
            ipProt114  (114), -- any 0-hop protocol                   [IANA]
            l2tp       (115), -- Layer Two Tunneling Protocol        [Aboba]
            ddx        (116), -- D-II Data Exchange (DDX)           [Worley] 
            iatp       (117), -- Interactive Agent Transfer Protocol [Murphy]
            stp        (118), -- Schedule Transfer Protocol            [JMP]
            srp        (119), -- SpectraLink Radio Protocol       [Hamilton]
            uti        (120), -- UTI                              [Lothberg]
            smp        (121), -- Simple Message Protocol            [Ekblad]
            sm         (122), -- SM                              [Crowcroft]
            ptp        (123), -- Performance Transparency Protocol   [Welzl]
            isisIpv4   (124), -- ISIS over IPv4                 [Przygienda]
            fire       (125), --                                 [Partridge]
            crtp       (126), -- Combat Radio Transport Protocol   [Sautter]
            crudp      (127), -- Combat Radio User Datagram        [Sautter]
            sscopmce   (128), --                                     [Waber]
            iplt       (129), --                                  [Hollbach]
            sps        (130), -- Secure Packet Shield             [McIntosh] 
            pipe       (131), -- Private IP Encapsulation within IP  [Petri]
            sctp       (132), -- Stream Control Transmission Protocol [Stewart]
            fc         (133), -- Fibre Channel                   [Rajagopal]
            rsvpE2eIgn (134), -- RSVP-E2E-IGNORE                   [RFC3175]
            mobHeader  (135), -- Mobility Header                   [RFC3775]
            udpLite    (136), -- UDPLite                           [RFC3828]
            mpls       (137), -- MPLS-in-IP                        [RFC4023]
            ipProto138 (138), -- Unassigned                           [IANA]
            ipProto139 (139), -- Unassigned                           [IANA]
            ipProto140 (140), -- Unassigned                           [IANA]
            ipProto141 (141), -- Unassigned                           [IANA]
            ipProto142 (142), -- Unassigned                           [IANA]
            ipProto143 (143), -- Unassigned                           [IANA]
            ipProto144 (144), -- Unassigned                           [IANA]
            ipProto145 (145), -- Unassigned                           [IANA]
            ipProto146 (146), -- Unassigned                           [IANA]
            ipProto147 (147), -- Unassigned                           [IANA]
            ipProto148 (148), -- Unassigned                           [IANA]
            ipProto149 (149), -- Unassigned                           [IANA]
            ipProto150 (150), -- Unassigned                           [IANA]
            ipProto151 (151), -- Unassigned                           [IANA]
            ipProto152 (152), -- Unassigned                           [IANA]
            ipProto153 (153), -- Unassigned                           [IANA]
            ipProto154 (154), -- Unassigned                           [IANA]
            ipProto155 (155), -- Unassigned                           [IANA]
            ipProto156 (156), -- Unassigned                           [IANA]
            ipProto157 (157), -- Unassigned                           [IANA]
            ipProto158 (158), -- Unassigned                           [IANA]
            ipProto159 (159), -- Unassigned                           [IANA]
            ipProto160 (160), -- Unassigned                           [IANA]
            ipProto161 (161), -- Unassigned                           [IANA]
            ipProto162 (162), -- Unassigned                           [IANA]
            ipProto163 (163), -- Unassigned                           [IANA]
            ipProto164 (164), -- Unassigned                           [IANA]
            ipProto165 (165), -- Unassigned                           [IANA]
            ipProto166 (166), -- Unassigned                           [IANA]
            ipProto167 (167), -- Unassigned                           [IANA]
            ipProto168 (168), -- Unassigned                           [IANA]
            ipProto169 (169), -- Unassigned                           [IANA]
            ipProto170 (170), -- Unassigned                           [IANA]
            ipProto171 (171), -- Unassigned                           [IANA]
            ipProto172 (172), -- Unassigned                           [IANA]
            ipProto173 (173), -- Unassigned                           [IANA]
            ipProto174 (174), -- Unassigned                           [IANA]
            ipProto175 (175), -- Unassigned                           [IANA]
            ipProto176 (176), -- Unassigned                           [IANA]
            ipProto177 (177), -- Unassigned                           [IANA]
            ipProto178 (178), -- Unassigned                           [IANA]
            ipProto179 (179), -- Unassigned                           [IANA]
            ipProto180 (180), -- Unassigned                           [IANA]
            ipProto181 (181), -- Unassigned                           [IANA]
            ipProto182 (182), -- Unassigned                           [IANA]
            ipProto183 (183), -- Unassigned                           [IANA]
            ipProto184 (184), -- Unassigned                           [IANA]
            ipProto185 (185), -- Unassigned                           [IANA]
            ipProto186 (186), -- Unassigned                           [IANA]
            ipProto187 (187), -- Unassigned                           [IANA]
            ipProto188 (188), -- Unassigned                           [IANA]
            ipProto189 (189), -- Unassigned                           [IANA]
            ipProto190 (190), -- Unassigned                           [IANA]
            ipProto191 (191), -- Unassigned                           [IANA]
            ipProto192 (192), -- Unassigned                           [IANA]
            ipProto193 (193), -- Unassigned                           [IANA]
            ipProto194 (194), -- Unassigned                           [IANA]
            ipProto195 (195), -- Unassigned                           [IANA]
            ipProto196 (196), -- Unassigned                           [IANA]
            ipProto197 (197), -- Unassigned                           [IANA]
            ipProto198 (198), -- Unassigned                           [IANA]
            ipProto199 (199), -- Unassigned                           [IANA]
            ipProto200 (200), -- Unassigned                           [IANA]
            ipProto201 (201), -- Unassigned                           [IANA]
            ipProto202 (202), -- Unassigned                           [IANA]
            ipProto203 (203), -- Unassigned                           [IANA]
            ipProto204 (204), -- Unassigned                           [IANA]
            ipProto205 (205), -- Unassigned                           [IANA]
            ipProto206 (206), -- Unassigned                           [IANA]
            ipProto207 (207), -- Unassigned                           [IANA]
            ipProto208 (208), -- Unassigned                           [IANA]
            ipProto209 (209), -- Unassigned                           [IANA]
            ipProto210 (210), -- Unassigned                           [IANA]
            ipProto211 (211), -- Unassigned                           [IANA]
            ipProto212 (212), -- Unassigned                           [IANA]
            ipProto213 (213), -- Unassigned                           [IANA]
            ipProto214 (214), -- Unassigned                           [IANA]
            ipProto215 (215), -- Unassigned                           [IANA]
            ipProto216 (216), -- Unassigned                           [IANA]
            ipProto217 (217), -- Unassigned                           [IANA]
            ipProto218 (218), -- Unassigned                           [IANA]
            ipProto219 (219), -- Unassigned                           [IANA]
            ipProto220 (220), -- Unassigned                           [IANA]
            ipProto221 (221), -- Unassigned                           [IANA]
            ipProto222 (222), -- Unassigned                           [IANA]
            ipProto223 (223), -- Unassigned                           [IANA]
            ipProto224 (224), -- Unassigned                           [IANA]
            ipProto225 (225), -- Unassigned                           [IANA]
            ipProto226 (226), -- Unassigned                           [IANA]
            ipProto227 (227), -- Unassigned                           [IANA]
            ipProto228 (228), -- Unassigned                           [IANA]
            ipProto229 (229), -- Unassigned                           [IANA]
            ipProto230 (230), -- Unassigned                           [IANA]
            ipProto231 (231), -- Unassigned                           [IANA]
            ipProto232 (232), -- Unassigned                           [IANA]
            ipProto233 (233), -- Unassigned                           [IANA]
            ipProto234 (234), -- Unassigned                           [IANA]
            ipProto235 (235), -- Unassigned                           [IANA]
            ipProto236 (236), -- Unassigned                           [IANA]
            ipProto237 (237), -- Unassigned                           [IANA]
            ipProto238 (238), -- Unassigned                           [IANA]
            ipProto239 (239), -- Unassigned                           [IANA]
            ipProto240 (240), -- Unassigned                           [IANA]
            ipProto241 (241), -- Unassigned                           [IANA]
            ipProto242 (242), -- Unassigned                           [IANA]
            ipProto243 (243), -- Unassigned                           [IANA]
            ipProto244 (244), -- Unassigned                           [IANA]
            ipProto245 (245), -- Unassigned                           [IANA]
            ipProto246 (246), -- Unassigned                           [IANA]
            ipProto247 (247), -- Unassigned                           [IANA]
            ipProto248 (248), -- Unassigned                           [IANA]
            ipProto249 (249), -- Unassigned                           [IANA]
            ipProto250 (250), -- Unassigned                           [IANA]
            ipProto251 (251), -- Unassigned                           [IANA]
            ipProto252 (252), -- Unassigned                           [IANA]
            ipProto253 (253), -- Use for experimentation and testing [RFC3692] 
            ipProto254 (254), -- Use for experimentation and testing [RFC3692] 
            ipProto255 (255)  -- Reserved                             [IANA]
        }

-- -------------------------------------------------------------
-- MIB Objects
-- -------------------------------------------------------------
etsysMgmdExtObjects                     OBJECT IDENTIFIER ::= { etsysMgmdExtMIB 1 }
etsysMgmdExtConfigGroup                 OBJECT IDENTIFIER ::= { etsysMgmdExtObjects 1 }
etsysMgmdExtInterfaceGroup              OBJECT IDENTIFIER ::= { etsysMgmdExtObjects 2 }
etsysMgmdExtStaticCacheGroup            OBJECT IDENTIFIER ::= { etsysMgmdExtObjects 3 }
etsysMgmdExtCacheGroup                  OBJECT IDENTIFIER ::= { etsysMgmdExtObjects 4 }
etsysMgmdExtDiscoveredRouterGroup       OBJECT IDENTIFIER ::= { etsysMgmdExtObjects 5 }
etsysMgmdExtPortGroup                   OBJECT IDENTIFIER ::= { etsysMgmdExtObjects 6 }
etsysMgmdExtPortFastLeaveGroup          OBJECT IDENTIFIER ::= { etsysMgmdExtObjects 7 }
etsysMgmdExtStatsCntrsGroup             OBJECT IDENTIFIER ::= { etsysMgmdExtObjects 8 }
etsysMgmdExtProtocolClassificationGroup OBJECT IDENTIFIER ::= { etsysMgmdExtObjects 9 }

-- -------------------------------------------------------------
-- etsysMgmdExtConfigGroup
-- -------------------------------------------------------------
etsysMgmdExtConfigRevString OBJECT-TYPE
    SYNTAX     SnmpAdminString
    MAX-ACCESS read-only
    STATUS     current
    DESCRIPTION
          "This object is a textual representation of the revision of the
          Enterasys MGMD MIB in the firmware."
    ::= { etsysMgmdExtConfigGroup 1 }

etsysMgmdExtConfigFullAction OBJECT-TYPE
    SYNTAX    INTEGER {
                routers(1),
                flood(2)
                      }
    MAX-ACCESS read-write
    STATUS     current
    DESCRIPTION
          "This object defines the behavior of IGMP/MLD when its group table
           is full.  The user may choose to send multicast frames to
           known routers, or flood these frames to the vlan."
    DEFVAL  { flood }
    ::= { etsysMgmdExtConfigGroup 2 }

etsysMgmdExtConfigMinNumberOfGroups OBJECT-TYPE
    SYNTAX     Integer32
    MAX-ACCESS read-only
    STATUS     current
    DESCRIPTION
          " This object will state the minimum number of multicast groups this
            device is capable of setting."
    ::= { etsysMgmdExtConfigGroup 3 }

etsysMgmdExtConfigDefaultNumberOfGroups OBJECT-TYPE
    SYNTAX     Integer32
    MAX-ACCESS read-only
    STATUS     current
    DESCRIPTION
          " This object states the default number of multicast groups this
            device will be set to."
    ::= { etsysMgmdExtConfigGroup 4 }

etsysMgmdExtConfigMaxNumberOfGroups OBJECT-TYPE
    SYNTAX     Integer32
    MAX-ACCESS read-only
    STATUS     current
    DESCRIPTION
          " This object states the maximum number of multicast groups this
            device is capable of setting."
    ::= { etsysMgmdExtConfigGroup 5 }

etsysMgmdExtConfigNumberOfGroups OBJECT-TYPE
    SYNTAX     MGMDNumGroupsTc
    MAX-ACCESS read-write
    STATUS     current
    DESCRIPTION
          " This object allow the user to select the IGMP/MLD group table
            size for this device."
    DEFVAL { default }
    ::= { etsysMgmdExtConfigGroup 6 }

-- -------------------------------------------------------------
-- etsysMgmdExtInterfaceGroup
-- -------------------------------------------------------------
etsysMgmdExtInterfaceTable OBJECT-TYPE
     SYNTAX     SEQUENCE OF EtsysMgmdExtInterfaceEntry
     MAX-ACCESS not-accessible
     STATUS     current
     DESCRIPTION
          "The (conceptual) table listing the interfaces on which IGMP/MLD
          is enabled."
     ::= { etsysMgmdExtInterfaceGroup 1 }

etsysMgmdExtInterfaceEntry OBJECT-TYPE
     SYNTAX     EtsysMgmdExtInterfaceEntry
     MAX-ACCESS not-accessible
     STATUS     current
     DESCRIPTION
          "An entry (conceptual row) representing an interface on
           which IGMP/MLD is enabled."
     INDEX { etsysMgmdExtInterfaceApplication, ifIndex }
     ::= { etsysMgmdExtInterfaceTable 1 }

EtsysMgmdExtInterfaceEntry      ::= SEQUENCE {
     etsysMgmdExtInterfaceApplication         InetAddressType,
     etsysMgmdExtInterfaceQueryEnableState    EnabledStatus,
     etsysMgmdExtInterfaceFastLeaveState      EnabledStatus,
     etsysMgmdExtInterfaceClearGroups         TruthValue,
     etsysMgmdExtRtrAlertRequired             TruthValue
     }

etsysMgmdExtInterfaceApplication OBJECT-TYPE
    SYNTAX     InetAddressType
    MAX-ACCESS not-accessible
    STATUS     current
    DESCRIPTION
         "The multicast application this object refers to.
          ipv4(1) refers to IGMP, ipv6(2) refers to MLD."
    ::= {etsysMgmdExtInterfaceEntry 1 }
     
etsysMgmdExtInterfaceQueryEnableState OBJECT-TYPE
    SYNTAX     EnabledStatus
    MAX-ACCESS read-create
    STATUS     current
    DESCRIPTION
         "The state of active querying on this interface."
    DEFVAL { disabled }
    ::= { etsysMgmdExtInterfaceEntry 2 }

etsysMgmdExtInterfaceFastLeaveState OBJECT-TYPE
     SYNTAX     EnabledStatus
     MAX-ACCESS read-create
     STATUS     current
     DESCRIPTION
          "The state of Fast Leave on this interface."
     DEFVAL { disabled }
     ::= { etsysMgmdExtInterfaceEntry 3 }

etsysMgmdExtInterfaceClearGroups OBJECT-TYPE
     SYNTAX    TruthValue 
     MAX-ACCESS read-write
     STATUS     current
     DESCRIPTION
          "A mechanism to flush the database of IP group members maintained 
           by the IGMP snooping application on this interface.  Setting the 
           value to true will clear the group members.  Setting the value
           to false will have no effect.  This value will always read false"
     ::= { etsysMgmdExtInterfaceEntry 4 }

etsysMgmdExtRtrAlertRequired OBJECT-TYPE
     SYNTAX    TruthValue 
     MAX-ACCESS read-write
     STATUS     current
     DESCRIPTION
          "A mechanism to allow backward compatibility with older 
           implementations of IGMPv2 that may be present on this interface. 
           The default setting of this value to true will cause IGMPv2 
           messages missing the router alert IP option to be discarded.
           Setting this value to false will cause the router alert requirement
           for IGMPv2 messages heard on this interface to be ignored."
     REFERENCE "RFC 2236, sections 2 and 10.  RFC 3376, sections 4 and 9."
	 DEFVAL { true }
     ::= { etsysMgmdExtInterfaceEntry 5 }

-- -------------------------------------------------------------
-- etsysMgmdExtStaticCacheGroup
-- -------------------------------------------------------------
etsysMgmdExtStaticCacheTable OBJECT-TYPE
    SYNTAX        SEQUENCE OF EtsysMgmdExtStaticCacheEntry
    MAX-ACCESS    not-accessible
    STATUS        current
    DESCRIPTION
         "The (conceptual) table listing the static IGMP/MLD cache entries."
    ::= { etsysMgmdExtStaticCacheGroup 1 }

etsysMgmdExtStaticCacheEntry OBJECT-TYPE
    SYNTAX        EtsysMgmdExtStaticCacheEntry
    MAX-ACCESS    not-accessible
    STATUS        current
    DESCRIPTION
         "An entry (conceptual row) representing a static entry that
          IGMP/MLD will act upon."
    INDEX { etsysMgmdExtStaticCacheIPAddrType,
            etsysMgmdExtStaticCacheGroupIPAddress,
            ifIndex,
            etsysMgmdExtStaticCacheSourceIPAddress }
::= { etsysMgmdExtStaticCacheTable 1 }

EtsysMgmdExtStaticCacheEntry ::= SEQUENCE {
        etsysMgmdExtStaticCacheIPAddrType               InetAddressType,
        etsysMgmdExtStaticCacheGroupIPAddress           InetAddress,
        etsysMgmdExtStaticCacheSourceIPAddress          InetAddress,
        etsysMgmdExtStaticCacheIncludeList              PortList,
        etsysMgmdExtStaticCacheExcludeList              PortList,
        etsysMgmdExtStaticCacheRowStatus                RowStatus
     }

etsysMgmdExtStaticCacheIPAddrType OBJECT-TYPE
    SYNTAX        InetAddressType
    MAX-ACCESS    not-accessible
    STATUS        current
    DESCRIPTION
          "The IP address type of the group and source IPs."
    ::= { etsysMgmdExtStaticCacheEntry 1 }

etsysMgmdExtStaticCacheGroupIPAddress OBJECT-TYPE
    SYNTAX        InetAddress (SIZE(4|16))
    MAX-ACCESS    not-accessible
    STATUS        current
    DESCRIPTION
         "The IP multicast group address for IGMP to send
          multicast data to."
    ::= { etsysMgmdExtStaticCacheEntry 2 }

etsysMgmdExtStaticCacheSourceIPAddress OBJECT-TYPE
     SYNTAX     InetAddress (SIZE(4|16))
     MAX-ACCESS not-accessible
     STATUS     current
     DESCRIPTION
          "The IP source address of this entry. For IGMP Version 2,
           and MLD v1, use the unspecified address."
    ::= { etsysMgmdExtStaticCacheEntry 3 }

etsysMgmdExtStaticCacheIncludeList OBJECT-TYPE
    SYNTAX        PortList
    MAX-ACCESS    read-write
    STATUS        current
    DESCRIPTION
         "The set of ports configured by management for this multicast
          group and this interface to which multicast group-addressed
          data frames are to be forwarded. The default is all bits
          cleared."
    ::= { etsysMgmdExtStaticCacheEntry 4 }

etsysMgmdExtStaticCacheExcludeList OBJECT-TYPE
    SYNTAX        PortList
    MAX-ACCESS    read-write
    STATUS        current
    DESCRIPTION
         "The set of ports configured by management for this multicast
          group and this interface for which multicast group-addressed
          data frames are not to be forwarded. The default is all bits
          cleared."
    ::= { etsysMgmdExtStaticCacheEntry 5 }

etsysMgmdExtStaticCacheRowStatus OBJECT-TYPE
    SYNTAX        RowStatus
    MAX-ACCESS    read-create
    STATUS        current
    DESCRIPTION
         "active(1) creates a static entry.
          notInService(2) disables a static entry.
          destroy(6) deletes a static entry."
    ::= { etsysMgmdExtStaticCacheEntry 6 }

-- -------------------------------------------------------------
-- etsysMgmdExtCacheGroup
-- -------------------------------------------------------------
etsysMgmdExtCacheTable OBJECT-TYPE
     SYNTAX     SEQUENCE OF EtsysMgmdExtCacheEntry
     MAX-ACCESS not-accessible
     STATUS     current
     DESCRIPTION
          "The (conceptual) table listing the IP multicast groups for
           interfaces with members on this particular interface. This table
           provides a version 3 capable etsysMgmdExtCacheTable, with a bridge
           PortList leaf vs mib2 interface index."
     ::= { etsysMgmdExtCacheGroup 1 }

etsysMgmdExtCacheEntry OBJECT-TYPE
     SYNTAX     EtsysMgmdExtCacheEntry
     MAX-ACCESS not-accessible
     STATUS     current
     DESCRIPTION
          "An entry (conceptual row) in the etsysMgmdExtCacheTable."
     INDEX { etsysMgmdExtCacheIPAddrType,
             etsysMgmdExtCacheGroupIPAddress,
             ifIndex,
             etsysMgmdExtCacheSourceIPAddress }
     ::= { etsysMgmdExtCacheTable 1 }

EtsysMgmdExtCacheEntry      ::= SEQUENCE {
     etsysMgmdExtCacheIPAddrType           InetAddressType,
     etsysMgmdExtCacheGroupIPAddress       InetAddress,
     etsysMgmdExtCacheSourceIPAddress      InetAddress,
     etsysMgmdExtCacheExpiryTime           Integer32,
     etsysMgmdExtCacheIncludePortList      PortList,
     etsysMgmdExtCacheExcludePortList      PortList,
     etsysMgmdExtCacheSrcPort              Integer32
     }

etsysMgmdExtCacheIPAddrType OBJECT-TYPE
     SYNTAX     InetAddressType
     MAX-ACCESS not-accessible
     STATUS     current
     DESCRIPTION
           "The IP address type of the group and source IP
            addresses."
     ::= { etsysMgmdExtCacheEntry 1}

etsysMgmdExtCacheGroupIPAddress OBJECT-TYPE
     SYNTAX     InetAddress (SIZE(4|16))
     MAX-ACCESS not-accessible
     STATUS     current
     DESCRIPTION
          "The IP multicast group address for this entry."
     ::= { etsysMgmdExtCacheEntry 2 }

etsysMgmdExtCacheSourceIPAddress OBJECT-TYPE
     SYNTAX     InetAddress (SIZE(4|16))
     MAX-ACCESS not-accessible
     STATUS     current
     DESCRIPTION
          "The IP source address of this entry."
     ::= { etsysMgmdExtCacheEntry 3 }

etsysMgmdExtCacheExpiryTime OBJECT-TYPE
     SYNTAX     Integer32
     UNITS      "seconds"
     MAX-ACCESS read-only
     STATUS     current
     DESCRIPTION
           "The time in seconds this entry will expire in."
     ::= { etsysMgmdExtCacheEntry 4 }

etsysMgmdExtCacheIncludePortList OBJECT-TYPE
     SYNTAX     PortList
     MAX-ACCESS read-only
     STATUS     current
     DESCRIPTION
          "The set of bridge ports for this multicast group, interface, and
           source IP address where the entry filter-mode is include."
     REFERENCE "RFC 3376 and RFC 3810"
     ::= { etsysMgmdExtCacheEntry 5 }

etsysMgmdExtCacheExcludePortList OBJECT-TYPE
     SYNTAX     PortList
     MAX-ACCESS read-only
     STATUS     current
     DESCRIPTION
          "The set of bridge ports for this multicast group, interface, and
           source IP address where the entry filter-mode is exclude."
     REFERENCE "RFC 3376 and RFC 3810"
     ::= { etsysMgmdExtCacheEntry 6 }

etsysMgmdExtCacheSrcPort OBJECT-TYPE
     SYNTAX      Integer32(1..65535)
     MAX-ACCESS  read-only
     STATUS      current
     DESCRIPTION
          "The source bridge port of the multicast data stream if available."
     ::= { etsysMgmdExtCacheEntry 7 }

-- -------------------------------------------------------------
-- etsysMgmdExtDiscoveredRouterGroup
-- -------------------------------------------------------------
etsysMgmdExtDiscoveredRouterTable OBJECT-TYPE
    SYNTAX        SEQUENCE OF EtsysMgmdExtDiscoveredRouterEntry
    MAX-ACCESS    not-accessible
    STATUS        current
    DESCRIPTION
         "The (conceptual) table listing the routers seen on particular ports
          of a VLAN through either protocol snooping or ICMP Router Discovery."
    ::= { etsysMgmdExtDiscoveredRouterGroup 1 }

etsysMgmdExtDiscoveredRouterEntry OBJECT-TYPE
    SYNTAX        EtsysMgmdExtDiscoveredRouterEntry
    MAX-ACCESS    not-accessible
    STATUS        current
    DESCRIPTION
         "An entry representing the routers seen on particular ports on a
          given interface index."
    INDEX { etsysMgmdExtDiscoveredRouterApplication,
            ifIndex,
            dot1dBasePort}
::= { etsysMgmdExtDiscoveredRouterTable 1 }

EtsysMgmdExtDiscoveredRouterEntry ::= SEQUENCE {
        etsysMgmdExtDiscoveredRouterApplication       InetAddressType,
        etsysMgmdExtDiscoveredRouterLearnedMethod     MGMDDiscoveredRouterModeTc,
        etsysMgmdExtDiscoveredRouterEgressing         TruthValue,
        etsysMgmdExtDiscoveredRouterStaticPortList    EnabledStatus,
        etsysMgmdExtDiscoveredRouterBridgePortAgeTime TimeTicks
     }

etsysMgmdExtDiscoveredRouterApplication OBJECT-TYPE
    SYNTAX        InetAddressType
    MAX-ACCESS    not-accessible
    STATUS        current
    DESCRIPTION
         "The application these objects refer to, ipv4(1) - IGMP,
          ipv6(2) - MLD."
    ::= { etsysMgmdExtDiscoveredRouterEntry 1 }

etsysMgmdExtDiscoveredRouterLearnedMethod OBJECT-TYPE
    SYNTAX        MGMDDiscoveredRouterModeTc
    MAX-ACCESS    read-only
    STATUS        current
    DESCRIPTION
         "The method this router was learned by."
    ::= { etsysMgmdExtDiscoveredRouterEntry 2 }

etsysMgmdExtDiscoveredRouterEgressing OBJECT-TYPE
    SYNTAX        TruthValue
    MAX-ACCESS    read-only
    STATUS        current
    DESCRIPTION
         "Indicates if this bridge port is egressing out this interface."
    ::= { etsysMgmdExtDiscoveredRouterEntry 3 }

etsysMgmdExtDiscoveredRouterStaticPortList OBJECT-TYPE
    SYNTAX        EnabledStatus
    MAX-ACCESS    read-write
    STATUS        current
    DESCRIPTION
         "Indicates if this bridge port on this interface is static.
          This leaf is OPTIONAL"

    DEFVAL { disabled }
    ::= { etsysMgmdExtDiscoveredRouterEntry 4 }

etsysMgmdExtDiscoveredRouterBridgePortAgeTime OBJECT-TYPE
    SYNTAX         TimeTicks
    MAX-ACCESS     read-only
    STATUS         current
    DESCRIPTION
         "The time in ticks from the last received protocol packet,
          until this bridge port will age out."

    ::= {etsysMgmdExtDiscoveredRouterEntry 5 }

-- -------------------------------------------------------------
-- etsysMgmdExtPortGroup
-- -------------------------------------------------------------
 etsysMgmdExtPortTable OBJECT-TYPE
     SYNTAX        SEQUENCE OF EtsysMgmdExtPortTableEntry
     MAX-ACCESS    not-accessible
     STATUS        current
     DESCRIPTION
          "The (conceptual) table listing a bridge port's bindings to multicast
           group IP addresses, interface ids, and source IP addresses."
     ::= { etsysMgmdExtPortGroup 1 }

 etsysMgmdExtPortTableEntry OBJECT-TYPE
    SYNTAX        EtsysMgmdExtPortTableEntry
    MAX-ACCESS    not-accessible
    STATUS        current
    DESCRIPTION
         "An entry representing the binding of bridge port to multicast group
          IP address, interface, and source IP address."
    INDEX { dot1dBasePort,
            etsysMgmdExtPortMode,   
            etsysMgmdExtPortIPAddressType,
            etsysMgmdExtPortTableGroupIPAddress,
            ifIndex,
            etsysMgmdExtPortTableSourceIPAddress }
    ::= { etsysMgmdExtPortTable 1 }

EtsysMgmdExtPortTableEntry ::= SEQUENCE {
        etsysMgmdExtPortMode                          MGMDPortModeTc,
        etsysMgmdExtPortIPAddressType                 InetAddressType,
        etsysMgmdExtPortTableGroupIPAddress           InetAddress,
        etsysMgmdExtPortTableSourceIPAddress          InetAddress,
        etsysMgmdExtPortTableExpireTime               Integer32
        }

etsysMgmdExtPortMode OBJECT-TYPE
   SYNTAX         MGMDPortModeTc
   MAX-ACCESS     not-accessible
   STATUS         current
   DESCRIPTION
        "The mode of the given bridge port."
   ::= { etsysMgmdExtPortTableEntry 1 }

etsysMgmdExtPortIPAddressType OBJECT-TYPE
   SYNTAX         InetAddressType
   MAX-ACCESS     not-accessible
   STATUS         current
   DESCRIPTION
        "The type of group and source IP addresses."
   ::= { etsysMgmdExtPortTableEntry 2 }

etsysMgmdExtPortTableGroupIPAddress OBJECT-TYPE
   SYNTAX         InetAddress (SIZE(4|16))
   MAX-ACCESS     not-accessible
   STATUS         current
   DESCRIPTION
        "The multicast group IP address bound to this port entry."
   ::= { etsysMgmdExtPortTableEntry 3 }

etsysMgmdExtPortTableSourceIPAddress OBJECT-TYPE
   SYNTAX         InetAddress (SIZE(4|16))
   MAX-ACCESS     not-accessible
   STATUS         current
   DESCRIPTION
        "The IP source address bound to this port entry."
   ::= { etsysMgmdExtPortTableEntry 4 }

etsysMgmdExtPortTableExpireTime OBJECT-TYPE
   SYNTAX         Integer32
   UNITS          "seconds"
   MAX-ACCESS     read-only
   STATUS         current
   DESCRIPTION
        "The time in seconds from the last join received until
         that this port will expire."
   ::= { etsysMgmdExtPortTableEntry 5 }

-- -------------------------------------------------------------
-- etsysMgmdExtPortFastLeaveGroup
-- -------------------------------------------------------------
etsysMgmdExtPortFastLeaveTable OBJECT-TYPE
    SYNTAX        SEQUENCE OF EtsysMgmdExtPortFastLeaveTableEntry
    MAX-ACCESS    not-accessible
    STATUS        current
    DESCRIPTION
         "The (conceptual) table listing a bridge port's fast leave state."
    ::= { etsysMgmdExtPortFastLeaveGroup 1 }

etsysMgmdExtPortFastLeaveTableEntry OBJECT-TYPE
    SYNTAX        EtsysMgmdExtPortFastLeaveTableEntry
    MAX-ACCESS    not-accessible
    STATUS        current
    DESCRIPTION
         "An entry representing the state of the fast leave function for the
          given bridge port."
    INDEX { dot1dBasePort }
    ::= { etsysMgmdExtPortFastLeaveTable 1 }

EtsysMgmdExtPortFastLeaveTableEntry ::= SEQUENCE {
        etsysMgmdExtPortFastLeaveState             EnabledStatus
        }

etsysMgmdExtPortFastLeaveState OBJECT-TYPE
   SYNTAX         EnabledStatus
   MAX-ACCESS     read-write
   STATUS         current
   DESCRIPTION
        "Enable or disable the fast leave function for the given bridge
         port."
   DEFVAL { disabled }
   ::= { etsysMgmdExtPortFastLeaveTableEntry 1 }

-- -------------------------------------------------------------
-- etsysMgmdExtStatsCntrsGroup
-- -------------------------------------------------------------     
etsysMgmdExtStatsCntrsTable OBJECT-TYPE
    SYNTAX        SEQUENCE OF EtsysMgmdExtStatsCntrsEntry
    MAX-ACCESS    not-accessible
    STATUS        current
    DESCRIPTION
         "The (conceptual) table listing counters and statistics seen on the 
          given multicast application."
    ::= { etsysMgmdExtStatsCntrsGroup 1 }

etsysMgmdExtStatsCntrsEntry OBJECT-TYPE
    SYNTAX        EtsysMgmdExtStatsCntrsEntry
    MAX-ACCESS    not-accessible
    STATUS        current
    DESCRIPTION
         "An entry representing the statistics and counters on the given application."
    INDEX { etsysMgmdExtStatsCntrsApplication }
::= { etsysMgmdExtStatsCntrsTable 1 }

EtsysMgmdExtStatsCntrsEntry ::= SEQUENCE {
        etsysMgmdExtStatsCntrsApplication                InetAddressType,
        etsysMgmdExtStatsCntrsGroupFull                  TruthValue,
        etsysMgmdExtStatsCntrsNumV1QueriesSent           Counter32,
        etsysMgmdExtStatsCntrsNumV2QueriesSent           Counter32,
        etsysMgmdExtStatsCntrsNumV3QueriesSent           Counter32,
        etsysMgmdExtStatsCntrsNumGSQueriesSent           Counter32,
        etsysMgmdExtStatsCntrsNumGAndSQueriesSent        Counter32,
        etsysMgmdExtStatsCntrsNumV1QueriesRcvd           Counter32,
        etsysMgmdExtStatsCntrsNumV2QueriesRcvd           Counter32,
        etsysMgmdExtStatsCntrsNumV3QueriesRcvd           Counter32,
        etsysMgmdExtStatsCntrsNumGSQueriesRcvd           Counter32,
        etsysMgmdExtStatsCntrsNumGAndSQueriesRcvd        Counter32,
        etsysMgmdExtStatsCntrsNumWrongVersionQueriesRcvd Counter32,
        etsysMgmdExtStatsCntrsNumV1ReportsRcvd           Counter32,
        etsysMgmdExtStatsCntrsNumV2ReportsRcvd           Counter32,
        etsysMgmdExtStatsCntrsNumV3ReportsRcvd           Counter32,
        etsysMgmdExtStatsCntrsNumLeavesRcvd              Counter32,
        etsysMgmdExtStatsCntrsNumBadFramesRcvd           Counter32,
        etsysMgmdExtStatsCntrsClear                      TruthValue
     }

etsysMgmdExtStatsCntrsApplication OBJECT-TYPE
    SYNTAX        InetAddressType
    MAX-ACCESS    not-accessible
    STATUS        current
    DESCRIPTION
         "The multicast application to get stats and counters for.
          ipv4(1) - IGMP, ipv6(2) - MLD."
    ::= { etsysMgmdExtStatsCntrsEntry 1 }

etsysMgmdExtStatsCntrsGroupFull OBJECT-TYPE
    SYNTAX        TruthValue
    MAX-ACCESS    read-only
    STATUS        current
    DESCRIPTION
         "Flag to indicate if the group table is full(true) or not(false)."
    ::= { etsysMgmdExtStatsCntrsEntry 2 }

etsysMgmdExtStatsCntrsNumV1QueriesSent OBJECT-TYPE
    SYNTAX        Counter32
    MAX-ACCESS    read-only
    STATUS        current
    DESCRIPTION
         "The number of version 1 queries this device has sent out."
    ::= { etsysMgmdExtStatsCntrsEntry 3 }

etsysMgmdExtStatsCntrsNumV2QueriesSent OBJECT-TYPE
    SYNTAX        Counter32
    MAX-ACCESS    read-only
    STATUS        current
    DESCRIPTION
         "The number of version 2 queries this device has sent out."
    ::= { etsysMgmdExtStatsCntrsEntry 4 }

etsysMgmdExtStatsCntrsNumV3QueriesSent OBJECT-TYPE
    SYNTAX        Counter32
    MAX-ACCESS    read-only
    STATUS        current
    DESCRIPTION
         "The number of version 3 queries this device has sent out.
          This will read 0 for MLD."
    ::= { etsysMgmdExtStatsCntrsEntry 5 }

etsysMgmdExtStatsCntrsNumGSQueriesSent OBJECT-TYPE
    SYNTAX        Counter32
    MAX-ACCESS    read-only
    STATUS        current
    DESCRIPTION
         "The number of Group Specific queries this device has sent out."
    ::= { etsysMgmdExtStatsCntrsEntry 6 }

etsysMgmdExtStatsCntrsNumGAndSQueriesSent OBJECT-TYPE
    SYNTAX        Counter32
    MAX-ACCESS    read-only
    STATUS        current
    DESCRIPTION
         "The number of Group and Source specific queries the device has
          sent out."
    ::= {etsysMgmdExtStatsCntrsEntry 7 }

etsysMgmdExtStatsCntrsNumV1QueriesRcvd OBJECT-TYPE
    SYNTAX        Counter32
    MAX-ACCESS    read-only
    STATUS        current
    DESCRIPTION
         "The number of version 1 queries received."
    ::= { etsysMgmdExtStatsCntrsEntry 8 }

etsysMgmdExtStatsCntrsNumV2QueriesRcvd OBJECT-TYPE
    SYNTAX        Counter32
    MAX-ACCESS    read-only
    STATUS        current
    DESCRIPTION
         "The number of version 2 queries received."
    ::= { etsysMgmdExtStatsCntrsEntry 9 }

etsysMgmdExtStatsCntrsNumV3QueriesRcvd OBJECT-TYPE
    SYNTAX        Counter32
    MAX-ACCESS    read-only
    STATUS        current
    DESCRIPTION
         "The number of version 3 queries received.
          Will read 0 for MLD."
    ::= { etsysMgmdExtStatsCntrsEntry 10 }

etsysMgmdExtStatsCntrsNumGSQueriesRcvd OBJECT-TYPE
    SYNTAX        Counter32
    MAX-ACCESS    read-only
    STATUS        current
    DESCRIPTION
         "The number of group specific queries received."
    ::= { etsysMgmdExtStatsCntrsEntry 11 }

etsysMgmdExtStatsCntrsNumGAndSQueriesRcvd OBJECT-TYPE
    SYNTAX        Counter32
    MAX-ACCESS    read-only
    STATUS        current
    DESCRIPTION
         "The number of group and source specific
          queries received."
    ::= { etsysMgmdExtStatsCntrsEntry 12 }

etsysMgmdExtStatsCntrsNumWrongVersionQueriesRcvd OBJECT-TYPE
    SYNTAX        Counter32
    MAX-ACCESS    read-only
    STATUS        current
    DESCRIPTION
         "The number of queries with the wrong version this device
          has seen from the network."
    ::= { etsysMgmdExtStatsCntrsEntry 13 }

etsysMgmdExtStatsCntrsNumV1ReportsRcvd OBJECT-TYPE
    SYNTAX        Counter32
    MAX-ACCESS    read-only
    STATUS        current
    DESCRIPTION
         "The number of version 1 reports this device has received."
    ::= { etsysMgmdExtStatsCntrsEntry 14 }

etsysMgmdExtStatsCntrsNumV2ReportsRcvd OBJECT-TYPE
    SYNTAX        Counter32
    MAX-ACCESS    read-only
    STATUS        current
    DESCRIPTION
         "The number of version 2 reports this device has received."
    ::= { etsysMgmdExtStatsCntrsEntry 15 }

etsysMgmdExtStatsCntrsNumV3ReportsRcvd OBJECT-TYPE
    SYNTAX        Counter32
    MAX-ACCESS    read-only
    STATUS        current
    DESCRIPTION
         "The number of version 3 reports this device has received.
          This will read 0 for MLD."
    ::= { etsysMgmdExtStatsCntrsEntry 16 }

etsysMgmdExtStatsCntrsNumLeavesRcvd OBJECT-TYPE
    SYNTAX        Counter32
    MAX-ACCESS    read-only
    STATUS        current
    DESCRIPTION
         "The number of IGMP version 1 or 2 leaves this device has
          received. Number of MLD version 1 dones this device has
          received."
    ::= { etsysMgmdExtStatsCntrsEntry 17 }

etsysMgmdExtStatsCntrsNumBadFramesRcvd OBJECT-TYPE
    SYNTAX        Counter32
    MAX-ACCESS    read-only
    STATUS        current
    DESCRIPTION
         "The number of frames deemed received with errors."
    ::= {etsysMgmdExtStatsCntrsEntry 18 }

etsysMgmdExtStatsCntrsClear OBJECT-TYPE
     SYNTAX    TruthValue 
     MAX-ACCESS read-write
     STATUS     current
     DESCRIPTION
          "A mechanism to clear the various counters maintained by the IGMP
           snooping application.  Setting the value to true will clear the
           counters.  Setting the value to false will have no effect.  This
           value will always read false"
    ::= {etsysMgmdExtStatsCntrsEntry 19 }

-- -------------------------------------------------------------
-- etsysMgmdExtProtocolClassificationGroup
-- -------------------------------------------------------------
etsysMgmdExtProtocolClassificationTable OBJECT-TYPE
    SYNTAX        SEQUENCE OF EtsysMgmdExtProtocolClassificationEntry
    MAX-ACCESS    not-accessible
    STATUS        current
    DESCRIPTION
         "This table contains a listing of how MGMD will
          classify received IP protocol frames. For example,
          for a UDP multicast frame received which is IP type 17,
          MGMD can classify that frame in one of three ways.
          It can be classified as a multicast data frame, a routing protocol,
          or it can be ignored. A user may have a need to multicast
          TCP frames, but still want to send them ONLY to MGMD clients.
          To do this one would set protocol id 6(TCP) to 'multicastData'"
    ::= { etsysMgmdExtProtocolClassificationGroup 1 }

etsysMgmdExtProtocolClassificationEntry OBJECT-TYPE
    SYNTAX        EtsysMgmdExtProtocolClassificationEntry
    MAX-ACCESS    not-accessible
    STATUS        current
    DESCRIPTION
         "An entry representing the binding of IP protocol id, to
          the IGMP classification of a received frame."
    INDEX { etsysMgmdExtProtocolClassification }
    ::= { etsysMgmdExtProtocolClassificationTable 1 }

EtsysMgmdExtProtocolClassificationEntry ::= SEQUENCE {
    etsysMgmdExtProtocolClassification         MGMDProtocolClassTc,
    etsysMgmdExtProtocolIdentifier             MGMDProtocolIdTc
    }

etsysMgmdExtProtocolClassification OBJECT-TYPE
    SYNTAX        MGMDProtocolClassTc
    MAX-ACCESS    not-accessible
    STATUS        current
    DESCRIPTION
         "The classification of this protocol id.
          1 - Classify as multicast data frame.
          2 - Classify as a routing protocol.
          3 - Classify as Ignore."
    ::= { etsysMgmdExtProtocolClassificationEntry 1}

etsysMgmdExtProtocolIdentifier OBJECT-TYPE
    SYNTAX        MGMDProtocolIdTc
    MAX-ACCESS    read-write
    STATUS        current
    DESCRIPTION
         "The set of IP protocol ids to apply the classification to.
          Example: If this set has protocols(bits) 1 and 5 set to a
          '1', and the classification is 'multicastData', this will
          force IGMP to treat received frames with IP protocol ids of
          1 and 5 as 'multicast data', and forward those frames to 
          IGMP joined clients. Similarly if ids 1 and 5 were set to 
          'routing protocol' then IGMP would treat received frames with
          these ids as routing protocols, etc. "
    ::= { etsysMgmdExtProtocolClassificationEntry 2}
    
-- -------------------------------------------------------------
-- Conformance Information
-- -------------------------------------------------------------

etsysMgmdExtConformance OBJECT IDENTIFIER ::= { etsysMgmdExtMIB 2 }

etsysMgmdExtGroups      OBJECT IDENTIFIER ::= { etsysMgmdExtConformance 1 }
etsysMgmdExtCompliances OBJECT IDENTIFIER ::= { etsysMgmdExtConformance 2 }

-- -------------------------------------------------------------
-- Units of conformance
-- -------------------------------------------------------------
etsysMgmdExtConfigGroups OBJECT-GROUP
    OBJECTS {
                etsysMgmdExtConfigRevString,
                etsysMgmdExtConfigFullAction,
                etsysMgmdExtConfigMinNumberOfGroups,
                etsysMgmdExtConfigDefaultNumberOfGroups,
                etsysMgmdExtConfigMaxNumberOfGroups,
                etsysMgmdExtConfigNumberOfGroups
             }

    STATUS   current
    DESCRIPTION
        "Global object controlling this feature."
    ::= { etsysMgmdExtGroups 1 }

etsysMgmdExtInterfaceGroups OBJECT-GROUP
    OBJECTS {
                etsysMgmdExtInterfaceFastLeaveState
            }
    STATUS current
    DESCRIPTION
        "Global object controlling this feature."
    ::= { etsysMgmdExtGroups 2 }

etsysMgmdExtStaticCacheGroups OBJECT-GROUP
    OBJECTS {
                etsysMgmdExtStaticCacheIncludeList,
                etsysMgmdExtStaticCacheExcludeList,
                etsysMgmdExtStaticCacheRowStatus
            }
    STATUS current
    DESCRIPTION
        "Global object controlling this feature."
    ::= { etsysMgmdExtGroups 3 }

etsysMgmdExtCacheGroups OBJECT-GROUP
    OBJECTS {
                etsysMgmdExtCacheExpiryTime,
                etsysMgmdExtCacheIncludePortList,
                etsysMgmdExtCacheExcludePortList,
                etsysMgmdExtCacheSrcPort
            }
    STATUS current
    DESCRIPTION
       "Global object controlling this feature."
    ::= { etsysMgmdExtGroups 4 }

 etsysMgmdExtDiscoveredRouterGroups OBJECT-GROUP
     OBJECTS {
                 etsysMgmdExtDiscoveredRouterLearnedMethod,
                 etsysMgmdExtDiscoveredRouterEgressing,
                 etsysMgmdExtDiscoveredRouterStaticPortList,
                 etsysMgmdExtDiscoveredRouterBridgePortAgeTime
             }
     STATUS current
     DESCRIPTION
         "Global object controlling this feature."
     ::= { etsysMgmdExtGroups 5 }

 etsysMgmdExtPortGroups OBJECT-GROUP
     OBJECTS{
                etsysMgmdExtPortTableGroupIPAddress,
                etsysMgmdExtPortTableSourceIPAddress,
                etsysMgmdExtPortTableExpireTime
            }
     STATUS current
     DESCRIPTION
         "Global object controlling this feature."
     ::= { etsysMgmdExtGroups 6 }

 etsysMgmdExtPortFastLeaveGroups OBJECT-GROUP
     OBJECTS {
                 etsysMgmdExtPortFastLeaveState
             }
     STATUS current
     DESCRIPTION
         "Global object controlling this feature."
     ::= { etsysMgmdExtGroups 7 }

 etsysMgmdExtStatsCntsGroups OBJECT-GROUP
     OBJECTS {
                etsysMgmdExtStatsCntrsApplication,
                etsysMgmdExtStatsCntrsGroupFull,
                etsysMgmdExtStatsCntrsNumV1QueriesSent,
                etsysMgmdExtStatsCntrsNumV2QueriesSent,
                etsysMgmdExtStatsCntrsNumV3QueriesSent,
                etsysMgmdExtStatsCntrsNumGSQueriesSent,
                etsysMgmdExtStatsCntrsNumGAndSQueriesSent,
                etsysMgmdExtStatsCntrsNumV1QueriesRcvd,
                etsysMgmdExtStatsCntrsNumV2QueriesRcvd,
                etsysMgmdExtStatsCntrsNumV3QueriesRcvd,
                etsysMgmdExtStatsCntrsNumGSQueriesRcvd,
                etsysMgmdExtStatsCntrsNumGAndSQueriesRcvd,
                etsysMgmdExtStatsCntrsNumWrongVersionQueriesRcvd,
                etsysMgmdExtStatsCntrsNumV1ReportsRcvd,
                etsysMgmdExtStatsCntrsNumV2ReportsRcvd,
                etsysMgmdExtStatsCntrsNumV3ReportsRcvd,
                etsysMgmdExtStatsCntrsNumLeavesRcvd,
                etsysMgmdExtStatsCntrsNumBadFramesRcvd
             }
     STATUS current
     DESCRIPTION
         "Global object controlling this feature."
     ::= { etsysMgmdExtGroups 8 }

etsysMgmdExtProtocolClassificationGroups OBJECT-GROUP
    OBJECTS {
                etsysMgmdExtProtocolClassification,
                etsysMgmdExtProtocolIdentifier
            }
    STATUS current
    DESCRIPTION
        "Global object controlling this feature."
    ::= { etsysMgmdExtGroups 9 }

etsysMgmdExtReadBaseGroup OBJECT-GROUP
    OBJECTS {
                etsysMgmdExtConfigRevString,
                etsysMgmdExtConfigFullAction,
                etsysMgmdExtConfigMinNumberOfGroups,
                etsysMgmdExtConfigDefaultNumberOfGroups,
                etsysMgmdExtConfigMaxNumberOfGroups,
                etsysMgmdExtConfigNumberOfGroups,
                etsysMgmdExtInterfaceFastLeaveState,
                etsysMgmdExtStaticCacheIncludeList,
                etsysMgmdExtStaticCacheExcludeList,
                etsysMgmdExtStaticCacheRowStatus,
                etsysMgmdExtCacheExpiryTime,
                etsysMgmdExtCacheIncludePortList,
                etsysMgmdExtCacheExcludePortList,
                etsysMgmdExtCacheSrcPort,
                etsysMgmdExtDiscoveredRouterLearnedMethod,
                etsysMgmdExtDiscoveredRouterEgressing,
                etsysMgmdExtDiscoveredRouterStaticPortList,
                etsysMgmdExtDiscoveredRouterBridgePortAgeTime,
                etsysMgmdExtPortFastLeaveState,
                etsysMgmdExtStatsCntrsGroupFull,
                etsysMgmdExtStatsCntrsNumV1QueriesSent,
                etsysMgmdExtStatsCntrsNumV2QueriesSent,
                etsysMgmdExtStatsCntrsNumV3QueriesSent,
                etsysMgmdExtStatsCntrsNumGSQueriesSent,
                etsysMgmdExtStatsCntrsNumGAndSQueriesSent,
                etsysMgmdExtStatsCntrsNumV1QueriesRcvd,
                etsysMgmdExtStatsCntrsNumV2QueriesRcvd,
                etsysMgmdExtStatsCntrsNumV3QueriesRcvd,
                etsysMgmdExtStatsCntrsNumGSQueriesRcvd,
                etsysMgmdExtStatsCntrsNumGAndSQueriesRcvd,
                etsysMgmdExtStatsCntrsNumWrongVersionQueriesRcvd,
                etsysMgmdExtStatsCntrsNumV1ReportsRcvd,
                etsysMgmdExtStatsCntrsNumV2ReportsRcvd,
                etsysMgmdExtStatsCntrsNumV3ReportsRcvd,
                etsysMgmdExtStatsCntrsNumLeavesRcvd,
                etsysMgmdExtStatsCntrsNumBadFramesRcvd
    }
    STATUS      current
    DESCRIPTION
        " The read MGMD data that must be supported."
    ::= { etsysMgmdExtGroups 10 }

etsysMgmdExtWriteBaseGroup OBJECT-GROUP
    OBJECTS {
                etsysMgmdExtConfigFullAction,
                etsysMgmdExtConfigNumberOfGroups,
                etsysMgmdExtInterfaceFastLeaveState,
                etsysMgmdExtStaticCacheIncludeList,
                etsysMgmdExtStaticCacheExcludeList,
                etsysMgmdExtStaticCacheRowStatus,
                etsysMgmdExtDiscoveredRouterStaticPortList,
                etsysMgmdExtPortFastLeaveState,
                etsysMgmdExtProtocolIdentifier
            }
    STATUS      current        
    DESCRIPTION
        " The write MGMD data that must be supported."
    ::= { etsysMgmdExtGroups 11 }

-- -------------------------------------------------------------
-- Compliance statements
-- -------------------------------------------------------------

etsysMgmdExtReadCompliance MODULE-COMPLIANCE
    STATUS      current
    DESCRIPTION
        "The compliance statement for devices that support reads from 
         the etsysMgmdExt MIB."

    MODULE
        MANDATORY-GROUPS { etsysMgmdExtReadBaseGroup }

    ::= { etsysMgmdExtCompliances 1 }

etsysMgmdExtWriteCompliance MODULE-COMPLIANCE
    STATUS      current
    DESCRIPTION
        "The compliance statement for device that support writes to the 
         etsysMgmdExt MIB."
    MODULE
        MANDATORY-GROUPS { etsysMgmdExtWriteBaseGroup }

    ::= { etsysMgmdExtCompliances 2 }

END
