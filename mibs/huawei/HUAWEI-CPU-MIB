-- =================================================================
-- Copyright (C) 2001,2002 by  HUAWEI TECHNOLOGIES. All rights reserved.
--
-- Description: the huawei cpu mib from huawei-device-mib
-- Reference:
-- Version:     V1.0
-- History:
--    
-- =================================================================

HUAWEI-CPU-MIB DEFINITIONS ::= BEGIN

    IMPORTS
        hwFrameIndex, hwSlotIndex
            FROM HUAWEI-DEVICE-MIB    
        OBJECT-GROUP, MODULE-COMPLIANCE            
            FROM SNMPv2-CONF                                
        OBJECT-TYPE, MODULE-IDENTITY, Integer32
            FROM SNMPv2-SMI
        huaweiUtility            
            FROM HUAWEI-MIB;
    
    --This mib defines the CPU usage statistics information. NMS can query CPU utilization
    --from device by the mib.
    
    hwDev MODULE-IDENTITY
        LAST-UPDATED "200406280900Z"
        ORGANIZATION "Fix-Net Dept, Huawei Technologies Co.,Ltd."
        CONTACT-INFO 
            "Block 4, R&D Building,
            Huawei Longgang Production Base,
            Shenzhen,   P.R.C.
            http://www.huawei.com
            Zip:518057
            "
        DESCRIPTION 
            "huawei device  mib."
        ::= { huaweiUtility 3 }
    
    hwCpuDevTable OBJECT-TYPE
        SYNTAX SEQUENCE OF HwCpuDevEntry
        MAX-ACCESS not-accessible
        STATUS current
        DESCRIPTION
            "
            This table provides the information of CPU usage statistics of device 
            in the period of last 5 seconds, 1 minute,or 5 minutes.
            "
        ::= { hwDev 4 }
    
    hwCpuDevEntry OBJECT-TYPE
        SYNTAX HwCpuDevEntry
        MAX-ACCESS not-accessible
        STATUS current
        DESCRIPTION
            "
            The Entries of hwCpuDevTable.                
            
            The hwCpuDevTable is indexed by hwFrameIndex, hwSlotIndex and hwCpuDevIndex.
            
            hwFrameIndex  - the index of frame of the device. for example, hwFrameIndex 
            equals 0 in NE16.
            hwSlotIndex   - the slot number of the device, the MAX value varies with 
            different devices.
            hwCpuDevIndex - for the purpose of extension.In single CPU devices (NE16,eg.),
            hwCpuDevIndex equals 0."
        INDEX { hwFrameIndex, hwSlotIndex, hwCpuDevIndex }
        ::= { hwCpuDevTable 1 }
    
    HwCpuDevEntry ::=
        SEQUENCE { 
            hwCpuDevIndex
                Integer32,
            hwCpuDevDuty
                Integer32,
            hwAvgDuty1min
                Integer32,
            hwAvgDuty5min
                Integer32
            }

    hwCpuDevIndex OBJECT-TYPE
        SYNTAX Integer32 (0..255)
        MAX-ACCESS not-accessible
        STATUS current
        DESCRIPTION
            "
            The object is used only for the purpose of extension. 
            For single-CPU devices, the value of this object equals 0.
            "
        ::= { hwCpuDevEntry 1 }
    
    hwCpuDevDuty OBJECT-TYPE
        SYNTAX Integer32 (0..100)
        MAX-ACCESS read-only
        STATUS current
        DESCRIPTION
            "
            The value of this object identifies the average CPU occupancy of a board or an entity."
        ::= { hwCpuDevEntry 2 }
    
    hwAvgDuty1min OBJECT-TYPE
        SYNTAX Integer32 (0..100)
        MAX-ACCESS read-only
        STATUS current
        DESCRIPTION
            "
            The value of this object identifies the average CPU occupancy of a board or an entity 
            in the last one minute before you access the object. "
        ::= { hwCpuDevEntry 3 }
    
    hwAvgDuty5min OBJECT-TYPE
        SYNTAX Integer32 (0..100)
        MAX-ACCESS read-only
        STATUS current
        DESCRIPTION
            "
            The value of this object identifies the average CPU occupancy of a board or an entity  
            in the last five minutes before you access the object. "
        ::= { hwCpuDevEntry 4 }

END
