TIMETRA-SAS-IEEE8021-CFM-MIB DEFINITIONS ::= BEGIN

IMPORTS
        MODULE-IDENTITY, Unsigned32, OBJECT-TYPE,
        NOTIFICATION-TYPE, Integer32, Counter32,
        Gauge32                                       FROM SNMPv2-SMI

        MODULE-COMPLIANCE, NOTIFICATION-GROUP,
        OBJECT-GROUP                                  FROM SNMPv2-CONF

        TruthValue                                    FROM SNMPv2-TC

        dot1agCfmMepEntry                             FROM IEEE8021-CFM-MIB
        
        timetraSASObjs, timetraSASModules, 
        timetraSASConfs                               FROM TIMETRA-SAS-GLOBAL-MIB        
        ;
  

timetraSASIEEE8021CfmMIBModule MODULE-IDENTITY
        LAST-UPDATED    "0902280000Z"
        ORGANIZATION    "Alcatel"
        CONTACT-INFO    
            "Alcatel 7x50 Support
             Web: http://www.alcatel.com/comps/pages/carrier_support.jhtml"
        DESCRIPTION
        "This document is the SNMP MIB module to manage and provision dot1ag 
        Connectivity Fault Management module functionality for the Alcatel 7210
        products. This includes extensions to the IEEE8021-CFM MIB. 

        Copyright 2011-2013 Alcatel-Lucent. All rights reserved.
        Reproduction of this document is authorized on the condition that
        the foregoing copyright notice is included.

        This SNMP MIB module (Specification) embodies Alcatel's
        proprietary intellectual property.  Alcatel retains
        all title and ownership in the Specification, including any
        revisions.

        Alcatel grants all interested parties a non-exclusive
        license to use and distribute an unmodified copy of this
        Specification in connection with management of Alcatel
        products, and without fee, provided this copyright notice and
        license appear on all copies.

        This Specification is supplied 'as is', and Alcatel
        makes no warranty, either express or implied, as to the use,
        operation, condition, or performance of the Specification."
--
--  Revision History
--

        REVISION        "1001010000Z"
        DESCRIPTION     "Rev 1.0                01 Jan 2010 00:00
                         Initial version of the TIMETRA-IEEE8021-CFM-MIB."
                         
        ::= { timetraSASModules 11 }

--%%%%%%%%%%%%%%%%%%%%%%%%%%%%%%%%%%%%%%%%%%%%%%%%%%%%%%%%%%%%%%%%%%%%%%
--
--  Alcatel 7210 product series IEEE8021-CFM extensions
--

tmnxSASDot1agMIBObjs                OBJECT IDENTIFIER ::= { timetraSASObjs 11 }
tmnxSASDot1agMIBConformance         OBJECT IDENTIFIER ::= { timetraSASConfs 7 }

-- Groups in the Alcatel CFM MIB Module
tmnxSASDot1agCfmMep                 OBJECT IDENTIFIER ::= { tmnxSASDot1agMIBObjs 1 }              
tmnxSASDot1agNotificationsPrefix    OBJECT IDENTIFIER ::= { tmnxSASDot1agMIBObjs 2 }
 tmnxSASDot1agNotifications OBJECT IDENTIFIER ::= { tmnxSASDot1agNotificationsPrefix  1 }


tmnxDot1agCfmMepExtnTable            OBJECT-TYPE
    SYNTAX     SEQUENCE OF TmnxDot1agCfmMepExtnEntry
    MAX-ACCESS not-accessible
    STATUS     current
    DESCRIPTION
       "This table augments the Maintenance Association End Point (MEP) table
        of the IEEE8021-CFM-MIB."
    ::= { tmnxSASDot1agCfmMep 1 }

tmnxDot1agCfmMepExtnEntry            OBJECT-TYPE
    SYNTAX     TmnxDot1agCfmMepExtnEntry
    MAX-ACCESS not-accessible
    STATUS     current
    DESCRIPTION
       "A conceptual row in the tmnxDot1agCfmMepExtnTable. This row exists only
        if the association dot1agCfmMepEntry is active."
    AUGMENTS { dot1agCfmMepEntry }
    ::= { tmnxDot1agCfmMepExtnTable 1 }

TmnxDot1agCfmMepExtnEntry ::= SEQUENCE {
    tmnxDot1agCfmMepSendAisOnPortDown            TruthValue,
    tmnxDot1agCfmMepControlSapTag                Unsigned32
}    

tmnxDot1agCfmMepSendAisOnPortDown    OBJECT-TYPE
    SYNTAX     TruthValue
    MAX-ACCESS read-create
    STATUS     current
    DESCRIPTION
        " The value of tmnxDot1agCfmMepSendAisOnPortDown specifies that ETH-AIS
         should be generated for client MEP-s immediately when port down is detected
         on a SAP where server MEP resides"
    DEFVAL { false }
    ::= { tmnxDot1agCfmMepExtnEntry 1 }

tmnxDot1agCfmMepControlSapTag    OBJECT-TYPE
    SYNTAX     Unsigned32  (0..4096)
    MAX-ACCESS read-create
    STATUS     current
    DESCRIPTION
        " tmnxDot1agCfmMepControlSapTag specifies the control sap tag."
    DEFVAL { 0 }
    ::= { tmnxDot1agCfmMepExtnEntry 2 }
    

-- Conformance Information
--

tmnxSASDot1agCfmCompliances OBJECT IDENTIFIER ::= { tmnxSASDot1agMIBConformance 1 }
tmnxSASDot1agCfmGroups      OBJECT IDENTIFIER ::= { tmnxSASDot1agMIBConformance 2 }

-- Compliance statements

tmnxSASDot1agCfmComplianceV2v0 MODULE-COMPLIANCE
    STATUS     current
    DESCRIPTION
       "The compliance statement for revision 2.0 of the 7210 system"
    MODULE -- this module
       MANDATORY-GROUPS {
           tmnxSASDot1agCfmMepGroupV2v0
       }
    ::= { tmnxSASDot1agCfmCompliances 2 }

tmnxSASDot1agCfmMepGroupV2v0       OBJECT-GROUP
    OBJECTS {
        tmnxDot1agCfmMepSendAisOnPortDown
    }
    STATUS     current
    DESCRIPTION
       "The group of objects for management of dot1ag MEP Table applicable
        to implementing SDP-Bindings."
    ::= { tmnxSASDot1agCfmGroups 1 }

tmnxSASDot1agCfmMepGroupV4v0       OBJECT-GROUP
    OBJECTS {
        tmnxDot1agCfmMepSendAisOnPortDown,
        tmnxDot1agCfmMepControlSapTag
    }
    STATUS     current
    DESCRIPTION
       "The group of objects for management of dot1ag MEP Table applicable
        to implementing SDP-Bindings."
    ::= { tmnxSASDot1agCfmGroups 2 }

END
