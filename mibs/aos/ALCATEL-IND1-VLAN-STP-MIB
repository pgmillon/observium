ALCATEL-IND1-VLAN-STP-MIB DEFINITIONS ::= BEGIN


	IMPORTS
		Counter32, TimeTicks, MODULE-IDENTITY, OBJECT-IDENTITY,
		OBJECT-TYPE, Integer32, NOTIFICATION-TYPE
			FROM SNMPv2-SMI
		OBJECT-GROUP, NOTIFICATION-GROUP, MODULE-COMPLIANCE
			FROM SNMPv2-CONF
		DisplayString, MacAddress, TEXTUAL-CONVENTION, RowStatus
        	FROM SNMPv2-TC
		BridgeId, Timeout
			FROM BRIDGE-MIB
		softentIND1VlanStp, spanningTreeTraps
			FROM ALCATEL-IND1-BASE
        InterfaceIndex
            FROM IF-MIB
			;

	alcatelIND1VLANSTPMIB MODULE-IDENTITY
		LAST-UPDATED "200704030000Z"
		ORGANIZATION "Alcatel-Lucent"
		CONTACT-INFO
		    "Please consult with Customer Service to ensure the most appropriate
		     version of this document is used with the products in question:

				Alcatel-Lucent, Enterprise Solutions Division
			       (Formerly Alcatel Internetworking, Incorporated)
				       26801 West Agoura Road
			 	   Agoura Hills, CA  91301-5122
			      		United States Of America

	    	     Telephone:              North America  +1 800 995 2696
			 	     	     Latin America  +1 877 919 9526
					         Europe         +31 23 556 0100
				     	     Asia           +65 394 7933
				     	     All Other      +1 818 878 4507

	             Electronic Mail:         support@ind.alcatel.com
	             World Wide Web:          http://alcatel-lucent.com/wps/portal/enterprise
	             File Transfer Protocol:  ftp://ftp.ind.alcatel.com/pub/products/mibs"
		DESCRIPTION
			         "The Spanning Tree parameters for Vlans and ports that
			          support the Spanning Tree protocol.
			          Large percentage of this group is lifted from rfc1493.
			          Implementation of this group is mandatory for AOS products.

                The right to make changes in specification and other information
                contained in this document without prior notice is reserved.

                No liability shall be assumed for any incidental, indirect, special, or
                consequential damages whatsoever arising from or related to this
                document or the information contained herein.

                Vendors, end-users, and other interested parties are granted
                non-exclusive license to use this specification in connection with
                management of the products for which it is intended to be used.

                               Copyright (C) 1995-2006 Alcatel-Lucent
	                                 ALL RIGHTS RESERVED WORLDWIDE"
		::= { softentIND1VlanStp 1}

-- -------------------------------------------------------------
-- Textual Conventions
-- -------------------------------------------------------------

VlanBitmap ::= TEXTUAL-CONVENTION
    STATUS      current
    DESCRIPTION
        "bit map of Vlans from 1 to 4096."
    SYNTAX      BITS {
unused(0),vl1(1),vl2(2),vl3(3),vl4(4),vl5(5),
vl6(6),vl7(7),vl8(8),vl9(9),vl10(10),vl11(11)
,vl12(12),vl13(13),vl14(14),vl15(15),vl16(16),
vl17(17),vl18(18),vl19(19),vl20(20),vl21(21),
vl22(22),vl23(23),vl24(24),vl25(25),vl26(26),
vl27(27),vl28(28),vl29(29),vl30(30),vl31(31),
vl32(32),vl33(33),vl34(34),vl35(35),vl36(36),
vl37(37),vl38(38),vl39(39),vl40(40),vl41(41),
vl42(42),vl43(43),vl44(44),vl45(45),vl46(46),
vl47(47),vl48(48),vl49(49),vl50(50),vl51(51),
vl52(52),vl53(53),vl54(54),vl55(55),vl56(56),
vl57(57),vl58(58),vl59(59),vl60(60),vl61(61),
vl62(62),vl63(63),vl64(64),vl65(65),vl66(66),
vl67(67),vl68(68),vl69(69),vl70(70),vl71(71),
vl72(72),vl73(73),vl74(74),vl75(75),vl76(76),
vl77(77),vl78(78),vl79(79),vl80(80),vl81(81),
vl82(82),vl83(83),vl84(84),vl85(85),vl86(86),
vl87(87),vl88(88),vl89(89),vl90(90),vl91(91),
vl92(92),vl93(93),vl94(94),vl95(95),vl96(96),
vl97(97),vl98(98),vl99(99),vl100(100),
vl101(101),vl102(102),
vl103(103),vl104(104),vl105(105),vl106(106),
vl107(107),vl108(108),vl109(109),vl110(110),
vl111(111),vl112(112),vl113(113),vl114(114),
vl115(115),vl116(116),vl117(117),vl118(118),
vl119(119),vl120(120),vl121(121),vl122(122),
vl123(123),vl124(124),vl125(125),vl126(126),
vl127(127),vl128(128),vl129(129),vl130(130),
vl131(131),vl132(132),vl133(133),vl134(134),
vl135(135),vl136(136),vl137(137),vl138(138),
vl139(139),vl140(140),vl141(141),vl142(142),
vl143(143),vl144(144),vl145(145),vl146(146),
vl147(147),vl148(148),vl149(149),vl150(150),
vl151(151),vl152(152),vl153(153),vl154(154),
vl155(155),vl156(156),vl157(157),vl158(158),
vl159(159),vl160(160),vl161(161),vl162(162),
vl163(163),vl164(164),vl165(165),vl166(166),
vl167(167),vl168(168),vl169(169),vl170(170),
vl171(171),vl172(172),vl173(173),vl174(174),
vl175(175),vl176(176),vl177(177),vl178(178),
vl179(179),vl180(180),vl181(181),vl182(182),
vl183(183),vl184(184),vl185(185),vl186(186),
vl187(187),vl188(188),vl189(189),vl190(190),
vl191(191),vl192(192),vl193(193),vl194(194),
vl195(195),vl196(196),vl197(197),vl198(198),
vl199(199),vl200(200),vl201(201),vl202(202),
vl203(203),vl204(204),vl205(205),vl206(206),
vl207(207),vl208(208),vl209(209),vl210(210),
vl211(211),vl212(212),vl213(213),vl214(214),
vl215(215),vl216(216),vl217(217),vl218(218),
vl219(219),vl220(220),vl221(221),vl222(222),
vl223(223),vl224(224),vl225(225),vl226(226),
vl227(227),vl228(228),vl229(229),vl230(230),
vl231(231),vl232(232),vl233(233),vl234(234),
vl235(235),vl236(236),vl237(237),vl238(238),
vl239(239),vl240(240),vl241(241),vl242(242),
vl243(243),vl244(244),vl245(245),vl246(246),
vl247(247),vl248(248),vl249(249),vl250(250),
vl251(251),vl252(252),vl253(253),vl254(254),
vl255(255),vl256(256),vl257(257),vl258(258),
vl259(259),vl260(260),vl261(261),vl262(262),
vl263(263),vl264(264),vl265(265),vl266(266),
vl267(267),vl268(268),vl269(269),vl270(270),
vl271(271),vl272(272),vl273(273),vl274(274),
vl275(275),vl276(276),vl277(277),vl278(278),
vl279(279),vl280(280),vl281(281),vl282(282),
vl283(283),vl284(284),vl285(285),vl286(286),
vl287(287),vl288(288),vl289(289),vl290(290),
vl291(291),vl292(292),vl293(293),vl294(294),
vl295(295),vl296(296),vl297(297),vl298(298),
vl299(299),vl300(300),vl301(301),vl302(302),
vl303(303),vl304(304),vl305(305),vl306(306),
vl307(307),vl308(308),vl309(309),vl310(310),
vl311(311),vl312(312),vl313(313),vl314(314),
vl315(315),vl316(316),vl317(317),vl318(318),
vl319(319),vl320(320),vl321(321),vl322(322),
vl323(323),vl324(324),vl325(325),vl326(326),
vl327(327),vl328(328),vl329(329),vl330(330),
vl331(331),vl332(332),vl333(333),vl334(334),
vl335(335),vl336(336),vl337(337),vl338(338),
vl339(339),vl340(340),vl341(341),vl342(342),
vl343(343),vl344(344),vl345(345),vl346(346),
vl347(347),vl348(348),vl349(349),vl350(350),
vl351(351),vl352(352),vl353(353),vl354(354),
vl355(355),vl356(356),vl357(357),vl358(358),
vl359(359),vl360(360),vl361(361),vl362(362),
vl363(363),vl364(364),vl365(365),vl366(366),
vl367(367),vl368(368),vl369(369),vl370(370),
vl371(371),vl372(372),vl373(373),vl374(374),
vl375(375),vl376(376),vl377(377),vl378(378),
vl379(379),vl380(380),vl381(381),vl382(382),
vl383(383),vl384(384),vl385(385),vl386(386),
vl387(387),vl388(388),vl389(389),vl390(390),
vl391(391),vl392(392),vl393(393),vl394(394),
vl395(395),vl396(396),vl397(397),vl398(398),
vl399(399),vl400(400),vl401(401),vl402(402),
vl403(403),vl404(404),vl405(405),vl406(406),
vl407(407),vl408(408),vl409(409),vl410(410),
vl411(411),vl412(412),vl413(413),vl414(414),
vl415(415),vl416(416),vl417(417),vl418(418),
vl419(419),vl420(420),vl421(421),vl422(422),
vl423(423),vl424(424),vl425(425),vl426(426),
vl427(427),vl428(428),vl429(429),vl430(430),
vl431(431),vl432(432),vl433(433),vl434(434),
vl435(435),vl436(436),vl437(437),vl438(438),
vl439(439),vl440(440),vl441(441),vl442(442),
vl443(443),vl444(444),vl445(445),vl446(446),
vl447(447),vl448(448),vl449(449),vl450(450),
vl451(451),vl452(452),vl453(453),vl454(454),
vl455(455),vl456(456),vl457(457),vl458(458),
vl459(459),vl460(460),vl461(461),vl462(462),
vl463(463),vl464(464),vl465(465),vl466(466),
vl467(467),vl468(468),vl469(469),vl470(470),
vl471(471),vl472(472),vl473(473),vl474(474),
vl475(475),vl476(476),vl477(477),vl478(478),
vl479(479),vl480(480),vl481(481),vl482(482),
vl483(483),vl484(484),vl485(485),vl486(486),
vl487(487),vl488(488),vl489(489),vl490(490),
vl491(491),vl492(492),vl493(493),vl494(494),
vl495(495),vl496(496),vl497(497),vl498(498),
vl499(499),vl500(500),vl501(501),vl502(502),
vl503(503),vl504(504),vl505(505),vl506(506),
vl507(507),vl508(508),vl509(509),vl510(510),
vl511(511),vl512(512),vl513(513),vl514(514),
vl515(515),vl516(516),vl517(517),vl518(518),
vl519(519),vl520(520),vl521(521),vl522(522),
vl523(523),vl524(524),vl525(525),vl526(526),
vl527(527),vl528(528),vl529(529),vl530(530),
vl531(531),vl532(532),vl533(533),vl534(534),
vl535(535),vl536(536),vl537(537),vl538(538),
vl539(539),vl540(540),vl541(541),vl542(542),
vl543(543),vl544(544),vl545(545),vl546(546),
vl547(547),vl548(548),vl549(549),vl550(550),
vl551(551),vl552(552),vl553(553),vl554(554),
vl555(555),vl556(556),vl557(557),vl558(558),
vl559(559),vl560(560),vl561(561),vl562(562),
vl563(563),vl564(564),vl565(565),vl566(566),
vl567(567),vl568(568),vl569(569),vl570(570),
vl571(571),vl572(572),vl573(573),vl574(574),
vl575(575),vl576(576),vl577(577),vl578(578),
vl579(579),vl580(580),vl581(581),vl582(582),
vl583(583),vl584(584),vl585(585),vl586(586),
vl587(587),vl588(588),vl589(589),vl590(590),
vl591(591),vl592(592),vl593(593),vl594(594),
vl595(595),vl596(596),vl597(597),vl598(598),
vl599(599),vl600(600),vl601(601),vl602(602),
vl603(603),vl604(604),vl605(605),vl606(606),
vl607(607),vl608(608),vl609(609),vl610(610),
vl611(611),vl612(612),vl613(613),vl614(614),
vl615(615),vl616(616),vl617(617),vl618(618),
vl619(619),vl620(620),vl621(621),vl622(622),
vl623(623),vl624(624),vl625(625),vl626(626),
vl627(627),vl628(628),vl629(629),vl630(630),
vl631(631),vl632(632),vl633(633),vl634(634),
vl635(635),vl636(636),vl637(637),vl638(638),
vl639(639),vl640(640),vl641(641),vl642(642),
vl643(643),vl644(644),vl645(645),vl646(646),
vl647(647),vl648(648),vl649(649),vl650(650),
vl651(651),vl652(652),vl653(653),vl654(654),
vl655(655),vl656(656),vl657(657),vl658(658),
vl659(659),vl660(660),vl661(661),vl662(662),
vl663(663),vl664(664),vl665(665),vl666(666),
vl667(667),vl668(668),vl669(669),vl670(670),
vl671(671),vl672(672),vl673(673),vl674(674),
vl675(675),vl676(676),vl677(677),vl678(678),
vl679(679),vl680(680),vl681(681),vl682(682),
vl683(683),vl684(684),vl685(685),vl686(686),
vl687(687),vl688(688),vl689(689),vl690(690),
vl691(691),vl692(692),vl693(693),vl694(694),
vl695(695),vl696(696),vl697(697),vl698(698),
vl699(699),vl700(700),vl701(701),vl702(702),
vl703(703),vl704(704),vl705(705),vl706(706),
vl707(707),vl708(708),vl709(709),vl710(710),
vl711(711),vl712(712),vl713(713),vl714(714),
vl715(715),vl716(716),vl717(717),vl718(718),
vl719(719),vl720(720),vl721(721),vl722(722),
vl723(723),vl724(724),vl725(725),vl726(726),
vl727(727),vl728(728),vl729(729),vl730(730),
vl731(731),vl732(732),vl733(733),vl734(734),
vl735(735),vl736(736),vl737(737),vl738(738),
vl739(739),vl740(740),vl741(741),vl742(742),
vl743(743),vl744(744),vl745(745),vl746(746),
vl747(747),vl748(748),vl749(749),vl750(750),
vl751(751),vl752(752),vl753(753),vl754(754),
vl755(755),vl756(756),vl757(757),vl758(758),
vl759(759),vl760(760),vl761(761),vl762(762),
vl763(763),vl764(764),vl765(765),vl766(766),
vl767(767),vl768(768),vl769(769),vl770(770),
vl771(771),vl772(772),vl773(773),vl774(774),
vl775(775),vl776(776),vl777(777),vl778(778),
vl779(779),vl780(780),vl781(781),vl782(782),
vl783(783),vl784(784),vl785(785),vl786(786),
vl787(787),vl788(788),vl789(789),vl790(790),
vl791(791),vl792(792),vl793(793),vl794(794),
vl795(795),vl796(796),vl797(797),vl798(798),
vl799(799),vl800(800),vl801(801),vl802(802),
vl803(803),vl804(804),vl805(805),vl806(806),
vl807(807),vl808(808),vl809(809),vl810(810),
vl811(811),vl812(812),vl813(813),vl814(814),
vl815(815),vl816(816),vl817(817),vl818(818),
vl819(819),vl820(820),vl821(821),vl822(822),
vl823(823),vl824(824),vl825(825),vl826(826),
vl827(827),vl828(828),vl829(829),vl830(830),
vl831(831),vl832(832),vl833(833),vl834(834),
vl835(835),vl836(836),vl837(837),vl838(838),
vl839(839),vl840(840),vl841(841),vl842(842),
vl843(843),vl844(844),vl845(845),vl846(846),
vl847(847),vl848(848),vl849(849),vl850(850),
vl851(851),vl852(852),vl853(853),vl854(854),
vl855(855),vl856(856),vl857(857),vl858(858),
vl859(859),vl860(860),vl861(861),vl862(862),
vl863(863),vl864(864),vl865(865),vl866(866),
vl867(867),vl868(868),vl869(869),vl870(870),
vl871(871),vl872(872),vl873(873),vl874(874),
vl875(875),vl876(876),vl877(877),vl878(878),
vl879(879),vl880(880),vl881(881),vl882(882),
vl883(883),vl884(884),vl885(885),vl886(886),
vl887(887),vl888(888),vl889(889),vl890(890),
vl891(891),vl892(892),vl893(893),vl894(894),
vl895(895),vl896(896),vl897(897),vl898(898),
vl899(899),vl900(900),vl901(901),vl902(902),
vl903(903),vl904(904),vl905(905),vl906(906),
vl907(907),vl908(908),vl909(909),vl910(910),
vl911(911),vl912(912),vl913(913),vl914(914),
vl915(915),vl916(916),vl917(917),vl918(918),
vl919(919),vl920(920),vl921(921),vl922(922),
vl923(923),vl924(924),vl925(925),vl926(926),
vl927(927),vl928(928),vl929(929),vl930(930),
vl931(931),vl932(932),vl933(933),vl934(934),
vl935(935),vl936(936),vl937(937),vl938(938),
vl939(939),vl940(940),vl941(941),vl942(942),
vl943(943),vl944(944),vl945(945),vl946(946),
vl947(947),vl948(948),vl949(949),vl950(950),
vl951(951),vl952(952),vl953(953),vl954(954),
vl955(955),vl956(956),vl957(957),vl958(958),
vl959(959),vl960(960),vl961(961),vl962(962),
vl963(963),vl964(964),vl965(965),vl966(966),
vl967(967),vl968(968),vl969(969),vl970(970),
vl971(971),vl972(972),vl973(973),vl974(974),
vl975(975),vl976(976),vl977(977),vl978(978),
vl979(979),vl980(980),vl981(981),vl982(982),
vl983(983),vl984(984),vl985(985),vl986(986),
vl987(987),vl988(988),vl989(989),vl990(990),
vl991(991),vl992(992),vl993(993),vl994(994),
vl995(995),vl996(996),vl997(997),vl998(998),
vl999(999),vl1000(1000),vl1001(1001),vl1002(1002),
vl1003(1003),vl1004(1004),vl1005(1005),vl1006(1006),
vl1007(1007),vl1008(1008),vl1009(1009),vl1010(1010),
vl1011(1011),vl1012(1012),vl1013(1013),vl1014(1014),
vl1015(1015),vl1016(1016),vl1017(1017),vl1018(1018),
vl1019(1019),vl1020(1020),vl1021(1021),vl1022(1022),
vl1023(1023),vl1024(1024),vl1025(1025),vl1026(1026),
vl1027(1027),vl1028(1028),vl1029(1029),vl1030(1030),
vl1031(1031),vl1032(1032),vl1033(1033),vl1034(1034),
vl1035(1035),vl1036(1036),vl1037(1037),vl1038(1038),
vl1039(1039),vl1040(1040),vl1041(1041),vl1042(1042),
vl1043(1043),vl1044(1044),vl1045(1045),vl1046(1046),
vl1047(1047),vl1048(1048),vl1049(1049),vl1050(1050),
vl1051(1051),vl1052(1052),vl1053(1053),vl1054(1054),
vl1055(1055),vl1056(1056),vl1057(1057),vl1058(1058),
vl1059(1059),vl1060(1060),vl1061(1061),vl1062(1062),
vl1063(1063),vl1064(1064),vl1065(1065),vl1066(1066),
vl1067(1067),vl1068(1068),vl1069(1069),vl1070(1070),
vl1071(1071),vl1072(1072),vl1073(1073),vl1074(1074),
vl1075(1075),vl1076(1076),vl1077(1077),vl1078(1078),
vl1079(1079),vl1080(1080),vl1081(1081),vl1082(1082),
vl1083(1083),vl1084(1084),vl1085(1085),vl1086(1086),
vl1087(1087),vl1088(1088),vl1089(1089),vl1090(1090),
vl1091(1091),vl1092(1092),vl1093(1093),vl1094(1094),
vl1095(1095),vl1096(1096),vl1097(1097),vl1098(1098),
vl1099(1099),vl1100(1100),vl1101(1101),vl1102(1102),
vl1103(1103),vl1104(1104),vl1105(1105),vl1106(1106),
vl1107(1107),vl1108(1108),vl1109(1109),vl1110(1110),
vl1111(1111),vl1112(1112),vl1113(1113),vl1114(1114),
vl1115(1115),vl1116(1116),vl1117(1117),vl1118(1118),
vl1119(1119),vl1120(1120),vl1121(1121),vl1122(1122),
vl1123(1123),vl1124(1124),vl1125(1125),vl1126(1126),
vl1127(1127),vl1128(1128),vl1129(1129),vl1130(1130),
vl1131(1131),vl1132(1132),vl1133(1133),vl1134(1134),
vl1135(1135),vl1136(1136),vl1137(1137),vl1138(1138),
vl1139(1139),vl1140(1140),vl1141(1141),vl1142(1142),
vl1143(1143),vl1144(1144),vl1145(1145),vl1146(1146),
vl1147(1147),vl1148(1148),vl1149(1149),vl1150(1150),
vl1151(1151),vl1152(1152),vl1153(1153),vl1154(1154),
vl1155(1155),vl1156(1156),vl1157(1157),vl1158(1158),
vl1159(1159),vl1160(1160),vl1161(1161),vl1162(1162),
vl1163(1163),vl1164(1164),vl1165(1165),vl1166(1166),
vl1167(1167),vl1168(1168),vl1169(1169),vl1170(1170),
vl1171(1171),vl1172(1172),vl1173(1173),vl1174(1174),
vl1175(1175),vl1176(1176),vl1177(1177),vl1178(1178),
vl1179(1179),vl1180(1180),vl1181(1181),vl1182(1182),
vl1183(1183),vl1184(1184),vl1185(1185),vl1186(1186),
vl1187(1187),vl1188(1188),vl1189(1189),vl1190(1190),
vl1191(1191),vl1192(1192),vl1193(1193),vl1194(1194),
vl1195(1195),vl1196(1196),vl1197(1197),vl1198(1198),
vl1199(1199),vl1200(1200),vl1201(1201),vl1202(1202),
vl1203(1203),vl1204(1204),vl1205(1205),vl1206(1206),
vl1207(1207),vl1208(1208),vl1209(1209),vl1210(1210),
vl1211(1211),vl1212(1212),vl1213(1213),vl1214(1214),
vl1215(1215),vl1216(1216),vl1217(1217),vl1218(1218),
vl1219(1219),vl1220(1220),vl1221(1221),vl1222(1222),
vl1223(1223),vl1224(1224),vl1225(1225),vl1226(1226),
vl1227(1227),vl1228(1228),vl1229(1229),vl1230(1230),
vl1231(1231),vl1232(1232),vl1233(1233),vl1234(1234),
vl1235(1235),vl1236(1236),vl1237(1237),vl1238(1238),
vl1239(1239),vl1240(1240),vl1241(1241),vl1242(1242),
vl1243(1243),vl1244(1244),vl1245(1245),vl1246(1246),
vl1247(1247),vl1248(1248),vl1249(1249),vl1250(1250),
vl1251(1251),vl1252(1252),vl1253(1253),vl1254(1254),
vl1255(1255),vl1256(1256),vl1257(1257),vl1258(1258),
vl1259(1259),vl1260(1260),vl1261(1261),vl1262(1262),
vl1263(1263),vl1264(1264),vl1265(1265),vl1266(1266),
vl1267(1267),vl1268(1268),vl1269(1269),vl1270(1270),
vl1271(1271),vl1272(1272),vl1273(1273),vl1274(1274),
vl1275(1275),vl1276(1276),vl1277(1277),vl1278(1278),
vl1279(1279),vl1280(1280),vl1281(1281),vl1282(1282),
vl1283(1283),vl1284(1284),vl1285(1285),vl1286(1286),
vl1287(1287),vl1288(1288),vl1289(1289),vl1290(1290),
vl1291(1291),vl1292(1292),vl1293(1293),vl1294(1294),
vl1295(1295),vl1296(1296),vl1297(1297),vl1298(1298),
vl1299(1299),vl1300(1300),vl1301(1301),vl1302(1302),
vl1303(1303),vl1304(1304),vl1305(1305),vl1306(1306),
vl1307(1307),vl1308(1308),vl1309(1309),vl1310(1310),
vl1311(1311),vl1312(1312),vl1313(1313),vl1314(1314),
vl1315(1315),vl1316(1316),vl1317(1317),vl1318(1318),
vl1319(1319),vl1320(1320),vl1321(1321),vl1322(1322),
vl1323(1323),vl1324(1324),vl1325(1325),vl1326(1326),
vl1327(1327),vl1328(1328),vl1329(1329),vl1330(1330),
vl1331(1331),vl1332(1332),vl1333(1333),vl1334(1334),
vl1335(1335),vl1336(1336),vl1337(1337),vl1338(1338),
vl1339(1339),vl1340(1340),vl1341(1341),vl1342(1342),
vl1343(1343),vl1344(1344),vl1345(1345),vl1346(1346),
vl1347(1347),vl1348(1348),vl1349(1349),vl1350(1350),
vl1351(1351),vl1352(1352),vl1353(1353),vl1354(1354),
vl1355(1355),vl1356(1356),vl1357(1357),vl1358(1358),
vl1359(1359),vl1360(1360),vl1361(1361),vl1362(1362),
vl1363(1363),vl1364(1364),vl1365(1365),vl1366(1366),
vl1367(1367),vl1368(1368),vl1369(1369),vl1370(1370),
vl1371(1371),vl1372(1372),vl1373(1373),vl1374(1374),
vl1375(1375),vl1376(1376),vl1377(1377),vl1378(1378),
vl1379(1379),vl1380(1380),vl1381(1381),vl1382(1382),
vl1383(1383),vl1384(1384),vl1385(1385),vl1386(1386),
vl1387(1387),vl1388(1388),vl1389(1389),vl1390(1390),
vl1391(1391),vl1392(1392),vl1393(1393),vl1394(1394),
vl1395(1395),vl1396(1396),vl1397(1397),vl1398(1398),
vl1399(1399),vl1400(1400),vl1401(1401),vl1402(1402),
vl1403(1403),vl1404(1404),vl1405(1405),vl1406(1406),
vl1407(1407),vl1408(1408),vl1409(1409),vl1410(1410),
vl1411(1411),vl1412(1412),vl1413(1413),vl1414(1414),
vl1415(1415),vl1416(1416),vl1417(1417),vl1418(1418),
vl1419(1419),vl1420(1420),vl1421(1421),vl1422(1422),
vl1423(1423),vl1424(1424),vl1425(1425),vl1426(1426),
vl1427(1427),vl1428(1428),vl1429(1429),vl1430(1430),
vl1431(1431),vl1432(1432),vl1433(1433),vl1434(1434),
vl1435(1435),vl1436(1436),vl1437(1437),vl1438(1438),
vl1439(1439),vl1440(1440),vl1441(1441),vl1442(1442),
vl1443(1443),vl1444(1444),vl1445(1445),vl1446(1446),
vl1447(1447),vl1448(1448),vl1449(1449),vl1450(1450),
vl1451(1451),vl1452(1452),vl1453(1453),vl1454(1454),
vl1455(1455),vl1456(1456),vl1457(1457),vl1458(1458),
vl1459(1459),vl1460(1460),vl1461(1461),vl1462(1462),
vl1463(1463),vl1464(1464),vl1465(1465),vl1466(1466),
vl1467(1467),vl1468(1468),vl1469(1469),vl1470(1470),
vl1471(1471),vl1472(1472),vl1473(1473),vl1474(1474),
vl1475(1475),vl1476(1476),vl1477(1477),vl1478(1478),
vl1479(1479),vl1480(1480),vl1481(1481),vl1482(1482),
vl1483(1483),vl1484(1484),vl1485(1485),vl1486(1486),
vl1487(1487),vl1488(1488),vl1489(1489),vl1490(1490),
vl1491(1491),vl1492(1492),vl1493(1493),vl1494(1494),
vl1495(1495),vl1496(1496),vl1497(1497),vl1498(1498),
vl1499(1499),vl1500(1500),vl1501(1501),vl1502(1502),
vl1503(1503),vl1504(1504),vl1505(1505),vl1506(1506),
vl1507(1507),vl1508(1508),vl1509(1509),vl1510(1510),
vl1511(1511),vl1512(1512),vl1513(1513),vl1514(1514),
vl1515(1515),vl1516(1516),vl1517(1517),vl1518(1518),
vl1519(1519),vl1520(1520),vl1521(1521),vl1522(1522),
vl1523(1523),vl1524(1524),vl1525(1525),vl1526(1526),
vl1527(1527),vl1528(1528),vl1529(1529),vl1530(1530),
vl1531(1531),vl1532(1532),vl1533(1533),vl1534(1534),
vl1535(1535),vl1536(1536),vl1537(1537),vl1538(1538),
vl1539(1539),vl1540(1540),vl1541(1541),vl1542(1542),
vl1543(1543),vl1544(1544),vl1545(1545),vl1546(1546),
vl1547(1547),vl1548(1548),vl1549(1549),vl1550(1550),
vl1551(1551),vl1552(1552),vl1553(1553),vl1554(1554),
vl1555(1555),vl1556(1556),vl1557(1557),vl1558(1558),
vl1559(1559),vl1560(1560),vl1561(1561),vl1562(1562),
vl1563(1563),vl1564(1564),vl1565(1565),vl1566(1566),
vl1567(1567),vl1568(1568),vl1569(1569),vl1570(1570),
vl1571(1571),vl1572(1572),vl1573(1573),vl1574(1574),
vl1575(1575),vl1576(1576),vl1577(1577),vl1578(1578),
vl1579(1579),vl1580(1580),vl1581(1581),vl1582(1582),
vl1583(1583),vl1584(1584),vl1585(1585),vl1586(1586),
vl1587(1587),vl1588(1588),vl1589(1589),vl1590(1590),
vl1591(1591),vl1592(1592),vl1593(1593),vl1594(1594),
vl1595(1595),vl1596(1596),vl1597(1597),vl1598(1598),
vl1599(1599),vl1600(1600),vl1601(1601),vl1602(1602),
vl1603(1603),vl1604(1604),vl1605(1605),vl1606(1606),
vl1607(1607),vl1608(1608),vl1609(1609),vl1610(1610),
vl1611(1611),vl1612(1612),vl1613(1613),vl1614(1614),
vl1615(1615),vl1616(1616),vl1617(1617),vl1618(1618),
vl1619(1619),vl1620(1620),vl1621(1621),vl1622(1622),
vl1623(1623),vl1624(1624),vl1625(1625),vl1626(1626),
vl1627(1627),vl1628(1628),vl1629(1629),vl1630(1630),
vl1631(1631),vl1632(1632),vl1633(1633),vl1634(1634),
vl1635(1635),vl1636(1636),vl1637(1637),vl1638(1638),
vl1639(1639),vl1640(1640),vl1641(1641),vl1642(1642),
vl1643(1643),vl1644(1644),vl1645(1645),vl1646(1646),
vl1647(1647),vl1648(1648),vl1649(1649),vl1650(1650),
vl1651(1651),vl1652(1652),vl1653(1653),vl1654(1654),
vl1655(1655),vl1656(1656),vl1657(1657),vl1658(1658),
vl1659(1659),vl1660(1660),vl1661(1661),vl1662(1662),
vl1663(1663),vl1664(1664),vl1665(1665),vl1666(1666),
vl1667(1667),vl1668(1668),vl1669(1669),vl1670(1670),
vl1671(1671),vl1672(1672),vl1673(1673),vl1674(1674),
vl1675(1675),vl1676(1676),vl1677(1677),vl1678(1678),
vl1679(1679),vl1680(1680),vl1681(1681),vl1682(1682),
vl1683(1683),vl1684(1684),vl1685(1685),vl1686(1686),
vl1687(1687),vl1688(1688),vl1689(1689),vl1690(1690),
vl1691(1691),vl1692(1692),vl1693(1693),vl1694(1694),
vl1695(1695),vl1696(1696),vl1697(1697),vl1698(1698),
vl1699(1699),vl1700(1700),vl1701(1701),vl1702(1702),
vl1703(1703),vl1704(1704),vl1705(1705),vl1706(1706),
vl1707(1707),vl1708(1708),vl1709(1709),vl1710(1710),
vl1711(1711),vl1712(1712),vl1713(1713),vl1714(1714),
vl1715(1715),vl1716(1716),vl1717(1717),vl1718(1718),
vl1719(1719),vl1720(1720),vl1721(1721),vl1722(1722),
vl1723(1723),vl1724(1724),vl1725(1725),vl1726(1726),
vl1727(1727),vl1728(1728),vl1729(1729),vl1730(1730),
vl1731(1731),vl1732(1732),vl1733(1733),vl1734(1734),
vl1735(1735),vl1736(1736),vl1737(1737),vl1738(1738),
vl1739(1739),vl1740(1740),vl1741(1741),vl1742(1742),
vl1743(1743),vl1744(1744),vl1745(1745),vl1746(1746),
vl1747(1747),vl1748(1748),vl1749(1749),vl1750(1750),
vl1751(1751),vl1752(1752),vl1753(1753),vl1754(1754),
vl1755(1755),vl1756(1756),vl1757(1757),vl1758(1758),
vl1759(1759),vl1760(1760),vl1761(1761),vl1762(1762),
vl1763(1763),vl1764(1764),vl1765(1765),vl1766(1766),
vl1767(1767),vl1768(1768),vl1769(1769),vl1770(1770),
vl1771(1771),vl1772(1772),vl1773(1773),vl1774(1774),
vl1775(1775),vl1776(1776),vl1777(1777),vl1778(1778),
vl1779(1779),vl1780(1780),vl1781(1781),vl1782(1782),
vl1783(1783),vl1784(1784),vl1785(1785),vl1786(1786),
vl1787(1787),vl1788(1788),vl1789(1789),vl1790(1790),
vl1791(1791),vl1792(1792),vl1793(1793),vl1794(1794),
vl1795(1795),vl1796(1796),vl1797(1797),vl1798(1798),
vl1799(1799),vl1800(1800),vl1801(1801),vl1802(1802),
vl1803(1803),vl1804(1804),vl1805(1805),vl1806(1806),
vl1807(1807),vl1808(1808),vl1809(1809),vl1810(1810),
vl1811(1811),vl1812(1812),vl1813(1813),vl1814(1814),
vl1815(1815),vl1816(1816),vl1817(1817),vl1818(1818),
vl1819(1819),vl1820(1820),vl1821(1821),vl1822(1822),
vl1823(1823),vl1824(1824),vl1825(1825),vl1826(1826),
vl1827(1827),vl1828(1828),vl1829(1829),vl1830(1830),
vl1831(1831),vl1832(1832),vl1833(1833),vl1834(1834),
vl1835(1835),vl1836(1836),vl1837(1837),vl1838(1838),
vl1839(1839),vl1840(1840),vl1841(1841),vl1842(1842),
vl1843(1843),vl1844(1844),vl1845(1845),vl1846(1846),
vl1847(1847),vl1848(1848),vl1849(1849),vl1850(1850),
vl1851(1851),vl1852(1852),vl1853(1853),vl1854(1854),
vl1855(1855),vl1856(1856),vl1857(1857),vl1858(1858),
vl1859(1859),vl1860(1860),vl1861(1861),vl1862(1862),
vl1863(1863),vl1864(1864),vl1865(1865),vl1866(1866),
vl1867(1867),vl1868(1868),vl1869(1869),vl1870(1870),
vl1871(1871),vl1872(1872),vl1873(1873),vl1874(1874),
vl1875(1875),vl1876(1876),vl1877(1877),vl1878(1878),
vl1879(1879),vl1880(1880),vl1881(1881),vl1882(1882),
vl1883(1883),vl1884(1884),vl1885(1885),vl1886(1886),
vl1887(1887),vl1888(1888),vl1889(1889),vl1890(1890),
vl1891(1891),vl1892(1892),vl1893(1893),vl1894(1894),
vl1895(1895),vl1896(1896),vl1897(1897),vl1898(1898),
vl1899(1899),vl1900(1900),vl1901(1901),vl1902(1902),
vl1903(1903),vl1904(1904),vl1905(1905),vl1906(1906),
vl1907(1907),vl1908(1908),vl1909(1909),vl1910(1910),
vl1911(1911),vl1912(1912),vl1913(1913),vl1914(1914),
vl1915(1915),vl1916(1916),vl1917(1917),vl1918(1918),
vl1919(1919),vl1920(1920),vl1921(1921),vl1922(1922),
vl1923(1923),vl1924(1924),vl1925(1925),vl1926(1926),
vl1927(1927),vl1928(1928),vl1929(1929),vl1930(1930),
vl1931(1931),vl1932(1932),vl1933(1933),vl1934(1934),
vl1935(1935),vl1936(1936),vl1937(1937),vl1938(1938),
vl1939(1939),vl1940(1940),vl1941(1941),vl1942(1942),
vl1943(1943),vl1944(1944),vl1945(1945),vl1946(1946),
vl1947(1947),vl1948(1948),vl1949(1949),vl1950(1950),
vl1951(1951),vl1952(1952),vl1953(1953),vl1954(1954),
vl1955(1955),vl1956(1956),vl1957(1957),vl1958(1958),
vl1959(1959),vl1960(1960),vl1961(1961),vl1962(1962),
vl1963(1963),vl1964(1964),vl1965(1965),vl1966(1966),
vl1967(1967),vl1968(1968),vl1969(1969),vl1970(1970),
vl1971(1971),vl1972(1972),vl1973(1973),vl1974(1974),
vl1975(1975),vl1976(1976),vl1977(1977),vl1978(1978),
vl1979(1979),vl1980(1980),vl1981(1981),vl1982(1982),
vl1983(1983),vl1984(1984),vl1985(1985),vl1986(1986),
vl1987(1987),vl1988(1988),vl1989(1989),vl1990(1990),
vl1991(1991),vl1992(1992),vl1993(1993),vl1994(1994),
vl1995(1995),vl1996(1996),vl1997(1997),vl1998(1998),
vl1999(1999),vl2000(2000),vl2001(2001),vl2002(2002),
vl2003(2003),vl2004(2004),vl2005(2005),vl2006(2006),
vl2007(2007),vl2008(2008),vl2009(2009),vl2010(2010),
vl2011(2011),vl2012(2012),vl2013(2013),vl2014(2014),
vl2015(2015),vl2016(2016),vl2017(2017),vl2018(2018),
vl2019(2019),vl2020(2020),vl2021(2021),vl2022(2022),
vl2023(2023),vl2024(2024),vl2025(2025),vl2026(2026),
vl2027(2027),vl2028(2028),vl2029(2029),vl2030(2030),
vl2031(2031),vl2032(2032),vl2033(2033),vl2034(2034),
vl2035(2035),vl2036(2036),vl2037(2037),vl2038(2038),
vl2039(2039),vl2040(2040),vl2041(2041),vl2042(2042),
vl2043(2043),vl2044(2044),vl2045(2045),vl2046(2046),
vl2047(2047),vl2048(2048),vl2049(2049),vl2050(2050),
vl2051(2051),vl2052(2052),vl2053(2053),vl2054(2054),
vl2055(2055),vl2056(2056),vl2057(2057),vl2058(2058),
vl2059(2059),vl2060(2060),vl2061(2061),vl2062(2062),
vl2063(2063),vl2064(2064),vl2065(2065),vl2066(2066),
vl2067(2067),vl2068(2068),vl2069(2069),vl2070(2070),
vl2071(2071),vl2072(2072),vl2073(2073),vl2074(2074),
vl2075(2075),vl2076(2076),vl2077(2077),vl2078(2078),
vl2079(2079),vl2080(2080),vl2081(2081),vl2082(2082),
vl2083(2083),vl2084(2084),vl2085(2085),vl2086(2086),
vl2087(2087),vl2088(2088),vl2089(2089),vl2090(2090),
vl2091(2091),vl2092(2092),vl2093(2093),vl2094(2094),
vl2095(2095),vl2096(2096),vl2097(2097),vl2098(2098),
vl2099(2099),vl2100(2100),vl2101(2101),vl2102(2102),
vl2103(2103),vl2104(2104),vl2105(2105),vl2106(2106),
vl2107(2107),vl2108(2108),vl2109(2109),vl2110(2110),
vl2111(2111),vl2112(2112),vl2113(2113),vl2114(2114),
vl2115(2115),vl2116(2116),vl2117(2117),vl2118(2118),
vl2119(2119),vl2120(2120),vl2121(2121),vl2122(2122),
vl2123(2123),vl2124(2124),vl2125(2125),vl2126(2126),
vl2127(2127),vl2128(2128),vl2129(2129),vl2130(2130),
vl2131(2131),vl2132(2132),vl2133(2133),vl2134(2134),
vl2135(2135),vl2136(2136),vl2137(2137),vl2138(2138),
vl2139(2139),vl2140(2140),vl2141(2141),vl2142(2142),
vl2143(2143),vl2144(2144),vl2145(2145),vl2146(2146),
vl2147(2147),vl2148(2148),vl2149(2149),vl2150(2150),
vl2151(2151),vl2152(2152),vl2153(2153),vl2154(2154),
vl2155(2155),vl2156(2156),vl2157(2157),vl2158(2158),
vl2159(2159),vl2160(2160),vl2161(2161),vl2162(2162),
vl2163(2163),vl2164(2164),vl2165(2165),vl2166(2166),
vl2167(2167),vl2168(2168),vl2169(2169),vl2170(2170),
vl2171(2171),vl2172(2172),vl2173(2173),vl2174(2174),
vl2175(2175),vl2176(2176),vl2177(2177),vl2178(2178),
vl2179(2179),vl2180(2180),vl2181(2181),vl2182(2182),
vl2183(2183),vl2184(2184),vl2185(2185),vl2186(2186),
vl2187(2187),vl2188(2188),vl2189(2189),vl2190(2190),
vl2191(2191),vl2192(2192),vl2193(2193),vl2194(2194),
vl2195(2195),vl2196(2196),vl2197(2197),vl2198(2198),
vl2199(2199),vl2200(2200),vl2201(2201),vl2202(2202),
vl2203(2203),vl2204(2204),vl2205(2205),vl2206(2206),
vl2207(2207),vl2208(2208),vl2209(2209),vl2210(2210),
vl2211(2211),vl2212(2212),vl2213(2213),vl2214(2214),
vl2215(2215),vl2216(2216),vl2217(2217),vl2218(2218),
vl2219(2219),vl2220(2220),vl2221(2221),vl2222(2222),
vl2223(2223),vl2224(2224),vl2225(2225),vl2226(2226),
vl2227(2227),vl2228(2228),vl2229(2229),vl2230(2230),
vl2231(2231),vl2232(2232),vl2233(2233),vl2234(2234),
vl2235(2235),vl2236(2236),vl2237(2237),vl2238(2238),
vl2239(2239),vl2240(2240),vl2241(2241),vl2242(2242),
vl2243(2243),vl2244(2244),vl2245(2245),vl2246(2246),
vl2247(2247),vl2248(2248),vl2249(2249),vl2250(2250),
vl2251(2251),vl2252(2252),vl2253(2253),vl2254(2254),
vl2255(2255),vl2256(2256),vl2257(2257),vl2258(2258),
vl2259(2259),vl2260(2260),vl2261(2261),vl2262(2262),
vl2263(2263),vl2264(2264),vl2265(2265),vl2266(2266),
vl2267(2267),vl2268(2268),vl2269(2269),vl2270(2270),
vl2271(2271),vl2272(2272),vl2273(2273),vl2274(2274),
vl2275(2275),vl2276(2276),vl2277(2277),vl2278(2278),
vl2279(2279),vl2280(2280),vl2281(2281),vl2282(2282),
vl2283(2283),vl2284(2284),vl2285(2285),vl2286(2286),
vl2287(2287),vl2288(2288),vl2289(2289),vl2290(2290),
vl2291(2291),vl2292(2292),vl2293(2293),vl2294(2294),
vl2295(2295),vl2296(2296),vl2297(2297),vl2298(2298),
vl2299(2299),vl2300(2300),vl2301(2301),vl2302(2302),
vl2303(2303),vl2304(2304),vl2305(2305),vl2306(2306),
vl2307(2307),vl2308(2308),vl2309(2309),vl2310(2310),
vl2311(2311),vl2312(2312),vl2313(2313),vl2314(2314),
vl2315(2315),vl2316(2316),vl2317(2317),vl2318(2318),
vl2319(2319),vl2320(2320),vl2321(2321),vl2322(2322),
vl2323(2323),vl2324(2324),vl2325(2325),vl2326(2326),
vl2327(2327),vl2328(2328),vl2329(2329),vl2330(2330),
vl2331(2331),vl2332(2332),vl2333(2333),vl2334(2334),
vl2335(2335),vl2336(2336),vl2337(2337),vl2338(2338),
vl2339(2339),vl2340(2340),vl2341(2341),vl2342(2342),
vl2343(2343),vl2344(2344),vl2345(2345),vl2346(2346),
vl2347(2347),vl2348(2348),vl2349(2349),vl2350(2350),
vl2351(2351),vl2352(2352),vl2353(2353),vl2354(2354),
vl2355(2355),vl2356(2356),vl2357(2357),vl2358(2358),
vl2359(2359),vl2360(2360),vl2361(2361),vl2362(2362),
vl2363(2363),vl2364(2364),vl2365(2365),vl2366(2366),
vl2367(2367),vl2368(2368),vl2369(2369),vl2370(2370),
vl2371(2371),vl2372(2372),vl2373(2373),vl2374(2374),
vl2375(2375),vl2376(2376),vl2377(2377),vl2378(2378),
vl2379(2379),vl2380(2380),vl2381(2381),vl2382(2382),
vl2383(2383),vl2384(2384),vl2385(2385),vl2386(2386),
vl2387(2387),vl2388(2388),vl2389(2389),vl2390(2390),
vl2391(2391),vl2392(2392),vl2393(2393),vl2394(2394),
vl2395(2395),vl2396(2396),vl2397(2397),vl2398(2398),
vl2399(2399),vl2400(2400),vl2401(2401),vl2402(2402),
vl2403(2403),vl2404(2404),vl2405(2405),vl2406(2406),
vl2407(2407),vl2408(2408),vl2409(2409),vl2410(2410),
vl2411(2411),vl2412(2412),vl2413(2413),vl2414(2414),
vl2415(2415),vl2416(2416),vl2417(2417),vl2418(2418),
vl2419(2419),vl2420(2420),vl2421(2421),vl2422(2422),
vl2423(2423),vl2424(2424),vl2425(2425),vl2426(2426),
vl2427(2427),vl2428(2428),vl2429(2429),vl2430(2430),
vl2431(2431),vl2432(2432),vl2433(2433),vl2434(2434),
vl2435(2435),vl2436(2436),vl2437(2437),vl2438(2438),
vl2439(2439),vl2440(2440),vl2441(2441),vl2442(2442),
vl2443(2443),vl2444(2444),vl2445(2445),vl2446(2446),
vl2447(2447),vl2448(2448),vl2449(2449),vl2450(2450),
vl2451(2451),vl2452(2452),vl2453(2453),vl2454(2454),
vl2455(2455),vl2456(2456),vl2457(2457),vl2458(2458),
vl2459(2459),vl2460(2460),vl2461(2461),vl2462(2462),
vl2463(2463),vl2464(2464),vl2465(2465),vl2466(2466),
vl2467(2467),vl2468(2468),vl2469(2469),vl2470(2470),
vl2471(2471),vl2472(2472),vl2473(2473),vl2474(2474),
vl2475(2475),vl2476(2476),vl2477(2477),vl2478(2478),
vl2479(2479),vl2480(2480),vl2481(2481),vl2482(2482),
vl2483(2483),vl2484(2484),vl2485(2485),vl2486(2486),
vl2487(2487),vl2488(2488),vl2489(2489),vl2490(2490),
vl2491(2491),vl2492(2492),vl2493(2493),vl2494(2494),
vl2495(2495),vl2496(2496),vl2497(2497),vl2498(2498),
vl2499(2499),vl2500(2500),vl2501(2501),vl2502(2502),
vl2503(2503),vl2504(2504),vl2505(2505),vl2506(2506),
vl2507(2507),vl2508(2508),vl2509(2509),vl2510(2510),
vl2511(2511),vl2512(2512),vl2513(2513),vl2514(2514),
vl2515(2515),vl2516(2516),vl2517(2517),vl2518(2518),
vl2519(2519),vl2520(2520),vl2521(2521),vl2522(2522),
vl2523(2523),vl2524(2524),vl2525(2525),vl2526(2526),
vl2527(2527),vl2528(2528),vl2529(2529),vl2530(2530),
vl2531(2531),vl2532(2532),vl2533(2533),vl2534(2534),
vl2535(2535),vl2536(2536),vl2537(2537),vl2538(2538),
vl2539(2539),vl2540(2540),vl2541(2541),vl2542(2542),
vl2543(2543),vl2544(2544),vl2545(2545),vl2546(2546),
vl2547(2547),vl2548(2548),vl2549(2549),vl2550(2550),
vl2551(2551),vl2552(2552),vl2553(2553),vl2554(2554),
vl2555(2555),vl2556(2556),vl2557(2557),vl2558(2558),
vl2559(2559),vl2560(2560),vl2561(2561),vl2562(2562),
vl2563(2563),vl2564(2564),vl2565(2565),vl2566(2566),
vl2567(2567),vl2568(2568),vl2569(2569),vl2570(2570),
vl2571(2571),vl2572(2572),vl2573(2573),vl2574(2574),
vl2575(2575),vl2576(2576),vl2577(2577),vl2578(2578),
vl2579(2579),vl2580(2580),vl2581(2581),vl2582(2582),
vl2583(2583),vl2584(2584),vl2585(2585),vl2586(2586),
vl2587(2587),vl2588(2588),vl2589(2589),vl2590(2590),
vl2591(2591),vl2592(2592),vl2593(2593),vl2594(2594),
vl2595(2595),vl2596(2596),vl2597(2597),vl2598(2598),
vl2599(2599),vl2600(2600),vl2601(2601),vl2602(2602),
vl2603(2603),vl2604(2604),vl2605(2605),vl2606(2606),
vl2607(2607),vl2608(2608),vl2609(2609),vl2610(2610),
vl2611(2611),vl2612(2612),vl2613(2613),vl2614(2614),
vl2615(2615),vl2616(2616),vl2617(2617),vl2618(2618),
vl2619(2619),vl2620(2620),vl2621(2621),vl2622(2622),
vl2623(2623),vl2624(2624),vl2625(2625),vl2626(2626),
vl2627(2627),vl2628(2628),vl2629(2629),vl2630(2630),
vl2631(2631),vl2632(2632),vl2633(2633),vl2634(2634),
vl2635(2635),vl2636(2636),vl2637(2637),vl2638(2638),
vl2639(2639),vl2640(2640),vl2641(2641),vl2642(2642),
vl2643(2643),vl2644(2644),vl2645(2645),vl2646(2646),
vl2647(2647),vl2648(2648),vl2649(2649),vl2650(2650),
vl2651(2651),vl2652(2652),vl2653(2653),vl2654(2654),
vl2655(2655),vl2656(2656),vl2657(2657),vl2658(2658),
vl2659(2659),vl2660(2660),vl2661(2661),vl2662(2662),
vl2663(2663),vl2664(2664),vl2665(2665),vl2666(2666),
vl2667(2667),vl2668(2668),vl2669(2669),vl2670(2670),
vl2671(2671),vl2672(2672),vl2673(2673),vl2674(2674),
vl2675(2675),vl2676(2676),vl2677(2677),vl2678(2678),
vl2679(2679),vl2680(2680),vl2681(2681),vl2682(2682),
vl2683(2683),vl2684(2684),vl2685(2685),vl2686(2686),
vl2687(2687),vl2688(2688),vl2689(2689),vl2690(2690),
vl2691(2691),vl2692(2692),vl2693(2693),vl2694(2694),
vl2695(2695),vl2696(2696),vl2697(2697),vl2698(2698),
vl2699(2699),vl2700(2700),vl2701(2701),vl2702(2702),
vl2703(2703),vl2704(2704),vl2705(2705),vl2706(2706),
vl2707(2707),vl2708(2708),vl2709(2709),vl2710(2710),
vl2711(2711),vl2712(2712),vl2713(2713),vl2714(2714),
vl2715(2715),vl2716(2716),vl2717(2717),vl2718(2718),
vl2719(2719),vl2720(2720),vl2721(2721),vl2722(2722),
vl2723(2723),vl2724(2724),vl2725(2725),vl2726(2726),
vl2727(2727),vl2728(2728),vl2729(2729),vl2730(2730),
vl2731(2731),vl2732(2732),vl2733(2733),vl2734(2734),
vl2735(2735),vl2736(2736),vl2737(2737),vl2738(2738),
vl2739(2739),vl2740(2740),vl2741(2741),vl2742(2742),
vl2743(2743),vl2744(2744),vl2745(2745),vl2746(2746),
vl2747(2747),vl2748(2748),vl2749(2749),vl2750(2750),
vl2751(2751),vl2752(2752),vl2753(2753),vl2754(2754),
vl2755(2755),vl2756(2756),vl2757(2757),vl2758(2758),
vl2759(2759),vl2760(2760),vl2761(2761),vl2762(2762),
vl2763(2763),vl2764(2764),vl2765(2765),vl2766(2766),
vl2767(2767),vl2768(2768),vl2769(2769),vl2770(2770),
vl2771(2771),vl2772(2772),vl2773(2773),vl2774(2774),
vl2775(2775),vl2776(2776),vl2777(2777),vl2778(2778),
vl2779(2779),vl2780(2780),vl2781(2781),vl2782(2782),
vl2783(2783),vl2784(2784),vl2785(2785),vl2786(2786),
vl2787(2787),vl2788(2788),vl2789(2789),vl2790(2790),
vl2791(2791),vl2792(2792),vl2793(2793),vl2794(2794),
vl2795(2795),vl2796(2796),vl2797(2797),vl2798(2798),
vl2799(2799),vl2800(2800),vl2801(2801),vl2802(2802),
vl2803(2803),vl2804(2804),vl2805(2805),vl2806(2806),
vl2807(2807),vl2808(2808),vl2809(2809),vl2810(2810),
vl2811(2811),vl2812(2812),vl2813(2813),vl2814(2814),
vl2815(2815),vl2816(2816),vl2817(2817),vl2818(2818),
vl2819(2819),vl2820(2820),vl2821(2821),vl2822(2822),
vl2823(2823),vl2824(2824),vl2825(2825),vl2826(2826),
vl2827(2827),vl2828(2828),vl2829(2829),vl2830(2830),
vl2831(2831),vl2832(2832),vl2833(2833),vl2834(2834),
vl2835(2835),vl2836(2836),vl2837(2837),vl2838(2838),
vl2839(2839),vl2840(2840),vl2841(2841),vl2842(2842),
vl2843(2843),vl2844(2844),vl2845(2845),vl2846(2846),
vl2847(2847),vl2848(2848),vl2849(2849),vl2850(2850),
vl2851(2851),vl2852(2852),vl2853(2853),vl2854(2854),
vl2855(2855),vl2856(2856),vl2857(2857),vl2858(2858),
vl2859(2859),vl2860(2860),vl2861(2861),vl2862(2862),
vl2863(2863),vl2864(2864),vl2865(2865),vl2866(2866),
vl2867(2867),vl2868(2868),vl2869(2869),vl2870(2870),
vl2871(2871),vl2872(2872),vl2873(2873),vl2874(2874),
vl2875(2875),vl2876(2876),vl2877(2877),vl2878(2878),
vl2879(2879),vl2880(2880),vl2881(2881),vl2882(2882),
vl2883(2883),vl2884(2884),vl2885(2885),vl2886(2886),
vl2887(2887),vl2888(2888),vl2889(2889),vl2890(2890),
vl2891(2891),vl2892(2892),vl2893(2893),vl2894(2894),
vl2895(2895),vl2896(2896),vl2897(2897),vl2898(2898),
vl2899(2899),vl2900(2900),vl2901(2901),vl2902(2902),
vl2903(2903),vl2904(2904),vl2905(2905),vl2906(2906),
vl2907(2907),vl2908(2908),vl2909(2909),vl2910(2910),
vl2911(2911),vl2912(2912),vl2913(2913),vl2914(2914),
vl2915(2915),vl2916(2916),vl2917(2917),vl2918(2918),
vl2919(2919),vl2920(2920),vl2921(2921),vl2922(2922),
vl2923(2923),vl2924(2924),vl2925(2925),vl2926(2926),
vl2927(2927),vl2928(2928),vl2929(2929),vl2930(2930),
vl2931(2931),vl2932(2932),vl2933(2933),vl2934(2934),
vl2935(2935),vl2936(2936),vl2937(2937),vl2938(2938),
vl2939(2939),vl2940(2940),vl2941(2941),vl2942(2942),
vl2943(2943),vl2944(2944),vl2945(2945),vl2946(2946),
vl2947(2947),vl2948(2948),vl2949(2949),vl2950(2950),
vl2951(2951),vl2952(2952),vl2953(2953),vl2954(2954),
vl2955(2955),vl2956(2956),vl2957(2957),vl2958(2958),
vl2959(2959),vl2960(2960),vl2961(2961),vl2962(2962),
vl2963(2963),vl2964(2964),vl2965(2965),vl2966(2966),
vl2967(2967),vl2968(2968),vl2969(2969),vl2970(2970),
vl2971(2971),vl2972(2972),vl2973(2973),vl2974(2974),
vl2975(2975),vl2976(2976),vl2977(2977),vl2978(2978),
vl2979(2979),vl2980(2980),vl2981(2981),vl2982(2982),
vl2983(2983),vl2984(2984),vl2985(2985),vl2986(2986),
vl2987(2987),vl2988(2988),vl2989(2989),vl2990(2990),
vl2991(2991),vl2992(2992),vl2993(2993),vl2994(2994),
vl2995(2995),vl2996(2996),vl2997(2997),vl2998(2998),
vl2999(2999),vl3000(3000),vl3001(3001),vl3002(3002),
vl3003(3003),vl3004(3004),vl3005(3005),vl3006(3006),
vl3007(3007),vl3008(3008),vl3009(3009),vl3010(3010),
vl3011(3011),vl3012(3012),vl3013(3013),vl3014(3014),
vl3015(3015),vl3016(3016),vl3017(3017),vl3018(3018),
vl3019(3019),vl3020(3020),vl3021(3021),vl3022(3022),
vl3023(3023),vl3024(3024),vl3025(3025),vl3026(3026),
vl3027(3027),vl3028(3028),vl3029(3029),vl3030(3030),
vl3031(3031),vl3032(3032),vl3033(3033),vl3034(3034),
vl3035(3035),vl3036(3036),vl3037(3037),vl3038(3038),
vl3039(3039),vl3040(3040),vl3041(3041),vl3042(3042),
vl3043(3043),vl3044(3044),vl3045(3045),vl3046(3046),
vl3047(3047),vl3048(3048),vl3049(3049),vl3050(3050),
vl3051(3051),vl3052(3052),vl3053(3053),vl3054(3054),
vl3055(3055),vl3056(3056),vl3057(3057),vl3058(3058),
vl3059(3059),vl3060(3060),vl3061(3061),vl3062(3062),
vl3063(3063),vl3064(3064),vl3065(3065),vl3066(3066),
vl3067(3067),vl3068(3068),vl3069(3069),vl3070(3070),
vl3071(3071),vl3072(3072),vl3073(3073),vl3074(3074),
vl3075(3075),vl3076(3076),vl3077(3077),vl3078(3078),
vl3079(3079),vl3080(3080),vl3081(3081),vl3082(3082),
vl3083(3083),vl3084(3084),vl3085(3085),vl3086(3086),
vl3087(3087),vl3088(3088),vl3089(3089),vl3090(3090),
vl3091(3091),vl3092(3092),vl3093(3093),vl3094(3094),
vl3095(3095),vl3096(3096),vl3097(3097),vl3098(3098),
vl3099(3099),vl3100(3100),vl3101(3101),vl3102(3102),
vl3103(3103),vl3104(3104),vl3105(3105),vl3106(3106),
vl3107(3107),vl3108(3108),vl3109(3109),vl3110(3110),
vl3111(3111),vl3112(3112),vl3113(3113),vl3114(3114),
vl3115(3115),vl3116(3116),vl3117(3117),vl3118(3118),
vl3119(3119),vl3120(3120),vl3121(3121),vl3122(3122),
vl3123(3123),vl3124(3124),vl3125(3125),vl3126(3126),
vl3127(3127),vl3128(3128),vl3129(3129),vl3130(3130),
vl3131(3131),vl3132(3132),vl3133(3133),vl3134(3134),
vl3135(3135),vl3136(3136),vl3137(3137),vl3138(3138),
vl3139(3139),vl3140(3140),vl3141(3141),vl3142(3142),
vl3143(3143),vl3144(3144),vl3145(3145),vl3146(3146),
vl3147(3147),vl3148(3148),vl3149(3149),vl3150(3150),
vl3151(3151),vl3152(3152),vl3153(3153),vl3154(3154),
vl3155(3155),vl3156(3156),vl3157(3157),vl3158(3158),
vl3159(3159),vl3160(3160),vl3161(3161),vl3162(3162),
vl3163(3163),vl3164(3164),vl3165(3165),vl3166(3166),
vl3167(3167),vl3168(3168),vl3169(3169),vl3170(3170),
vl3171(3171),vl3172(3172),vl3173(3173),vl3174(3174),
vl3175(3175),vl3176(3176),vl3177(3177),vl3178(3178),
vl3179(3179),vl3180(3180),vl3181(3181),vl3182(3182),
vl3183(3183),vl3184(3184),vl3185(3185),vl3186(3186),
vl3187(3187),vl3188(3188),vl3189(3189),vl3190(3190),
vl3191(3191),vl3192(3192),vl3193(3193),vl3194(3194),
vl3195(3195),vl3196(3196),vl3197(3197),vl3198(3198),
vl3199(3199),vl3200(3200),vl3201(3201),vl3202(3202),
vl3203(3203),vl3204(3204),vl3205(3205),vl3206(3206),
vl3207(3207),vl3208(3208),vl3209(3209),vl3210(3210),
vl3211(3211),vl3212(3212),vl3213(3213),vl3214(3214),
vl3215(3215),vl3216(3216),vl3217(3217),vl3218(3218),
vl3219(3219),vl3220(3220),vl3221(3221),vl3222(3222),
vl3223(3223),vl3224(3224),vl3225(3225),vl3226(3226),
vl3227(3227),vl3228(3228),vl3229(3229),vl3230(3230),
vl3231(3231),vl3232(3232),vl3233(3233),vl3234(3234),
vl3235(3235),vl3236(3236),vl3237(3237),vl3238(3238),
vl3239(3239),vl3240(3240),vl3241(3241),vl3242(3242),
vl3243(3243),vl3244(3244),vl3245(3245),vl3246(3246),
vl3247(3247),vl3248(3248),vl3249(3249),vl3250(3250),
vl3251(3251),vl3252(3252),vl3253(3253),vl3254(3254),
vl3255(3255),vl3256(3256),vl3257(3257),vl3258(3258),
vl3259(3259),vl3260(3260),vl3261(3261),vl3262(3262),
vl3263(3263),vl3264(3264),vl3265(3265),vl3266(3266),
vl3267(3267),vl3268(3268),vl3269(3269),vl3270(3270),
vl3271(3271),vl3272(3272),vl3273(3273),vl3274(3274),
vl3275(3275),vl3276(3276),vl3277(3277),vl3278(3278),
vl3279(3279),vl3280(3280),vl3281(3281),vl3282(3282),
vl3283(3283),vl3284(3284),vl3285(3285),vl3286(3286),
vl3287(3287),vl3288(3288),vl3289(3289),vl3290(3290),
vl3291(3291),vl3292(3292),vl3293(3293),vl3294(3294),
vl3295(3295),vl3296(3296),vl3297(3297),vl3298(3298),
vl3299(3299),vl3300(3300),vl3301(3301),vl3302(3302),
vl3303(3303),vl3304(3304),vl3305(3305),vl3306(3306),
vl3307(3307),vl3308(3308),vl3309(3309),vl3310(3310),
vl3311(3311),vl3312(3312),vl3313(3313),vl3314(3314),
vl3315(3315),vl3316(3316),vl3317(3317),vl3318(3318),
vl3319(3319),vl3320(3320),vl3321(3321),vl3322(3322),
vl3323(3323),vl3324(3324),vl3325(3325),vl3326(3326),
vl3327(3327),vl3328(3328),vl3329(3329),vl3330(3330),
vl3331(3331),vl3332(3332),vl3333(3333),vl3334(3334),
vl3335(3335),vl3336(3336),vl3337(3337),vl3338(3338),
vl3339(3339),vl3340(3340),vl3341(3341),vl3342(3342),
vl3343(3343),vl3344(3344),vl3345(3345),vl3346(3346),
vl3347(3347),vl3348(3348),vl3349(3349),vl3350(3350),
vl3351(3351),vl3352(3352),vl3353(3353),vl3354(3354),
vl3355(3355),vl3356(3356),vl3357(3357),vl3358(3358),
vl3359(3359),vl3360(3360),vl3361(3361),vl3362(3362),
vl3363(3363),vl3364(3364),vl3365(3365),vl3366(3366),
vl3367(3367),vl3368(3368),vl3369(3369),vl3370(3370),
vl3371(3371),vl3372(3372),vl3373(3373),vl3374(3374),
vl3375(3375),vl3376(3376),vl3377(3377),vl3378(3378),
vl3379(3379),vl3380(3380),vl3381(3381),vl3382(3382),
vl3383(3383),vl3384(3384),vl3385(3385),vl3386(3386),
vl3387(3387),vl3388(3388),vl3389(3389),vl3390(3390),
vl3391(3391),vl3392(3392),vl3393(3393),vl3394(3394),
vl3395(3395),vl3396(3396),vl3397(3397),vl3398(3398),
vl3399(3399),vl3400(3400),vl3401(3401),vl3402(3402),
vl3403(3403),vl3404(3404),vl3405(3405),vl3406(3406),
vl3407(3407),vl3408(3408),vl3409(3409),vl3410(3410),
vl3411(3411),vl3412(3412),vl3413(3413),vl3414(3414),
vl3415(3415),vl3416(3416),vl3417(3417),vl3418(3418),
vl3419(3419),vl3420(3420),vl3421(3421),vl3422(3422),
vl3423(3423),vl3424(3424),vl3425(3425),vl3426(3426),
vl3427(3427),vl3428(3428),vl3429(3429),vl3430(3430),
vl3431(3431),vl3432(3432),vl3433(3433),vl3434(3434),
vl3435(3435),vl3436(3436),vl3437(3437),vl3438(3438),
vl3439(3439),vl3440(3440),vl3441(3441),vl3442(3442),
vl3443(3443),vl3444(3444),vl3445(3445),vl3446(3446),
vl3447(3447),vl3448(3448),vl3449(3449),vl3450(3450),
vl3451(3451),vl3452(3452),vl3453(3453),vl3454(3454),
vl3455(3455),vl3456(3456),vl3457(3457),vl3458(3458),
vl3459(3459),vl3460(3460),vl3461(3461),vl3462(3462),
vl3463(3463),vl3464(3464),vl3465(3465),vl3466(3466),
vl3467(3467),vl3468(3468),vl3469(3469),vl3470(3470),
vl3471(3471),vl3472(3472),vl3473(3473),vl3474(3474),
vl3475(3475),vl3476(3476),vl3477(3477),vl3478(3478),
vl3479(3479),vl3480(3480),vl3481(3481),vl3482(3482),
vl3483(3483),vl3484(3484),vl3485(3485),vl3486(3486),
vl3487(3487),vl3488(3488),vl3489(3489),vl3490(3490),
vl3491(3491),vl3492(3492),vl3493(3493),vl3494(3494),
vl3495(3495),vl3496(3496),vl3497(3497),vl3498(3498),
vl3499(3499),vl3500(3500),vl3501(3501),vl3502(3502),
vl3503(3503),vl3504(3504),vl3505(3505),vl3506(3506),
vl3507(3507),vl3508(3508),vl3509(3509),vl3510(3510),
vl3511(3511),vl3512(3512),vl3513(3513),vl3514(3514),
vl3515(3515),vl3516(3516),vl3517(3517),vl3518(3518),
vl3519(3519),vl3520(3520),vl3521(3521),vl3522(3522),
vl3523(3523),vl3524(3524),vl3525(3525),vl3526(3526),
vl3527(3527),vl3528(3528),vl3529(3529),vl3530(3530),
vl3531(3531),vl3532(3532),vl3533(3533),vl3534(3534),
vl3535(3535),vl3536(3536),vl3537(3537),vl3538(3538),
vl3539(3539),vl3540(3540),vl3541(3541),vl3542(3542),
vl3543(3543),vl3544(3544),vl3545(3545),vl3546(3546),
vl3547(3547),vl3548(3548),vl3549(3549),vl3550(3550),
vl3551(3551),vl3552(3552),vl3553(3553),vl3554(3554),
vl3555(3555),vl3556(3556),vl3557(3557),vl3558(3558),
vl3559(3559),vl3560(3560),vl3561(3561),vl3562(3562),
vl3563(3563),vl3564(3564),vl3565(3565),vl3566(3566),
vl3567(3567),vl3568(3568),vl3569(3569),vl3570(3570),
vl3571(3571),vl3572(3572),vl3573(3573),vl3574(3574),
vl3575(3575),vl3576(3576),vl3577(3577),vl3578(3578),
vl3579(3579),vl3580(3580),vl3581(3581),vl3582(3582),
vl3583(3583),vl3584(3584),vl3585(3585),vl3586(3586),
vl3587(3587),vl3588(3588),vl3589(3589),vl3590(3590),
vl3591(3591),vl3592(3592),vl3593(3593),vl3594(3594),
vl3595(3595),vl3596(3596),vl3597(3597),vl3598(3598),
vl3599(3599),vl3600(3600),vl3601(3601),vl3602(3602),
vl3603(3603),vl3604(3604),vl3605(3605),vl3606(3606),
vl3607(3607),vl3608(3608),vl3609(3609),vl3610(3610),
vl3611(3611),vl3612(3612),vl3613(3613),vl3614(3614),
vl3615(3615),vl3616(3616),vl3617(3617),vl3618(3618),
vl3619(3619),vl3620(3620),vl3621(3621),vl3622(3622),
vl3623(3623),vl3624(3624),vl3625(3625),vl3626(3626),
vl3627(3627),vl3628(3628),vl3629(3629),vl3630(3630),
vl3631(3631),vl3632(3632),vl3633(3633),vl3634(3634),
vl3635(3635),vl3636(3636),vl3637(3637),vl3638(3638),
vl3639(3639),vl3640(3640),vl3641(3641),vl3642(3642),
vl3643(3643),vl3644(3644),vl3645(3645),vl3646(3646),
vl3647(3647),vl3648(3648),vl3649(3649),vl3650(3650),
vl3651(3651),vl3652(3652),vl3653(3653),vl3654(3654),
vl3655(3655),vl3656(3656),vl3657(3657),vl3658(3658),
vl3659(3659),vl3660(3660),vl3661(3661),vl3662(3662),
vl3663(3663),vl3664(3664),vl3665(3665),vl3666(3666),
vl3667(3667),vl3668(3668),vl3669(3669),vl3670(3670),
vl3671(3671),vl3672(3672),vl3673(3673),vl3674(3674),
vl3675(3675),vl3676(3676),vl3677(3677),vl3678(3678),
vl3679(3679),vl3680(3680),vl3681(3681),vl3682(3682),
vl3683(3683),vl3684(3684),vl3685(3685),vl3686(3686),
vl3687(3687),vl3688(3688),vl3689(3689),vl3690(3690),
vl3691(3691),vl3692(3692),vl3693(3693),vl3694(3694),
vl3695(3695),vl3696(3696),vl3697(3697),vl3698(3698),
vl3699(3699),vl3700(3700),vl3701(3701),vl3702(3702),
vl3703(3703),vl3704(3704),vl3705(3705),vl3706(3706),
vl3707(3707),vl3708(3708),vl3709(3709),vl3710(3710),
vl3711(3711),vl3712(3712),vl3713(3713),vl3714(3714),
vl3715(3715),vl3716(3716),vl3717(3717),vl3718(3718),
vl3719(3719),vl3720(3720),vl3721(3721),vl3722(3722),
vl3723(3723),vl3724(3724),vl3725(3725),vl3726(3726),
vl3727(3727),vl3728(3728),vl3729(3729),vl3730(3730),
vl3731(3731),vl3732(3732),vl3733(3733),vl3734(3734),
vl3735(3735),vl3736(3736),vl3737(3737),vl3738(3738),
vl3739(3739),vl3740(3740),vl3741(3741),vl3742(3742),
vl3743(3743),vl3744(3744),vl3745(3745),vl3746(3746),
vl3747(3747),vl3748(3748),vl3749(3749),vl3750(3750),
vl3751(3751),vl3752(3752),vl3753(3753),vl3754(3754),
vl3755(3755),vl3756(3756),vl3757(3757),vl3758(3758),
vl3759(3759),vl3760(3760),vl3761(3761),vl3762(3762),
vl3763(3763),vl3764(3764),vl3765(3765),vl3766(3766),
vl3767(3767),vl3768(3768),vl3769(3769),vl3770(3770),
vl3771(3771),vl3772(3772),vl3773(3773),vl3774(3774),
vl3775(3775),vl3776(3776),vl3777(3777),vl3778(3778),
vl3779(3779),vl3780(3780),vl3781(3781),vl3782(3782),
vl3783(3783),vl3784(3784),vl3785(3785),vl3786(3786),
vl3787(3787),vl3788(3788),vl3789(3789),vl3790(3790),
vl3791(3791),vl3792(3792),vl3793(3793),vl3794(3794),
vl3795(3795),vl3796(3796),vl3797(3797),vl3798(3798),
vl3799(3799),vl3800(3800),vl3801(3801),vl3802(3802),
vl3803(3803),vl3804(3804),vl3805(3805),vl3806(3806),
vl3807(3807),vl3808(3808),vl3809(3809),vl3810(3810),
vl3811(3811),vl3812(3812),vl3813(3813),vl3814(3814),
vl3815(3815),vl3816(3816),vl3817(3817),vl3818(3818),
vl3819(3819),vl3820(3820),vl3821(3821),vl3822(3822),
vl3823(3823),vl3824(3824),vl3825(3825),vl3826(3826),
vl3827(3827),vl3828(3828),vl3829(3829),vl3830(3830),
vl3831(3831),vl3832(3832),vl3833(3833),vl3834(3834),
vl3835(3835),vl3836(3836),vl3837(3837),vl3838(3838),
vl3839(3839),vl3840(3840),vl3841(3841),vl3842(3842),
vl3843(3843),vl3844(3844),vl3845(3845),vl3846(3846),
vl3847(3847),vl3848(3848),vl3849(3849),vl3850(3850),
vl3851(3851),vl3852(3852),vl3853(3853),vl3854(3854),
vl3855(3855),vl3856(3856),vl3857(3857),vl3858(3858),
vl3859(3859),vl3860(3860),vl3861(3861),vl3862(3862),
vl3863(3863),vl3864(3864),vl3865(3865),vl3866(3866),
vl3867(3867),vl3868(3868),vl3869(3869),vl3870(3870),
vl3871(3871),vl3872(3872),vl3873(3873),vl3874(3874),
vl3875(3875),vl3876(3876),vl3877(3877),vl3878(3878),
vl3879(3879),vl3880(3880),vl3881(3881),vl3882(3882),
vl3883(3883),vl3884(3884),vl3885(3885),vl3886(3886),
vl3887(3887),vl3888(3888),vl3889(3889),vl3890(3890),
vl3891(3891),vl3892(3892),vl3893(3893),vl3894(3894),
vl3895(3895),vl3896(3896),vl3897(3897),vl3898(3898),
vl3899(3899),vl3900(3900),vl3901(3901),vl3902(3902),
vl3903(3903),vl3904(3904),vl3905(3905),vl3906(3906),
vl3907(3907),vl3908(3908),vl3909(3909),vl3910(3910),
vl3911(3911),vl3912(3912),vl3913(3913),vl3914(3914),
vl3915(3915),vl3916(3916),vl3917(3917),vl3918(3918),
vl3919(3919),vl3920(3920),vl3921(3921),vl3922(3922),
vl3923(3923),vl3924(3924),vl3925(3925),vl3926(3926),
vl3927(3927),vl3928(3928),vl3929(3929),vl3930(3930),
vl3931(3931),vl3932(3932),vl3933(3933),vl3934(3934),
vl3935(3935),vl3936(3936),vl3937(3937),vl3938(3938),
vl3939(3939),vl3940(3940),vl3941(3941),vl3942(3942),
vl3943(3943),vl3944(3944),vl3945(3945),vl3946(3946),
vl3947(3947),vl3948(3948),vl3949(3949),vl3950(3950),
vl3951(3951),vl3952(3952),vl3953(3953),vl3954(3954),
vl3955(3955),vl3956(3956),vl3957(3957),vl3958(3958),
vl3959(3959),vl3960(3960),vl3961(3961),vl3962(3962),
vl3963(3963),vl3964(3964),vl3965(3965),vl3966(3966),
vl3967(3967),vl3968(3968),vl3969(3969),vl3970(3970),
vl3971(3971),vl3972(3972),vl3973(3973),vl3974(3974),
vl3975(3975),vl3976(3976),vl3977(3977),vl3978(3978),
vl3979(3979),vl3980(3980),vl3981(3981),vl3982(3982),
vl3983(3983),vl3984(3984),vl3985(3985),vl3986(3986),
vl3987(3987),vl3988(3988),vl3989(3989),vl3990(3990),
vl3991(3991),vl3992(3992),vl3993(3993),vl3994(3994),
vl3995(3995),vl3996(3996),vl3997(3997),vl3998(3998),
vl3999(3999),vl4000(4000),vl4001(4001),vl4002(4002),
vl4003(4003),vl4004(4004),vl4005(4005),vl4006(4006),
vl4007(4007),vl4008(4008),vl4009(4009),vl4010(4010),
vl4011(4011),vl4012(4012),vl4013(4013),vl4014(4014),
vl4015(4015),vl4016(4016),vl4017(4017),vl4018(4018),
vl4019(4019),vl4020(4020),vl4021(4021),vl4022(4022),
vl4023(4023),vl4024(4024),vl4025(4025),vl4026(4026),
vl4027(4027),vl4028(4028),vl4029(4029),vl4030(4030),
vl4031(4031),vl4032(4032),vl4033(4033),vl4034(4034),
vl4035(4035),vl4036(4036),vl4037(4037),vl4038(4038),
vl4039(4039),vl4040(4040),vl4041(4041),vl4042(4042),
vl4043(4043),vl4044(4044),vl4045(4045),vl4046(4046),
vl4047(4047),vl4048(4048),vl4049(4049),vl4050(4050),
vl4051(4051),vl4052(4052),vl4053(4053),vl4054(4054),
vl4055(4055),vl4056(4056),vl4057(4057),vl4058(4058),
vl4059(4059),vl4060(4060),vl4061(4061),vl4062(4062),
vl4063(4063),vl4064(4064),vl4065(4065),vl4066(4066),
vl4067(4067),vl4068(4068),vl4069(4069),vl4070(4070),
vl4071(4071),vl4072(4072),vl4073(4073),vl4074(4074),
vl4075(4075),vl4076(4076),vl4077(4077),vl4078(4078),
vl4079(4079),vl4080(4080),vl4081(4081),vl4082(4082),
vl4083(4083),vl4084(4084),vl4085(4085),vl4086(4086),
vl4087(4087),vl4088(4088),vl4089(4089),vl4090(4090),
vl4091(4091),vl4092(4092),vl4093(4093),vl4094(4094),
vl4095(4095)

                }

-- This causes errors by using a TC DisplayString in another TC ... RGovil
-- MstList ::= TEXTUAL-CONVENTION
--    STATUS      current
--    DESCRIPTION
--        "Each Mst Instance will be displayed in a
--         seperated by comas. (maximum 64 Msti) "
--    SYNTAX      DisplayString(SIZE (0..128))
--



       DigestId ::= OCTET STRING (SIZE (16))-- the
                                            -- digest-Identifier
                                            -- defined by 802.1s
                                            -- Spanning Tree


-- -------------------------------------------------------------


	alcatelIND1VLANSTPMIBObjects OBJECT-IDENTITY
        STATUS current
        DESCRIPTION
            "Branch For Spanning Tree
             Managed Objects."
        ::= { alcatelIND1VLANSTPMIB 1 }


        alcatelIND1VLANSTPMIBConformance OBJECT-IDENTITY
        STATUS current
        DESCRIPTION
            "Branch For Spanning Tree
             Conformance Information."
        ::= { alcatelIND1VLANSTPMIB 2 }


        alcatelIND1VLANSTPMIBGroups OBJECT-IDENTITY
        STATUS current
        DESCRIPTION
            "Branch For Spanning Tree
             Units Of Conformance."
        ::= { alcatelIND1VLANSTPMIBConformance 1 }


        alcatelIND1VLANSTPMIBCompliances OBJECT-IDENTITY
        STATUS current
        DESCRIPTION
            "Branch For Spanning Tree
             Compliance Statements."
        ::= { alcatelIND1VLANSTPMIBConformance 2 }


	vStpInfo OBJECT IDENTIFIER ::= { alcatelIND1VLANSTPMIBObjects 1 }


	vStpTable  OBJECT-TYPE
	    SYNTAX  SEQUENCE OF VStpEntry
	    MAX-ACCESS  not-accessible
	    STATUS deprecated
	    DESCRIPTION
		 "A list of Spanning Tree instances in this physical Switch."
	    ::= { vStpInfo 1 }

	vStpEntry  OBJECT-TYPE
	    SYNTAX  VStpEntry
	    MAX-ACCESS  not-accessible
	    STATUS deprecated
	    DESCRIPTION
		 "A STP entry."
	    INDEX { vStpNumber }
	    ::= { vStpTable 1 }

	VStpEntry ::=
	   SEQUENCE {
	    vStpNumber
		INTEGER,
	    vStpMode
		INTEGER,
	    vStpProtocolSpecification
		INTEGER,
	    vStpPriority
		INTEGER,
	    vStpBridgeAddress
		BridgeId,
	    vStpTimeSinceTopologyChange
		TimeTicks,
	    vStpTopChanges
		Counter32,
	    vStpDesignatedRoot
		BridgeId,
            vStpRootCost
                Integer32,
	    vStpRootPortNumber
		Integer32,
            vStpNextBestRootCost
                Integer32,
            vStpNextBestRootPortNumber
                Integer32,
            vStpMaxAge
                Timeout,
            vStpHelloTime
                Timeout,
            vStpHoldTime
                Integer32,
            vStpForwardDelay
                Integer32,
            vStpBridgeMaxAge
                Timeout,
            vStpBridgeHelloTime
                Timeout,
            vStpBridgeForwardDelay
                Timeout
	    }

	vStpNumber  OBJECT-TYPE
	    SYNTAX  INTEGER (1..65535)
	    MAX-ACCESS  read-only
	    STATUS  deprecated
	    DESCRIPTION
		 "The Spanning Tree number identifying this instance. Valid
		  range from 1 to 65535."
	    ::= { vStpEntry 1 }

	vStpMode OBJECT-TYPE
	    SYNTAX  INTEGER {
			flat(1),
			onePerVlan(2),
			multiple(3)
			}
	    MAX-ACCESS  read-only
	    STATUS  deprecated
	    DESCRIPTION
		"The mode of the Spanning Tree Protocol implemented
		 for this bridge.  The multiple mode (IEEE 802.1s
		 multiple spanning tree) is to be implemented
		 in a future version."
	    DEFVAL { onePerVlan }
	    ::= { vStpEntry 2 }

	vStpProtocolSpecification OBJECT-TYPE
	    SYNTAX  INTEGER {
			unknown(1),
			decLb100(2),
			ieee8021d(3),
			ieee8021w(4)
			}
	    MAX-ACCESS  read-only
	    STATUS  deprecated
	    DESCRIPTION
		"The version of the Spanning Tree Protocol implemented
		 for this instance.  The IEEE 802.1d and 802.1w (fast
		 spanning tree) implementation are the only versions supported.
		 If future versions of the IEEE Spanning Tree Protocol
		 are released that are incompatible with the current
		 version a new value will be defined."
	    DEFVAL { ieee8021d }
	    ::= { vStpEntry 3 }

	vStpPriority OBJECT-TYPE
	    SYNTAX  INTEGER (0..65535)
	    MAX-ACCESS  read-only
	    STATUS  deprecated
	    DESCRIPTION
		"The value of the write-able portion of the Bridge
		 ID, i.e., the first two octets of the (8 octet
		 long) Bridge ID (vStpBridgeAddress).  The other (last)
		 6 octets of the Bridge ID are recommended to be the
		 numerically smallest MAC address of all ports that
		 belong to this Spanning tree instance."
	    DEFVAL { 32768 }
	    ::= { vStpEntry 4 }

	vStpBridgeAddress OBJECT-TYPE
	    SYNTAX  BridgeId
	    MAX-ACCESS  read-only
	    STATUS  deprecated
	    DESCRIPTION
		"The bridge identifier of this spanning tree instance
		 as determined by the Spanning Tree Protocol."
	    ::= { vStpEntry 5 }


	vStpTimeSinceTopologyChange OBJECT-TYPE
	    SYNTAX  TimeTicks
	    MAX-ACCESS  read-only
	    STATUS  deprecated
	    DESCRIPTION
		"The time (in hundredths of a second) since the
		 last time a topology change was detected by this
		 spanning tree instance."
	    ::= { vStpEntry 6 }

	vStpTopChanges OBJECT-TYPE
	    SYNTAX  Counter32
	    MAX-ACCESS  read-only
	    STATUS  deprecated
	    DESCRIPTION
		"The total number of topology changes detected by
		 this spanning tree instance since the management
		 entity was last reset or initialized."
	    ::= { vStpEntry 7 }

	vStpDesignatedRoot OBJECT-TYPE
	    SYNTAX  BridgeId
	    MAX-ACCESS  read-only
	    STATUS  deprecated
	    DESCRIPTION
		"The bridge identifier of the root of the spanning
		 tree as determined by the Spanning Tree Protocol as executed
		 by this instance.
		 This value is used as the Root Identifier parameter in all
		 Configuration Bridge PDUs originated by this node for this
		 instance."
	    ::= { vStpEntry 8 }

	vStpRootCost OBJECT-TYPE
	    SYNTAX  Integer32
	    MAX-ACCESS  read-only
	    STATUS  deprecated
	    DESCRIPTION
		"The cost of the path to the root as seen from
		 this bridge for this spanning tree instance."
	    ::= { vStpEntry 9 }

	vStpRootPortNumber OBJECT-TYPE
	    SYNTAX  Integer32
	    MAX-ACCESS  read-only
	    STATUS  deprecated
	    DESCRIPTION
		"The  port ifindex of the port which offers the
		 lowest cost path from this bridge to the root
		 bridge for this spanning tree instance."
	    ::= { vStpEntry 10 }

	vStpNextBestRootCost OBJECT-TYPE
	    SYNTAX  Integer32
	    MAX-ACCESS  read-only
	    STATUS  deprecated
	    DESCRIPTION
		"The cost of the path to the root through the next
		 best root port as seen from this bridge
		 for this spanning tree instance."
	    ::= { vStpEntry 11 }

	vStpNextBestRootPortNumber OBJECT-TYPE
	    SYNTAX  Integer32
	    MAX-ACCESS  read-only
	    STATUS  deprecated
	    DESCRIPTION
		"The  port ifindex of the next port which offers
		 the lowestcost path from this bridge to the root
		 bridge for this spanning tree instance. This port
		 will become root port if the actual root port goes down."
	    ::= { vStpEntry 12 }

	vStpMaxAge OBJECT-TYPE
	    SYNTAX  Timeout
	    MAX-ACCESS  read-only
	    STATUS  deprecated
	    DESCRIPTION
		"The maximum age of Spanning Tree Protocol
		 information learned from the network on any port
		 before it is discarded, in units of hundredths of
		 a second.  This is the actual value that this
		 spanning tree instance is currently using."
	    ::= { vStpEntry 13 }

	vStpHelloTime OBJECT-TYPE
	    SYNTAX  Timeout
	    MAX-ACCESS  read-only
	    STATUS  deprecated
	    DESCRIPTION
		"The amount of time between the transmission of
		 Configuration bridge PDUs by this instance on any port
		 when it is the root of the spanning tree or trying
		 to become so, in units of hundredths of a second.
		 This is the actual value that this instance is
		 currently using."
	    ::= { vStpEntry 14 }

	vStpHoldTime OBJECT-TYPE
	    SYNTAX  Integer32
	    MAX-ACCESS  read-only
	    STATUS  deprecated
	    DESCRIPTION
		"This time value determines the interval length
		 during which no more than two Configuration bridge
		 PDUs shall be transmitted by this instance, in units
		 of hundredths of a second."
	    ::= { vStpEntry 15 }

	vStpForwardDelay OBJECT-TYPE
	    SYNTAX  Integer32
	    MAX-ACCESS  read-only
	    STATUS  deprecated
	    DESCRIPTION
		"This time value, measured in units of hundredths
		 of a second, controls how fast a port changes its
		 spanning state when moving towards the Forwarding
		 state.  The value determines how long the port
		 stays in each of the Listening and Learning
		 states, which precede the Forwarding state.  This
		 value is also used, when a topology change has
		 been detected and is underway, to age all dynamic
		 entries in the Forwarding Database.  [Note that
		 this value is the one that this instance is
		 currently using, in contrast to
		 vStpBridgeForwardDelay which is the value that
		 this instance and all others would start using
		 if/when this bridge were to become the root.]"
	    ::= { vStpEntry 16 }

	vStpBridgeMaxAge OBJECT-TYPE
	    SYNTAX  Timeout (600..4000)
	    MAX-ACCESS  read-only
	    STATUS  deprecated
	    DESCRIPTION
		"The value that all bridges use for MaxAge when
		 this bridge is acting as the root.  Note that
		 802.1D-1990 specifies that the range for this
		 parameter is related to the value of
		 vStpBridgeHelloTime. The granularity of this
		 timer is specified by 802.1D-1990 to be 1 second.
		 An agent may return a badValue error if a set is
		 attempted to a value which is not a whole number
		 of seconds."
	    DEFVAL { 2000 }
	    ::= { vStpEntry 17 }

	vStpBridgeHelloTime OBJECT-TYPE
	    SYNTAX  Timeout (100..1000)
	    MAX-ACCESS  read-only
	    STATUS  deprecated
	    DESCRIPTION
		"The value that all bridges use for HelloTime when
		 this bridge is acting as the root.  The
		 granularity of this timer is specified by 802.1D-
		 1990 to be 1 second.  An agent may return a
		 badValue error if a set is attempted to a value
		 which is not a whole number of seconds."
	    DEFVAL { 200 }
	    ::= { vStpEntry 18 }

	vStpBridgeForwardDelay OBJECT-TYPE
	    SYNTAX  Timeout (400..3000)
	    MAX-ACCESS  read-only
	    STATUS  deprecated
	    DESCRIPTION
		"The value that all bridges use for ForwardDelay
		 when this bridge is acting as the root.  Note that
		 802.1D-1990 specifies that the range for this
		 parameter is related to the value of
		 vStpBridgeMaxAge.  The granularity of this
		 timer is specified by 802.1D-1990 to be 1 second.
		 An agent may return a badValue error if a set is
		 attempted to a value which is not a whole number
		 of seconds."
	    DEFVAL { 1500 }
	    ::= { vStpEntry 19 }

-- New STP Instance table to handle multiple instances and modes --

	vStpInsTable  OBJECT-TYPE
	    SYNTAX  SEQUENCE OF VStpInsEntry
	    MAX-ACCESS  not-accessible
	    STATUS  current
	    DESCRIPTION
		 "A list of Spanning Tree instances on this bridge."
	    ::= { vStpInfo 3 }

	vStpInsEntry  OBJECT-TYPE
	    SYNTAX  VStpInsEntry
	    MAX-ACCESS  not-accessible
	    STATUS  current
	    DESCRIPTION
		 "A STP instance entry. Either one multiple spanning tree
          instance, or a per VLAN instance."
	    INDEX { vStpBridgeMode, vStpInsNumber }
	    ::= { vStpInsTable 1 }

	VStpInsEntry ::=
        SEQUENCE {
        vStpInsNumber
            INTEGER,
	    vStpInsProtocolSpecification
            INTEGER,
	    vStpInsPriority
            INTEGER,
	    vStpInsBridgeAddress
            BridgeId,
	    vStpInsTimeSinceTopologyChange
            TimeTicks,
	    vStpInsTopChanges
            Counter32,
	    vStpInsDesignatedRoot
            BridgeId,
        vStpInsRootCost
            Integer32,
	    vStpInsRootPortNumber
            Integer32,
        vStpInsNextBestRootCost
            Integer32,
        vStpInsNextBestRootPortNumber
            Integer32,
        vStpInsMaxAge
            Timeout,
        vStpInsHelloTime
            Timeout,
        vStpInsHoldTime
            Integer32,
        vStpInsForwardDelay
            Integer32,
        vStpInsBridgeMaxAge
            Timeout,
        vStpInsBridgeHelloTime
            Timeout,
        vStpInsBridgeForwardDelay
            Timeout,
        vStpInsBpduSwitching
            INTEGER,
        vStpInsCistRegionalRootId
            BridgeId,
        vStpInsCistPathCost
            Integer32,
        vStpIns1x1VlanNumber
            Integer32,
	    vStpInsMstiNumber
            Integer32,
	    vStpInsMode
            INTEGER,
	    vStpInsAutoVlanContainment
            INTEGER,
            vStpInsBridgeTxHoldCount
            INTEGER,
	vStpInsStatus
	    INTEGER
	    }

	vStpInsNumber  OBJECT-TYPE
	    SYNTAX  INTEGER (0..4095)
	    MAX-ACCESS  read-only
	    STATUS  current
	    DESCRIPTION
		 "The Spanning Tree number identifying this instance.
          In 1x1 mode the accepted range is 1-4095 and corresponds
          to the VLAN.  In Flat mode the range is 0-4095 and corresponds to the
          Spanning tree instance."
	    ::= { vStpInsEntry 1 }

	vStpInsProtocolSpecification OBJECT-TYPE
	    SYNTAX  INTEGER {
			unknown(1),
			decLb100(2),
			ieeeSTP(3),
			ieeeRSTP(4),
			ieeeMSTP(5)
			}
	    MAX-ACCESS  read-write
	    STATUS  current
	    DESCRIPTION
		"The version of the Spanning Tree Protocol implemented
		 for this instance. ieeeSTP represents standard STP of 802.1d 1998.
         ieeeRSTP stands for Rapid STP.  Multiple STP or
         MSTP (802.1s) is only supported in flat
         mode, using instance 0.  If future versions of the
         IEEE Spanning Tree Protocol are released that are
         incompatible with the current version, a new value will
         be defined."
	    DEFVAL { ieeeSTP }
	    ::= { vStpInsEntry 2 }

	vStpInsPriority OBJECT-TYPE
	    SYNTAX  INTEGER (0..65535)
	    MAX-ACCESS  read-write
	    STATUS  current
	    DESCRIPTION
		"The value of the write-able portion of the Bridge
		 ID, i.e., the first two octets of the (8 octet
		 long) Bridge ID (vStpBridgeAddress).  The other (last)
		 6 octets of the Bridge ID are recommended to be the
		 numerically smallest MAC address of all ports that
		 belong to this Spanning tree instance."
	    DEFVAL { 32768 }
	    ::= { vStpInsEntry 3 }

	vStpInsBridgeAddress OBJECT-TYPE
	    SYNTAX  BridgeId
	    MAX-ACCESS  read-only
	    STATUS  current
	    DESCRIPTION
		"The bridge identifier of this spanning tree instance
		 as determined by the Spanning Tree Protocol."
	    ::= { vStpInsEntry 4 }


	vStpInsTimeSinceTopologyChange OBJECT-TYPE
	    SYNTAX  TimeTicks
	    MAX-ACCESS  read-only
	    STATUS  current
	    DESCRIPTION
		"The time (in hundredths of a second) since the
		 last time a topology change was detected by this
		 spanning tree instance."
	    ::= { vStpInsEntry 5 }

	vStpInsTopChanges OBJECT-TYPE
	    SYNTAX  Counter32
	    MAX-ACCESS  read-only
	    STATUS  current
	    DESCRIPTION
		"The total number of topology changes detected by
		 this spanning tree instance since the management
		 entity was last reset or initialized."
	    ::= { vStpInsEntry 6 }

	vStpInsDesignatedRoot OBJECT-TYPE
	    SYNTAX  BridgeId
	    MAX-ACCESS  read-only
	    STATUS  current
	    DESCRIPTION
		"The bridge identifier of the root of the spanning
		 tree as determined by the Spanning Tree Protocol as executed
		 by this instance.
		 This value is used as the Root Identifier parameter in all
		 Configuration Bridge PDUs originated by this node for this
		 instance."
	    ::= { vStpInsEntry 7 }

	vStpInsRootCost OBJECT-TYPE
	    SYNTAX  Integer32
	    MAX-ACCESS  read-only
	    STATUS  current
	    DESCRIPTION
		"The cost of the path to the root as seen from
		 this bridge for this spanning tree instance."
	    ::= { vStpInsEntry 8 }

	vStpInsRootPortNumber OBJECT-TYPE
	    SYNTAX  Integer32
	    MAX-ACCESS  read-only
	    STATUS  current
	    DESCRIPTION
		"The ifindex of the port which offers the
		 lowest cost path from this bridge to the root
		 bridge for this spanning tree instance."
	    ::= { vStpInsEntry 9 }

	vStpInsNextBestRootCost OBJECT-TYPE
	    SYNTAX  Integer32
	    MAX-ACCESS  read-only
	    STATUS  current
	    DESCRIPTION
		"The cost of the path to the root through the next
		 best root port as seen from this bridge
		 for this spanning tree instance."
	    ::= { vStpInsEntry 10 }

	vStpInsNextBestRootPortNumber OBJECT-TYPE
	    SYNTAX  Integer32
	    MAX-ACCESS  read-only
	    STATUS  current
	    DESCRIPTION
		"The ifindex of the next port which offers
		 the lowest cost path from this bridge to the root
		 bridge for this spanning tree instance. This port
		 will become root port if the actual root port goes down."
	    ::= { vStpInsEntry 11 }

	vStpInsMaxAge OBJECT-TYPE
	    SYNTAX  Timeout
	    MAX-ACCESS  read-only
	    STATUS  current
	    DESCRIPTION
		"The maximum age of Spanning Tree Protocol
		 information learned from the network on any port
		 before it is discarded, in units of hundredths of
		 a second.  This is the actual value that this
		 spanning tree instance is currently using."
	    ::= { vStpInsEntry 12 }

	vStpInsHelloTime OBJECT-TYPE
	    SYNTAX  Timeout
	    MAX-ACCESS  read-only
	    STATUS  current
	    DESCRIPTION
		"The amount of time between the transmission of
		 Configuration bridge PDUs by this instance on any port
		 when it is the root of the spanning tree or trying
		 to become so, in units of hundredths of a second.
		 This is the actual value that this instance is
		 currently using."
	    ::= { vStpInsEntry 13 }

	vStpInsHoldTime OBJECT-TYPE
	    SYNTAX  Integer32
	    MAX-ACCESS  read-only
	    STATUS  current
	    DESCRIPTION
		"This time value determines the interval length
		 during which no more than two Configuration bridge
		 PDUs shall be transmitted by this instance, in units
		 of hundredths of a second."
	    ::= { vStpInsEntry 14 }

	vStpInsForwardDelay OBJECT-TYPE
	    SYNTAX  Integer32
	    MAX-ACCESS  read-only
	    STATUS  current
	    DESCRIPTION
		"This time value, measured in units of hundredths
		 of a second, controls how fast a port changes its
		 spanning state when moving towards the Forwarding
		 state.  The value determines how long the port
		 stays in each of the Listening and Learning
		 states, which precede the Forwarding state.  This
		 value is also used, when a topology change has
		 been detected and is underway, to age all dynamic
		 entries in the Forwarding Database.  (Note that
		 this value is the one that this instance is
		 currently using, in contrast to
		 vStpBridgeForwardDelay which is the value that
		 this instance and all others would start using
		 if/when this bridge were to become the root.)"
	    ::= { vStpInsEntry 15 }

	vStpInsBridgeMaxAge OBJECT-TYPE
	    SYNTAX  Timeout (600..4000)
	    MAX-ACCESS  read-write
	    STATUS  current
	    DESCRIPTION
		"The value that all bridges use for MaxAge when
		 this bridge is acting as the root.  Note that
		 802.1D-1990 specifies that the range for this
		 parameter is related to the value of
		 vStpBridgeHelloTime. The granularity of this
		 timer is specified by 802.1D-1990 to be 1 second.
		 An agent may return a badValue error if a set is
		 attempted to a value which is not a whole number
		 of seconds."
	    DEFVAL { 2000 }
	    ::= { vStpInsEntry 16 }

	vStpInsBridgeHelloTime OBJECT-TYPE
	    SYNTAX  Timeout (100..1000)
	    MAX-ACCESS  read-write
	    STATUS  current
	    DESCRIPTION
		"The value that all bridges use for HelloTime when
		 this bridge is acting as the root.  The
		 granularity of this timer is specified by 802.1D-
		 1990 to be 1 second.  An agent may return a
		 badValue error if a set is attempted to a value
		 which is not a whole number of seconds."
	    DEFVAL { 200 }
	    ::= { vStpInsEntry 17 }

	vStpInsBridgeForwardDelay OBJECT-TYPE
	    SYNTAX  Timeout (400..3000)
	    MAX-ACCESS  read-write
	    STATUS  current
	    DESCRIPTION
		"The value that all bridges use for ForwardDelay
		 when this bridge is acting as the root.  Note that
		 802.1D-1990 specifies that the range for this
		 parameter is related to the value of
		 vStpBridgeMaxAge.  The granularity of this
		 timer is specified by 802.1D-1990 to be 1 second.
		 An agent may return a badValue error if a set is
		 attempted to a value which is not a whole number
		 of seconds."
	    DEFVAL { 1500 }
	    ::= { vStpInsEntry 18 }

    vStpInsBpduSwitching OBJECT-TYPE
        SYNTAX INTEGER {
            enabled (1),
            disabled (2)
            }
        MAX-ACCESS read-write
        STATUS current
        DESCRIPTION
        "When this field is enabled, the BPDUs received for
        this instance to be switched when spanning tree is disabled.
        When the field is disabled, the BPDUs received on this
        instance will be dropped if spanning tree is disabled."
        DEFVAL { disabled }
        ::= { vStpInsEntry 19 }

	vStpInsCistRegionalRootId OBJECT-TYPE
	    SYNTAX  BridgeId
	    MAX-ACCESS  read-only
	    STATUS  current
	    DESCRIPTION
		"The bridge identifier of the regional CIST root bridge of
		 the spanning tree as determined by the Spanning Tree
         Protocol. This value is only used in flat mode"
	    ::= { vStpInsEntry 20 }


	vStpInsCistPathCost OBJECT-TYPE
	    SYNTAX  Integer32
	    MAX-ACCESS  read-only
	    STATUS  current
	    DESCRIPTION
		"The cost of the path to the cist regional root.
         This value is only used in flat mode"
	    ::= { vStpInsEntry 21 }


	vStpIns1x1VlanNumber OBJECT-TYPE
	    SYNTAX  Integer32
	    MAX-ACCESS  read-only
	    STATUS  current
	    DESCRIPTION
		"The Vlan number of this instance.  Only valid in
        1x1 mode."
	    ::= { vStpInsEntry 22 }

	vStpInsMstiNumber  OBJECT-TYPE
	    SYNTAX  Integer32
	    MAX-ACCESS  read-only
	    STATUS  current
	    DESCRIPTION
		"The Mst instance.  Only valid in Flat Mode."
	    ::= { vStpInsEntry 23 }

	vStpInsMode  OBJECT-TYPE
	    SYNTAX  INTEGER {
			flat(1),
			onePerVlan(2)
			}
	    MAX-ACCESS  read-only
	    STATUS  current
	    DESCRIPTION
		"The current mode of the Spanning Tree Protocol this instance
         is a part of."
	    ::= { vStpInsEntry 24 }

	vStpInsAutoVlanContainment  OBJECT-TYPE
	    SYNTAX  INTEGER {
			enable(1),
			disable(2)
			}
	    MAX-ACCESS  read-write
	    STATUS  current
	    DESCRIPTION
		"The current enabled status for this instance of the Auto
                Vlan containment feature which controls path costs in MSTP."
	    ::= { vStpInsEntry 25 }
	
        vStpInsBridgeTxHoldCount  OBJECT-TYPE
	    SYNTAX  INTEGER (1..10)
	    MAX-ACCESS  read-write
	    STATUS  current
	    DESCRIPTION
		 "A limit controlling the number of PDUs transmitted per port
                 per second for this instance."
            DEFVAL { 6 }
	    ::= { vStpInsEntry 26 }

	vStpInsStatus OBJECT-TYPE
            SYNTAX  INTEGER
			{
			enabled(1),
			disabled(2)
			}
            MAX-ACCESS  read-only
            STATUS  current
            DESCRIPTION
                 "This object specifies if the STP status is enabled (1) or
		 disabled (2) on this STP instance."
	    ::= { vStpInsEntry 27 }

	--  The Spanning Tree Port Table for Omniswitch VLAN implementation

	vStpPortTable OBJECT-TYPE
	    SYNTAX  SEQUENCE OF VStpPortEntry
	    MAX-ACCESS  not-accessible
	    STATUS  deprecated
	    DESCRIPTION
		"A table that contains port-specific information
		 for the Spanning Tree Protocol."
	    ::= { vStpInfo 2 }

	vStpPortEntry OBJECT-TYPE
	    SYNTAX  VStpPortEntry
	    MAX-ACCESS  not-accessible
	    STATUS  deprecated
	    DESCRIPTION
		"A list of information maintained for every Spanning Tree
   		 instance by every port about the Spanning Tree Protocol state
		 for that port."
	    INDEX   { vStpNumber, vStpPortNumber }
	    ::= { vStpPortTable 1 }

	VStpPortEntry ::=
	    SEQUENCE {
		vStpPortNumber
		    Integer32,
		vStpPortPriority
		    INTEGER,
		vStpPortState
		    INTEGER,
		vStpPortEnable
		    INTEGER,
		vStpPortPathCost
		    INTEGER,
		vStpPortDesignatedRoot
		    BridgeId,
		vStpPortDesignatedCost
		    Integer32,
		vStpPortDesignatedBridge
		    BridgeId,
		vStpPortDesignatedPtPrio
		    Integer32,
		vStpPortDesignatedPtNumber
		    Integer32,
		vStpPortForwardTransitions
		    Integer32,
		vStpPortManualMode
		    INTEGER,
		vStpPortRole
		    INTEGER,
		vStpPortPrimaryPortNumber
		    Integer32,
		vStpPortAdminConnectionType
		    INTEGER,
		vStpPortOperConnectionType
		    INTEGER
	    }

	vStpPortNumber OBJECT-TYPE
	    SYNTAX  Integer32 (1..2147483647)
	    MAX-ACCESS  read-only
	    STATUS  deprecated
	    DESCRIPTION
		"The  port ifindex of the port for which this
		 entry contains Spanning Tree Protocol management
		 information."
	    ::= { vStpPortEntry 1 }

	vStpPortPriority OBJECT-TYPE
	    SYNTAX  INTEGER (0..15)
	    MAX-ACCESS  read-only
	    STATUS  deprecated
	    DESCRIPTION
		"The priority of this port which used originally as
		 part of the port ID specified in 802.1D."
	    DEFVAL { 8 }
	    ::= { vStpPortEntry 2 }

	vStpPortState OBJECT-TYPE
	    SYNTAX  INTEGER {
			disabled(1),
			blocking(2),
			listening(3),
			learning(4),
			forwarding(5)
			}
	    MAX-ACCESS  read-only
	    STATUS  deprecated
	    DESCRIPTION
		"The port's current state as defined by
		 application of the Spanning Tree Protocol.  This
		 state controls what action a port takes on
		 reception of a frame.  For ports which are disabled
		 (see vStpPortEnable), this object will have a value
                 of disabled(1).  Falcon does not support the broken(6)
		 state as defined in RFC1493."
	    ::= { vStpPortEntry 3 }

	vStpPortEnable OBJECT-TYPE
	    SYNTAX  INTEGER {
			enabled(1),
			disabled(2)
			}
	    MAX-ACCESS  read-only
	    STATUS  deprecated
	    DESCRIPTION
		"The enabled/disabled status of the port."
	    DEFVAL { enabled }
	    ::= { vStpPortEntry 4 }

	vStpPortPathCost OBJECT-TYPE
	    SYNTAX  INTEGER (0..65535)
	    MAX-ACCESS  read-only
	    STATUS  deprecated
	    DESCRIPTION
		"The contribution of this port to the path cost of
		 paths towards the spanning tree root which include
		 this port.  802.1D-1990 recommends that the
		 default value of this parameter be in inverse
		 proportion to the speed of the attached LAN."
	    DEFVAL { 0 }
	    ::= { vStpPortEntry 5 }

	vStpPortDesignatedRoot OBJECT-TYPE
	    SYNTAX  BridgeId
	    MAX-ACCESS  read-only
	    STATUS  deprecated
	    DESCRIPTION
		"The unique Bridge Identifier of the Bridge
		 recorded as the Root in the Configuration BPDUs
		 transmitted by the Designated Bridge for the
		 segment to which the port is attached."
	    ::= { vStpPortEntry 6 }

	vStpPortDesignatedCost OBJECT-TYPE
	    SYNTAX  Integer32
	    MAX-ACCESS  read-only
	    STATUS  deprecated
	    DESCRIPTION
		"The path cost of the Designated Port of the
		 segment connected to this port.  This value is
		 compared to the Root Path Cost field in received
		 bridge PDUs."
	    ::= { vStpPortEntry 7 }

	vStpPortDesignatedBridge OBJECT-TYPE
	    SYNTAX  BridgeId
	    MAX-ACCESS  read-only
	    STATUS  deprecated
	    DESCRIPTION
		"The Bridge Identifier of the bridge which this
		 port considers to be the Designated Bridge for
		 this port's segment."
	    ::= { vStpPortEntry 8 }

	vStpPortDesignatedPtPrio OBJECT-TYPE
	    SYNTAX  Integer32
	    MAX-ACCESS  read-only
	    STATUS  deprecated
	    DESCRIPTION
		"The priority portion of the port ID on the Designated
		 Bridge for this port's segment."
	    ::= { vStpPortEntry 9 }

	vStpPortDesignatedPtNumber OBJECT-TYPE
	    SYNTAX  Integer32
	    MAX-ACCESS  read-only
	    STATUS  deprecated
	    DESCRIPTION
		"The Port Identifier of the port on the Designated
		 Bridge for this port's segment (defined in IEEE
		 802.1D-1998: Section 8.5.5.7)."
	    ::= { vStpPortEntry 10 }

	vStpPortForwardTransitions OBJECT-TYPE
	    SYNTAX  Integer32
	    MAX-ACCESS  read-only
	    STATUS  deprecated
	    DESCRIPTION
		"The number of times this port has transitioned
		 from the Learning state to the Forwarding state."
	    ::= { vStpPortEntry 11 }

	vStpPortManualMode OBJECT-TYPE
	    SYNTAX  INTEGER {
			no(1),
			blocking(2),
			forwarding(3)
			}
	    MAX-ACCESS  read-only
	    STATUS  deprecated
	    DESCRIPTION
		"The port's manual mode for this spanning tree
		 instance. This mode defines the way the state
		 of the port(vStpPortState) is managed.
		 The mode can be dynamic (1) (managed by the Spanning Tree), or
		 manual (blocking(2) or forwarding(3)). In manual mode,
		 the port is not involved in the Spanning tree algorithm
		 computation."
	    DEFVAL { no }
	    ::= { vStpPortEntry 12 }

	vStpPortRole OBJECT-TYPE
	    SYNTAX  INTEGER {
			root(1),
			designated(2),
			alternate(3),
			backup(4),
			disabled(5)
			}
	    MAX-ACCESS  read-only
	    STATUS  deprecated
	    DESCRIPTION
		"The port's role for this spanning tree
		 instance."
	    ::= { vStpPortEntry 13 }

	vStpPortPrimaryPortNumber OBJECT-TYPE
	    SYNTAX  Integer32
	    MAX-ACCESS  read-only
	    STATUS  deprecated
	    DESCRIPTION
		"The  port ifindex of the associated primary port
		 for this spanning tree instance. This information is
		 only available if the port role is backup
		 (vStpPortRole = 4)"
	    ::= { vStpPortEntry 14 }

	vStpPortAdminConnectionType OBJECT-TYPE
	    SYNTAX  INTEGER {
			nopointtopoint(1),
			pointtopoint(2),
			autopointtopoint(3),
			edgeport(4)
			}
	    MAX-ACCESS  read-only
	    STATUS  deprecated
	    DESCRIPTION
		"The administrative port's connection type for this
		 spanning tree instance. This parameter is used to
		 optimise the fast Spanning Tree (6.4.3 of P802.1w).
		 The default value is nopointtopoint(1). The value
		 pointtopoint(2) forces the port to be treated as if
		 it is connected through a point-to-point LAN segment
		 to another switch. Set this parameter to autopointtopoint(3)
		 makes the point-to-point status to be determined automatically
		 by the MAC entity. The value edgeport(4) indicates that the
		 port is considered to be an edge port (18.3.3 of P802.1t)."
	    DEFVAL { nopointtopoint }
	    ::= { vStpPortEntry 15 }

	vStpPortOperConnectionType OBJECT-TYPE
	    SYNTAX  INTEGER {
			nopointtopoint(1),
			pointtopoint(2),
		  	nonsignificant(3),
			edgeport(4)
			}
	    MAX-ACCESS  read-only
	    STATUS  deprecated
	    DESCRIPTION
		"The operational port's connection type for this
		 spanning tree instance.This parameter is used to
		 optimise the fast Spanning Tree."
	    ::= { vStpPortEntry 16 }

-- New Spanning Tree Port table for mst --

	vStpInsPortTable OBJECT-TYPE
	    SYNTAX  SEQUENCE OF VStpInsPortEntry
	    MAX-ACCESS  not-accessible
	    STATUS  current
	    DESCRIPTION
		"A table that contains port-specific information
		 for the Spanning Tree Protocol."
	    ::= { vStpInfo 4 }

	vStpInsPortEntry OBJECT-TYPE
	    SYNTAX  VStpInsPortEntry
	    MAX-ACCESS  not-accessible
	    STATUS  current
	    DESCRIPTION
		"A list of information maintained for every Spanning Tree
   		 instance by every port about the Spanning Tree Protocol state
		 for that port."
	    INDEX   { vStpBridgeMode, vStpInsNumber, vStpInsPortNumber }
	    ::= { vStpInsPortTable 1 }

	VStpInsPortEntry ::=
	    SEQUENCE {
		vStpInsPortNumber
		    Integer32,
		vStpInsPortPriority
		    INTEGER,
		vStpInsPortState
		    INTEGER,
		vStpInsPortEnable
		    INTEGER,
		vStpInsPortPathCost
		    Integer32,
		vStpInsPortDesignatedRoot
		    BridgeId,
		vStpInsPortDesignatedCost
		    Integer32,
		vStpInsPortDesignatedBridge
		    BridgeId,
		vStpInsPortDesignatedPtPrio
		    Integer32,
		vStpInsPortDesignatedPtNumber
		    Integer32,
		vStpInsPortForwardTransitions
		    Integer32,
		vStpInsPortManualMode
		    INTEGER,
		vStpInsPortRole
		    INTEGER,
		vStpInsPortPrimaryPortNumber
		    Integer32,
		vStpInsPortAdminConnectionType
		    INTEGER,
		vStpInsPortOperConnectionType
		    INTEGER,
        vStpInsPortCistRegionRootId
            BridgeId,
        vStpInsPortCistPathCost
            Integer32,
		vStpInsPortHelloTime
            Timeout,
		vStpInsPortBridgeHelloTime
            Timeout,
        vstpInsPortRcvdInternal
            INTEGER,
            vStpInsPortAdminEdge
                INTEGER,
            vStpInsPortAutoEdge
                INTEGER,
            vStpInsPortRestrictedRole
                INTEGER,
            vStpInsPortRestrictedTcn
                INTEGER
	    }


	vStpInsPortNumber OBJECT-TYPE
	    SYNTAX  Integer32 (1..2147483647)
	    MAX-ACCESS  read-only
	    STATUS  current
	    DESCRIPTION
		"The ifindex of the port for which this
		 entry contains Spanning Tree Protocol management
		 information."
	    ::= { vStpInsPortEntry 1 }

	vStpInsPortPriority OBJECT-TYPE
	    SYNTAX  INTEGER (0..15)
	    MAX-ACCESS  read-write
	    STATUS  current
	    DESCRIPTION
		"The priority of this port which was used originally as
		 part of the port ID specified in 802.1D."
	    DEFVAL { 8 }
	    ::= { vStpInsPortEntry 2 }

	vStpInsPortState OBJECT-TYPE
	    SYNTAX  INTEGER {
			disabled(1),
			blocking(2),
			listening(3),
			learning(4),
			forwarding(5)
			}
	    MAX-ACCESS  read-only
	    STATUS  current
	    DESCRIPTION
		"The port's current state as defined by
		 application of the Spanning Tree Protocol.  This
		 state controls what action a port takes on
		 reception of a frame.  For ports which are disabled
		 (see vStpInsPortEnable), this object will have a value
         of disabled(1).  AOS does not support the broken(6)
		 state as defined in RFC1493."
	    ::= { vStpInsPortEntry 3 }

	vStpInsPortEnable OBJECT-TYPE
	    SYNTAX  INTEGER {
			enabled(1),
			disabled(2)
			}
	    MAX-ACCESS  read-write
	    STATUS  current
	    DESCRIPTION
		"The enabled/disabled status of the port."
	    DEFVAL { enabled }
	    ::= { vStpInsPortEntry 4 }

	vStpInsPortPathCost OBJECT-TYPE
	    SYNTAX  Integer32
	    MAX-ACCESS  read-write
	    STATUS  current
	    DESCRIPTION
		"The contribution of this port to the path cost of
		 paths towards the spanning tree root which include
		 this port.  802.1D-1990 recommends that the
		 default value of this parameter be in inverse
		 proportion to the speed of the attached LAN."
	    DEFVAL { 0 }
	    ::= { vStpInsPortEntry 5 }

	vStpInsPortDesignatedRoot OBJECT-TYPE
	    SYNTAX  BridgeId
	    MAX-ACCESS  read-only
	    STATUS  current
	    DESCRIPTION
		"The unique Bridge Identifier of the Bridge
		 recorded as the Root in the Configuration BPDUs
		 transmitted by the Designated Bridge for the
		 segment to which the port is attached."
	    ::= { vStpInsPortEntry 6 }

	vStpInsPortDesignatedCost OBJECT-TYPE
	    SYNTAX  Integer32
	    MAX-ACCESS  read-only
	    STATUS  current
	    DESCRIPTION
		"The path cost of the Designated Port of the
		 segment connected to this port.  This value is
		 compared to the Root Path Cost field in received
		 bridge PDUs."
	    ::= { vStpInsPortEntry 7 }

	vStpInsPortDesignatedBridge OBJECT-TYPE
	    SYNTAX  BridgeId
	    MAX-ACCESS  read-only
	    STATUS  current
	    DESCRIPTION
		"The Bridge Identifier of the bridge which this
		 port considers to be the Designated Bridge for
		 this port's segment."
	    ::= { vStpInsPortEntry 8 }

	vStpInsPortDesignatedPtPrio OBJECT-TYPE
	    SYNTAX  Integer32
	    MAX-ACCESS  read-only
	    STATUS  current
	    DESCRIPTION
		"The priority portion of the port ID on the Designated
		 Bridge for this port's segment."
	    ::= { vStpInsPortEntry 9 }

	vStpInsPortDesignatedPtNumber OBJECT-TYPE
	    SYNTAX  Integer32
	    MAX-ACCESS  read-only
	    STATUS  current
	    DESCRIPTION
		"The Port Identifier of the port on the Designated
		 Bridge for this port's segment (defined in IEEE
		 802.1D-1998: Section 8.5.5.7)."
	    ::= { vStpInsPortEntry 10 }

	vStpInsPortForwardTransitions OBJECT-TYPE
	    SYNTAX  Integer32
	    MAX-ACCESS  read-only
	    STATUS  current
	    DESCRIPTION
		"The number of times this port has transitioned
		 from the Learning state to the Forwarding state."
	    ::= { vStpInsPortEntry 11 }

	vStpInsPortManualMode OBJECT-TYPE
	    SYNTAX  INTEGER {
			no(1),
			blocking(2),
			forwarding(3)
			}
	    MAX-ACCESS  read-write
	    STATUS  current
	    DESCRIPTION
		"The port's manual mode for this spanning tree
		 instance. This mode defines the way the state
		 of the port(vStpPortState) is managed.
		 The mode can be dynamic (1) (managed by the Spanning Tree), or
		 manual (blocking(2) or forwarding(3)). In manual mode,
		 the port is not involved in the Spanning tree algorithm
		 computation."
	    DEFVAL { no }
	    ::= { vStpInsPortEntry 12 }

	vStpInsPortRole OBJECT-TYPE
	    SYNTAX  INTEGER {
			root(1),
			designated(2),
			alternate(3),
			backup(4),
			disabled(5),
                        master(6)
			}
	    MAX-ACCESS  read-only
	    STATUS  current
	    DESCRIPTION
		"The port's role for this spanning tree
		 instance."
	    ::= { vStpInsPortEntry 13 }

	vStpInsPortPrimaryPortNumber OBJECT-TYPE
	    SYNTAX  Integer32
	    MAX-ACCESS  read-only
	    STATUS  current
	    DESCRIPTION
		"The ifindex of the associated primary port
		 for this spanning tree instance. This information is
		 only available if the port role is backup
		 (vStpInsPortRole = 4)"
	    ::= { vStpInsPortEntry 14 }

	vStpInsPortAdminConnectionType OBJECT-TYPE
	    SYNTAX  INTEGER {
			nopointtopoint(1),
			pointtopoint(2),
			autopointtopoint(3),
			edgeport(4)
			}
	    MAX-ACCESS  read-write
	    STATUS  current
	    DESCRIPTION
		"The administrative port's connection type for this
		 spanning tree instance. This parameter is used to
		 optimise the fast Spanning Tree (6.4.3 of P802.1w).
		 The default value is nopointtopoint(1). The value
		 pointtopoint(2) forces the port to be treated as if
		 it is connected through a point-to-point LAN segment
		 to another switch. Set this parameter to autopointtopoint(3)
		 makes the point-to-point status to be determined automatically
		 by the MAC entity. The value edgeport(4) indicates that the
		 port is considered to be an edge port (18.3.3 of P802.1t)."
	    DEFVAL { nopointtopoint }
	    ::= { vStpInsPortEntry 15 }

	vStpInsPortOperConnectionType OBJECT-TYPE
	    SYNTAX  INTEGER {
			nopointtopoint(1),
			pointtopoint(2),
		  	nonsignificant(3),
			edgeport(4)
			}
	    MAX-ACCESS  read-only
	    STATUS  current
	    DESCRIPTION
		"The operational port's connection type for this
		 spanning tree instance.This parameter is used to
		 optimise the fast Spanning Tree."
	    ::= { vStpInsPortEntry 16 }


	vStpInsPortCistRegionRootId OBJECT-TYPE
	    SYNTAX  BridgeId
	    MAX-ACCESS  read-only
	    STATUS  current
	    DESCRIPTION
		"The bridge identifier of the regional CIST root bridge as
         determined by the Spanning Tree Protocol.
         This value is only used in flat mode"
	    ::= { vStpInsPortEntry 17 }


	vStpInsPortCistPathCost OBJECT-TYPE
	    SYNTAX  Integer32
	    MAX-ACCESS  read-only
	    STATUS  current
	    DESCRIPTION
		"The cost of the path to the cist regional root.
         This value is only used in flat mode"
	    ::= { vStpInsPortEntry 18 }

	vStpInsPortHelloTime OBJECT-TYPE
	    SYNTAX  Timeout (100..1000)
	    MAX-ACCESS  read-only
	    STATUS  current
	    DESCRIPTION
		"The value that is used by the  port for HelloTime when
		 this bridge is acting as the root.  The
		 granularity of this timer is specified by 802.1D-
		 1990 to be 1 second.  An agent may return a
		 badValue error if a set is attempted to a value
		 which is not a whole number of seconds."
	    DEFVAL { 200 }
	    ::= { vStpInsPortEntry 19 }

	vStpInsPortBridgeHelloTime OBJECT-TYPE
	    SYNTAX  Timeout (100..1000)
	    MAX-ACCESS  read-only
	    STATUS  current
	    DESCRIPTION
		"The value that all bridges use for HelloTime when
		 this bridge is acting as the root.  The
		 granularity of this timer is specified by 802.1D-
		 1990 to be 1 second.  An agent may return a
		 badValue error if a set is attempted to a value
		 which is not a whole number of seconds."
	    DEFVAL { 200 }
	    ::= { vStpInsPortEntry 20 }



	vstpInsPortRcvdInternal OBJECT-TYPE
	    SYNTAX  INTEGER {
			external(1),
			internal(2),
		  	unkown(3)
			}
	    MAX-ACCESS  read-only
	    STATUS  current
	    DESCRIPTION
		"The operational port's connection type for this
		 spanning tree instance.This parameter is used to
		 optimise the fast Spanning Tree."
	    ::= { vStpInsPortEntry 21 }
	
         vStpInsPortAdminEdge OBJECT-TYPE
	    SYNTAX  INTEGER {
			enable(1),
			disable(2)
			}
	    MAX-ACCESS  read-write
	    STATUS  current
	    DESCRIPTION
                "Upon intiliazation of the port, this will be
                the default setting of the operational edge
                status of the port.  May change depending on
                AutoEdge setting.  Will not change status after
                link is up on port."
	    DEFVAL { disable }
	    ::= { vStpInsPortEntry 22 }

         vStpInsPortAutoEdge OBJECT-TYPE
	    SYNTAX  INTEGER {
			enable(1),
			disable(2)
			}
	    MAX-ACCESS  read-write
	    STATUS  current
	    DESCRIPTION
                "When enabled STP will determine the operational
                edge status of the port.  May overwrite the
                AdminEdge status, if enabled.  If disabled, port
                will remain as the AdminEdge state."
	    DEFVAL { enable }
	    ::= { vStpInsPortEntry 23 }

         vStpInsPortRestrictedRole OBJECT-TYPE
	    SYNTAX  INTEGER {
			enable(1),
			disable(2)
			}
	    MAX-ACCESS  read-write
	    STATUS  current
	    DESCRIPTION
                "When enabled, this port will not be selected as
                the Root port and will be selected as Alternate
                after the Root port is selected."
	    DEFVAL { disable }
	    ::= { vStpInsPortEntry 24 }

         vStpInsPortRestrictedTcn OBJECT-TYPE
	    SYNTAX  INTEGER {
			enable(1),
			disable(2)
			}
	    MAX-ACCESS  read-write
	    STATUS  current
	    DESCRIPTION
                "When set to enable, this port will not propogate
                any topology changes or notifications to other ports.
                Is used to prevent bridges outside of a core network
                from causing flushes within the core network."
	    DEFVAL { disable }
	    ::= { vStpInsPortEntry 25 }
	-- -------------------------------------------------------------

	-- -------------------------------------------------------------
	-- The stp bridge Table
	-- -------------------------------------------------------------

--	DESCRIPTION
--			"The bridge group specific
--           information for the spanning tree
--           protocol"


	vStpBridge      OBJECT IDENTIFIER ::= { vStpInfo 5 }

	vStpBridgeMode OBJECT-TYPE
	    SYNTAX  INTEGER {
			flat(1),
			onePerVlan(2)
			}
	    MAX-ACCESS  read-write
	    STATUS  current
	    DESCRIPTION
		"The mode of the Spanning Tree Protocol activated
		 on this bridge."
	    DEFVAL { onePerVlan }
	    ::= { vStpBridge 1 }


	vStpBridgeAddressId OBJECT-TYPE
	    SYNTAX  MacAddress
	    MAX-ACCESS  read-only
	    STATUS  current
	    DESCRIPTION
		"The bridge identifier as determined
	     by the Spanning Tree Protocol."
	    ::= { vStpBridge 2 }


        vStpBridgeLastChanged OBJECT-TYPE
            SYNTAX    TimeTicks
	    MAX-ACCESS read-only
	    STATUS current
	    DESCRIPTION
	    "This object indicates the time of the
		 most recent change to the vStpBridge group
         vStpMstRegionTable"
	::= { vStpBridge 3 }

        vStpBridgePathCostMode OBJECT-TYPE
            SYNTAX    INTEGER {
                thrityTwoBit(1),
                auto(2)
            }
	    MAX-ACCESS read-write
	    STATUS current
	    DESCRIPTION
	    "This object describes what the default
		 path costs the bridge gives to ports upon link
         up.  thirtyTwoBit designates 32 bit path cost value range
         in accordance with IEEE 802.1w standard and newer.  Auto
         designates 16 bit path cost value range in accordance
         to IEEE 802.1d 1998 standard, except when the bridge is
         operating in MSTP protocol when 32 bit values will be in
         effect"
         DEFVAL { auto }
	::= { vStpBridge 4 }
	
        vStpBridgeAutoVlanContainment  OBJECT-TYPE
	    SYNTAX  INTEGER {
			enable(1),
			disable(2),
			notApplicable(3)
			}
	    MAX-ACCESS  read-write
	    STATUS  current
	    DESCRIPTION
		"The current enabled status for the whole bridge
                of the Auto Vlan containment feature
                which controls path costs in MSTP. This object is
		applicable only when bridge mode is flat."
	    ::= { vStpBridge 5 }

	vStpBridgeModePVST OBJECT-TYPE
	    SYNTAX  INTEGER {
			enable(1),
			disable(2)
			}
	    MAX-ACCESS  read-write
	    STATUS  current
	    DESCRIPTION
		"When enabled, Spanning Tree can interoperate with Cisco switch
		 in PVST+ mode. When disabled, Spanning Tree is back to normal
		 1x1 mode."
	    DEFVAL { disable }
	    ::= { vStpBridge 6 }

	-- -------------------------------------------------------------

	-- -------------------------------------------------------------
	-- The stp Mst region Table
	-- -------------------------------------------------------------



	vStpMstRegionTable OBJECT-TYPE
		SYNTAX SEQUENCE OF VStpMstRegionEntry
		MAX-ACCESS not-accessible
		STATUS current
		DESCRIPTION
			"This table contains Region-specific
             information for the spanning tree
             protocol 802.1s"
	::= { vStpInfo 6 }

	vStpMstRegionEntry  OBJECT-TYPE
	    SYNTAX  VStpMstRegionEntry
	    MAX-ACCESS  not-accessible
	    STATUS  current
	    DESCRIPTION
		 "A Region entry."
	    INDEX { vStpMstRegionNumber }
	    ::= { vStpMstRegionTable 1 }

	VStpMstRegionEntry ::=
	   SEQUENCE {
	   vStpMstRegionNumber
                INTEGER,
	    vStpMstRegionConfigFormatSelector
                INTEGER,
	    vStpMstRegionConfigDigest
                DigestId,
        vStpMstRegionConfigName
                DisplayString,
	    vStpMstRegionConfigRevisionLevel
                INTEGER,
        vStpMstRegionMstiList
                DisplayString,
        vStpMstRegionCistInstanceNumber
                INTEGER,
	    vStpMstRegionMaxHops
                INTEGER
	    }


	vStpMstRegionNumber  OBJECT-TYPE
	    SYNTAX  INTEGER (0..4)
	    MAX-ACCESS  read-only
	    STATUS  current
	    DESCRIPTION
		 "The 802.1s spec. defines only 1 region. However, for
          possible future enhancements it may be desired to have
          the ability to configure more than one region on the
          the same bridge."
	    ::= { vStpMstRegionEntry 1 }


	vStpMstRegionConfigFormatSelector OBJECT-TYPE
	    SYNTAX  INTEGER (0..255)
	    MAX-ACCESS  read-only
	    STATUS  current
	    DESCRIPTION
		"The Mst format selector. When 0, this field indicates
         the use of the following components as specified in
         802.1s standard; config name, revision level, and
         config digest."
	    ::= { vStpMstRegionEntry 2 }

         vStpMstRegionConfigDigest OBJECT-TYPE
	    SYNTAX  DigestId
	    MAX-ACCESS  read-only
	    STATUS  current
	    DESCRIPTION
		"The Mst Region identifier, a 16 octet field of type
         HMAC-MD5. It is an encoding of the VID to MSTID table
         and sent in the MSTP BPDU to allow bridges to recognize
         their neighbors region."
	    ::= { vStpMstRegionEntry 3 }

	vStpMstRegionConfigName OBJECT-TYPE
		SYNTAX DisplayString (SIZE (0..31))
		MAX-ACCESS read-write
		 STATUS current
		DESCRIPTION
			"Name of the region defined by the
             802.1s standard"
		REFERENCE
			" specific to ALCATEL"
		::= { vStpMstRegionEntry  4 }


	vStpMstRegionConfigRevisionLevel OBJECT-TYPE
		SYNTAX INTEGER  (0..65535)
		MAX-ACCESS read-write
		 STATUS current
		DESCRIPTION
			"Revision level of the region defined by the
             802.1s standard"
		REFERENCE
			" specific to ALCATEL"
		::= { vStpMstRegionEntry  5 }

	vStpMstRegionMstiList OBJECT-TYPE
		SYNTAX DisplayString(SIZE (0..128))
		MAX-ACCESS read-only
		 STATUS current
		DESCRIPTION
			"List of Mst instances configured
             in this region. Each Mst Instance will be displayed
             seperated by comas. (maximum 64 Msti)"
		REFERENCE
			" specific to ALCATEL"
		::= { vStpMstRegionEntry  6 }


	vStpMstRegionCistInstanceNumber OBJECT-TYPE
		SYNTAX INTEGER (0..4095)
		MAX-ACCESS read-only
		 STATUS current
		DESCRIPTION
			"Number of the CIST instance. Always
             0 in this release and limited to one region"
		REFERENCE
			" specific to ALCATEL"
		::= { vStpMstRegionEntry  7 }


	vStpMstRegionMaxHops OBJECT-TYPE

	    SYNTAX  INTEGER (1..40)
	    MAX-ACCESS  read-write
		 STATUS current
		DESCRIPTION
		"The value that all bridges use for MaxHops in
         the region when this bridge is acting as the
         root."
		REFERENCE
			" specific to ALCATEL"
	    DEFVAL { 20 }
		::= { vStpMstRegionEntry  8 }


	-- -------------------------------------------------------------
	-- The stp Mst Instance Table
	-- -------------------------------------------------------------



	vStpMstInstanceTable OBJECT-TYPE
		SYNTAX  SEQUENCE OF VStpMstInstanceEntry
		MAX-ACCESS  not-accessible
		STATUS current
		DESCRIPTION
			"This table contains Mst Instance-specific
             information for the spanning tree
             protocol 802.1s"
	::= { vStpInfo 7 }

	vStpMstInstanceEntry  OBJECT-TYPE
	    SYNTAX  VStpMstInstanceEntry
	    MAX-ACCESS  not-accessible
	    STATUS  current
	    DESCRIPTION
		 "A Mst Instance entry."
	    INDEX { vStpMstInstanceNumber }
	    ::= { vStpMstInstanceTable 1 }

	VStpMstInstanceEntry ::=
	   SEQUENCE {
	    vStpMstInstanceNumber
		INTEGER,
	     vStpMstInstanceName
            DisplayString,
	     vStpMstInstanceVlanBitmapAddition
            VlanBitmap,
	     vStpMstInstanceVlanBitmapDeletion
            VlanBitmap,
         vStpMstInstanceVlanBitmapState
            VlanBitmap,
	     vStpMstInstanceRowStatus
	        RowStatus
	    }

	 vStpMstInstanceNumber  OBJECT-TYPE
	        SYNTAX  INTEGER (0..63)
	        MAX-ACCESS  read-write
	        STATUS  current
	        DESCRIPTION
		       "The Mst Instance number identfies a Spanning Tree instance and
                its vlan range assocaited. To create a new instance a rowStatus
                is required. The instance 0 is reserved for the CIST.  See also
                the vStpTable. By default all vlans are associated to the CIST
                instance 0"
	    ::= { vStpMstInstanceEntry 1 }

	 vStpMstInstanceName  OBJECT-TYPE
		SYNTAX DisplayString (SIZE (0..31))
		MAX-ACCESS read-write
		STATUS current
		DESCRIPTION
			"An optional 32 character string assignable by the
             operator."
		REFERENCE
			" specific to ALCATEL "
		::= { vStpMstInstanceEntry 2 }

	 vStpMstInstanceVlanBitmapAddition  OBJECT-TYPE
		SYNTAX VlanBitmap
		MAX-ACCESS read-write
		STATUS current
		DESCRIPTION
			"A string of 4096 bits forming a bitmap which defines a
             set of VLANs to be added to the membership of the MSTI."
		REFERENCE
			" specific to ALCATEL "
		::= { vStpMstInstanceEntry 3 }

	 vStpMstInstanceVlanBitmapDeletion  OBJECT-TYPE
		SYNTAX VlanBitmap
		MAX-ACCESS read-write
		STATUS current
		DESCRIPTION
			"A string of 4096 bits forming a bitmap which defines a
             set of VLANs to revoke membership from the MSTI."
		REFERENCE
			" specific to ALCATEL "
		::= { vStpMstInstanceEntry 4 }

	 vStpMstInstanceVlanBitmapState  OBJECT-TYPE
		SYNTAX VlanBitmap
		MAX-ACCESS read-only
		STATUS current
		DESCRIPTION
			"A string of 4096 bits forming a bitmap which defines the
            set of VLANs that are members of this MSTI."
		REFERENCE
			" specific to ALCATEL "
		::= { vStpMstInstanceEntry 5 }

	vStpMstInstanceRowStatus OBJECT-TYPE
                SYNTAX RowStatus
      		MAX-ACCESS read-write
      		STATUS current
      		DESCRIPTION
         		"This object is the RowStatus (locking flag) for creating or
  			     deleting Mst Instance objects"
		REFERENCE
			" specific to ALCATEL "
		::= { vStpMstInstanceEntry 6 }



	-- -------------------------------------------------------------
	-- The stp Mst Vlan Assignment Table
	-- -------------------------------------------------------------


	vStpMstVlanAssignmentTable OBJECT-TYPE
		SYNTAX SEQUENCE OF VStpMstVlanAssignmentEntry
		MAX-ACCESS not-accessible
		STATUS current
		DESCRIPTION
			"This table displays the VLAN to MSTI assignment."
	::= { vStpInfo 8 }

	vStpMstVlanAssignmentEntry  OBJECT-TYPE
	    SYNTAX  VStpMstVlanAssignmentEntry
	    MAX-ACCESS  not-accessible
	    STATUS  current
	    DESCRIPTION
		 "A Mst Instance entry."
	    INDEX { vStpMstVlanAssignmentVlanNumber }
	    ::= { vStpMstVlanAssignmentTable 1 }

	VStpMstVlanAssignmentEntry ::=
	   SEQUENCE {
	    vStpMstVlanAssignmentVlanNumber
		INTEGER,
	     vStpMstVlanAssignmentMstiNumber
                INTEGER
	    }

	vStpMstVlanAssignmentVlanNumber  OBJECT-TYPE
	    SYNTAX  INTEGER (1..4095)
	    MAX-ACCESS  read-only
	    STATUS  current
	    DESCRIPTION
		 "The VLAN number identifying this instance. Valid
		  range from 1 to 4095."
	    ::= { vStpMstVlanAssignmentEntry 1 }

	vStpMstVlanAssignmentMstiNumber  OBJECT-TYPE
	    SYNTAX  INTEGER (0..63)
	    MAX-ACCESS  read-write
	    STATUS  current
	    DESCRIPTION
		 "The Msti number assigned to this vlan.
		  All VLANs by default are placed in MSTI 0.
          An MSTI must exist for the assignment to occur."
	--     DEFVAL { 0 }
	   ::= { vStpMstVlanAssignmentEntry 2 }

	-- -------------------------------------------------------------
	-- The stp port instance independant table.
	-- -------------------------------------------------------------


	vStpPortConfigTable OBJECT-TYPE
	    SYNTAX  SEQUENCE OF VStpPortConfigEntry
	    MAX-ACCESS  not-accessible
	    STATUS  current
	    DESCRIPTION
		"A table that contains protocol independant
        port-specific information for the Spanning
        Tree Protocol."
	    ::= { vStpInfo 9 }

	vStpPortConfigEntry OBJECT-TYPE
	    SYNTAX  VStpPortConfigEntry
	    MAX-ACCESS  not-accessible
	    STATUS  current
	    DESCRIPTION
		"A list of information maintained for every Spanning Tree
   		 instance by every port about the protocol independant state
		 for that port."
	    INDEX   { vStpPortConfigIfIndex }
	    ::= { vStpPortConfigTable 1 }

	VStpPortConfigEntry ::=
	    SEQUENCE {
		vStpPortConfigIfIndex
		    InterfaceIndex,
		vStpPortConfigTenGigOs8800Opt
		    INTEGER,
		vStpPortConfigPVST
		    INTEGER,
		vStpPortConfigStatePVST
		    INTEGER,
                vStpPortConfigLoopGuard
                    INTEGER
	    }


	vStpPortConfigIfIndex OBJECT-TYPE
	    SYNTAX  InterfaceIndex
	    MAX-ACCESS  read-only
	    STATUS  current
	    DESCRIPTION
		"The ifindex of the port for which this
		 entry contains Spanning Tree Protocol management
		 information."
	    ::= { vStpPortConfigEntry 1 }

	vStpPortConfigTenGigOs8800Opt OBJECT-TYPE
	    SYNTAX  INTEGER {
            enable(1),
            disable(2)
            }
	    MAX-ACCESS  read-write
	    STATUS  current
	    DESCRIPTION
		"The status of whether this port is interacting
        with a 10 gigabit link to a OS8800 switch."
	    DEFVAL { enable }
	    ::= { vStpPortConfigEntry 2 }

	vStpPortConfigPVST OBJECT-TYPE
	    SYNTAX  INTEGER {
	    auto(1),
	    enable(2),
	    disable(3)
	    }
	    MAX-ACCESS  read-write
	    STATUS  current
	    DESCRIPTION
		"Configure a port what type of BPDU to use when PVST+ mode
		 is enabled:
		 Auto: Use IEEE BPDUs until a PVST+ BPDU is detected.
		 Enable: Use PVST+ BPDUs.
		 Disable: Use IEEE BPDUs."
	    DEFVAL { auto }
	    ::= { vStpPortConfigEntry 3 }

	vStpPortConfigStatePVST OBJECT-TYPE
	    SYNTAX  INTEGER {
	    on(1),
	    off(2)
	    }
	    MAX-ACCESS  read-only
	    STATUS  current
	    DESCRIPTION
		"The status of whether the type of PVST+ BPDU is on or off for
		 this port."
	    DEFVAL { off }
	    ::= { vStpPortConfigEntry 4 }

	vStpPortConfigLoopGuard OBJECT-TYPE
            SYNTAX  INTEGER {
            enable(1),
            disable(2)
            }
            MAX-ACCESS  read-write
            STATUS  current
            DESCRIPTION
                "Configure STP loop guard on the port."
            DEFVAL { disable }
            ::= { vStpPortConfigEntry 5 }

-- -------------------------------------------------------------
	-- The Ring Rapid spanning tree global state

	    vStpRrstpGlobalState OBJECT-TYPE
	    SYNTAX  INTEGER {
            enable(1),
            disable(2)
	    }
	    MAX-ACCESS  read-write
	    STATUS  current
	    DESCRIPTION
		"The state of Ring rapid spanning tree on a global level.
		When the RRSTP is disabled gobally, all the rings get disabled. 		When the RRSTP is enabled globally, the rings can be
		individually configured to be enabled or disabled."
	    DEFVAL { disable }
	    ::= { vStpInfo 10}

	-- The Ring Rapid spanning tree ring configuration table
	-- -------------------------------------------------------------


	vStpRrstpRingConfigTable OBJECT-TYPE
	    SYNTAX  SEQUENCE OF VStpRrstpRingConfigEntry
	    MAX-ACCESS  not-accessible
	    STATUS  current
	    DESCRIPTION
		"A table that contains RRSTP ring configuration related
		 information."
	    ::= { vStpInfo 11 }

	vStpRrstpRingConfigEntry OBJECT-TYPE
	    SYNTAX  VStpRrstpRingConfigEntry
	    MAX-ACCESS  not-accessible
	    STATUS  current
	    DESCRIPTION
		"A list of information maintained for each RRSTP ring
   		 about ports that are part of the ring."
	    INDEX   { vStpRrstpRingId }
	    ::= { vStpRrstpRingConfigTable 1 }

	VStpRrstpRingConfigEntry ::=
	    SEQUENCE {
		vStpRrstpRingId
		    INTEGER,
		vStpRrstpRingPort1
		    InterfaceIndex,
		vStpRrstpRingPort2
		    InterfaceIndex,
		vStpRrstpRingVlanTag
		    INTEGER,
		vStpRrstpRingState
		    INTEGER,
		vStpRrstpRingRowStatus
			RowStatus
	    }

	vStpRrstpRingId OBJECT-TYPE
	    SYNTAX  INTEGER (1..128)
	    MAX-ACCESS  read-create
	    STATUS  current
	    DESCRIPTION
		"The identifier of the RRSTP ring."
	    ::= { vStpRrstpRingConfigEntry 1 }

	vStpRrstpRingPort1 OBJECT-TYPE
	    SYNTAX  InterfaceIndex
	    MAX-ACCESS  read-create
	    STATUS  current
	    DESCRIPTION
		"The interface index of first port that belongs
		to the ring."
	    ::= { vStpRrstpRingConfigEntry 2 }	
	
	vStpRrstpRingPort2 OBJECT-TYPE
	    SYNTAX  InterfaceIndex
	    MAX-ACCESS  read-create
	    STATUS  current
	    DESCRIPTION
		"The interface index of second port that belongs
		to the ring."
	    ::= { vStpRrstpRingConfigEntry 3 }	

	vStpRrstpRingVlanTag OBJECT-TYPE
            SYNTAX INTEGER (1..4094)
	    MAX-ACCESS  read-create
	    STATUS  current
	    DESCRIPTION
		"The VLAN tag applied to the ring with which RRSTP
		 ring frames shall be tagged. Valid range from
		 1 to 4094"
	    ::= { vStpRrstpRingConfigEntry 4 }	

	vStpRrstpRingState OBJECT-TYPE
	    SYNTAX  INTEGER {
            enable(1),
            disable(2)
	    }
	    MAX-ACCESS  read-create
	    STATUS  current
	    DESCRIPTION
		"The state of the ring. A ring can be created but can be made
		active or inactive."
	    DEFVAL { disable }
	    ::= { vStpRrstpRingConfigEntry 5 }

	vStpRrstpRingRowStatus OBJECT-TYPE
                SYNTAX RowStatus
      		MAX-ACCESS read-create
      		STATUS current
      		DESCRIPTION
         		"This object is the RowStatus (locking flag) for creating or
  			     deleting RRSTP Ring"
		REFERENCE
			" specific to ALCATEL "
		::= { vStpRrstpRingConfigEntry 6 }
		
-- Traps for the Spanning Tree Protocol*********************

 stpNewRoot NOTIFICATION-TYPE
    OBJECTS    {
                  vStpNumber
               }
    STATUS  current
    DESCRIPTION
           "The NewRoot trap indicates that the bridge has
            become the new root for this Spanning Tree instance;
	    the trap is sent by a bridge soon after its election
            as the new root, upon expiration of the
            Topology Change Timer immediately subsequent to
            its election."
    ::= { spanningTreeTraps 0 1 }


 stpRootPortChange NOTIFICATION-TYPE
    OBJECTS    {
                  vStpNumber,
		  vStpRootPortNumber
               }
    STATUS  current
    DESCRIPTION
            "A RootPortChange trap is sent for a Spannnig Tree
            instance by a bridge when its root port has changed.
	    The root port is the port which offers the
	    lowest cost path from this bridge to the root
	    bridge."
    ::= { spanningTreeTraps 0 2 }

stpLoopGuardError NOTIFICATION-TYPE
    OBJECTS    {
                  vStpPortConfigIfIndex,
                  vStpNumber
               }
    STATUS  current
    DESCRIPTION
            "This trap is sent by a bridge when a port
            enters the Loop inconsistent state (ERR state)."
    ::= { spanningTreeTraps 0 3 }

stpLoopGuardRecovery NOTIFICATION-TYPE
    OBJECTS    {
                  vStpPortConfigIfIndex,
                  vStpNumber
               }
    STATUS  current
    DESCRIPTION
            "This trap is sent by a bridge when a port
            leaves the Loop inconsistent state (ERR state)."
    ::= { spanningTreeTraps 0 4 }

-- Conformance Information

   vStpGroup OBJECT-GROUP
        OBJECTS
        {
          vStpInsNumber,	                   -- vStp table
          vStpInsProtocolSpecification,
          vStpInsPriority,
          vStpInsBridgeAddress,
          vStpInsTimeSinceTopologyChange,
          vStpInsTopChanges,
          vStpInsDesignatedRoot,
          vStpInsRootCost,
          vStpInsRootPortNumber,
          vStpInsNextBestRootCost,
          vStpInsNextBestRootPortNumber,
          vStpInsMaxAge,
          vStpInsHelloTime,
          vStpInsHoldTime,
          vStpInsForwardDelay,
          vStpInsBridgeMaxAge,
          vStpInsBridgeHelloTime,
          vStpInsBridgeForwardDelay,
          vStpInsBpduSwitching,
          vStpInsCistRegionalRootId,
          vStpInsCistPathCost,
          vStpIns1x1VlanNumber,
          vStpInsMstiNumber,
          vStpInsMode,
          vStpInsAutoVlanContainment,
          vStpBridgeAddress ,
          vStpBridgeForwardDelay ,
          vStpBridgeHelloTime ,
          vStpBridgeMaxAge,
          vStpDesignatedRoot,
          vStpForwardDelay ,
          vStpHelloTime ,
          vStpHoldTime,
          vStpMaxAge,  
          vStpMode,
          vStpNextBestRootCost,
          vStpNextBestRootPortNumber,
          vStpNumber,
          vStpPriority,
          vStpProtocolSpecification,
          vStpRootPortNumber,
          vStpTimeSinceTopologyChange,  
          vStpTopChanges  
        }
        STATUS  current
        DESCRIPTION
            "Collection of objects for management of Spanning Tree instances."
        ::= { alcatelIND1VLANSTPMIBGroups 1 }


    vStpPortGroup OBJECT-GROUP
        OBJECTS
        {
	    	vStpInsPortNumber,		   -- vStpPort table
	    	vStpInsPortPriority,
	    	vStpInsPortState,
	    	vStpInsPortEnable,
	    	vStpInsPortPathCost,
	     	vStpInsPortDesignatedRoot,
	    	vStpInsPortDesignatedCost,
	    	vStpInsPortDesignatedBridge,
	    	vStpInsPortDesignatedPtPrio,
	    	vStpInsPortDesignatedPtNumber,
	    	vStpInsPortForwardTransitions,
	    	vStpInsPortManualMode,
	    	vStpInsPortRole,
	    	vStpInsPortPrimaryPortNumber,
	    	vStpInsPortAdminConnectionType,
	        vStpInsPortOperConnectionType,
	        vStpInsPortCistRegionRootId,
	        vStpInsPortCistPathCost,
	        vStpInsPortHelloTime,
	        vStpInsBridgeHelloTime,
            vstpInsPortRcvdInternal,
            vStpInsBridgeTxHoldCount,
            vStpInsPortAdminEdge ,
            vStpInsPortAutoEdge,
            vStpInsPortBridgeHelloTime,
            --vStpInsPortEntry,
            vStpInsPortRestrictedRole,
            vStpInsPortRestrictedTcn,
            vStpInsStatus,
            vStpPortAdminConnectionType,
          	vStpPortConfigPVST ,
          	vStpPortConfigStatePVST,
          	vStpPortDesignatedBridge,   
            vStpPortDesignatedCost,
            vStpPortDesignatedPtNumber,  
            vStpPortDesignatedPtPrio,
            vStpPortDesignatedRoot,
            vStpPortEnable,
            vStpPortForwardTransitions,
            vStpPortManualMode,
            vStpPortNumber,
            vStpPortOperConnectionType,
            vStpPortPathCost,
            vStpPortPrimaryPortNumber,
            vStpPortPriority,
            vStpPortRole,
            vStpPortState,
            
            vStpRootCost         
        }
        STATUS  current
        DESCRIPTION
            "Collection of objects for management of Spanning Tree port instances."
        ::= { alcatelIND1VLANSTPMIBGroups 2 }

    vStpMstRegionGroup OBJECT-GROUP
	OBJECTS
        {
	      vStpMstRegionNumber,
	      vStpMstRegionConfigFormatSelector,
	      vStpMstRegionConfigDigest,
              vStpMstRegionConfigName,
	      vStpMstRegionConfigRevisionLevel,
              vStpMstRegionMstiList,
              vStpMstRegionCistInstanceNumber,
              vStpMstRegionMaxHops
	 }
	 STATUS  current
         DESCRIPTION
            "Collection of objects for management of Spanning Tree mst region instances."
         ::= { alcatelIND1VLANSTPMIBGroups 6 }


	vStpMstInstanceGroup OBJECT-GROUP
	OBJECTS
	{
	    vStpMstInstanceNumber,
	    vStpMstInstanceName,
	    vStpMstInstanceVlanBitmapAddition,
	    vStpMstInstanceVlanBitmapDeletion,
            vStpMstInstanceVlanBitmapState,
	    vStpMstInstanceRowStatus
	 }
	 STATUS  current
         DESCRIPTION
            "Collection of objects for management of Spanning Tree mst instances."
         ::= { alcatelIND1VLANSTPMIBGroups 4 }


	vStpMstVlanAssignmentGroup OBJECT-GROUP
	OBJECTS
	{
	    vStpMstVlanAssignmentVlanNumber,
	    vStpMstVlanAssignmentMstiNumber
	}
	 STATUS  current
         DESCRIPTION
            "Collection of objects for management of Spanning Tree
              assignment vlan to msti instances."
         ::= { alcatelIND1VLANSTPMIBGroups 5 }
 
          
	vStpPortConfigGroup OBJECT-GROUP
	OBJECTS
	{
	    vStpPortConfigIfIndex,
	    vStpPortConfigTenGigOs8800Opt,
	    vStpPortConfigLoopGuard        
	}
	 STATUS  current
         DESCRIPTION
            "Collection of objects for management of protocol
            indepentant port configuration."
         ::= { alcatelIND1VLANSTPMIBGroups 7 }


    vStpNotificationGroup NOTIFICATION-GROUP
    NOTIFICATIONS {
	  stpNewRoot,
          stpRootPortChange,
          stpLoopGuardError,
          stpLoopGuardRecovery
	}
    STATUS current
    DESCRIPTION
 	    "The Spanning Tree Notification Group."
    ::= { alcatelIND1VLANSTPMIBGroups 3 }

vStpRrstpRingConfigGroup OBJECT-GROUP
	OBJECTS
	{
         vStpRrstpRingId,
	 	 vStpRrstpRingPort1,
         vStpRrstpRingPort2,
         vStpRrstpRingState,
         vStpRrstpRingRowStatus,
         vStpRrstpRingVlanTag
	}
	 STATUS  current
         DESCRIPTION
            "Collection of objects maintained for each RRSTP ring
   		 about ports that are part of the ring."
         ::= { alcatelIND1VLANSTPMIBGroups 8 }

vStpRrstpRingBaseGroup OBJECT-GROUP
   OBJECTS {
      vStpRrstpGlobalState
   }
   STATUS      current
   DESCRIPTION
      "State of Ring rapid spanning tree on a global level"
   ::= { alcatelIND1VLANSTPMIBGroups 9 }


vStpBridgeGroup OBJECT-GROUP
   OBJECTS {
    vStpBridgeAddressId,
    vStpBridgeLastChanged,
    vStpBridgeAutoVlanContainment ,
    vStpBridgeMode ,
    vStpBridgeModePVST,
    vStpBridgePathCostMode
   }
   STATUS      current
   DESCRIPTION
      "Spanning Tree Protocol activated
		 on this bridge."
   ::= { alcatelIND1VLANSTPMIBGroups 10 }
	
	

    alcatelIND1VLANSTPMIBCompliance MODULE-COMPLIANCE
        STATUS  current
        DESCRIPTION
            "Compliance statement for
             Spanning Tree."
        MODULE
            MANDATORY-GROUPS
            {
                vStpGroup,
                vStpPortGroup,
	        	vStpMstRegionGroup,
                vStpMstInstanceGroup,
				vStpMstVlanAssignmentGroup,
                vStpPortConfigGroup,
                vStpNotificationGroup,
                vStpRrstpRingConfigGroup,
                vStpRrstpRingBaseGroup,
                vStpBridgeGroup
                
                
            }

        ::= { alcatelIND1VLANSTPMIBCompliances 1 }

	END
