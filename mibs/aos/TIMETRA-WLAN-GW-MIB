TIMETRA-WLAN-GW-MIB DEFINITIONS ::= BEGIN

IMPORTS
    Unsigned32, Gauge32, Counter32, Counter64,
    MODULE-IDENTITY,
    OBJECT-TYPE,
    NOTIFICATION-TYPE
                                                                FROM SNMPv2-SMI


    RowStatus, TEXTUAL-CONVENTION, 
    TimeStamp, DateAndTime, TruthValue,
    DisplayString,
    MacAddress
                                                                 FROM SNMPv2-TC


    OBJECT-GROUP, MODULE-COMPLIANCE,
    NOTIFICATION-GROUP
                                                               FROM SNMPv2-CONF

    InetAddressType, InetAddress,
    InetAddressPrefixLength,
    InetPortNumber
                                                          FROM INET-ADDRESS-MIB
                                                         
    MplsLabel                                                 FROM MPLS-LSR-MIB
    
    timetraSRMIBModules, tmnxSRObjs, tmnxSRConfs, 
    tmnxSRNotifyPrefix
                                                        FROM TIMETRA-GLOBAL-MIB

    TItemDescription, TNamedItem, TNamedItemOrEmpty,  
    TmnxVRtrID, TmnxVRtrIDOrZero, TmnxServId,
    TmnxAdminState, TmnxOperState, TmnxEnabledDisabled,
    TPolicyID, TPortSchedulerPIR, TmnxPortID, 
    TmnxEncapVal,
    QTagFullRange, QTagFullRangeOrNone,
    SvcISID,
    TmnxMobProfIpTtl,
    TmnxMobMccOrEmpty, TmnxMobMncOrEmpty,
    TmnxMobApn, TmnxMobApnOrZero, TmnxMobImsiStr,
    TmnxMobBearerId, TmnxMobPathMgmtState
                                                            FROM TIMETRA-TC-MIB

    tmnxChassisIndex, tmnxCardSlotNum,
    TmnxChassisIndexOrZero, TmnxSlotNumOrZero
                                                       FROM TIMETRA-CHASSIS-MIB
    
    vRtrID                                          
                                                          FROM TIMETRA-VRTR-MIB
 
    svcId, iesIfIndex
                                                          FROM TIMETRA-SERV-MIB

    TmnxMobProfMsgReTxTimeout,
    TmnxMobProfMsgReTxRetryCount,
    TmnxMobProfKeepAliveTimeout,
    TmnxMobProfKeepAliveRetryCount,
    TmnxMobProfKeepAliveResponse,
    TmnxMobProfKeepAliveInterval
                                                FROM TIMETRA-MOBILE-PROFILE-MIB                                                          
    ;
timetraWlanGwMIBModule    MODULE-IDENTITY
    LAST-UPDATED    "201202281200Z"
    ORGANIZATION    "Alcatel-Lucent"
    CONTACT-INFO
    "Alcatel-Lucent 7xxx Support
    Web: http://www.alcatel-lucent.com/wps/portal/Support"
    DESCRIPTION
    "This document is the SNMP MIB module to manage and provision
    the Wireless Local Access Network Gateway function
    for the Alcatel-Lucent 7xxx device.

    Copyright 2011-2012 Alcatel-Lucent. All rights reserved.
    Reproduction of this document is authorized on the condition that
    the foregoing copyright notice is included.

    This SNMP MIB module (Specification) embodies Alcatel-Lucent's
    proprietary intellectual property. Alcatel-Lucent retains all title and
    ownership in the Specification, including any revisions.

    Alcatel-Lucent grants all interested parties a non-exclusive
    license to use and distribute an unmodified copy of this
    Specification in connection with management of Alcatel products,
    and without fee, provided this copyright notice and license appear
    on all copies.

    This Specification is supplied 'as is', and Alcatel-Lucent
    makes no warranty, either express or implied, as to the use,
    operation, condition, or performance of the Specification."

--
--  Revision History
--

    REVISION        "201202281200Z"
    DESCRIPTION     "Rev 10.0                28 Februari 2012 12:00
                     10.0 release of the TIMETRA-WLAN-GW-MIB."

    ::= { timetraSRMIBModules 81 }

-- ----------------------------------------------------------------------------
--  Alcatel-Lucent 7xxx series WLAN Gateway MIB structure
-- ----------------------------------------------------------------------------
tmnxWlanGw                     OBJECT IDENTIFIER ::= { tmnxSRObjs 81 }
    tmnxWlanGwObjs             OBJECT IDENTIFIER ::= { tmnxWlanGw 1 }
    tmnxWlanGwNotificationObjs OBJECT IDENTIFIER ::= { tmnxWlanGw 2 }

tmnxWlanGwConformance          OBJECT IDENTIFIER ::= { tmnxSRConfs 81 }
    tmnxWlanGwCompliances      OBJECT IDENTIFIER ::= { tmnxWlanGwConformance 1 }
    tmnxWlanGwGroups           OBJECT IDENTIFIER ::= { tmnxWlanGwConformance 2 }

tmnxWlanGwNotifyPrefix         OBJECT IDENTIFIER ::= { tmnxSRNotifyPrefix 81 }
    tmnxWlanGwNotifications    OBJECT IDENTIFIER ::= { tmnxWlanGwNotifyPrefix 0 }

--
-- Subtrees
--
tmnxWlanGwIsaObjs              OBJECT IDENTIFIER ::= { tmnxWlanGwObjs 1 }
tmnxWlanGwSoftGreObjs          OBJECT IDENTIFIER ::= { tmnxWlanGwObjs 2 }
tmnxWlanGwMgwObjs          OBJECT IDENTIFIER ::= { tmnxWlanGwObjs 6 }
tmnxWlanGwSysCfgObjs           OBJECT IDENTIFIER ::= { tmnxWlanGwObjs 7 }

-- ----------------------------------------------------------------------------
--  Textual Conventions
-- ----------------------------------------------------------------------------
TmnxWlanGwIsaGrpId ::= TEXTUAL-CONVENTION
    STATUS  current
    DESCRIPTION
       "The TmnxWlanGwIsaGrpId data type contains an identification number 
        for a Wireless Local Access Network Gateway 
        Integrated Service Adaptor group."
    SYNTAX Unsigned32 (1..4)

TmnxWlanGwIsaGrpIdOrZero ::= TEXTUAL-CONVENTION
    STATUS  current
    DESCRIPTION
       "The TmnxWlanGwIsaGrpIdOrZero data type contains an identification number 
        for a Wireless Local Access Network Gateway
        Integrated Service Adaptor (ISA) group.
        
        The value zero means that no WLAN Gateway ISA Group is defined."
    SYNTAX Unsigned32 (0..4)

TmnxWlanGwIsaIomOperState ::= TEXTUAL-CONVENTION
    STATUS  current
    DESCRIPTION         
        "TmnxWlanGwIsaIomOperState is an enumerated integer 
         that indicates the operational state of a WLAN Gateway ISA IOM 
         within a WLAN Gateway ISA group."
    SYNTAX INTEGER {
               unavail (0),
               primary (1),
               backup  (2),
               busy    (3)
           }

TmnxWlanGwQoSOperState ::= TEXTUAL-CONVENTION
    STATUS  current
    DESCRIPTION         
        "TmnxWlanGwQoSOperState is an enumerated integer 
         that indicates the operational state of a WLAN Gateway
         User Equipment (UE)."
    SYNTAX INTEGER {
                adminDown (0),
                active (1),
                pending (2),
                problem (3)
            }

-- ----------------------------------------------------------------------------
--      The "WLAN Gateway ISA" Group
-- ----------------------------------------------------------------------------

--
--      The WLAN Gateway ISA Group Table
--

tmnxWlanGwGrpTable   OBJECT-TYPE
    SYNTAX      SEQUENCE OF TmnxWlanGwGrpEntry
    MAX-ACCESS  not-accessible
    STATUS      current
    DESCRIPTION
       "The tmnxWlanGwGrpTable contains objects to configure 
        WLAN Gateway Integrated Service Adaptor (ISA) Groups.
        
        A WLAN Gateway ISA group is used to represent multiple hardware 
        adaptors as a single entity, allowing for warm redundancy between 
        multiple WLAN Gateway ISA's."
    ::= { tmnxWlanGwIsaObjs 1 }

tmnxWlanGwGrpEntry   OBJECT-TYPE
        SYNTAX          TmnxWlanGwGrpEntry
        MAX-ACCESS      not-accessible
        STATUS          current
        DESCRIPTION
       "Each conceptual row represents a WLAN Gateway
        Integrated Service Adaptor Group.

        Entries in this table can be created or deleted via SNMP operations."
    INDEX { tmnxWlanGwGrpId }
    ::= { tmnxWlanGwGrpTable 1 }

TmnxWlanGwGrpEntry ::= 
    SEQUENCE {
        tmnxWlanGwGrpId                  TmnxWlanGwIsaGrpId,
        tmnxWlanGwGrpRowStatus           RowStatus,
        tmnxWlanGwGrpLastMgmtChange      TimeStamp,
        tmnxWlanGwGrpDescription         TItemDescription,
        tmnxWlanGwGrpAdminState          TmnxAdminState,
        tmnxWlanGwGrpActiveIomLimit      Unsigned32,
        tmnxWlanGwGrpPortPlcy            TNamedItemOrEmpty,
        tmnxWlanGwGrpTunnelPortPlcy      TNamedItemOrEmpty,
        tmnxWlanGwGrpOperState           TmnxOperState
    }
        
tmnxWlanGwGrpId OBJECT-TYPE
    SYNTAX      TmnxWlanGwIsaGrpId
    MAX-ACCESS  not-accessible
    STATUS      current
    DESCRIPTION
       "The value of the object tmnxWlanGwGrpId specifies the identifier of
        the WLAN Gateway Integrated Service Adaptor group."
    ::= { tmnxWlanGwGrpEntry 1 }

tmnxWlanGwGrpRowStatus OBJECT-TYPE
    SYNTAX      RowStatus
    MAX-ACCESS  read-create
    STATUS      current
    DESCRIPTION
       "The value of tmnxWlanGwGrpRowStatus specifies the row status of
        this row."
    ::= { tmnxWlanGwGrpEntry 2 }

tmnxWlanGwGrpLastMgmtChange OBJECT-TYPE
    SYNTAX      TimeStamp
    MAX-ACCESS  read-only
    STATUS      current
    DESCRIPTION
        "The value of tmnxWlanGwGrpLastMgmtChange indicates the sysUpTime at
         the time of the most recent management-initiated change to this
         table row."
    ::= { tmnxWlanGwGrpEntry 3 }

tmnxWlanGwGrpDescription OBJECT-TYPE
    SYNTAX      TItemDescription
    MAX-ACCESS  read-create
    STATUS      current
    DESCRIPTION
       "The value of tmnxWlanGwGrpDescription specifies the
        description of this WLAN Gateway ISA group."
    DEFVAL { "" }
    ::= { tmnxWlanGwGrpEntry 4 }

tmnxWlanGwGrpAdminState OBJECT-TYPE
    SYNTAX      TmnxAdminState
    MAX-ACCESS  read-create
    STATUS      current
    DESCRIPTION
       "The value of tmnxWlanGwGrpAdminState specifies the
        administrative state of this WLAN Gateway ISA group."
    DEFVAL { outOfService }
    ::= { tmnxWlanGwGrpEntry 5 }

tmnxWlanGwGrpActiveIomLimit OBJECT-TYPE
    SYNTAX      Unsigned32 (0..3)
    MAX-ACCESS  read-create
    STATUS      current
    DESCRIPTION
       "The value of tmnxWlanGwGrpActiveIomLimit specifies the
        number of IOM's in this WLAN Gateway ISA group that are intended for 
        active use.

        A non-zero value must be specified before setting the value of 
        tmnxWlanGwGrpAdminState to 'inService'."
    DEFVAL { 0 }
    ::= { tmnxWlanGwGrpEntry 6 }

tmnxWlanGwGrpPortPlcy OBJECT-TYPE
    SYNTAX      TNamedItemOrEmpty
    MAX-ACCESS  read-create
    STATUS      current
    DESCRIPTION
       "The value of tmnxWlanGwGrpPortPlcy specifies the
        port policy of this WLAN Gateway ISA group.
        
        This object refers to a row in 
        the TIMETRA-PORT-MIB::tmnxPortPlcyTable.
        
        If a port policy is associated with a WLAN Gateway ISA group,
        ports created for this group can take applicable configuration
        from that port policy.
        
        This port policy is applicable to those ports 
        that take part in the per-UE QoS processing"
    DEFVAL { "" }
    ::= { tmnxWlanGwGrpEntry 7 }

tmnxWlanGwGrpTunnelPortPlcy OBJECT-TYPE
    SYNTAX      TNamedItemOrEmpty
    MAX-ACCESS  read-create
    STATUS      current
    DESCRIPTION
       "The value of tmnxWlanGwGrpTunnelPortPlcy specifies a
        port policy of this WLAN Gateway ISA group.
        
        This object refers to a row in 
        the TIMETRA-PORT-MIB::tmnxPortPlcyTable.
        
        If a port policy is associated with a WLAN Gateway ISA group,
        ports created for this group can take applicable configuration
        from that port policy.
        
        This port policy is applicable to those ports 
        that take part in the per-tunnel QoS processing."
    DEFVAL { "" }
    ::= { tmnxWlanGwGrpEntry 8 }

tmnxWlanGwGrpOperState  OBJECT-TYPE
    SYNTAX      TmnxOperState 
    MAX-ACCESS  read-only
    STATUS      current
    DESCRIPTION
        "The value of tmnxWlanGwGrpOperState indicates the operational 
         status of this WLAN Gateway ISA group."
    ::= { tmnxWlanGwGrpEntry 50 }


--
--      The WLAN Gateway ISA Group IOM Table
--

tmnxWlanGwIomTable   OBJECT-TYPE
    SYNTAX      SEQUENCE OF TmnxWlanGwIomEntry
    MAX-ACCESS  not-accessible
    STATUS      current
    DESCRIPTION
       "The tmnxWlanGwIomTable contains objects to configure 
        the WLAN Gateway ISA Group Input/Output Modules (IOM)."
    ::= { tmnxWlanGwIsaObjs 2 }

tmnxWlanGwIomEntry   OBJECT-TYPE
    SYNTAX      TmnxWlanGwIomEntry
    MAX-ACCESS  not-accessible
    STATUS      current
    DESCRIPTION
       "Each conceptual row represents an WLAN Gateway 
        ISA Input/Output Module (IOM) of a WLAN Gateway ISA Group.

        Entries in this table can be created or deleted via SNMP operations."
    INDEX { tmnxWlanGwGrpId ,
            tmnxChassisIndex, 
            tmnxCardSlotNum }
    ::= { tmnxWlanGwIomTable 1 }

TmnxWlanGwIomEntry ::= 
    SEQUENCE {
        tmnxWlanGwIomRowStatus           RowStatus,
        tmnxWlanGwIomLastMgmtChange      TimeStamp,
        tmnxWlanGwIomOperState           TmnxWlanGwIsaIomOperState
    }

tmnxWlanGwIomRowStatus OBJECT-TYPE
    SYNTAX      RowStatus
    MAX-ACCESS  read-create
    STATUS      current
    DESCRIPTION
       "The value of tmnxWlanGwIomRowStatus specifies the row status of
        this row."
    ::= { tmnxWlanGwIomEntry 1 }

tmnxWlanGwIomLastMgmtChange OBJECT-TYPE
    SYNTAX      TimeStamp
    MAX-ACCESS  read-only
    STATUS      current
    DESCRIPTION
        "The value of tmnxWlanGwIomLastMgmtChange indicates the sysUpTime at
         the time of the most recent management-initiated change to this
         table row."
    ::= { tmnxWlanGwIomEntry 2 }

tmnxWlanGwIomOperState OBJECT-TYPE
    SYNTAX      TmnxWlanGwIsaIomOperState
    MAX-ACCESS  read-only
    STATUS      current
    DESCRIPTION
       "The value of tmnxWlanGwIomOperState indicates the
        operational state of this WLAN Gateway ISA IOM."
    ::= { tmnxWlanGwIomEntry 3 }
    
--
--      The WLAN Gateway group ISA Member Table
--


tmnxWlanGwIsaMemberTable   OBJECT-TYPE
    SYNTAX      SEQUENCE OF TmnxWlanGwIsaMemberEntry
    MAX-ACCESS  not-accessible
    STATUS      current
    DESCRIPTION
       "The tmnxWlanGwIsaMemberTable contains status and statistics information 
        about the members of a WLAN Gateway ISA Group.
        
        A member of a WLAN Gateway ISA Group can be mapped to a physical ISA MDA."
    ::= { tmnxWlanGwIsaObjs 3 }

tmnxWlanGwIsaMemberEntry   OBJECT-TYPE
    SYNTAX      TmnxWlanGwIsaMemberEntry
    MAX-ACCESS  not-accessible
    STATUS      current
    DESCRIPTION
       "Each conceptual row contains WLAN Gateway-specific
        status and basic statistics information
        about a member of a WLAN Gateway ISA Group.

        Entries in this table are created and removed automatically by the 
        system."
    INDEX { tmnxWlanGwGrpId,
            tmnxWlanGwIsaMemberId }
    ::= { tmnxWlanGwIsaMemberTable 1 }

TmnxWlanGwIsaMemberEntry ::= 
    SEQUENCE {
        tmnxWlanGwIsaMemberId            Unsigned32,
        tmnxWlanGwIsaMemberChassisIndex  TmnxChassisIndexOrZero,
        tmnxWlanGwIsaMemberCardSlotNum   TmnxSlotNumOrZero,
        tmnxWlanGwIsaMemberSlotNum       Unsigned32,
        tmnxWlanGwIsaMemberNumSoftGreTu  Gauge32,
        tmnxWlanGwIsaMemberNumUe         Gauge32,
        tmnxWlanGwIsaMemberEegMemberAct  Gauge32,
        tmnxWlanGwIsaMemberEegMemberPend Gauge32,
        tmnxWlanGwIsaMemberTuQosProblem  Gauge32
    }
        
tmnxWlanGwIsaMemberId OBJECT-TYPE
    SYNTAX      Unsigned32
    MAX-ACCESS  not-accessible
    STATUS      current
    DESCRIPTION
       "The value of the object tmnxWlanGwIsaMemberId indicates the identifier of
        this WLAN Gateway ISA Group member."
    ::= { tmnxWlanGwIsaMemberEntry 1 }

tmnxWlanGwIsaMemberChassisIndex OBJECT-TYPE
    SYNTAX      TmnxChassisIndexOrZero
    MAX-ACCESS  read-only
    STATUS      current
    DESCRIPTION
       "The value of tmnxWlanGwIsaMemberChassisIndex indicates the
        chassis of the MDA associated with this member.
        
        The value zero means that there is currently no MDA associated with this
        member."
    ::= { tmnxWlanGwIsaMemberEntry 2 }

tmnxWlanGwIsaMemberCardSlotNum OBJECT-TYPE
    SYNTAX      TmnxSlotNumOrZero
    MAX-ACCESS  read-only
    STATUS      current
    DESCRIPTION
       "The value of tmnxWlanGwIsaMemberCardSlotNum indicates the
        IOM slot of the MDA associated with this member.
        
        The value zero means that there is currently no MDA associated with this
        member."
    ::= { tmnxWlanGwIsaMemberEntry 3 }

tmnxWlanGwIsaMemberSlotNum OBJECT-TYPE
    SYNTAX      Unsigned32
    MAX-ACCESS  read-only
    STATUS      current
    DESCRIPTION
       "The value of tmnxWlanGwIsaMemberSlotNum indicates the
        MDA slot within the IOM of the MDA associated with this member.
        
        The value zero means that there is currently no MDA associated with this
        member."
    ::= { tmnxWlanGwIsaMemberEntry 4 }

tmnxWlanGwIsaMemberNumSoftGreTu OBJECT-TYPE
    SYNTAX      Gauge32
    MAX-ACCESS  read-only
    STATUS      current
    DESCRIPTION
       "The value of tmnxWlanGwIsaMemberNumSoftGreTu indicates the
        number of Soft GRE tunnels processed by the MDA 
        associated with this member."
    ::= { tmnxWlanGwIsaMemberEntry 5 }

tmnxWlanGwIsaMemberNumUe OBJECT-TYPE
    SYNTAX      Gauge32
    MAX-ACCESS  read-only
    STATUS      current
    DESCRIPTION
       "The value of tmnxWlanGwIsaMemberNumUe indicates the
        number of UE processed by the MDA 
        associated with this member."
    ::= { tmnxWlanGwIsaMemberEntry 6 }

tmnxWlanGwIsaMemberEegMemberAct OBJECT-TYPE
    SYNTAX      Gauge32
    MAX-ACCESS  read-only
    STATUS      current
    DESCRIPTION
       "The value of tmnxWlanGwIsaMemberEegMemberAct indicates the
        number of activated Egress Encapsulation Group members 
        associated with this ISA group member."
    ::= { tmnxWlanGwIsaMemberEntry 7 }

tmnxWlanGwIsaMemberEegMemberPend OBJECT-TYPE
    SYNTAX      Gauge32
    MAX-ACCESS  read-only
    STATUS      current
    DESCRIPTION
       "The value of tmnxWlanGwIsaMemberEegMemberPend indicates the
        number of pending Egress Encapsulation Group members 
        associated with this ISA group member."
    ::= { tmnxWlanGwIsaMemberEntry 8 }

tmnxWlanGwIsaMemberTuQosProblem OBJECT-TYPE
    SYNTAX      Gauge32
    MAX-ACCESS  read-only
    STATUS      current
    DESCRIPTION
       "The value of tmnxWlanGwIsaMemberTuQosProblem indicates the
        number of tunnel Qos infrastructure configuration instances 
        on the MDA associated with this ISA group member 
        that have a resource issue."
    ::= { tmnxWlanGwIsaMemberEntry 9 }

--
--      The WLAN Gateway ISA Group Member Statistics Table
--


tmnxWlanGwIsaMemberStatsTable   OBJECT-TYPE
    SYNTAX      SEQUENCE OF TmnxWlanGwIsaMemberStatsEntry
    MAX-ACCESS  not-accessible
    STATUS      current
    DESCRIPTION
       "The tmnxWlanGwIsaMemberStatsTable contains detailed statistics information 
        about the members of a WLAN Gateway ISA ISA Group."
    ::= { tmnxWlanGwIsaObjs 4 }

tmnxWlanGwIsaMemberStatsEntry   OBJECT-TYPE
    SYNTAX      TmnxWlanGwIsaMemberStatsEntry
    MAX-ACCESS  not-accessible
    STATUS      current
    DESCRIPTION
       "Each conceptual row contains detailed statistics information
        about a member of a WLAN Gateway ISA Group.

        Entries in this table are created and removed automatically by the 
        system."
    INDEX { tmnxWlanGwGrpId,
            tmnxWlanGwIsaMemberId,
            tmnxWlanGwIsaMemberStatsType }
    ::= { tmnxWlanGwIsaMemberStatsTable 1 }

TmnxWlanGwIsaMemberStatsEntry ::= 
    SEQUENCE {
        tmnxWlanGwIsaMemberStatsType        Unsigned32,
        tmnxWlanGwIsaMemberStatsName        DisplayString,
        tmnxWlanGwIsaMemberStatsVal         Counter32,
        tmnxWlanGwIsaMemberStatsValHw       Counter32,
        tmnxWlanGwIsaMemberStatsValue       Counter64
    }

tmnxWlanGwIsaMemberStatsType OBJECT-TYPE
    SYNTAX      Unsigned32
    MAX-ACCESS  not-accessible
    STATUS      current
    DESCRIPTION
        "The value of tmnxWlanGwIsaMemberStatsType indicates
         the type of WLAN Gateway statistics contained in this conceptual row."
    ::= { tmnxWlanGwIsaMemberStatsEntry 1 }

tmnxWlanGwIsaMemberStatsName OBJECT-TYPE
    SYNTAX      DisplayString (SIZE (1..64))
    MAX-ACCESS  read-only
    STATUS      current
    DESCRIPTION 
       "The value of the object tmnxWlanGwIsaMemberStatsName indicates
        the human-readable identifier of the statistics 
        contained in this conceptual row."
    ::= { tmnxWlanGwIsaMemberStatsEntry 2 }

tmnxWlanGwIsaMemberStatsVal OBJECT-TYPE
    SYNTAX      Counter32
    MAX-ACCESS  read-only
    STATUS      current
    DESCRIPTION 
       "The value of the object tmnxWlanGwIsaMemberStatsVal indicates
        the lower 32-bits word of the statistics 
        contained in this conceptual row."
    ::= { tmnxWlanGwIsaMemberStatsEntry 3 }

tmnxWlanGwIsaMemberStatsValHw OBJECT-TYPE
    SYNTAX      Counter32
    MAX-ACCESS  read-only
    STATUS      current
    DESCRIPTION 
       "The value of the object tmnxWlanGwIsaMemberStatsValHw indicates
        the higher 32-bits word of the statistics 
        contained in this conceptual row."
    ::= { tmnxWlanGwIsaMemberStatsEntry 4 }

tmnxWlanGwIsaMemberStatsValue OBJECT-TYPE
    SYNTAX      Counter64
    MAX-ACCESS  read-only
    STATUS      current
    DESCRIPTION 
       "The value of the object tmnxWlanGwIsaMemberStatsValue indicates
        the value of the statistics contained in this conceptual row."
    ::= { tmnxWlanGwIsaMemberStatsEntry 5 }

-- --------------------------------------------------------
--      Soft GRE 
-- --------------------------------------------------------
--
--      Soft GRE Group Interface Table
--
--      Sparse augment of the TIMETRA-SERV-MIB::iesIfTable

tmnxWlanGwSoftGreIfTable   OBJECT-TYPE
    SYNTAX      SEQUENCE OF TmnxWlanGwSoftGreIfEntry
    MAX-ACCESS  not-accessible
    STATUS      current
    DESCRIPTION
       "The tmnxWlanGwSoftGreIfTable contains objects to configure 
        Soft GRE Group-Interfaces.
        
        Entries in this table are created and destroyed by the system.
        
        The system automatically creates an entry in this table for each
        entry in the TIMETRA-SERV-MIB::iesIfTable where the value of iesIfType
        is equal to 'group' and the value of iesIfGroupInterfaceType is equal to 'softGre'. 
        
        Deletion of such a row in the iesIfTable results in the same fate
        for the corresponding row in this table."
    ::= { tmnxWlanGwSoftGreObjs 1 }

tmnxWlanGwSoftGreIfEntry OBJECT-TYPE
    SYNTAX      TmnxWlanGwSoftGreIfEntry
    MAX-ACCESS  not-accessible
    STATUS      current
    DESCRIPTION
        "Each conceptual row contains Soft GRE specific information of a specific group interface."
    INDEX { svcId, iesIfIndex }
    ::= { tmnxWlanGwSoftGreIfTable 1 }

TmnxWlanGwSoftGreIfEntry ::=
    SEQUENCE {
        tmnxWlanGwSoftGreIfLastCh        TimeStamp,
        tmnxWlanGwSoftGreIfAdminState    TmnxAdminState,
        tmnxWlanGwSoftGreIfRouter        TmnxVRtrIDOrZero,
        tmnxWlanGwSoftGreIfGwAddrType    InetAddressType,
        tmnxWlanGwSoftGreIfGwAddr        InetAddress,
        tmnxWlanGwSoftGreIfGrpId         TmnxWlanGwIsaGrpIdOrZero,
        tmnxWlanGwSoftGreIfShapingType   INTEGER,
        tmnxWlanGwSoftGreIfShapeMultiUe  TruthValue,
        tmnxWlanGwSoftGreIfEQosPlcy      TPolicyID,
        tmnxWlanGwSoftGreIfESchedPlcy    TNamedItemOrEmpty,
        tmnxWlanGwSoftGreIfEAggRateLimit TPortSchedulerPIR,
        tmnxWlanGwSoftGreIfMobTrigger    BITS,
        tmnxWlanGwSoftGreIfMobHoldTime   Unsigned32,
        tmnxWlanGwSoftGreIfDefRetailSvc  TmnxServId,
        tmnxWlanGwSoftGreIfTcpMssAdjust  Unsigned32,
        tmnxWlanGwSoftGreIfEHoldTime     Unsigned32,
        tmnxWlanGwSoftGreIfNumSoftGreTu  Gauge32
    }

tmnxWlanGwSoftGreIfLastCh OBJECT-TYPE
    SYNTAX      TimeStamp
    MAX-ACCESS  read-only
    STATUS      current
    DESCRIPTION
        "The value of tmnxWlanGwSoftGreIfLastCh indicates the sysUpTime at
         the time of the most recent management-initiated change to this
         table row."
    ::= { tmnxWlanGwSoftGreIfEntry 1 }

tmnxWlanGwSoftGreIfAdminState OBJECT-TYPE
    SYNTAX      TmnxAdminState
    MAX-ACCESS  read-create
    STATUS      current
    DESCRIPTION
       "The value of tmnxWlanGwSoftGreIfAdminState specifies the
        administrative state of Soft GRE on this group interface."
    DEFVAL { outOfService }
    ::= { tmnxWlanGwSoftGreIfEntry 2 }

tmnxWlanGwSoftGreIfRouter OBJECT-TYPE
    SYNTAX      TmnxVRtrIDOrZero
    MAX-ACCESS  read-create
    STATUS      current
    DESCRIPTION
        "The value of tmnxWlanGwSoftGreIfRouter specifies 
         the identifier of the virtual router instance 
         where the tunneled User Equipment traffic is routed.
         
         The value zero specifies that the router instance corresponding
         to the service containing this interface is used." 
    DEFVAL { 0 }
    ::= { tmnxWlanGwSoftGreIfEntry 3 }
    
tmnxWlanGwSoftGreIfGwAddrType OBJECT-TYPE
    SYNTAX      InetAddressType
    MAX-ACCESS  read-create
    STATUS      current
    DESCRIPTION
        "The value of tmnxWlanGwSoftGreIfGwAddrType specifies the type of
         address stored in tmnxWlanGwSoftGreIfGwAddr."
    DEFVAL { unknown }
    ::= { tmnxWlanGwSoftGreIfEntry 4 }

tmnxWlanGwSoftGreIfGwAddr OBJECT-TYPE
    SYNTAX      InetAddress (SIZE(0|4|16))
    MAX-ACCESS  read-create
    STATUS      current
    DESCRIPTION
        "The value of tmnxWlanGwSoftGreIfGwAddr specifies the IP address of
         the WLAN Gateway GRE function of this system on this group interface."
    DEFVAL { ''H }  
    ::= { tmnxWlanGwSoftGreIfEntry 5 }

tmnxWlanGwSoftGreIfGrpId OBJECT-TYPE
    SYNTAX      TmnxWlanGwIsaGrpIdOrZero
    MAX-ACCESS  read-create
    STATUS      current
    DESCRIPTION
        "The value of tmnxWlanGwSoftGreIfGrpId specifies the identifier
         of the WLAN Gateway ISA group that terminates GRE for this group interface."
    DEFVAL { 0 }
    ::= { tmnxWlanGwSoftGreIfEntry 6 }
    
tmnxWlanGwSoftGreIfShapingType OBJECT-TYPE
    SYNTAX      INTEGER {
                    none      (0),
                    perTunnel (1),
                    perRetailer (2)
                }
    MAX-ACCESS  read-create
    STATUS      current
    DESCRIPTION
       "The value of tmnxWlanGwSoftGreIfShapingType specifies 
        the granularity of the egress shaping 
        for Soft GRE on this group interface.
        
        The value of this object can only be modified 
        while the value of tmnxWlanGwSoftGreIfAdminState 
        is equal to 'outOfService'.
        
        The value 'perTunnel' specifies that a separate shaper is applied
        to each Soft GRE tunnel; the value 'perRetailer' specifies that a separate
        shaper is applied to each retailer Mobile Network Operator's fraction of the
        Soft GRE tunnel payload."
    DEFVAL { none }
    ::= { tmnxWlanGwSoftGreIfEntry 7 }

tmnxWlanGwSoftGreIfShapeMultiUe OBJECT-TYPE
    SYNTAX      TruthValue
    MAX-ACCESS  read-create
    STATUS      current
    DESCRIPTION
       "The value of tmnxWlanGwSoftGreIfShapeMultiUe specifies 
        conditional egress shaping.
        
        If the value of tmnxWlanGwSoftGreIfShapeMultiUe is equal to 'true',
        egress shaping is only enabled for a Soft GRE tunnel while there are
        multiple UE (User Equipment) using it.
        
        If the value of tmnxWlanGwSoftGreIfShapeMultiUe is equal to 'false',
        egress shaping is always enabled for every Soft GRE tunnel, 
        also while there is only a single UE using it."
    DEFVAL { false }
    ::= { tmnxWlanGwSoftGreIfEntry 8 }

tmnxWlanGwSoftGreIfEQosPlcy OBJECT-TYPE
    SYNTAX      TPolicyID (1..65535)
    MAX-ACCESS  read-create
    STATUS      current
    DESCRIPTION
        "The value of tmnxWlanGwSoftGreIfEQosPlcy specifies the identifier
         of the egress QoS policy associated with each Soft GRE tunnel
         of this interface."
    DEFVAL { 1 }
    ::= { tmnxWlanGwSoftGreIfEntry 9 }

tmnxWlanGwSoftGreIfESchedPlcy OBJECT-TYPE
    SYNTAX      TNamedItemOrEmpty
    MAX-ACCESS  read-create
    STATUS      current
    DESCRIPTION
        "The value of tmnxWlanGwSoftGreIfESchedPlcy specifies the identifier
         of the egress scheduler policy associated with each Soft GRE tunnel
         of this interface."
    DEFVAL { "" }
    ::= { tmnxWlanGwSoftGreIfEntry 10 }
    
tmnxWlanGwSoftGreIfEAggRateLimit OBJECT-TYPE
    SYNTAX      TPortSchedulerPIR
    UNITS       "kbps"
    MAX-ACCESS  read-create
    STATUS      current
    DESCRIPTION
        "The value of tmnxWlanGwSoftGreIfEAggRateLimit specifies
         the aggregate rate limit of each shaper associated with this interface.
         
         The value minus one specifies that there is no limit configured."
    DEFVAL { -1 }
    ::= { tmnxWlanGwSoftGreIfEntry 11 }
    
tmnxWlanGwSoftGreIfMobTrigger OBJECT-TYPE
    SYNTAX      BITS {
                    data (0),
                    iapp (1)
                }
    MAX-ACCESS  read-create
    STATUS      current
    DESCRIPTION
       "The value of tmnxWlanGwSoftGreIfMobTrigger specifies 
        what is used as a trigger for mobility detection.
        
        The value 'data' specifies that data traffic be used as a trigger.
        
        The value 'iapp' specifies that Inter Access Point Protocol (IAPP)
        messages be used as a trigger"
    DEFVAL { '0'H }
    ::= { tmnxWlanGwSoftGreIfEntry 12 }

tmnxWlanGwSoftGreIfMobHoldTime OBJECT-TYPE
    SYNTAX      Unsigned32 (0..255)
    UNITS       "seconds"
    MAX-ACCESS  read-create
    STATUS      current
    DESCRIPTION
        "The value of tmnxWlanGwSoftGreIfMobHoldTime specifies
         the minimum time that a User Equipment will be held 
         associated with its current Access Point (AP)
         before being associated with a new AP.
         
         The hold time is used to prevent overwhelming the system
         with mobility triggers, by limiting the rate at which 
         a UE can move from one AP to another while the system 
         is very busy already."
    DEFVAL { 5 }
    ::= { tmnxWlanGwSoftGreIfEntry 13 }
    
tmnxWlanGwSoftGreIfDefRetailSvc OBJECT-TYPE
    SYNTAX      TmnxServId
    MAX-ACCESS  read-create
    STATUS      current
    DESCRIPTION
       "The value of tmnxWlanGwSoftGreIfDefRetailSvc specifies
        the identifier of the retail service to be used by default
        of a value in the retail service map of this interface.
        
        The value zero specifies that there is no default retail
        service configured."
    DEFVAL { 0 }
    ::= { tmnxWlanGwSoftGreIfEntry 14 }
    
tmnxWlanGwSoftGreIfTcpMssAdjust OBJECT-TYPE
    SYNTAX      Unsigned32 (0|160..10240)
    UNITS       "bytes"
    MAX-ACCESS  read-create
    STATUS      current
    DESCRIPTION
        "The value of tmnxWlanGwSoftGreIfTcpMssAdjust specifies 
         the value to put into the TCP Maximum Segment Size (MSS) option
         if not already present, or if the present value is higher.
         
         The value zero means that no MSS option adjustment is done."
    DEFVAL { 0 }
    ::= { tmnxWlanGwSoftGreIfEntry 15 }

tmnxWlanGwSoftGreIfEHoldTime OBJECT-TYPE
    SYNTAX      Unsigned32 (0..86400 | 'ffffffff'h)
    UNITS       "seconds"
    MAX-ACCESS  read-create
    STATUS      current
    DESCRIPTION
        "The value of tmnxWlanGwSoftGreIfEHoldTime specifies
         the minimum time that the egress QoS resources associated with 
         a Soft GRE tunnel (such as a shaper) are held after the last 
         User Equipment of the Soft GRE tunnel has disappeared.
         
         The value all ones specifies an infinite time.
         
         The value zero specifies that the resources are released immediately."
    DEFVAL { 0 }
    ::= { tmnxWlanGwSoftGreIfEntry 16 }
    
tmnxWlanGwSoftGreIfNumSoftGreTu OBJECT-TYPE
    SYNTAX      Gauge32
    MAX-ACCESS  read-only
    STATUS      current
    DESCRIPTION
        "The value of tmnxWlanGwSoftGreIfNumSoftGreTu indicates 
         the number of Soft GRE tunnels terminated on this interface."
    ::= { tmnxWlanGwSoftGreIfEntry 100 }
--
--      Soft GRE Tunnel Table
--

tmnxWlanGwSoftGreTuTable   OBJECT-TYPE
    SYNTAX      SEQUENCE OF TmnxWlanGwSoftGreTuEntry
    MAX-ACCESS  not-accessible
    STATUS      current
    DESCRIPTION
       "The tmnxWlanGwSoftGreTuTable contains information about
        Soft GRE tunnels terminated by this system."
    ::= { tmnxWlanGwSoftGreObjs 2 }

tmnxWlanGwSoftGreTuEntry   OBJECT-TYPE
    SYNTAX      TmnxWlanGwSoftGreTuEntry
    MAX-ACCESS  not-accessible
    STATUS      current
    DESCRIPTION
       "Each conceptual row represents a Soft GRE tunnel.

        Entries in this table are created and destroyed by the system."
    INDEX { vRtrID,
            tmnxWlanGwSoftGreTuRemoteAddrTyp,
            tmnxWlanGwSoftGreTuRemoteAddr,
            tmnxWlanGwSoftGreTuLocalAddrType,
            tmnxWlanGwSoftGreTuLocalAddr
          }
    ::= { tmnxWlanGwSoftGreTuTable 1 }

TmnxWlanGwSoftGreTuEntry ::= 
    SEQUENCE {
        tmnxWlanGwSoftGreTuRemoteAddrTyp InetAddressType,
        tmnxWlanGwSoftGreTuRemoteAddr    InetAddress,
        tmnxWlanGwSoftGreTuLocalAddrType InetAddressType,
        tmnxWlanGwSoftGreTuLocalAddr     InetAddress,
        tmnxWlanGwSoftGreTuEstabTime     DateAndTime,
        tmnxWlanGwSoftGreTuIsaGroup      TmnxWlanGwIsaGrpIdOrZero,
        tmnxWlanGwSoftGreTuIsaMember     Unsigned32,
        tmnxWlanGwSoftGreTuNumUe         Gauge32     
    }
        
tmnxWlanGwSoftGreTuRemoteAddrTyp OBJECT-TYPE
    SYNTAX      InetAddressType
    MAX-ACCESS  not-accessible
    STATUS      current
    DESCRIPTION 
        "The value of tmnxWlanGwSoftGreTuRemoteAddrTyp specifies
         the address type of tmnxWlanGwSoftGreTuRemoteAddr.
         
         The only values allowed are 'ipv4' and 'ipv6'."
    ::= { tmnxWlanGwSoftGreTuEntry 1 }

tmnxWlanGwSoftGreTuRemoteAddr OBJECT-TYPE
    SYNTAX      InetAddress (SIZE(4|16))
    MAX-ACCESS  not-accessible
    STATUS      current
    DESCRIPTION
        "The value of the object tmnxWlanGwSoftGreTuRemoteAddr specifies
         the IP address of the remote endpoint of this Soft GRE tunnel,
         that is the source IP address in the tunnel header of
         received packets."
    ::= { tmnxWlanGwSoftGreTuEntry 2 }

tmnxWlanGwSoftGreTuLocalAddrType OBJECT-TYPE
    SYNTAX      InetAddressType
    MAX-ACCESS  not-accessible
    STATUS      current
    DESCRIPTION 
        "The value of tmnxWlanGwSoftGreTuLocalAddrType specifies
         the address type of tmnxWlanGwSoftGreTuLocalAddr.
         
         The only values allowed are 'ipv4' and 'ipv6'."
    ::= { tmnxWlanGwSoftGreTuEntry 3 }

tmnxWlanGwSoftGreTuLocalAddr OBJECT-TYPE
    SYNTAX      InetAddress (SIZE(4|16))
    MAX-ACCESS  not-accessible
    STATUS      current
    DESCRIPTION
        "The value of the object tmnxWlanGwSoftGreTuLocalAddr specifies
         the IP address of the local endpoint of this Soft GRE tunnel,
         that is the destination IP address in the tunnel header of
         received packets.
         
         The value of this object is equal to the value
         of the tmnxWlanGwSoftGreIfGwAddr object in the conceptual row
         corresponding to the Soft GRE Group-Interface where this tunnel
         is terminated."
    ::= { tmnxWlanGwSoftGreTuEntry 4 }

tmnxWlanGwSoftGreTuEstabTime OBJECT-TYPE
    SYNTAX      DateAndTime (SIZE (11))
    MAX-ACCESS  read-only
    STATUS      current
    DESCRIPTION 
        "The value of the object tmnxWlanGwSoftGreTuEstabTime indicates
         the value of sysUpTime when this Soft GRE tunnel was established."
    ::= { tmnxWlanGwSoftGreTuEntry 5 }

tmnxWlanGwSoftGreTuIsaGroup OBJECT-TYPE
    SYNTAX      TmnxWlanGwIsaGrpIdOrZero
    MAX-ACCESS  read-only
    STATUS      current
    DESCRIPTION 
        "The value of the object tmnxWlanGwSoftGreTuIsaGroup indicates
         the identifier of the WLAN Gateway ISA group that processes
         this Soft GRE tunnel.
         
         The value of this object is equal to the value
         of the object tmnxWlanGwGrpId in the conceptual row that
         corresponds to the WLAN Gateway ISA group."
    ::= { tmnxWlanGwSoftGreTuEntry 6 }

tmnxWlanGwSoftGreTuIsaMember OBJECT-TYPE
    SYNTAX      Unsigned32
    MAX-ACCESS  read-only
    STATUS      current
    DESCRIPTION 
        "The value of the object tmnxWlanGwSoftGreTuIsaGroup indicates
         the identifier of the ISA Group member that processes
         this Soft GRE tunnel.
         
         The value of this object is equal to the value
         of the object tmnxWlanGwIsaMemberId in the
         conceptual row in the tmnxWlanGwIsaMemberTable
         that corresponds to thsi ISA Group member."
    ::= { tmnxWlanGwSoftGreTuEntry 7 }

tmnxWlanGwSoftGreTuNumUe OBJECT-TYPE
    SYNTAX      Gauge32
    MAX-ACCESS  read-only
    STATUS      current
    DESCRIPTION 
        "The value of the object tmnxWlanGwSoftGreTuNumUe indicates
         the number of User Equipment's connected to this system through
         this Soft GRE tunnel."
    ::= { tmnxWlanGwSoftGreTuEntry 8 }

--
--      Soft GRE Tunnel QoS Table
--

tmnxWlanGwTuQosTable   OBJECT-TYPE
    SYNTAX      SEQUENCE OF TmnxWlanGwTuQosEntry
    MAX-ACCESS  not-accessible
    STATUS      current
    DESCRIPTION
       "The tmnxWlanGwTuQosTable contains information about
        Soft GRE tunnels' Quality of Service (QoS) infrastructure.
        
        The QoS infrastructure of a Soft GRE tunnel consists of
        one or multiple Egress Encapsulation Groups."
    ::= { tmnxWlanGwSoftGreObjs 3 }

tmnxWlanGwTuQosEntry   OBJECT-TYPE
    SYNTAX      TmnxWlanGwTuQosEntry
    MAX-ACCESS  not-accessible
    STATUS      current
    DESCRIPTION
       "Each conceptual row represents information about a WLAN Gateway 
        tunnel-QoS-infrastructure.

        Entries in this table are created and destroyed by the system."
    INDEX { vRtrID,
            tmnxWlanGwSoftGreTuRemoteAddrTyp,
            tmnxWlanGwSoftGreTuRemoteAddr,
            tmnxWlanGwSoftGreTuLocalAddrType,
            tmnxWlanGwSoftGreTuLocalAddr,
            tmnxWlanGwTuQosRetailService
          }
    ::= { tmnxWlanGwTuQosTable 1 }

TmnxWlanGwTuQosEntry ::= 
    SEQUENCE {
        tmnxWlanGwTuQosRetailService     TmnxServId,
        tmnxWlanGwTuQosEegSvcId          TmnxServId,
        tmnxWlanGwTuQosEegPortId         TmnxPortID,
        tmnxWlanGwTuQosEegEncapValue     TmnxEncapVal,
        tmnxWlanGwTuQosEegName           TNamedItemOrEmpty,
        tmnxWlanGwTuQosEegMember         SvcISID,
        tmnxWlanGwTuQosState             TmnxWlanGwQoSOperState,     
        tmnxWlanGwTuQosNumUe             Gauge32,
        tmnxWlanGwTuQosRemainingHoldTime Gauge32     
    }
        
tmnxWlanGwTuQosRetailService OBJECT-TYPE
    SYNTAX      TmnxServId
    MAX-ACCESS  not-accessible
    STATUS      current
    DESCRIPTION     
        "The value of the object tmnxWlanGwTuQosRetailService indicates
         the identifier of the retail service.
         
         The value zero indicates that this tunnel has per-tunnel QoS."
    ::= { tmnxWlanGwTuQosEntry 1 }

tmnxWlanGwTuQosEegSvcId OBJECT-TYPE
    SYNTAX      TmnxServId
    MAX-ACCESS  read-only
    STATUS      current
    DESCRIPTION     
        "The value of the object tmnxWlanGwTuQosEegSvcId indicates
         the service identifier of the B-Component instance 
         of the Egress Encapsulation Group member of 
         this tunnel-QoS-infrastructure.
         
         The value zero indicates that there is no
         egress encapsulation group member."
    ::= { tmnxWlanGwTuQosEntry 2 }

tmnxWlanGwTuQosEegPortId OBJECT-TYPE
    SYNTAX      TmnxPortID
    MAX-ACCESS  read-only
    STATUS      current
    DESCRIPTION     
        "The value of the object tmnxWlanGwTuQosEegPortId indicates 
         the ID of the access port in the B-Component instance 
         of the Egress Encapsulation Group member of  
         this tunnel-QoS-infrastructure.
         
         The value zero indicates that there is no
         egress encapsulation group member."
    ::= { tmnxWlanGwTuQosEntry 3 }

tmnxWlanGwTuQosEegEncapValue OBJECT-TYPE
    SYNTAX      TmnxEncapVal
    MAX-ACCESS  read-only
    STATUS      current
    DESCRIPTION     
        "The value of the object tmnxWlanGwTuQosEegEncapValue indicates 
         the value of the label used to identify this SAP access port 
         in the B-Component instance of the Egress Encapsulation Group 
         member of this tunnel-QoS-infrastructure.
         
         The value zero indicates that there is no
         egress encapsulation group member."
    ::= { tmnxWlanGwTuQosEntry 4 }

tmnxWlanGwTuQosEegName OBJECT-TYPE
    SYNTAX      TNamedItemOrEmpty
    MAX-ACCESS  read-only
    STATUS      current
    DESCRIPTION     
        "The value of the object tmnxWlanGwTuQosEegName indicates 
         the name of the Egress Encapsulation Group of  
         this tunnel-QoS-infrastructure.
         
         An empty string indicates that there is no
         egress encapsulation group member."
    ::= { tmnxWlanGwTuQosEntry 5 }
    
tmnxWlanGwTuQosEegMember OBJECT-TYPE
    SYNTAX      SvcISID
    MAX-ACCESS  read-only
    STATUS      current
    DESCRIPTION
        "The value of tmnxWlanGwTuQosEegMember indicates 
         the identifier of the Egress Encapsulation Group 
         member of this tunnel-QoS-infrastructure.
         
         The value minus one indicates that there is no
         egress encapsulation group member." 
    ::= { tmnxWlanGwTuQosEntry 6 }

tmnxWlanGwTuQosState OBJECT-TYPE
    SYNTAX  TmnxWlanGwQoSOperState
    MAX-ACCESS  read-only
    STATUS      current
    DESCRIPTION
       "The value of tmnxWlanGwTuQosState indicates the
        operational state of this tunnel-QoS-infrastructure."
    ::= { tmnxWlanGwTuQosEntry 7 }

tmnxWlanGwTuQosNumUe OBJECT-TYPE
    SYNTAX      Gauge32
    MAX-ACCESS  read-only
    STATUS      current
    DESCRIPTION 
        "The value of the object tmnxWlanGwTuQosNumUe indicates
         the number of User Equipment's using this tunnel-QoS-infrastructure."
    ::= { tmnxWlanGwTuQosEntry 8 }

tmnxWlanGwTuQosRemainingHoldTime OBJECT-TYPE
    SYNTAX      Gauge32
    UNITS       "seconds"
    MAX-ACCESS  read-only
    STATUS      current
    DESCRIPTION 
        "The value of the object tmnxWlanGwTuQosRemainingHoldTime indicates
         the time remaining before this tunnel-QoS-infrastructure is released because
         there are no UE's using it.
         
         The value zero indicates that the hold timer is not running because there are still
         UE's using this tunnel-QoS-infrastructure.
         
         The value all ones indicates that this tunnel-QoS infrastructure is held infinitely."
    ::= { tmnxWlanGwTuQosEntry 9 }

--
--      Soft GRE Tunnel User Equipment Table
--

tmnxWlanGwSoftGreTuUeTable   OBJECT-TYPE
    SYNTAX      SEQUENCE OF TmnxWlanGwSoftGreTuUeEntry
    MAX-ACCESS  not-accessible
    STATUS      current
    DESCRIPTION
       "The tmnxWlanGwSoftGreTuUeTable contains the 
        WLAN Gateway User Equipment's (UE) connected to this system
        by means of Soft GRE tunnels, ordered by tunnel."
    ::= { tmnxWlanGwSoftGreObjs 4 }

tmnxWlanGwSoftGreTuUeEntry   OBJECT-TYPE
    SYNTAX      TmnxWlanGwSoftGreTuUeEntry
    MAX-ACCESS  not-accessible
    STATUS      current
    DESCRIPTION
       "Each conceptual row represents a WLAN Gateway User Equipment.

        Entries in this table are created and destroyed by the system."
    INDEX { vRtrID,
            tmnxWlanGwSoftGreTuRemoteAddrTyp,
            tmnxWlanGwSoftGreTuRemoteAddr,
            tmnxWlanGwSoftGreTuLocalAddrType,
            tmnxWlanGwSoftGreTuLocalAddr,
            tmnxWlanGwUeMacAddress
          }
    ::= { tmnxWlanGwSoftGreTuUeTable 1 }

TmnxWlanGwSoftGreTuUeEntry ::= 
    SEQUENCE {
        tmnxWlanGwSoftGreTuUeSsid        TNamedItemOrEmpty     
    }
        
tmnxWlanGwSoftGreTuUeSsid OBJECT-TYPE
    SYNTAX  TNamedItemOrEmpty
    MAX-ACCESS  read-only
    STATUS      current
    DESCRIPTION
       "The value of tmnxWlanGwUeSsid indicates 
        the Service Set ID (SSID) of this UE.
        
        This object refers to a conceptual row in the tmnxWlanGwSsidTable."
    ::= { tmnxWlanGwSoftGreTuUeEntry 1 }

--
--      The Group Interface Retail-Service Map Table
--

tmnxWlanGwIfRetailTable OBJECT-TYPE
    SYNTAX      SEQUENCE OF TmnxWlanGwIfRetailEntry
    MAX-ACCESS  not-accessible
    STATUS      current
    DESCRIPTION
       "The tmnxWlanGwIfRetailTable contains objects to configure
        the association between IEEE 802.1q VLAN tags and retail services
        for WLAN Gateway interfaces."
    ::= { tmnxWlanGwObjs 3 }

tmnxWlanGwIfRetailEntry OBJECT-TYPE
    SYNTAX      TmnxWlanGwIfRetailEntry
    MAX-ACCESS  not-accessible
    STATUS      current
    DESCRIPTION
        "Each conceptual row represents a range of VLAN Q-tags 
         on a particular interface, and its association with a Retail Service.
         
         WLAN Gateway traffic on this interface 
         tagged with a matching VLAN Q-tag is to be processed
         in the specified retailer service, unless a RADIUS server provided
         a retail service for the traffic from this User Equipment.

         Rows in this table can be created or deleted via SNMP operations.
         
         A row with the same values for svcId and iesIfIndex must exist
         in the tmnxWlanGwSoftGreIfTable."
    INDEX { svcId, iesIfIndex,
            tmnxWlanGwIfRetailTagStart,
            tmnxWlanGwIfRetailTagEnd
           }
    ::= { tmnxWlanGwIfRetailTable 1 }

TmnxWlanGwIfRetailEntry ::= 
    SEQUENCE {
        tmnxWlanGwIfRetailTagStart         QTagFullRange,
        tmnxWlanGwIfRetailTagEnd           QTagFullRange,
        tmnxWlanGwIfRetailRowStatus        RowStatus,
        tmnxWlanGwIfRetailLastCh           TimeStamp,
        tmnxWlanGwIfRetailService          TmnxServId
    }
tmnxWlanGwIfRetailTagStart OBJECT-TYPE
    SYNTAX      QTagFullRange
    MAX-ACCESS  not-accessible
    STATUS      current
    DESCRIPTION
        "The value of the object tmnxWlanGwIfRetailTagStart specifies
         the start VLAN tag of this range."
    ::= { tmnxWlanGwIfRetailEntry 1 }

tmnxWlanGwIfRetailTagEnd OBJECT-TYPE
    SYNTAX      QTagFullRange
    MAX-ACCESS  not-accessible
    STATUS      current
    DESCRIPTION
        "The value of the object tmnxWlanGwIfRetailTagEnd specifies
         the end VLAN tag of this range."
    ::= { tmnxWlanGwIfRetailEntry 2 }

tmnxWlanGwIfRetailRowStatus OBJECT-TYPE
    SYNTAX      RowStatus
    MAX-ACCESS  read-create
    STATUS      current
    DESCRIPTION
       "The value of tmnxWlanGwIfRetailRowStatus specifies 
        the row status of this row."
    ::= { tmnxWlanGwIfRetailEntry 3 }

tmnxWlanGwIfRetailLastCh OBJECT-TYPE
    SYNTAX      TimeStamp
    MAX-ACCESS  read-only
    STATUS      current
    DESCRIPTION
        "The value of tmnxWlanGwIfRetailLastCh indicates the sysUpTime at
         the time of the most recent management-initiated change to this
         table row."
    ::= { tmnxWlanGwIfRetailEntry 4 }

tmnxWlanGwIfRetailService OBJECT-TYPE
    SYNTAX      TmnxServId
    MAX-ACCESS  read-create
    STATUS      current
    DESCRIPTION
       "The value of tmnxWlanGwIfRetailService specifies 
        the identifier of the retail service associated with this range.
        
        A nonzero value for this object must be specified when a row is
        created."
    ::= { tmnxWlanGwIfRetailEntry 5 }

--
--      The WLAN Gateway User Equipment Table
--

tmnxWlanGwUeTable OBJECT-TYPE
    SYNTAX      SEQUENCE OF TmnxWlanGwUeEntry
    MAX-ACCESS  not-accessible
    STATUS      current
    DESCRIPTION
       "The tmnxWlanGwUeTable contains information about 
        WLAN Gateway User Equipment's (UE)."
    ::= { tmnxWlanGwObjs 4 }

tmnxWlanGwUeEntry OBJECT-TYPE
    SYNTAX      TmnxWlanGwUeEntry
    MAX-ACCESS  not-accessible
    STATUS      current
    DESCRIPTION
        "Each conceptual row represents information about
         a WLAN Gateway User Equipment.

         Entries in this table are created and destroyed automatically
         by the system."
    INDEX { tmnxWlanGwUeMacAddress }
    ::= { tmnxWlanGwUeTable 1 }

TmnxWlanGwUeEntry ::= 
    SEQUENCE {
        tmnxWlanGwUeMacAddress           MacAddress,
        tmnxWlanGwUeQTag                 QTagFullRangeOrNone,
        tmnxWlanGwUeMplsLabel            MplsLabel,
        tmnxWlanGwUeTuRouter             TmnxVRtrID,
        tmnxWlanGwUeTuAddrType           InetAddressType,
        tmnxWlanGwUeTuRemoteAddr         InetAddress,
        tmnxWlanGwUeTuLocalAddr          InetAddress,
        tmnxWlanGwUeTuQosRetailService   TmnxServId,
        tmnxWlanGwUeSsid                 TNamedItemOrEmpty,
        tmnxWlanGwUePrevApAddrType       InetAddressType,
        tmnxWlanGwUePrevApAddr           InetAddress,
        tmnxWlanGwUeLastMoveTime         DateAndTime,
        tmnxWlanGwUeImsi                 TmnxMobImsiStr
    }
    
tmnxWlanGwUeMacAddress OBJECT-TYPE
    SYNTAX      MacAddress
    MAX-ACCESS  not-accessible
    STATUS      current
    DESCRIPTION
        "The value of the object tmnxWlanGwUeMacAddress indicates
         the MAC address of this UE."
    ::= { tmnxWlanGwUeEntry 1 }

tmnxWlanGwUeQTag OBJECT-TYPE
    SYNTAX      QTagFullRangeOrNone
    MAX-ACCESS  read-only
    STATUS      current
    DESCRIPTION     
        "The value of the object tmnxWlanGwUeQTag indicates
         the VLAN Q-tag present in the traffic received from this UE.
         
         The value of this object can be used to identify the retailer
         service, by means of the tmnxWlanGwIfRetailTable.
         
         The value minus one indicates that the traffic received from this UE
         does not have a VLAN Q-tag."
    ::= { tmnxWlanGwUeEntry 3 }

tmnxWlanGwUeMplsLabel OBJECT-TYPE
    SYNTAX      MplsLabel
    MAX-ACCESS  read-only
    STATUS      current
    DESCRIPTION     
        "The value of the object tmnxWlanGwUeMplsLabel indicates
         the MPLS label present in the traffic received from this UE.
         
         The value zero indicates that the traffic received from this UE
         does not have an MPLS label."
    ::= { tmnxWlanGwUeEntry 4 }

tmnxWlanGwUeTuRouter OBJECT-TYPE
    SYNTAX      TmnxVRtrID
    MAX-ACCESS  read-only
    STATUS      current
    DESCRIPTION
        "The value of tmnxWlanGwUeTuRouter indicates 
         the identifier of the virtual router instance 
         where the tunneled User Equipment traffic is routed." 
    ::= { tmnxWlanGwUeEntry 5 }
    
tmnxWlanGwUeTuAddrType OBJECT-TYPE
    SYNTAX      InetAddressType
    MAX-ACCESS  read-only
    STATUS      current
    DESCRIPTION 
        "The value of tmnxWlanGwUeTuAddrType specifies
         the address type of tmnxWlanGwUeTuRemoteAddr 
         and tmnxWlanGwUeTuLocalAddr.
         
         The only values allowed are 'ipv4' and 'ipv6'."
    ::= { tmnxWlanGwUeEntry 6 }

tmnxWlanGwUeTuRemoteAddr OBJECT-TYPE
    SYNTAX      InetAddress (SIZE(4|16))
    MAX-ACCESS  read-only
    STATUS      current
    DESCRIPTION
        "The value of the object tmnxWlanGwUeTuRemoteAddr specifies
         the IP address of the remote endpoint of this UE's tunnel,
         that is the source IP address in the tunnel header of
         received packets."
    ::= { tmnxWlanGwUeEntry 7 }

tmnxWlanGwUeTuLocalAddr OBJECT-TYPE
    SYNTAX      InetAddress (SIZE(4|16))
    MAX-ACCESS  read-only
    STATUS      current
    DESCRIPTION
        "The value of the object tmnxWlanGwUeTuLocalAddr specifies
         the IP address of the local endpoint of this UE's tunnel,
         that is the destination IP address in the tunnel header of
         received packets."
    ::= { tmnxWlanGwUeEntry 8 }

tmnxWlanGwUeTuQosRetailService OBJECT-TYPE
    SYNTAX      TmnxServId
    MAX-ACCESS  read-only
    STATUS      current
    DESCRIPTION     
        "The value of the object tmnxWlanGwUeTuQosRetailService indicates
         the identifier of the retail service.
         
         The value zero indicates that this UE's tunnel has per-tunnel QoS."
    ::= { tmnxWlanGwUeEntry 9 }

tmnxWlanGwUeSsid OBJECT-TYPE
    SYNTAX      TNamedItemOrEmpty
    MAX-ACCESS  read-only
    STATUS      current
    DESCRIPTION 
       "The value of tmnxWlanGwUeSsid indicates 
        the Service Set ID (SSID) of this UE.
        
        This object refers to a conceptual row in the tmnxWlanGwSsidTable."
    ::= { tmnxWlanGwUeEntry 10 }
    
tmnxWlanGwUePrevApAddrType OBJECT-TYPE
    SYNTAX      InetAddressType
    MAX-ACCESS  read-only
    STATUS      current
    DESCRIPTION 
       "The value of tmnxWlanGwUePrevApAddrType indicates the
        address type of tmnxWlanGwUePrevApAddr."
    ::= { tmnxWlanGwUeEntry 11 }

tmnxWlanGwUePrevApAddr OBJECT-TYPE
    SYNTAX      InetAddress (SIZE(0|4|16))
    MAX-ACCESS  read-only
    STATUS      current
    DESCRIPTION 
       "The value of tmnxWlanGwUePrevApAddr indicates the IP
        address of the previous Access Point (AP) of this UE.
        
        Note that the address of the current AP of this UE is the
        value of the object tmnxWlanGwUeTuRemoteAddr."
    ::= { tmnxWlanGwUeEntry 12 }
    
tmnxWlanGwUeLastMoveTime OBJECT-TYPE
    SYNTAX      DateAndTime (SIZE (11))
    MAX-ACCESS  read-only
    STATUS      current
    DESCRIPTION
        "The value of tmnxWlanGwUeLastMoveTime indicates
         the time of the most recent Access Point move of this UE."
    ::= { tmnxWlanGwUeEntry 13 }

tmnxWlanGwUeImsi OBJECT-TYPE
    SYNTAX      TmnxMobImsiStr
    MAX-ACCESS  read-only
    STATUS      current
    DESCRIPTION
        "The value of tmnxWlanGwUeImsi indicates
         the IMSI (International Mobile Subscriber Identity) of this UE."
    ::= { tmnxWlanGwUeEntry 15 }
--
--      The WLAN Gateway Service Set ID (SSID) Table
--

tmnxWlanGwSsidTable OBJECT-TYPE
    SYNTAX      SEQUENCE OF TmnxWlanGwSsidEntry
    MAX-ACCESS  not-accessible
    STATUS      current
    DESCRIPTION
       "The tmnxWlanGwSsidTable contains information about 
        WLAN Gateway Service Set ID's (SSID) learned by this system."
    ::= { tmnxWlanGwObjs 5 }

tmnxWlanGwSsidEntry OBJECT-TYPE
    SYNTAX      TmnxWlanGwSsidEntry
    MAX-ACCESS  not-accessible
    STATUS      current
    DESCRIPTION
        "Each conceptual row represents information about
         a specific WLAN Gateway Service Set ID (SSID).

         Entries in this table are created and destroyed automatically
         by the system."
    INDEX { IMPLIED tmnxWlanGwSsid }
    ::= { tmnxWlanGwSsidTable 1 }

TmnxWlanGwSsidEntry ::= 
    SEQUENCE {
        tmnxWlanGwSsid                 TNamedItem,
        tmnxWlanGwSsidNumUe            Gauge32
    }
    
tmnxWlanGwSsid OBJECT-TYPE
    SYNTAX      TNamedItem
    MAX-ACCESS  not-accessible
    STATUS      current
    DESCRIPTION 
       "The value of tmnxWlanGwSsid indicates 
        a Service Set ID (SSID) learned by this system."
    ::= { tmnxWlanGwSsidEntry 1 }
    
tmnxWlanGwSsidNumUe OBJECT-TYPE
    SYNTAX      Gauge32
    MAX-ACCESS  read-only
    STATUS      current
    DESCRIPTION 
        "The value of the object tmnxWlanGwSsidNumUe indicates
         the number of User Equipment's connected to this system 
         using this SSID."
    ::= { tmnxWlanGwSsidEntry 2 }

-- --------------------------------------------------------
--      Mobile Gateway Profile 
-- --------------------------------------------------------
--
--      Mobile Gateway Profile Table
--
tmnxWlanGwMgwProfTable OBJECT-TYPE
    SYNTAX      SEQUENCE OF TmnxWlanGwMgwProfEntry
    MAX-ACCESS  not-accessible
    STATUS      current
    DESCRIPTION
        "The tmnxWlanGwMgwProfTable allows configuration of 
         how to communicate with a Mobile Gateway.
         
         A Mobile Gateway can be a Packet Data Network Gateway (PGW) or a
         Gateway GPRS Support Node (GGSN)."
    ::= { tmnxWlanGwMgwObjs 1 }

tmnxWlanGwMgwProfEntry OBJECT-TYPE
    SYNTAX      TmnxWlanGwMgwProfEntry
    MAX-ACCESS  not-accessible
    STATUS      current
    DESCRIPTION
        "Each entry represents the configuration
         for a specific Mobile Gateway Profile.
        
         Entries in this table can be created and deleted via SNMP SET
         operations to tmnxWlanGwMgwProfRowStatus."
    INDEX { IMPLIED tmnxWlanGwMgwProfName }
    ::= { tmnxWlanGwMgwProfTable 1 }

TmnxWlanGwMgwProfEntry ::=
    SEQUENCE {
        tmnxWlanGwMgwProfName            TNamedItem,
        tmnxWlanGwMgwProfRowStatus       RowStatus,
        tmnxWlanGwMgwProfLastChanged     TimeStamp,
        tmnxWlanGwMgwProfDescription     TItemDescription,
        tmnxWlanGwMgwProfMsgReTxTimeout  TmnxMobProfMsgReTxTimeout,
        tmnxWlanGwMgwProfMsgReTxRetryCnt TmnxMobProfMsgReTxRetryCount,
        tmnxWlanGwMgwProfKeepAlvTimeout  TmnxMobProfKeepAliveTimeout,
        tmnxWlanGwMgwProfKeepAlvRetryCnt TmnxMobProfKeepAliveRetryCount,
        tmnxWlanGwMgwProfKeepAlvResp     TmnxMobProfKeepAliveResponse,
        tmnxWlanGwMgwProfTtl             TmnxMobProfIpTtl,
        tmnxWlanGwMgwProfInterfaceType   INTEGER
    }

tmnxWlanGwMgwProfName OBJECT-TYPE
    SYNTAX      TNamedItem
    MAX-ACCESS  not-accessible
    STATUS      current
    DESCRIPTION
        "The value of tmnxWlanGwMgwProfName specifies
         the name that identifies this profile."
    ::= { tmnxWlanGwMgwProfEntry 1 }

tmnxWlanGwMgwProfRowStatus OBJECT-TYPE
    SYNTAX      RowStatus
    MAX-ACCESS  read-create
    STATUS      current
    DESCRIPTION
        "The value of tmnxWlanGwMgwProfRowStatus controls the creation and
         deletion of rows in the table."
    ::= { tmnxWlanGwMgwProfEntry 2 }

tmnxWlanGwMgwProfLastChanged OBJECT-TYPE
    SYNTAX      TimeStamp
    MAX-ACCESS  read-only
    STATUS      current
    DESCRIPTION
        "The value of tmnxWlanGwMgwProfLastChanged indicates the sysUpTime at
         the time of the most recent management-initiated change to this
         profile."
    ::= { tmnxWlanGwMgwProfEntry 3 }

tmnxWlanGwMgwProfDescription OBJECT-TYPE
    SYNTAX      TItemDescription
    MAX-ACCESS  read-create
    STATUS      current
    DESCRIPTION
        "The value of tmnxWlanGwMgwProfDescription specifies the user provided
         description of this profile."
    DEFVAL { "" }
    ::= { tmnxWlanGwMgwProfEntry 4 }

tmnxWlanGwMgwProfMsgReTxTimeout OBJECT-TYPE
    SYNTAX      TmnxMobProfMsgReTxTimeout
    UNITS       "seconds"
    MAX-ACCESS  read-create
    STATUS      current
    DESCRIPTION
        "The value of tmnxWlanGwMgwProfMsgReTxTimeout specifies, in seconds, the
         interval between retransmission of signalling request messages 
         towards the same peer Mobile Gateway."
    REFERENCE
       "3GPP TS 29.060, 
        section 7.6 Reliable Delivery of Signalling Messages."
    DEFVAL { 5 }
    ::= { tmnxWlanGwMgwProfEntry 5 }

tmnxWlanGwMgwProfMsgReTxRetryCnt OBJECT-TYPE
    SYNTAX      TmnxMobProfMsgReTxRetryCount
    MAX-ACCESS  read-create
    STATUS      current
    DESCRIPTION
        "The value of tmnxWlanGwMgwProfMsgReTxRetryCnt specifies the number of
         times a signalling request message is transmitted 
         towards the same peer."
    REFERENCE
       "3GPP TS 29.060, 
        section 7.6 Reliable Delivery of Signalling Messages."
    DEFVAL { 3 }
    ::= { tmnxWlanGwMgwProfEntry 6 }
    
tmnxWlanGwMgwProfKeepAlvTimeout OBJECT-TYPE
    SYNTAX      TmnxMobProfKeepAliveTimeout
    UNITS       "seconds"
    MAX-ACCESS  read-create
    STATUS      current
    DESCRIPTION
        "The value of tmnxWlanGwMgwProfKeepAlvTimeout specifies, in seconds, the
         interval between keep-alive Echo-Request messages towards the same peer.
         
         The value zero specifies that no Echo-Request messages be sent."
    REFERENCE
       "3GPP TS 29.060, 
        section 7.2.1 Echo Request."
    DEFVAL { 60 }
    ::= { tmnxWlanGwMgwProfEntry 7 }

tmnxWlanGwMgwProfKeepAlvRetryCnt OBJECT-TYPE
    SYNTAX      TmnxMobProfKeepAliveRetryCount
    MAX-ACCESS  read-create
    STATUS      current
    DESCRIPTION
        "The value of tmnxWlanGwMgwProfKeepAlvRetryCnt specifies the number of
         Echo-Request messages towards the same peer."
    REFERENCE
       "3GPP TS 29.060, 
        section 7.2.1 Echo Request."
    DEFVAL { 4 }
    ::= { tmnxWlanGwMgwProfEntry 8 }

tmnxWlanGwMgwProfKeepAlvResp OBJECT-TYPE
    SYNTAX      TmnxMobProfKeepAliveResponse
    UNITS       "seconds"
    MAX-ACCESS  read-create
    STATUS      current
    DESCRIPTION
        "The value of tmnxWlanGwMgwProfKeepAlvResp specifies, in seconds, the
         time between Echo-Request message retries towards the same peer."
    REFERENCE
       "3GPP TS 29.060, 
        section 7.2.1 Echo Request."
    DEFVAL { 5 }
    ::= { tmnxWlanGwMgwProfEntry 9 }

tmnxWlanGwMgwProfTtl OBJECT-TYPE
    SYNTAX      TmnxMobProfIpTtl
    UNITS       "hops"
    MAX-ACCESS  read-create
    STATUS      current
    DESCRIPTION
        "The value of tmnxWlanGwMgwProfTtl specifies
         the value to put in the IP header's TTL field for
         GTP (GPRS Tunnel Protocol) control messages."
    DEFVAL { 255 }
    ::= { tmnxWlanGwMgwProfEntry 10 }

tmnxWlanGwMgwProfInterfaceType OBJECT-TYPE
    SYNTAX      INTEGER {
                    gn                               (1),
                    s2a                              (2),
                    s2b                              (3) 
                }
    MAX-ACCESS  read-create
    STATUS      current
    DESCRIPTION
        "The value of tmnxWlanGwMgwProfInterfaceType specifies
         the interface type.
         
         The possible values are:
         'gn' for the Gn interface,
         's2a' for the S2a interface,
         's2b' for the S2b interface."
    DEFVAL { s2a }
    ::= { tmnxWlanGwMgwProfEntry 12 }
--
--      The MGW-Address-To-MGW-Profile map Table
--

tmnxWlanGwMgwAddrTable OBJECT-TYPE
    SYNTAX      SEQUENCE OF TmnxWlanGwMgwAddrEntry
    MAX-ACCESS  not-accessible
    STATUS      current
    DESCRIPTION
       "The tmnxWlanGwMgwAddrTable associates Mobile Gateways
        to Mobile Gateway Profiles."
    ::= { tmnxWlanGwMgwObjs 2 }

tmnxWlanGwMgwAddrEntry OBJECT-TYPE
    SYNTAX      TmnxWlanGwMgwAddrEntry
    MAX-ACCESS  not-accessible
    STATUS      current
    DESCRIPTION
        "Each conceptual row represents a prefix for 
         Mobile Gateway addresses, associating them 
         to a particular Mobile Gateway Profile.

         Entries in this table can be created or deleted via SNMP operations.
         
         A corresponding conceptual row in the tmnxNatVrtrTable must exist
         while creating a row in this table."
    INDEX { vRtrID,
            tmnxWlanGwMgwAddrType,
            tmnxWlanGwMgwAddr,
            tmnxWlanGwMgwAddrPrefixLen
           }
    ::= { tmnxWlanGwMgwAddrTable 1 }

TmnxWlanGwMgwAddrEntry ::= 
    SEQUENCE {
        tmnxWlanGwMgwAddrType            InetAddressType,
        tmnxWlanGwMgwAddr                InetAddress,
        tmnxWlanGwMgwAddrPrefixLen       InetAddressPrefixLength,
        tmnxWlanGwMgwAddrRowStatus       RowStatus,
        tmnxWlanGwMgwAddrLastMgmtChange  TimeStamp,
        tmnxWlanGwMgwAddrProfile         TNamedItem 
    }

tmnxWlanGwMgwAddrType OBJECT-TYPE
    SYNTAX      InetAddressType
    MAX-ACCESS  not-accessible
    STATUS      current
    DESCRIPTION 
        "The value of tmnxWlanGwMgwAddrType specifies
         the address type of tmnxWlanGwMgwAddr.
         
         The only value supported is 'ipv4'."
    ::= { tmnxWlanGwMgwAddrEntry 1 }

tmnxWlanGwMgwAddr OBJECT-TYPE
    SYNTAX      InetAddress (SIZE(4|16))
    MAX-ACCESS  not-accessible
    STATUS      current
    DESCRIPTION 
        "The value of tmnxWlanGwMgwAddrType specifies
         the IP address of the subnet.
         
         Only IPv4 addresses are supported."
    ::= { tmnxWlanGwMgwAddrEntry 2 }

tmnxWlanGwMgwAddrPrefixLen OBJECT-TYPE
    SYNTAX          InetAddressPrefixLength (0..32)
    MAX-ACCESS      not-accessible
    STATUS          current
    DESCRIPTION 
        "The value of tmnxWlanGwMgwAddrPrefixLen specifies
         the prefix length of the subnet."
    ::= { tmnxWlanGwMgwAddrEntry 3 }

tmnxWlanGwMgwAddrRowStatus OBJECT-TYPE
    SYNTAX      RowStatus
    MAX-ACCESS  read-create
    STATUS      current
    DESCRIPTION
       "The value of tmnxWlanGwMgwAddrRowStatus specifies 
        the row status of this row."
    ::= { tmnxWlanGwMgwAddrEntry 4 }

tmnxWlanGwMgwAddrLastMgmtChange OBJECT-TYPE
    SYNTAX          TimeStamp
    MAX-ACCESS      read-only
    STATUS          current
    DESCRIPTION
        "The value of tmnxWlanGwMgwAddrLastMgmtChange indicates the sysUpTime at
         the time of the most recent management-initiated change to this
         table row."
    ::= { tmnxWlanGwMgwAddrEntry 5 }

tmnxWlanGwMgwAddrProfile OBJECT-TYPE
    SYNTAX      TNamedItem
    MAX-ACCESS  read-create
    STATUS      current
    DESCRIPTION
       "The value of tmnxWlanGwMgwAddrProfile specifies the
        Mobile Gateway profile associated with this address prefix.
        
        This object refers to a row in the tmnxWlanGwMgwProfTable.
        
        A value for this object must be provided when the conceptual row
        is created."
    ::= { tmnxWlanGwMgwAddrEntry 6 }

--
--      The Mobile Gateway table
--

tmnxWlanGwMgwTable   OBJECT-TYPE
    SYNTAX      SEQUENCE OF TmnxWlanGwMgwEntry
    MAX-ACCESS  not-accessible
    STATUS      current
    DESCRIPTION
       "The tmnxWlanGwMgwTable contains information
        about Mobile Gateways connected to this system."
    ::= { tmnxWlanGwMgwObjs 3 }

tmnxWlanGwMgwEntry   OBJECT-TYPE
    SYNTAX      TmnxWlanGwMgwEntry
    MAX-ACCESS  not-accessible
    STATUS      current
    DESCRIPTION
        "Each conceptual row represents information about
         a particular Mobile Gateway connected to this system.

         Rows are created or removed automatically by the system."
    INDEX { vRtrID,
            tmnxWlanGwMgwRemoteAddrType,
            tmnxWlanGwMgwRemoteAddr,
            tmnxWlanGwMgwRemotePort
    }
    ::= { tmnxWlanGwMgwTable 1 }

TmnxWlanGwMgwEntry ::= 
    SEQUENCE {
        tmnxWlanGwMgwRemoteAddrType      InetAddressType,
        tmnxWlanGwMgwRemoteAddr          InetAddress,
        tmnxWlanGwMgwRemotePort          InetPortNumber,
        tmnxWlanGwMgwLocalAddrType       InetAddressType,
        tmnxWlanGwMgwLocalAddr           InetAddress,
        tmnxWlanGwMgwTime                DateAndTime,
        tmnxWlanGwMgwProfile             TNamedItemOrEmpty,
        tmnxWlanGwMgwControl             INTEGER,
        tmnxWlanGwMgwRestartCnt          Gauge32,
        tmnxWlanGwMgwState               TmnxMobPathMgmtState
    }

tmnxWlanGwMgwRemoteAddrType OBJECT-TYPE
    SYNTAX      InetAddressType
    MAX-ACCESS  not-accessible
    STATUS      current
    DESCRIPTION 
        "The value of tmnxWlanGwMgwRemoteAddrType indicates
         the address type of tmnxWlanGwMgwRemoteAddr.
         
         The only values allowed are 'ipv4' and 'ipv6'."
    ::= { tmnxWlanGwMgwEntry 1 }

tmnxWlanGwMgwRemoteAddr OBJECT-TYPE
    SYNTAX      InetAddress (SIZE(4|16))
    MAX-ACCESS  not-accessible
    STATUS      current
    DESCRIPTION
        "The value of the object tmnxWlanGwMgwRemoteAddr indicates
         the IP address of the Mobile Gateway,
         that is the source IP address in the tunnel header of
         received packets."
    ::= { tmnxWlanGwMgwEntry 2 }

tmnxWlanGwMgwRemotePort OBJECT-TYPE
    SYNTAX      InetPortNumber
    MAX-ACCESS  not-accessible
    STATUS      current
    DESCRIPTION 
        "The value of tmnxWlanGwMgwRemotePort indicates
         the remote port."
    ::= { tmnxWlanGwMgwEntry 3 }

tmnxWlanGwMgwLocalAddrType OBJECT-TYPE
    SYNTAX      InetAddressType
    MAX-ACCESS  read-only
    STATUS      current
    DESCRIPTION 
        "The value of tmnxWlanGwMgwRemoteAddrType specifies
         the address type of tmnxWlanGwMgwLocalAddr.
         
         The only values allowed are 'ipv4' and 'ipv6'."
    ::= { tmnxWlanGwMgwEntry 4 }

tmnxWlanGwMgwLocalAddr OBJECT-TYPE
    SYNTAX      InetAddress (SIZE(4|16))
    MAX-ACCESS  read-only
    STATUS      current
    DESCRIPTION
        "The value of the object tmnxWlanGwMgwLocalAddr indicates
         the IP address of this system,
         that is the destination IP address in the tunnel header of
         received packets."
    ::= { tmnxWlanGwMgwEntry 5 }

tmnxWlanGwMgwTime OBJECT-TYPE
    SYNTAX      DateAndTime (SIZE (11))
    MAX-ACCESS  read-only
    STATUS      current
    DESCRIPTION 
        "The value of the object tmnxWlanGwMgwTime indicates
         the value of sysUpTime when this conceptual row was created."
    ::= { tmnxWlanGwMgwEntry 6 }

tmnxWlanGwMgwProfile OBJECT-TYPE
    SYNTAX      TNamedItemOrEmpty
    MAX-ACCESS  read-only
    STATUS      current
    DESCRIPTION 
        "The value of the object tmnxWlanGwMgwProfile indicates
         the name of the profile used for the connection with this
         Mobile Gateway.
         
         A non-empty value of this object corresponds to a value of 
         the object tmnxWlanGwMgwProfName in the tmnxWlanGwMgwProfTable."
    ::= { tmnxWlanGwMgwEntry 7 }

tmnxWlanGwMgwControl   OBJECT-TYPE
    SYNTAX      INTEGER {
                    gtpv1C (1),
                    gtpv2C (2)
                }
    MAX-ACCESS  read-only
    STATUS      current
    DESCRIPTION
       "The value of tmnxWlanGwMgwControl indicates the
        control plane protocol used for the connection with this
        Mobile Gateway."
    ::= { tmnxWlanGwMgwEntry 8 }

tmnxWlanGwMgwRestartCnt   OBJECT-TYPE
    SYNTAX      Gauge32
    MAX-ACCESS  read-only
    STATUS      current
    DESCRIPTION
       "The value of tmnxWlanGwMgwRestartCnt indicates the
        number of times this Mobile Gateway restarted.
        
        This value is learned by means of the connection
        with this Mobile Gateway."
    ::= { tmnxWlanGwMgwEntry 9 }

tmnxWlanGwMgwState   OBJECT-TYPE
    SYNTAX      TmnxMobPathMgmtState
    MAX-ACCESS  read-only
    STATUS      current
    DESCRIPTION
       "The value of tmnxWlanGwMgwState indicates the
        state of the connection with this
        Mobile Gateway."
    ::= { tmnxWlanGwMgwEntry 10 }

--
--      The Mobile Gateway Statistics Table
--


tmnxWlanMgwStatsTable   OBJECT-TYPE
    SYNTAX      SEQUENCE OF TmnxWlanMgwStatsEntry
    MAX-ACCESS  not-accessible
    STATUS      current
    DESCRIPTION
       "The tmnxWlanMgwStatsTable contains detailed statistics information 
        about the Mobile Gateways connected to this system.
        
        The typical usage of this table is to fill in the part of the index
        that identifies a Mobile Gateway, and perform a partial walk
        to get all the statistics applicable to that Mobile Gateway."
    ::= { tmnxWlanGwMgwObjs 4 }

tmnxWlanMgwStatsEntry   OBJECT-TYPE
    SYNTAX      TmnxWlanMgwStatsEntry
    MAX-ACCESS  not-accessible
    STATUS      current
    DESCRIPTION
       "Each conceptual row contains detailed statistics information
        about a Mobile Gateway.

        Entries in this table are created and removed automatically by the 
        system."
    INDEX { vRtrID,
            tmnxWlanGwMgwRemoteAddrType,
            tmnxWlanGwMgwRemoteAddr,
            tmnxWlanGwMgwRemotePort,
            tmnxWlanMgwStatsId }
    ::= { tmnxWlanMgwStatsTable 1 }

TmnxWlanMgwStatsEntry ::= 
    SEQUENCE {
        tmnxWlanMgwStatsId               Unsigned32,
        tmnxWlanMgwStatsName             DisplayString,
        tmnxWlanMgwStatsVal              Counter64,
        tmnxWlanMgwStatsValLw            Counter32,
        tmnxWlanMgwStatsValHw            Counter32
    }

tmnxWlanMgwStatsId OBJECT-TYPE
    SYNTAX      Unsigned32
    MAX-ACCESS  not-accessible
    STATUS      current
    DESCRIPTION
        "The value of tmnxWlanMgwStatsId indicates
         the identifier of the WLAN Gateway statistics 
         contained in this conceptual row.
         
         It is a meaningless number generated by this system."
    ::= { tmnxWlanMgwStatsEntry 1 }

tmnxWlanMgwStatsName OBJECT-TYPE
    SYNTAX      DisplayString (SIZE (1..64))
    MAX-ACCESS  read-only
    STATUS      current
    DESCRIPTION 
       "The value of the object tmnxWlanMgwStatsName indicates
        the human-readable identifier of the statistics 
        contained in this conceptual row."
    ::= { tmnxWlanMgwStatsEntry 2 }

tmnxWlanMgwStatsVal OBJECT-TYPE
    SYNTAX      Counter64
    MAX-ACCESS  read-only
    STATUS      current
    DESCRIPTION 
       "The value of the object tmnxWlanMgwStatsVal indicates
        the value of the statistics contained in this conceptual row."
    ::= { tmnxWlanMgwStatsEntry 3 }

tmnxWlanMgwStatsValLw OBJECT-TYPE
    SYNTAX      Counter32
    MAX-ACCESS  read-only
    STATUS      current
    DESCRIPTION 
       "The value of the object tmnxWlanMgwStatsValLw indicates
        the lower 32 bits of the statistics contained in this conceptual row."
    ::= { tmnxWlanMgwStatsEntry 4 }

tmnxWlanMgwStatsValHw OBJECT-TYPE
    SYNTAX      Counter32
    MAX-ACCESS  read-only
    STATUS      current
    DESCRIPTION 
       "The value of the object tmnxWlanMgwStatsValHw indicates
        the higher 32 bits of the statistics contained in this conceptual row."
    ::= { tmnxWlanMgwStatsEntry 5 }

--
--      The GTP Session table
--

tmnxWlanGwGtpSeTable   OBJECT-TYPE
    SYNTAX      SEQUENCE OF TmnxWlanGwGtpSeEntry
    MAX-ACCESS  not-accessible
    STATUS      current
    DESCRIPTION
       "The tmnxWlanGwGtpSeTable contains information
        about GTP (GPRS Tunnel Protocol) sessions."
    ::= { tmnxWlanGwMgwObjs 5 }

tmnxWlanGwGtpSeEntry   OBJECT-TYPE
    SYNTAX      TmnxWlanGwGtpSeEntry
    MAX-ACCESS  not-accessible
    STATUS      current
    DESCRIPTION
        "Each conceptual row represents information about
         a particular GTP session.

         Rows are created or removed automatically by the system."
    INDEX { tmnxWlanGwGtpSeImsi,
            tmnxWlanGwGtpSeApn
    }
    ::= { tmnxWlanGwGtpSeTable 1 }

TmnxWlanGwGtpSeEntry ::= 
    SEQUENCE {
        tmnxWlanGwGtpSeImsi            TmnxMobImsiStr,
        tmnxWlanGwGtpSeApn             TmnxMobApn,
        tmnxWlanGwGtpSeMgwRouter       TmnxVRtrIDOrZero,
        tmnxWlanGwGtpSeMgwAddrType     InetAddressType,
        tmnxWlanGwGtpSeMgwAddr         InetAddress,
        tmnxWlanGwGtpSeRemoteCtrlTeid  Unsigned32,
        tmnxWlanGwGtpSeLocalCtrlTeid   Unsigned32
    }

tmnxWlanGwGtpSeImsi OBJECT-TYPE
    SYNTAX      TmnxMobImsiStr (SIZE(9..15))
    MAX-ACCESS  not-accessible
    STATUS      current
    DESCRIPTION 
        "The value of tmnxWlanGwGtpSeImsi indicates
         the IMSI."
    ::= { tmnxWlanGwGtpSeEntry 1 }

tmnxWlanGwGtpSeApn OBJECT-TYPE
    SYNTAX      TmnxMobApn
    MAX-ACCESS  not-accessible
    STATUS      current
    DESCRIPTION
        "The value of the object tmnxWlanGwGtpSeApn indicates
         the APN (Access Point Name)."
    REFERENCE
       "3GPP TS 23.003 Numbering, addressing and identification, 
        section 9 Definition of Access Point Name"
    ::= { tmnxWlanGwGtpSeEntry 2 }

tmnxWlanGwGtpSeMgwRouter OBJECT-TYPE
    SYNTAX      TmnxVRtrIDOrZero
    MAX-ACCESS  read-only
    STATUS      current
    DESCRIPTION
        "The value of tmnxWlanGwGtpSeMgwRouter indicates 
         the identifier of the virtual router instance 
         where the GTP tunnel is terminated." 
    ::= { tmnxWlanGwGtpSeEntry 3 }
    
tmnxWlanGwGtpSeMgwAddrType OBJECT-TYPE
    SYNTAX      InetAddressType
    MAX-ACCESS  read-only
    STATUS      current
    DESCRIPTION 
        "The value of tmnxWlanGwMgwRemoteAddrType indicates
         the address type of tmnxWlanGwMgwRemoteAddr."
    ::= { tmnxWlanGwGtpSeEntry 4 }

tmnxWlanGwGtpSeMgwAddr OBJECT-TYPE
    SYNTAX      InetAddress (SIZE(4|16))
    MAX-ACCESS  read-only
    STATUS      current
    DESCRIPTION
        "The value of the object tmnxWlanGwGtpSeMgwAddr indicates
         the IP address of the Mobile Gateway,
         that is the source IP address in the tunnel header of
         received packets."
    ::= { tmnxWlanGwGtpSeEntry 5 }

tmnxWlanGwGtpSeRemoteCtrlTeid OBJECT-TYPE
    SYNTAX      Unsigned32
    MAX-ACCESS  read-only
    STATUS      current
    DESCRIPTION
        "The value of tmnxWlanGwGtpSeRemoteCtrlTeid indicates 
         the remote control plane Tunnel Endpoint Identifier (TEID)." 
    ::= { tmnxWlanGwGtpSeEntry 6 }
    
tmnxWlanGwGtpSeLocalCtrlTeid OBJECT-TYPE
    SYNTAX      Unsigned32
    MAX-ACCESS  read-only
    STATUS      current
    DESCRIPTION
        "The value of tmnxWlanGwGtpSeLocalCtrlTeid indicates 
         the local control plane Tunnel Endpoint Identifier (TEID)." 
    ::= { tmnxWlanGwGtpSeEntry 7 }

--
--      The Bearer Context table
--

tmnxWlanGwBcTable   OBJECT-TYPE
    SYNTAX      SEQUENCE OF TmnxWlanGwBcEntry
    MAX-ACCESS  not-accessible
    STATUS      current
    DESCRIPTION
       "The tmnxWlanGwBcTable contains information
        about GTP (GPRS Tunnel Protocol) bearers."
    ::= { tmnxWlanGwMgwObjs 6 }

tmnxWlanGwBcEntry   OBJECT-TYPE
    SYNTAX      TmnxWlanGwBcEntry
    MAX-ACCESS  not-accessible
    STATUS      current
    DESCRIPTION
        "Each conceptual row represents information about
         a particular bearer context.

         Rows are created or removed automatically by the system."
    INDEX { tmnxWlanGwGtpSeImsi,
            tmnxWlanGwGtpSeApn,
            tmnxWlanGwBcId
    }
    ::= { tmnxWlanGwBcTable 1 }

TmnxWlanGwBcEntry ::= 
    SEQUENCE {
        tmnxWlanGwBcId          TmnxMobBearerId,
        tmnxWlanGwBcRemoteTeid  Unsigned32,
        tmnxWlanGwBcLocalTeid   Unsigned32
    }

tmnxWlanGwBcId OBJECT-TYPE
    SYNTAX      TmnxMobBearerId
    MAX-ACCESS  not-accessible
    STATUS      current
    DESCRIPTION 
        "The value of tmnxWlanGwBcId indicates
         the identifier of this bearer context."
    ::= { tmnxWlanGwBcEntry 1 }

tmnxWlanGwBcRemoteTeid OBJECT-TYPE
    SYNTAX      Unsigned32
    MAX-ACCESS  read-only
    STATUS      current
    DESCRIPTION
        "The value of tmnxWlanGwBcRemoteTeid indicates 
         the remote Tunnel Endpoint Identifier (TEID)." 
    ::= { tmnxWlanGwBcEntry 2 }
    
tmnxWlanGwBcLocalTeid OBJECT-TYPE
    SYNTAX      Unsigned32
    MAX-ACCESS  read-only
    STATUS      current
    DESCRIPTION
        "The value of tmnxWlanGwBcLocalTeid indicates 
         the local Tunnel Endpoint Identifier (TEID)." 
    ::= { tmnxWlanGwBcEntry 3 }

--
--      The Mobile Gateway Cache table
--

tmnxWlanGwMgwCacheTable   OBJECT-TYPE
    SYNTAX      SEQUENCE OF TmnxWlanGwMgwCacheEntry
    MAX-ACCESS  not-accessible
    STATUS      current
    DESCRIPTION
       "The tmnxWlanGwMgwCacheTable contains information
        about the Mobile Gateways DNS cache.
        
        When a DNS request is done to find a Mobile Gateway
        for a particular APN, the result is cached."
    ::= { tmnxWlanGwMgwObjs 7 }

tmnxWlanGwMgwCacheEntry   OBJECT-TYPE
    SYNTAX      TmnxWlanGwMgwCacheEntry
    MAX-ACCESS  not-accessible
    STATUS      current
    DESCRIPTION
        "Each conceptual row represents information about
         a particular Mobile Gateway cache instance.
         
         Each conceptual row associates an APN in a router instance
         with a Mobile Gateway.

         Rows are created or removed automatically by the system."
    INDEX { vRtrID,
            tmnxWlanGwMgwCacheApn,
            tmnxWlanGwMgwCacheAddrType,
            tmnxWlanGwMgwCacheAddr
    }
    ::= { tmnxWlanGwMgwCacheTable 1 }

TmnxWlanGwMgwCacheEntry ::= 
    SEQUENCE {
        tmnxWlanGwMgwCacheApn          TmnxMobApn,
        tmnxWlanGwMgwCacheAddrType     InetAddressType,
        tmnxWlanGwMgwCacheAddr         InetAddress,
        tmnxWlanGwMgwCacheTtl          Unsigned32
    }

tmnxWlanGwMgwCacheApn OBJECT-TYPE
    SYNTAX      TmnxMobApn
    MAX-ACCESS  not-accessible
    STATUS      current
    DESCRIPTION
        "The value of the object tmnxWlanGwMgwCacheApn indicates
         the APN (Access Point Name) of this DNS cache entry."
    REFERENCE
       "3GPP TS 23.003 Numbering, addressing and identification, 
        section 9 Definition of Access Point Name"
    ::= { tmnxWlanGwMgwCacheEntry 1 }

tmnxWlanGwMgwCacheAddrType OBJECT-TYPE
    SYNTAX      InetAddressType
    MAX-ACCESS  not-accessible
    STATUS      current
    DESCRIPTION 
        "The value of tmnxWlanGwMgwRemoteAddrType indicates
         the address type of tmnxWlanGwMgwRemoteAddr.
         
         The only values allowed are 'ipv4' and 'ipv6'."
    ::= { tmnxWlanGwMgwCacheEntry 2 }

tmnxWlanGwMgwCacheAddr OBJECT-TYPE
    SYNTAX      InetAddress (SIZE(4|16))
    MAX-ACCESS  not-accessible
    STATUS      current
    DESCRIPTION
        "The value of the object tmnxWlanGwMgwCacheAddr indicates
         the IP address of the Mobile Gateway."
    ::= { tmnxWlanGwMgwCacheEntry 3 }

tmnxWlanGwMgwCacheTtl OBJECT-TYPE    
    SYNTAX          Unsigned32
    UNITS           "seconds"
    MAX-ACCESS      read-only
    STATUS          current
    DESCRIPTION
        "The value of tmnxWlanGwMgwCacheTtl indicates
         the period of time left for this cache entry."
    ::= { tmnxWlanGwMgwCacheEntry 4 }

--
--      The WLAN Gateway router configuration table
-- 

tmnxWlanGwTable OBJECT-TYPE
    SYNTAX      SEQUENCE OF TmnxWlanGwEntry
    MAX-ACCESS  not-accessible
    STATUS      current
    DESCRIPTION
        "The tmnxWlanGwTable allows configuration of 
         WLAN Gateway functions in a virtual router instance."
    ::= { tmnxWlanGwObjs 8 }

tmnxWlanGwEntry OBJECT-TYPE
    SYNTAX      TmnxWlanGwEntry
    MAX-ACCESS  not-accessible
    STATUS      current
    DESCRIPTION
        "Each entry represents the configuration for 
         WLAN Gateway functions in a particular virtual router instance.
         
         Entries in this table can be created and deleted via SNMP SET
         operations to tmnxWlanGwRowStatus.
         
         A corresponding row in the TIMETRA-VRTR-MIB::vRtrConfTable must exist
         in order to create a row in this table."
    INDEX { vRtrID }
    ::= { tmnxWlanGwTable 1 }

TmnxWlanGwEntry ::=
    SEQUENCE {
        tmnxWlanGwRowStatus              RowStatus,
        tmnxWlanGwLastCh                 TimeStamp,
        tmnxWlanGwApn                    TmnxMobApnOrZero
    }

tmnxWlanGwRowStatus OBJECT-TYPE
    SYNTAX      RowStatus
    MAX-ACCESS  read-create
    STATUS      current
    DESCRIPTION
        "The value of tmnxWlanGwRowStatus controls the creation and
         deletion of rows in the table."
    ::= { tmnxWlanGwEntry 1 }

tmnxWlanGwLastCh OBJECT-TYPE
    SYNTAX      TimeStamp
    MAX-ACCESS  read-only
    STATUS      current
    DESCRIPTION
        "The value of tmnxWlanGwLastCh indicates the sysUpTime at
         the time of the most recent management-initiated change to this
         conceptual row."
    ::= { tmnxWlanGwEntry 2 }

tmnxWlanGwApn OBJECT-TYPE
    SYNTAX      TmnxMobApnOrZero
    MAX-ACCESS  read-create
    STATUS      current
    DESCRIPTION
        "The value of tmnxWlanGwApn specifies
         the Network Identifier part of the Access Point Name (APN) 
         to be used for UE in this virtual router instance 
         if the APN cannot be determined by other means."
    REFERENCE
       "3GPP TS 23.003, 
        section 9.1.1 Format of APN Network Identifier"
    DEFVAL { "" }
    ::= { tmnxWlanGwEntry 3 }

--
--      The GTP Statistics Table
--


tmnxWlanGwGtpStatsTable   OBJECT-TYPE
    SYNTAX      SEQUENCE OF TmnxWlanGwGtpStatsEntry
    MAX-ACCESS  not-accessible
    STATUS      current
    DESCRIPTION
       "The tmnxWlanGwGtpStatsTable contains detailed statistics information 
        about the GTP protocol in this system.
        
        The typical usage of this table is to perform a walk
        to get all the statistics."
    ::= { tmnxWlanGwMgwObjs 8 }

tmnxWlanGwGtpStatsEntry   OBJECT-TYPE
    SYNTAX      TmnxWlanGwGtpStatsEntry
    MAX-ACCESS  not-accessible
    STATUS      current
    DESCRIPTION
       "Each conceptual row contains detailed information
        about a GTP statistic.

        Entries in this table are created and removed automatically by the 
        system."
    INDEX { tmnxWlanGwGtpStatsId }
    ::= { tmnxWlanGwGtpStatsTable 1 }

TmnxWlanGwGtpStatsEntry ::= 
    SEQUENCE {
        tmnxWlanGwGtpStatsId             Unsigned32,
        tmnxWlanGwGtpStatsName           DisplayString,
        tmnxWlanGwGtpStatsVal            Counter64,
        tmnxWlanGwGtpStatsValLw          Counter32,
        tmnxWlanGwGtpStatsValHw          Counter32
    }

tmnxWlanGwGtpStatsId OBJECT-TYPE
    SYNTAX      Unsigned32
    MAX-ACCESS  not-accessible
    STATUS      current
    DESCRIPTION
        "The value of tmnxWlanGwGtpStatsId indicates
         the identifier of the GTP statistics 
         contained in this conceptual row.
         
         It is a meaningless number generated by this system."
    ::= { tmnxWlanGwGtpStatsEntry 1 }

tmnxWlanGwGtpStatsName OBJECT-TYPE
    SYNTAX      DisplayString (SIZE (1..56))
    MAX-ACCESS  read-only
    STATUS      current
    DESCRIPTION 
       "The value of the object tmnxWlanGwGtpStatsName indicates
        the human-readable identifier of the statistics 
        contained in this conceptual row."
    ::= { tmnxWlanGwGtpStatsEntry 2 }

tmnxWlanGwGtpStatsVal OBJECT-TYPE
    SYNTAX      Counter64
    MAX-ACCESS  read-only
    STATUS      current
    DESCRIPTION 
       "The value of the object tmnxWlanGwGtpStatsVal indicates
        the value of the statistics contained in this conceptual row."
    ::= { tmnxWlanGwGtpStatsEntry 3 }

tmnxWlanGwGtpStatsValLw OBJECT-TYPE
    SYNTAX      Counter32
    MAX-ACCESS  read-only
    STATUS      current
    DESCRIPTION 
       "The value of the object tmnxWlanGwGtpStatsValLw indicates
        the lower 32 bits of the statistics contained in this conceptual row."
    ::= { tmnxWlanGwGtpStatsEntry 4 }

tmnxWlanGwGtpStatsValHw OBJECT-TYPE
    SYNTAX      Counter32
    MAX-ACCESS  read-only
    STATUS      current
    DESCRIPTION 
       "The value of the object tmnxWlanGwGtpStatsValHw indicates
        the higher 32 bits of the statistics contained in this conceptual row."
    ::= { tmnxWlanGwGtpStatsEntry 5 }

-- --------------------------------------------------------
-- WLAN Gateway scalar objects
-- --------------------------------------------------------

--
-- System configuration objects
--
tmnxWlanGwSysCfgServingNwMcc  OBJECT-TYPE
    SYNTAX      TmnxMobMccOrEmpty
    MAX-ACCESS  read-write
    STATUS      current
    DESCRIPTION
        "The value of tmnxWlanGwSysCfgServingNwMcc specifies the Mobile
         Country Code (MCC) portion of the Serving Network."
    DEFVAL { ''H }    
    ::= { tmnxWlanGwSysCfgObjs 1 }

tmnxWlanGwSysCfgServingNwMnc  OBJECT-TYPE
    SYNTAX      TmnxMobMncOrEmpty
    MAX-ACCESS  read-write
    STATUS      current
    DESCRIPTION
        "The value of tmnxWlanGwSysCfgServingNwMnc specifies the Mobile
         Network Code (MNC) portion of the Serving Network."
    DEFVAL { ''H }
    ::= { tmnxWlanGwSysCfgObjs 2 }

--
-- Read-only objects
--
tmnxWlanGwGrpTableLastCh OBJECT-TYPE
    SYNTAX      TimeStamp
    MAX-ACCESS  read-only
    STATUS      current
    DESCRIPTION
        "The value of the object tmnxWlanGwGrpTableLastCh indicates
         the value of sysUpTime at the time of the last modification of
         an entry in the tmnxWlanGwGrpTable."
    ::= { tmnxWlanGwObjs 100 }

tmnxWlanGwIomTableLastCh OBJECT-TYPE
    SYNTAX      TimeStamp
    MAX-ACCESS  read-only
    STATUS      current
    DESCRIPTION
        "The value of the object tmnxWlanGwIomTableLastCh indicates
         the value of sysUpTime at the time of the last modification of
         an entry in the tmnxWlanGwIomTable."
    ::= { tmnxWlanGwObjs 101 }
    
tmnxWlanGwSoftGreIfTableLastCh OBJECT-TYPE
    SYNTAX      TimeStamp
    MAX-ACCESS  read-only
    STATUS      current
    DESCRIPTION
        "The value of the object tmnxWlanGwSoftGreIfTableLastCh indicates
         the value of sysUpTime at the time of the last modification of
         an entry in the tmnxWlanGwSoftGreIfTable."
    ::= { tmnxWlanGwObjs 102 }

tmnxWlanGwIfRetailTableLastCh OBJECT-TYPE
    SYNTAX      TimeStamp
    MAX-ACCESS  read-only
    STATUS      current
    DESCRIPTION
        "The value of the object tmnxWlanGwIfRetailTableLastCh indicates
         the value of sysUpTime at the time of the last modification of
         an entry in the tmnxWlanGwIfRetailTable."
    ::= { tmnxWlanGwObjs 103 }

tmnxWlanGwMgwProfTableLastCh OBJECT-TYPE
    SYNTAX      TimeStamp
    MAX-ACCESS  read-only
    STATUS      current
    DESCRIPTION
        "The value of the object tmnxWlanGwMgwProfTableLastCh indicates
         the value of sysUpTime at the time of the last modification of
         an entry in the tmnxWlanGwMgwProfTable."
    ::= { tmnxWlanGwObjs 104 }

tmnxWlanGwMgwAddrTableLastCh OBJECT-TYPE
    SYNTAX      TimeStamp
    MAX-ACCESS  read-only
    STATUS      current
    DESCRIPTION
        "The value of the object tmnxWlanGwMgwAddrTableLastCh indicates
         the value of sysUpTime at the time of the last modification of
         an entry in the tmnxWlanGwMgwAddrTable."
    ::= { tmnxWlanGwObjs 105 }

tmnxWlanGwTableLastCh OBJECT-TYPE
    SYNTAX      TimeStamp
    MAX-ACCESS  read-only
    STATUS      current
    DESCRIPTION
        "The value of the object tmnxWlanGwTableLastCh indicates
         the value of sysUpTime at the time of the last modification of
         an entry in the tmnxWlanGwTable."
    ::= { tmnxWlanGwObjs 106 }

tmnxWlanGwResrcProblem OBJECT-TYPE
    SYNTAX      TruthValue
    MAX-ACCESS  read-only
    STATUS      current
    DESCRIPTION
        "The value of the object tmnxWlanGwResrcProblem indicates
         if there is a resource problem detected while attempting
         to activate some part of the WLAN Gateway configuration of this system."
    ::= { tmnxWlanGwObjs 200 }

tmnxWlanGwNumSoftGreTu OBJECT-TYPE
    SYNTAX      Gauge32
    MAX-ACCESS  read-only
    STATUS      current
    DESCRIPTION
        "The value of the object tmnxWlanGwNumSoftGreTu indicates
         the actual number of Soft GRE tunnels terminated by this system."
    ::= { tmnxWlanGwObjs 201 }

tmnxWlanGwPeakNumSoftGreTu OBJECT-TYPE
    SYNTAX      Gauge32
    MAX-ACCESS  read-only
    STATUS      current
    DESCRIPTION
        "The value of the object tmnxWlanGwPeakNumSoftGreTu indicates
         the peak number of Soft GRE tunnels terminated by this system at any time,
         since the system was last initialized or the value of this object
         was last reset."
    ::= { tmnxWlanGwObjs 202 }

tmnxWlanGwNumUe OBJECT-TYPE
    SYNTAX      Gauge32
    MAX-ACCESS  read-only
    STATUS      current
    DESCRIPTION
        "The value of the object tmnxWlanGwNumSoftGreTu indicates
         the actual number of UE processed by this system."
    ::= { tmnxWlanGwObjs 203 }

tmnxWlanGwPeakNumUe OBJECT-TYPE
    SYNTAX      Gauge32
    MAX-ACCESS  read-only
    STATUS      current
    DESCRIPTION
        "The value of the object tmnxWlanGwPeakNumSoftGreTu indicates
         the peak number of UE processed by this system at any time,
         since the system was last initialized or the value of this object
         was last reset."
    ::= { tmnxWlanGwObjs 204 }

tmnxWlanGwNumMgw OBJECT-TYPE
    SYNTAX      Gauge32
    MAX-ACCESS  read-only
    STATUS      current
    DESCRIPTION
        "The value of the object tmnxWlanGwNumMgw indicates
         the actual number of Mobile Gateways connected to this system.
         
         It is equal to the number of rows in the tmnxWlanGwMgwTable."
    ::= { tmnxWlanGwObjs 205 }

-- ----------------------------------------------------------------------------
--  Notification objects
-- ----------------------------------------------------------------------------

tmnxWlanGwNotifyDescription  OBJECT-TYPE
    SYNTAX      DisplayString (SIZE(0..255))
    MAX-ACCESS  accessible-for-notify
    STATUS      current
    DESCRIPTION
        "The object tmnxWlanGwNotifyDescription is a printable character 
         string."
    ::= { tmnxWlanGwNotificationObjs 1 }

tmnxWlanGwNotifyTrue  OBJECT-TYPE
    SYNTAX      TruthValue
    MAX-ACCESS  accessible-for-notify
    STATUS      current
    DESCRIPTION
        "The object tmnxWlanGwNotifyTrue contains a boolean truth value."
    ::= { tmnxWlanGwNotificationObjs 2 }

-- ----------------------------------------------------------------------------
--  Notifications
-- ----------------------------------------------------------------------------

tmnxWlanGwResrcProblemDetected NOTIFICATION-TYPE
    OBJECTS {
        tmnxWlanGwResrcProblem
    }
    STATUS current
    DESCRIPTION
        "The tmnxWlanGwResrcProblemDetected notification is sent when 
         the value of the object tmnxWlanGwResrcProblem changes."
    ::= { tmnxWlanGwNotifications 1}

tmnxWlanGwResrcProblemCause NOTIFICATION-TYPE
    OBJECTS {
        tmnxWlanGwNotifyDescription
    }
    STATUS current
    DESCRIPTION
        "The tmnxWlanGwResrcProblemCause notification is sent 
         to describe the cause of a WLAN Gateway resource problem."
    ::= { tmnxWlanGwNotifications 2}

tmnxWlanGwTuQosProblem NOTIFICATION-TYPE
    OBJECTS {
        tmnxWlanGwIsaMemberTuQosProblem
    }
    STATUS current
    DESCRIPTION
        "The tmnxWlanGwTuQosProblem notification is sent when the value
         of the object tmnxWlanGwIsaMemberTuQosProblem changes from or to zero
         for some member of a WLAN Gateway ISA Group in the system.
         
         [CAUSE] While creating a WLAN Gateway tunnel QoS infrastructure 
         instance, there was a resource issue.  
         
         [EFFECT] There are UE with a QoS infrastructure that does not match
         the configuration, for example: no shaper was instantiated.
         
         [RECOVERY] This may be a temporary phenomenon.
         
         If it persists, the QoS configuration or the scaling may have to
         be modified to ensure enough resources are available for the UE QoS."
    ::= { tmnxWlanGwNotifications 3}

tmnxWlanGwGrpOperStateChanged NOTIFICATION-TYPE
    OBJECTS {
        tmnxWlanGwGrpOperState
    }
    STATUS current
    DESCRIPTION
        "The tmnxWlanGwGrpOperStateChanged notification is sent when 
         the value of the object tmnxWlanGwGrpOperState changes."
    ::= { tmnxWlanGwNotifications 4}

tmnxWlanGwIomActive NOTIFICATION-TYPE
    OBJECTS {
        tmnxWlanGwIomLastMgmtChange,
        tmnxWlanGwNotifyTrue
    }
    STATUS current
    DESCRIPTION
        "The tmnxWlanGwIomActive notification is sent when 
         the value of the object tmnxWlanGwIomOperState changes from
         'primary' to any other value, or the other way around.
         
         The value 'primary' means that the IOM is active in the group."
    ::= { tmnxWlanGwNotifications 5}

tmnxWlanGwMgwConnected NOTIFICATION-TYPE
    OBJECTS {
        tmnxWlanGwMgwTime,
        tmnxWlanGwNotifyTrue
    }
    STATUS current
    DESCRIPTION
        "The tmnxWlanGwMgwConnected notification is sent
         when this system adds a conceptual row to the tmnxWlanGwMgwTable,
         or removes it.
         
         [CAUSE] A connection is established between this system's WLAN Gateway
         function and a Mobile Gateway, or such a connection disappears.
         
         The interruption of a connection with a Mobile Gateway
         can be the expected result of a management action on the Mobile Gateway,
         or it can be caused by a network failure.
         
         [EFFECT] While there is a connection with a particular Mobile Gateway, 
         User Equipment (UE) belonging to the associated 
         PLMN (Public Land Mobile Network) and serviced by this WLAN Gateway
         can be connected to their Home PLMN.
         
         [RECOVERY] If a connection with a Mobile Gateway is interrupted as
         the expected result of a management action, no recovery is required."
    ::= { tmnxWlanGwNotifications 10}


tmnxWlanGwMgwRestarted NOTIFICATION-TYPE
    OBJECTS {
        tmnxWlanGwMgwRestartCnt
    }
    STATUS current
    DESCRIPTION
        "The tmnxWlanGwMgwRestarted notification is sent
         when this system learns that a Mobile Gateway has restarted.
         
         [CAUSE] A Mobile Gateway known to this system has restarted,
         has transmitted its restart counter to this system and 
         it was found to be higher than its previously known value.
         
         [EFFECT] This system clears all sessions associated with the
         restarted Mobile Gateway (because that Mobile Gateway has lost
         its session data anyway).
         
         [RECOVERY] No recovery is required on this system."
    ::= { tmnxWlanGwNotifications 11}

tmnxWlanGwNumMgwHi NOTIFICATION-TYPE
    OBJECTS {
        tmnxWlanGwNumMgw,
        tmnxWlanGwNotifyTrue
    }
    STATUS current
    DESCRIPTION
        "The tmnxWlanGwNumMgwHi notification is sent
         when the value of tmnxWlanGwNumMgw reaches its high 
         watermark ('true') or when it reaches its low watermark 
         again ('false'). The value of the object tmnxWlanGwNumMgw indicates
         the actual number of Mobile Gateways connected to this system.
         
         The description below applies to the notification
         when sent with the value of 'true'.
         
         [CAUSE] The number of Mobile Gateways connected to this system
         is approaching the maximum supported value.
         
         [EFFECT] If the increasing trend continues, this system will not be
         able to connect some User Equipment (UE) with their Home PLMN.
         
         [RECOVERY] The network configuration may have to be modified
         such that this system will be associated with less Mobile Gateways."
    ::= { tmnxWlanGwNotifications 12}

tmnxWlanGwMgwStateChanged NOTIFICATION-TYPE
    OBJECTS {
        tmnxWlanGwMgwState
    }
    STATUS current
    DESCRIPTION
        "The tmnxWlanGwMgwStateChanged notification is sent
         when the state of a connection with a Mobile Gateway has changed.
         
         [CAUSE] The state of a connection with a Mobile Gateway has changed.
         
         [EFFECT] The effect depends on the new state.
         
         [RECOVERY] No recovery is required on this system."
    ::= { tmnxWlanGwNotifications 13}

-- ----------------------------------------------------------------------------
--  Conformance Groups
-- ----------------------------------------------------------------------------
tmnxWlanGwIsaGroup OBJECT-GROUP
    OBJECTS {
        tmnxWlanGwGrpTableLastCh,
        tmnxWlanGwGrpRowStatus,         
        tmnxWlanGwGrpLastMgmtChange,    
        tmnxWlanGwGrpDescription,       
        tmnxWlanGwGrpAdminState,        
        tmnxWlanGwGrpActiveIomLimit,
        tmnxWlanGwGrpPortPlcy,    
        tmnxWlanGwGrpTunnelPortPlcy,    
        tmnxWlanGwGrpOperState,         
        tmnxWlanGwIomTableLastCh,
        tmnxWlanGwIomRowStatus,      
        tmnxWlanGwIomLastMgmtChange, 
        tmnxWlanGwIomOperState,
        tmnxWlanGwIsaMemberChassisIndex,
        tmnxWlanGwIsaMemberCardSlotNum,
        tmnxWlanGwIsaMemberSlotNum,
        tmnxWlanGwIsaMemberNumSoftGreTu,
        tmnxWlanGwIsaMemberNumUe,
        tmnxWlanGwIsaMemberEegMemberAct,
        tmnxWlanGwIsaMemberEegMemberPend,
        tmnxWlanGwIsaMemberTuQosProblem,
        tmnxWlanGwIsaMemberStatsName,
        tmnxWlanGwIsaMemberStatsVal,
        tmnxWlanGwIsaMemberStatsValHw,
        tmnxWlanGwIsaMemberStatsValue,
        tmnxWlanGwResrcProblem      
    }
    STATUS      current
    DESCRIPTION
        "The group of objects providing configuration of WLAN Gateway ISA 
          on Alcatel-Lucent SROS series systems."
    ::= { tmnxWlanGwGroups 1 }

tmnxWlanGwSoftGreGroup OBJECT-GROUP
    OBJECTS {
        tmnxWlanGwSoftGreIfLastCh,
        tmnxWlanGwSoftGreIfAdminState,
        tmnxWlanGwSoftGreIfRouter,
        tmnxWlanGwSoftGreIfGwAddrType,
        tmnxWlanGwSoftGreIfGwAddr,
        tmnxWlanGwSoftGreIfGrpId,
        tmnxWlanGwSoftGreIfShapingType,
        tmnxWlanGwSoftGreIfShapeMultiUe,
        tmnxWlanGwSoftGreIfEQosPlcy,
        tmnxWlanGwSoftGreIfESchedPlcy,
        tmnxWlanGwSoftGreIfEAggRateLimit,
        tmnxWlanGwSoftGreIfMobTrigger,
        tmnxWlanGwSoftGreIfMobHoldTime,
        tmnxWlanGwSoftGreIfDefRetailSvc,
        tmnxWlanGwSoftGreIfTcpMssAdjust,
        tmnxWlanGwSoftGreIfEHoldTime,
        tmnxWlanGwSoftGreIfNumSoftGreTu,
        tmnxWlanGwSoftGreIfTableLastCh,
        tmnxWlanGwSoftGreTuEstabTime,
        tmnxWlanGwSoftGreTuIsaGroup,
        tmnxWlanGwSoftGreTuIsaMember,
        tmnxWlanGwSoftGreTuNumUe,
        tmnxWlanGwTuQosEegSvcId,
        tmnxWlanGwTuQosEegPortId ,
        tmnxWlanGwTuQosEegEncapValue,
        tmnxWlanGwTuQosEegName,
        tmnxWlanGwTuQosEegMember,
        tmnxWlanGwTuQosState,     
        tmnxWlanGwTuQosNumUe,
        tmnxWlanGwTuQosRemainingHoldTime,     
        tmnxWlanGwSoftGreTuUeSsid
    }
    STATUS      current
    DESCRIPTION
        "The group of objects providing configuration of WLAN Gateway 
         Soft GRE group interfaces on Alcatel-Lucent SROS series systems."
    ::= { tmnxWlanGwGroups 2 }

tmnxWlanGwObjGroup OBJECT-GROUP
    OBJECTS {
        tmnxWlanGwIfRetailRowStatus,
        tmnxWlanGwIfRetailLastCh,
        tmnxWlanGwIfRetailService,
        tmnxWlanGwIfRetailTableLastCh,
        tmnxWlanGwUeQTag,
        tmnxWlanGwUeMplsLabel,
        tmnxWlanGwUeTuRouter,
        tmnxWlanGwUeTuAddrType,
        tmnxWlanGwUeTuRemoteAddr,
        tmnxWlanGwUeTuLocalAddr,
        tmnxWlanGwUeTuQosRetailService,
        tmnxWlanGwUeSsid,
        tmnxWlanGwUePrevApAddrType,
        tmnxWlanGwUePrevApAddr,
        tmnxWlanGwUeLastMoveTime,
        tmnxWlanGwSsidNumUe,
        tmnxWlanGwNumSoftGreTu,
        tmnxWlanGwPeakNumSoftGreTu,
        tmnxWlanGwNumUe,
        tmnxWlanGwPeakNumUe     
    }
    STATUS      current
    DESCRIPTION
        "The group of objects providing configuration of WLAN Gateway 
         on Alcatel-Lucent SROS series systems."
    ::= { tmnxWlanGwGroups 3 }

tmnxWlanGwMgwGroup OBJECT-GROUP
    OBJECTS {
        tmnxWlanGwUeImsi,
        tmnxWlanGwMgwProfTableLastCh,
        tmnxWlanGwMgwProfRowStatus,
        tmnxWlanGwMgwProfLastChanged,
        tmnxWlanGwMgwProfDescription,
        tmnxWlanGwMgwProfKeepAlvRetryCnt,
        tmnxWlanGwMgwProfMsgReTxTimeout,
        tmnxWlanGwMgwProfMsgReTxRetryCnt,
        tmnxWlanGwMgwProfKeepAlvTimeout,
        tmnxWlanGwMgwProfKeepAlvResp,
        tmnxWlanGwMgwProfTtl,
        tmnxWlanGwMgwProfInterfaceType,
        tmnxWlanGwMgwAddrTableLastCh,
        tmnxWlanGwMgwAddrRowStatus,
        tmnxWlanGwMgwAddrLastMgmtChange,
        tmnxWlanGwMgwAddrProfile,
        tmnxWlanGwMgwLocalAddrType,
        tmnxWlanGwMgwLocalAddr,
        tmnxWlanGwMgwTime,
        tmnxWlanGwMgwProfile,
        tmnxWlanGwMgwControl,
        tmnxWlanGwMgwRestartCnt,
        tmnxWlanGwMgwState,
        tmnxWlanMgwStatsName,
        tmnxWlanMgwStatsVal,
        tmnxWlanMgwStatsValLw,
        tmnxWlanMgwStatsValHw,
        tmnxWlanGwGtpSeMgwRouter,
        tmnxWlanGwGtpSeMgwAddrType,
        tmnxWlanGwGtpSeMgwAddr,
        tmnxWlanGwGtpSeRemoteCtrlTeid,
        tmnxWlanGwGtpSeLocalCtrlTeid,
        tmnxWlanGwBcRemoteTeid,
        tmnxWlanGwBcLocalTeid,
        tmnxWlanGwMgwCacheTtl,
        tmnxWlanGwSysCfgServingNwMcc,
        tmnxWlanGwSysCfgServingNwMnc,
        tmnxWlanGwRowStatus,
        tmnxWlanGwLastCh,
        tmnxWlanGwApn,
        tmnxWlanGwTableLastCh,
        tmnxWlanGwNumMgw,
        tmnxWlanGwGtpStatsName,
        tmnxWlanGwGtpStatsVal,
        tmnxWlanGwGtpStatsValLw,
        tmnxWlanGwGtpStatsValHw
    }
    STATUS      current
    DESCRIPTION
        "The group of objects providing configuration of WLAN Gateway 
         Mobile Gateway profiles on Alcatel-Lucent SROS series systems."
    ::= { tmnxWlanGwGroups 4 }

tmnxWlanGwNotifyObjsGroup     OBJECT-GROUP
    OBJECTS {   
        tmnxWlanGwNotifyDescription,
        tmnxWlanGwNotifyTrue
    }
    STATUS        current
    DESCRIPTION
        "The group of notification objects supporting WLAN Gateway notifications
         on Alcatel-Lucent SROS series systems."
    ::= { tmnxWlanGwGroups 99 }
    
tmnxWlanGwNotifyGroup NOTIFICATION-GROUP
    NOTIFICATIONS {
        tmnxWlanGwResrcProblemDetected,
        tmnxWlanGwResrcProblemCause,
        tmnxWlanGwTuQosProblem,
        tmnxWlanGwGrpOperStateChanged,
        tmnxWlanGwIomActive,
        tmnxWlanGwMgwConnected,
        tmnxWlanGwMgwRestarted,
        tmnxWlanGwNumMgwHi,
        tmnxWlanGwMgwStateChanged
    }
    STATUS      current
    DESCRIPTION
        "The group of notifications supporting WLAN Gateway
         on Alcatel-Lucent SROS series systems."
    ::= { tmnxWlanGwGroups 100 }

-- ----------------------------------------------------------------------------
--  Conformance information
-- ----------------------------------------------------------------------------
tmnxWlanGwCompliance MODULE-COMPLIANCE
    STATUS  obsolete
    DESCRIPTION
        "The compliance statement for management of WLAN Gateway
         on Alcatel-Lucent 7xxx series systems."
    MODULE  -- this module
        MANDATORY-GROUPS {
            tmnxWlanGwIsaGroup,
            tmnxWlanGwSoftGreGroup,
            tmnxWlanGwObjGroup
        }
    ::= { tmnxWlanGwCompliances 1 }

tmnxWlanGwNotifyCompliance MODULE-COMPLIANCE
    STATUS  current
    DESCRIPTION
        "The compliance statement for WLAN Gateway notifications
         on Alcatel-Lucent SROS series systems."
    MODULE  -- this module
        MANDATORY-GROUPS {
            tmnxWlanGwNotifyGroup
        }
    ::= { tmnxWlanGwCompliances 2 }

tmnxWlanGwV10Compliance MODULE-COMPLIANCE
    STATUS  current
    DESCRIPTION
        "The compliance statement for management of WLAN Gateway
         on Alcatel-Lucent 7xxx series systems."
    MODULE  -- this module
        MANDATORY-GROUPS {
            tmnxWlanGwIsaGroup,
            tmnxWlanGwSoftGreGroup,
            tmnxWlanGwObjGroup,
            tmnxWlanGwMgwGroup
        }
    ::= { tmnxWlanGwCompliances 3 }


END
