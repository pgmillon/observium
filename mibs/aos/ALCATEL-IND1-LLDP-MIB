ALCATEL-IND1-LLDP-MIB DEFINITIONS ::= BEGIN

     	IMPORTS
		MODULE-IDENTITY, OBJECT-IDENTITY, OBJECT-TYPE, NOTIFICATION-TYPE
			FROM SNMPv2-SMI
                MODULE-COMPLIANCE, OBJECT-GROUP,NOTIFICATION-GROUP
                        FROM SNMPv2-CONF
                InterfaceIndex
                        FROM IF-MIB
                softentIND1LLDP, alaLLDPTraps
                        FROM ALCATEL-IND1-BASE
                LldpPortNumber ,LldpChassisId,  LldpChassisIdSubtype , LldpPortId, LldpPortIdSubtype
                        FROM LLDP-MIB
			;

        alcatelIND1LLDPMIB MODULE-IDENTITY
                LAST-UPDATED "200908080000Z"
                ORGANIZATION "Alcatel-Lucent"
                CONTACT-INFO
            "Please consult with Customer Service to ensure the most appropriate
             version of this document is used with the products in question:

                        Alcatel-Lucent, Enterprise Solutions Division
                       (Formerly Alcatel Internetworking, Incorporated)
                               26801 West Agoura Road
                            Agoura Hills, CA  91301-5122
                              United States Of America

            Telephone:               North America  +1 800 995 2696
                                     Latin America  +1 877 919 9526
                                     Europe         +31 23 556 0100
                                     Asia           +65 394 7933
                                     All Other      +1 818 878 4507

            Electronic Mail:         support@ind.alcatel.com
            World Wide Web:          http://alcatel-lucent.com/wps/portal/enterprise
            File Transfer Protocol:  ftp://ftp.ind.alcatel.com/pub/products/mibs"

                DESCRIPTION
			"This module describes an authoritative enterprise-specific Simple
             Network Management Protocol (SNMP) Management Information Base (MIB):

             The LLDP  for the Birds Of Prey Product Line

             The right to make changes in specification and other information
             contained in this document without prior notice is reserved.

             No liability shall be assumed for any incidental, indirect, special, or
             consequential damages whatsoever arising from or related to this
             document or the information contained herein.

             Vendors, end-users, and other interested parties are granted
             non-exclusive license to use this specification in connection with
             management of the products for which it is intended to be used.

                         Copyright (C) 1995-2007 Alcatel-Lucent
                             ALL RIGHTS RESERVED WORLDWIDE"

		REVISION      "200908080000Z"
        DESCRIPTION
            "Addressing discrepancies with Alcatel Standard."
		::= { softentIND1LLDP 1}

alaIND1LLDPMIBObjects OBJECT-IDENTITY
        STATUS current
        DESCRIPTION
            "Branch For LLDP
            Subsystem Managed Objects."
        ::= { alcatelIND1LLDPMIB 1 }


    alaIND1LLDPMIBConformance OBJECT-IDENTITY
        STATUS current
        DESCRIPTION
            "Branch For LLDP
            Subsystem Conformance Information."
        ::= { alcatelIND1LLDPMIB 2 }


    alaIND1LLDPMIBGroups OBJECT-IDENTITY
        STATUS current
        DESCRIPTION
            "Branch For LLDP
            Subsystem Units Of Conformance."
        ::= { alaIND1LLDPMIBConformance 1 }

    alaIND1LLDPMIBCompliances OBJECT-IDENTITY
         STATUS  current
         DESCRIPTION
             "Branch for LLDP Module MIB Subsystem Compliance Statements."
         ::= { alaIND1LLDPMIBConformance 2 }

-- Port table

alaLLDPPortTable OBJECT-TYPE
    SYNTAX      SEQUENCE OF AlaLLDPPortEntry
    MAX-ACCESS  not-accessible
    STATUS      current
    DESCRIPTION
        "A table of system level information for each port
        supported by the LLDP security mechanism.  An entry appears
        in this table for each port of this system."
    ::= { alaIND1LLDPMIBObjects 1 }

alaLLDPPortEntry OBJECT-TYPE
    SYNTAX      AlaLLDPPortEntry
    MAX-ACCESS  not-accessible
    STATUS      current
    DESCRIPTION
        "An entry in the alaLLDPPortTable"
    INDEX { alaLLDPTrustLocalPortNumber }
    ::= { alaLLDPPortTable 1 }


AlaLLDPPortEntry ::=
    SEQUENCE {
      alaLLDPTrustLocalPortNumber
            LldpPortNumber,
        alaLldpTrustAdminStatus
            INTEGER,
        alaLldpTrustAction
            INTEGER,
        alaLldpTrustedStatus
            INTEGER,
        alaLldpTrustedChassisSubtype
            INTEGER
        }

alaLLDPTrustLocalPortNumber   OBJECT-TYPE
    SYNTAX      LldpPortNumber
    MAX-ACCESS  not-accessible
    STATUS      current
    DESCRIPTION
            "The index value used to identify the port component
            (contained in the local chassis with the LLDP agent)
            associated with this entry.  The lldpRemLocalPortNum
            identifies the port on which the remote system information
            is received.

            The value of this object is used as a port index to the
            lldpRemTable."
    ::= { alaLLDPPortEntry 1}

alaLldpTrustAdminStatus OBJECT-TYPE
    SYNTAX INTEGER {
       enabled(1),
       disabled(2)
    }
    MAX-ACCESS read-write
    STATUS      current
    DESCRIPTION
        "Admin status of the trust agent status on a given port."
    ::= { alaLLDPPortEntry 2 }

alaLldpTrustAction OBJECT-TYPE
    SYNTAX INTEGER {
       trap(1),
       shutdown(2),
       both(3)
    }
    MAX-ACCESS read-write
    STATUS      current
    DESCRIPTION
        "To decide what action to be taken in case of any voilation occure."
    ::= { alaLLDPPortEntry 3 }

alaLldpTrustedStatus OBJECT-TYPE
    SYNTAX INTEGER {
       trusted(1),
       voilated(2)
    }
    MAX-ACCESS read-only
    STATUS      current
    DESCRIPTION
        "To get the current voilation status of the give port."
    ::= { alaLLDPPortEntry 4 }

alaLldpTrustedChassisSubtype OBJECT-TYPE
    SYNTAX INTEGER {
            chassisComponent(1),
            interfaceAlias(2),
            portComponent(3),
            macAddress(4),
            networkAddress(5),
            interfaceName(6),
            local(7),
            any(8)
    }
    MAX-ACCESS read-write 
    STATUS      current
    DESCRIPTION
        "User configured/Allowed chassis id subtype on a given port."
    ::= { alaLLDPPortEntry 5 }


--  ***********************************************************
--
--          TRUSTED REMOTE    SYSTEMS    DATA
--
--  ***********************************************************

alaLLDPTrustedRemTable OBJECT-TYPE
    SYNTAX      SEQUENCE OF AlaLLDPTrustedRemEntry
    MAX-ACCESS  not-accessible
    STATUS      current
    DESCRIPTION
            "This table contains one trusted agent know on a given port."
    ::= { alaIND1LLDPMIBObjects 2 }

alaLLDPTrustedRemEntry OBJECT-TYPE
    SYNTAX      AlaLLDPTrustedRemEntry
    MAX-ACCESS  not-accessible
    STATUS      current
    DESCRIPTION
            "Information about a particular physical network connection.
            Entries may be read from this table by the agent,
            if a physical topology discovery process is active."
    INDEX   {

           alaLLDPTrustedRemLocalPortNumber

    }
    ::= { alaLLDPTrustedRemTable 1 }

AlaLLDPTrustedRemEntry ::= SEQUENCE {

      alaLLDPTrustedRemLocalPortNumber    LldpPortNumber,
      alaLLDPTrustedRemChassisIdSubtype   LldpChassisIdSubtype,
      alaLLDPTrustedRemChassisId          LldpChassisId,
      alaLLDPTrustedRemPortIdSubtype      LldpPortIdSubtype,
      alaLLDPTrustedRemPortId             LldpPortId
}


alaLLDPTrustedRemLocalPortNumber   OBJECT-TYPE
    SYNTAX      LldpPortNumber
    MAX-ACCESS  not-accessible
    STATUS      current
    DESCRIPTION
            "The index value used to identify the port component
            (contained in the local chassis with the LLDP agent)
            associated with this entry.  The lldpRemLocalPortNum
            identifies the port on which the remote system information
            is received.

            The value of this object is used as a port index to the
            lldpRemTable."
    ::= { alaLLDPTrustedRemEntry 1}

alaLLDPTrustedRemChassisIdSubtype  OBJECT-TYPE
    SYNTAX      LldpChassisIdSubtype
    MAX-ACCESS  read-only
    STATUS      current
    DESCRIPTION
            "The type of encoding used to identify the chassis associated
            with the remote system."
    REFERENCE
            "IEEE 802.1AB-2005 9.5.2.2"
    ::= { alaLLDPTrustedRemEntry 2}

alaLLDPTrustedRemChassisId  OBJECT-TYPE
    SYNTAX      LldpChassisId
    MAX-ACCESS  read-only
    STATUS      current
    DESCRIPTION
            "The string value used to identify the chassis component
            associated with the remote system."
    REFERENCE
            "IEEE 802.1AB-2005 9.5.2.3"
    ::= { alaLLDPTrustedRemEntry 3}

alaLLDPTrustedRemPortIdSubtype  OBJECT-TYPE
    SYNTAX      LldpPortIdSubtype
    MAX-ACCESS  read-only
    STATUS      current
    DESCRIPTION
            "The type of port identifier encoding used in the associated
            'lldpRemPortId' object."
    REFERENCE
            "IEEE 802.1AB-2005 9.5.3.2"
    ::= { alaLLDPTrustedRemEntry 4}

alaLLDPTrustedRemPortId  OBJECT-TYPE
    SYNTAX      LldpPortId
    MAX-ACCESS  read-only
    STATUS      current
    DESCRIPTION
            "The string value used to identify the port component
            associated with the remote system."
    REFERENCE
            "IEEE 802.1AB-2005 9.5.3.3"
    ::= { alaLLDPTrustedRemEntry 5}

--
--  NOTIFICATIONS
--

    alaLLDPTrapsDesc OBJECT IDENTIFIER ::= { alaLLDPTraps 1 }
    alaLLDPTrapsDescRoot OBJECT IDENTIFIER ::= { alaLLDPTrapsDesc 0 }
    alaLLDPTrapsObj OBJECT IDENTIFIER ::= { alaLLDPTraps 2 }

    alaLLDPTrustPortIfIndex   OBJECT-TYPE
    SYNTAX  InterfaceIndex
    MAX-ACCESS  accessible-for-notify
    STATUS      current
    DESCRIPTION
       "Interface index of the port, used for sending TRAP."
    ::= { alaIND1LLDPMIBObjects 3 }

    alaLLDPTrustViolationReason   OBJECT-TYPE
    SYNTAX  INTEGER {
           agentalreadyexistonport (1),
           agentalreadyexistonotherport (2),
           chassisidsubtypemissmatch(3)
    }
    MAX-ACCESS  accessible-for-notify
    STATUS  current
    DESCRIPTION
    "Type of Violation.
     agentalreadyexistonport - There is already one trust agent exists on the port, Only 
                                one trust agent can be allowed on a port.
     agentalreadyexistonotherport - Same agent already present on another port, Any given
                                   remote agent shall be part of only on port.
     chassisidsubtypemissmatch - Chassisid Subtype is not matching with configured subtype."
    ::= { alaIND1LLDPMIBObjects 4 }

    alaLLDPTrustPortId   OBJECT-TYPE
    SYNTAX               INTEGER
    MAX-ACCESS           accessible-for-notify
    STATUS               current
    DESCRIPTION          "LLDP Trust Port Violation."
    ::= { alaIND1LLDPMIBObjects 5 }

    alaLLDPTrustChassisId   OBJECT-TYPE
    SYNTAX               LldpChassisId
    MAX-ACCESS           accessible-for-notify
    STATUS               current
    DESCRIPTION          "LLDP Trust Port ChassisId"
    ::= { alaIND1LLDPMIBObjects 6 }

    alaLldpTrustViolation NOTIFICATION-TYPE
    OBJECTS {
          alaLLDPTrustPortIfIndex,
          alaLLDPTrustViolationReason,
    	  alaLLDPTrustPortId,
          alaLLDPTrustChassisId 
    }
    STATUS  current
    DESCRIPTION
       " Port configured to LLDP trust agent have violated.
         Notify the user by raising the Trap."
    ::= { alaLLDPTrapsDescRoot 1}



-- xxxxxxxxxxxxxxxxxxxxxxxxxxxxxxxxxxxxxxxxxxxxxxxxxxxxxxxxxx
-- UNITS OF CONFORMANCE
-- xxxxxxxxxxxxxxxxxxxxxxxxxxxxxxxxxxxxxxxxxxxxxxxxxxxxxxxxxx

    alaINDLLDPTrustBaseGroup   OBJECT-GROUP
        OBJECTS
        {
          alaLLDPTrustPortIfIndex,
          alaLLDPTrustViolationReason
        }
        STATUS  current
        DESCRIPTION
              "Collection of objects for management of LLDP Base Group."
       ::= { alaIND1LLDPMIBGroups 1 }

    alaINDLLDPTrustAgentGroup OBJECT-GROUP
        OBJECTS
        {
           alaLldpTrustAdminStatus,
           alaLldpTrustAction,
           alaLldpTrustedStatus,
           alaLldpTrustedChassisSubtype
        }
        STATUS  current
        DESCRIPTION
            "Collection of LLDP security mechanism objects for port status."
        ::= { alaIND1LLDPMIBGroups 2 }

    alaINDLLDPTrustRemoteAgentGroup OBJECT-GROUP
        OBJECTS
        {
          alaLLDPTrustedRemChassisIdSubtype,
          alaLLDPTrustedRemChassisId,
          alaLLDPTrustedRemPortIdSubtype,
          alaLLDPTrustedRemPortId
        }
        STATUS  current
        DESCRIPTION
            "Collection of LLDP trusted remote agent on port."
        ::= { alaIND1LLDPMIBGroups 3 }


   alaLldpTrustTrapGroup NOTIFICATION-GROUP
       NOTIFICATIONS
       {
          alaLldpTrustViolation
       }
       STATUS  current
       DESCRIPTION
           "Collection of objects for LLDP Traps."
       ::= { alaIND1LLDPMIBGroups 4 }


-- xxxxxxxxxxxxxxxxxxxxxxxxxxxxxxxxxxxxxxxxxxxxxxxxxxxxxxxxxx
-- COMPLIANCE
-- xxxxxxxxxxxxxxxxxxxxxxxxxxxxxxxxxxxxxxxxxxxxxxxx

    alaIND1LLDPMIBCompliance MODULE-COMPLIANCE
        STATUS  current
        DESCRIPTION
            "Compliance statement for Alcatel LLDP"
        MODULE
            MANDATORY-GROUPS
            {
                alaINDLLDPTrustBaseGroup,
                alaINDLLDPTrustAgentGroup,
                alaINDLLDPTrustRemoteAgentGroup,
                alaLldpTrustTrapGroup
            }

        ::= { alaIND1LLDPMIBCompliances 1 }

        END
