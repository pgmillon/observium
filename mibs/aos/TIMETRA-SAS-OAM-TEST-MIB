TIMETRA-SAS-OAM-TEST-MIB DEFINITIONS ::= BEGIN

IMPORTS
        MODULE-IDENTITY, OBJECT-TYPE, NOTIFICATION-TYPE, IpAddress,
        Integer32, Unsigned32, Gauge32, Counter32, Counter64
            FROM SNMPv2-SMI

        MODULE-COMPLIANCE, OBJECT-GROUP, NOTIFICATION-GROUP
            FROM SNMPv2-CONF

        TEXTUAL-CONVENTION, RowStatus, StorageType, TruthValue,
        DateAndTime, MacAddress, TimeStamp, DisplayString
            FROM SNMPv2-TC

        SnmpAdminString
            FROM SNMP-FRAMEWORK-MIB

        InetAddressType, InetAddress, InetAddressPrefixLength
            FROM INET-ADDRESS-MIB

        InterfaceIndex, InterfaceIndexOrZero
            FROM IF-MIB

        -- Alphasort
        IpAddressPrefixLength, SdpBindId, TFCName, TItemDescription,
        TLNamedItemOrEmpty, TNamedItemOrEmpty, TPolicyStatementNameOrEmpty,
        TProfile, TmnxAdminState, TmnxBgpRouteTarget, TmnxEncapVal, TmnxPortID,
        TmnxPwGlobalIdOrZero, TmnxServId, TmnxSpokeSdpIdOrZero, TmnxStrSapId,
        TmnxTunnelID, TmnxTunnelType, TmnxVPNRouteDistinguisher, TmnxVRtrID,
        TmnxVcId, TmnxVcIdOrNone, TmnxVcType, TDSCPNameOrEmpty, TNamedItem,
        Dot1PPriority
            FROM TIMETRA-TC-MIB

        timetraSRMIBModules, tmnxSRObjs,
        tmnxSRNotifyPrefix, tmnxSRConfs
            FROM TIMETRA-GLOBAL-MIB

       timetraSASObjs, timetraSASNotifyPrefix, 
       timetraSASConfs, timetraSASModules               
            FROM TIMETRA-SAS-GLOBAL-MIB

       InetAddressPrefixLength,
       InetAddressIPv6,
       InetAddressType, InetAddress            
           FROM INET-ADDRESS-MIB

       svcId
               FROM TIMETRA-SERV-MIB       
               
       sapPortId, sapEncapValue 
               FROM TIMETRA-SAP-MIB       

       TAdaptationRule
            FROM TIMETRA-SAS-QOS-MIB       
            
        ;

timetraSASOamTestMIBModule MODULE-IDENTITY
        LAST-UPDATED "201102010000Z"
        ORGANIZATION "Alcatel-Lucent"
        CONTACT-INFO
            "Alcatel-Lucent SROS Support
             Web: http://support.alcatel-lucent.com"

        DESCRIPTION
        "This document is the SNMP MIB module to manage and provision the
        Alcatel-Lucent SROS OAM tests.

        Copyright 2014 Alcatel-Lucent.  All rights reserved.
        Reproduction of this document is authorized on the condition that
        the foregoing copyright notice is included.

        This SNMP MIB module (Specification) embodies Alcatel-Lucent's
        proprietary intellectual property.  Alcatel-Lucent retains
        all title and ownership in the Specification, including any
        revisions.

        Alcatel-Lucent grants all interested parties a non-exclusive
        license to use and distribute an unmodified copy of this
        Specification in connection with management of Alcatel-Lucent
        products, and without fee, provided this copyright notice and
        license appear on all copies.

        This Specification is supplied 'as is', and Alcatel-Lucent
        makes no warranty, either express or implied, as to the use,
        operation, condition, or performance of the Specification."
--
--  Revision History
--
        REVISION        "1210010000Z"
        DESCRIPTION     "Rev 1.0                1 Nov 2012 00:00
                         5.0 release of the TIMETRA-SAS-OAM-TEST-MIB."

        ::= { timetraSASModules 18 }


tmnxSASOamTestObjs         OBJECT IDENTIFIER ::= { timetraSASObjs 17 }
    tmnxTestHdProfObjects                     OBJECT IDENTIFIER
        ::= { tmnxSASOamTestObjs 1 }
    tmnxTestHdProfNotifyObjs                     OBJECT IDENTIFIER
        ::= { tmnxSASOamTestObjs 2 }

tmnxSASOamNotifyPrefix    OBJECT IDENTIFIER ::= { timetraSASNotifyPrefix 3 }
    tmnxSASOamNotifications   OBJECT IDENTIFIER ::= { tmnxSASOamNotifyPrefix 1 }


tmnxSASOamTestConformance          OBJECT IDENTIFIER ::= { timetraSASConfs 17 }
    tmnxTestHdProfConformance              OBJECT IDENTIFIER
        ::= { tmnxSASOamTestConformance 1 }
    tmnxTestHdObjsGroups           OBJECT IDENTIFIER
        ::= { tmnxTestHdProfConformance 1 }

--

TTestHdCIRRate ::= TEXTUAL-CONVENTION
    STATUS       current
    DESCRIPTION
        "The rate to be used in kbps. "
    SYNTAX       INTEGER (0..1000000)

TTestHdPIRRate ::= TEXTUAL-CONVENTION
    STATUS       current
    DESCRIPTION
        "The rate to be used in kbps. The value -1 means pir rate not used."
    SYNTAX       INTEGER (-1 | 0..1000000)

--

tmnxTestHdProfTable OBJECT-TYPE
    SYNTAX       SEQUENCE OF TmnxTestHdProfEntry
    MAX-ACCESS   not-accessible
    STATUS       current
    DESCRIPTION  "  "
    ::= { tmnxTestHdProfObjects 1 }

tmnxTestHdProfEntry OBJECT-TYPE
    SYNTAX       TmnxTestHdProfEntry
    MAX-ACCESS   not-accessible
    STATUS       current
    DESCRIPTION
        ""
    INDEX { tmnxTestHdProfIndex }
    ::= { tmnxTestHdProfTable 1 }

TmnxTestHdProfEntry ::= SEQUENCE
    {
        tmnxTestHdProfIndex                 INTEGER,
        tmnxTestHdProfRowStatus             RowStatus,
        tmnxTestHdProfDescription           TItemDescription,
        tmnxTestHdProfCIRAdaptation         TAdaptationRule,
        tmnxTestHdProfOperCIR               TTestHdCIRRate,
        tmnxTestHdProfCIR                   TTestHdCIRRate,
        tmnxTestHdProfDurHr                 Integer32,
        tmnxTestHdProfDurMin                Integer32,
        tmnxTestHdProfDurSec                Integer32,        
        tmnxTestHdProfFrameSize             INTEGER,
        tmnxTestHdProfTrapEnable            TruthValue,        
        tmnxTestHdLastChanged               TimeStamp,
        tmnxTestHdProfAdminCIR              TTestHdCIRRate,
        tmnxTestHdProfAdminPIR              TTestHdPIRRate,
        tmnxTestHdProfOperPIR               TTestHdPIRRate,
        tmnxTestHdProfDot1pIn               Dot1PPriority,
        tmnxTestHdProfDot1pOut              Dot1PPriority,
        tmnxTestHdProfActiveTests           OCTET STRING,
        tmnxTestHdProfCompetedTests         OCTET STRING
    }

tmnxTestHdProfIndex OBJECT-TYPE
    SYNTAX       INTEGER (0..10)
    MAX-ACCESS   accessible-for-notify
    STATUS       current
    DESCRIPTION
        "tmnxTestHdProfIndex profile index for this entry"
    ::= { tmnxTestHdProfEntry 1 }

tmnxTestHdProfRowStatus OBJECT-TYPE
    SYNTAX       RowStatus
    MAX-ACCESS   read-create
    STATUS       current
    DESCRIPTION
        "RowStatus for this entry"
    ::= { tmnxTestHdProfEntry 2 }

tmnxTestHdProfDescription OBJECT-TYPE
    SYNTAX       TItemDescription
    MAX-ACCESS   read-create
    STATUS       current
    DESCRIPTION
        "user description for this profile"
    DEFVAL { ''H }
    ::= { tmnxTestHdProfEntry 3 }

   
tmnxTestHdProfCIRAdaptation OBJECT-TYPE
    SYNTAX       TAdaptationRule
    MAX-ACCESS   read-create
    STATUS       current
    DESCRIPTION
        "cir rule to be used in the test head test"
    DEFVAL { closest }
    ::= { tmnxTestHdProfEntry 4 }

tmnxTestHdProfOperCIR OBJECT-TYPE
    SYNTAX       TTestHdCIRRate
    MAX-ACCESS   read-only
    STATUS       current
    DESCRIPTION
        "oper cir used in the payload"
    ::= { tmnxTestHdProfEntry 5 }
  

tmnxTestHdProfCIR OBJECT-TYPE
    SYNTAX       TTestHdCIRRate
    MAX-ACCESS   read-create
    STATUS       deprecated
    DESCRIPTION
        "cir to be used in the payload, this object is supported for
        backward compatibility of 7210 devices using 5.0R4, tmnxTestHdProfOperCIR
        and tmnxTestHdProfAdminCIR to be used in 6.0 nodes"
    DEFVAL { 1000 }
    ::= { tmnxTestHdProfEntry 6 }

tmnxTestHdProfDurHr  OBJECT-TYPE
    SYNTAX      Integer32 (0..24)
    UNITS       "hours"
    MAX-ACCESS  read-create
    STATUS      current
    DESCRIPTION
        "tmnxTestHdProfDurHr is the number of hours the test head 
        test to be run"
    DEFVAL { 0 }
    ::= { tmnxTestHdProfEntry 8 }

tmnxTestHdProfDurMin  OBJECT-TYPE
    SYNTAX      Integer32 (0..60)
    UNITS       "minutes"
    MAX-ACCESS  read-create
    STATUS      current
    DESCRIPTION
        "tmnxTestHdProfDurMin is the number of minutes the test head 
        test to be run"
    DEFVAL { 3 }
    ::= { tmnxTestHdProfEntry 9 }


tmnxTestHdProfDurSec  OBJECT-TYPE
    SYNTAX      Integer32 (0..60)
    UNITS       "seconds"
    MAX-ACCESS  read-create
    STATUS      current
    DESCRIPTION
        "tmnxTestHdProfDurSec is the number of seconds the test head 
        test to be run"
    DEFVAL { 0 }
    ::= { tmnxTestHdProfEntry 10 }


tmnxTestHdProfFrameSize  OBJECT-TYPE
    SYNTAX      INTEGER (64..9212)
    MAX-ACCESS  read-create
    STATUS      current
    DESCRIPTION
        "tmnxTestHdProfFrameSize is the frame size to be used in frame 
        payload"
    DEFVAL { 1514 }
    ::= { tmnxTestHdProfEntry 11 }


tmnxTestHdProfTrapEnable OBJECT-TYPE
    SYNTAX       TruthValue
    MAX-ACCESS   read-create
    STATUS       current
    DESCRIPTION
        "tmnxTestHdProfTrapEnable when set to true tmnxOamTestHeadTestCompleted
        trap will be sent when the test run completes."
    DEFVAL { false }
    ::= { tmnxTestHdProfEntry 13 }

tmnxTestHdLastChanged OBJECT-TYPE
    SYNTAX       TimeStamp
    MAX-ACCESS   read-only
    STATUS       current
    DESCRIPTION
        "The value tmnxTestHdLastChanged indicates the system uptime when 
        an entry in tmnxTestHdProfTable was last changed."
    ::= { tmnxTestHdProfEntry 14 }    

tmnxTestHdProfAdminCIR OBJECT-TYPE
    SYNTAX       TTestHdCIRRate
    MAX-ACCESS   read-create
    STATUS       current
    DESCRIPTION
        "admin cir to be used in the payload"
    DEFVAL { 1000 }
    ::= { tmnxTestHdProfEntry 15 }
    

tmnxTestHdProfAdminPIR OBJECT-TYPE
    SYNTAX       TTestHdPIRRate
    MAX-ACCESS   read-create
    STATUS       current
    DESCRIPTION
        "admin pir to be used in the payload"
    DEFVAL { -1 }
    ::= { tmnxTestHdProfEntry 16 }

tmnxTestHdProfOperPIR OBJECT-TYPE
    SYNTAX       TTestHdPIRRate
    MAX-ACCESS   read-only
    STATUS       current
    DESCRIPTION
        "oper pir used in the payload"
    ::= { tmnxTestHdProfEntry 17 }

tmnxTestHdProfDot1pIn OBJECT-TYPE
    SYNTAX       Dot1PPriority 
    MAX-ACCESS   read-create
    STATUS       current
    DESCRIPTION
        "dot1p-in value to for this profile.
        "
    DEFVAL { -1 }
    ::= { tmnxTestHdProfEntry 18 }

tmnxTestHdProfDot1pOut OBJECT-TYPE
    SYNTAX       Dot1PPriority 
    MAX-ACCESS   read-create
    STATUS       current
    DESCRIPTION
        "dot1p-out value to for this profile.
        "
    DEFVAL { -1 }
    ::= { tmnxTestHdProfEntry 19 }

tmnxTestHdProfActiveTests OBJECT-TYPE
    SYNTAX       OCTET STRING 
    MAX-ACCESS   read-only
    STATUS       current
    DESCRIPTION
        "Active tests that are using this profile
        "
    ::= { tmnxTestHdProfEntry 20 }
    
tmnxTestHdProfCompetedTests OBJECT-TYPE
    SYNTAX       OCTET STRING 
    MAX-ACCESS   read-only
    STATUS       current
    DESCRIPTION
        "Completed tests that have used this profile
        "
    ::= { tmnxTestHdProfEntry 21 }
    
--

tmnxTestHdPayLdTable OBJECT-TYPE
    SYNTAX       SEQUENCE OF TmnxTestHdPayLdEntry
    MAX-ACCESS   not-accessible
    STATUS       current
    DESCRIPTION
        "This table maintains the mapping of a particular
         forwarding class traffic into the specified queue."
    ::= { tmnxTestHdProfObjects 2 }

tmnxTestHdPayLdEntry OBJECT-TYPE
    SYNTAX       TmnxTestHdPayLdEntry
    MAX-ACCESS   not-accessible
    STATUS       current
    DESCRIPTION
        "Information about a particular sap-ingress policy's
         forwarding class mappings to queues.

         Entries are created and deleted by user. They have
         a presumed StorageType of nonVolatile."
    INDEX { tmnxTestHdProfIndex, tmnxTestHdPayLdIndex }
    ::= { tmnxTestHdPayLdTable 1 }

TmnxTestHdPayLdEntry ::= SEQUENCE
    {
        tmnxTestHdPayLdIndex             INTEGER,
        tmnxTestHdPayLdRowStatus         RowStatus,
        tmnxTestHdPayLdDesc              TItemDescription,
        tmnxTestHdPayLddataPattrn        OCTET STRING, 
        tmnxTestHdPayLdSrcIpv4Addr       IpAddress,
        tmnxTestHdPayLdDstIpv4Addr       IpAddress,
        tmnxTestHdPayLdDSCP              TDSCPNameOrEmpty,
        tmnxTestHdPayLdIpProto           INTEGER,
        tmnxTestHdPayLdIpTos             INTEGER,
        tmnxTestHdPayLdIpTTL             INTEGER,
        tmnxTestHdPayLdSrcMac            MacAddress,
        tmnxTestHdPayLdDstMac            MacAddress,
        tmnxTestHdPayLdSrcPort           INTEGER,
        tmnxTestHdPayLdDstPort           INTEGER,
        tmnxTestHdPayLdLastChanged       TimeStamp,
        tmnxTestHdPayLdType              INTEGER,
        tmnxTestHdPayLdVTagOne           Integer32,
        tmnxTestHdPayLdVTagOneTpid      Unsigned32,
        tmnxTestHdPayLdVTagOneDot1p      Dot1PPriority,
        tmnxTestHdPayLdVTagTwo           Integer32,
        tmnxTestHdPayLdVTagTwoTpid      Unsigned32,
        tmnxTestHdPayLdVTagTwoDot1p      Dot1PPriority,
        tmnxTestHdPayLdEthertype         Unsigned32
    }
    
tmnxTestHdPayLdIndex OBJECT-TYPE
    SYNTAX       INTEGER (1..4)
    MAX-ACCESS   accessible-for-notify
    STATUS       current
    DESCRIPTION
        "tmnxTestHdPayLdIndex is the payload index"
    ::= { tmnxTestHdPayLdEntry 1 }

tmnxTestHdPayLdRowStatus OBJECT-TYPE
    SYNTAX       RowStatus
    MAX-ACCESS   read-create
    STATUS       current
    DESCRIPTION
        "Row Status for this entry."
    ::= { tmnxTestHdPayLdEntry 2 }

tmnxTestHdPayLdDesc OBJECT-TYPE
    SYNTAX       TItemDescription
    MAX-ACCESS   read-create
    STATUS       current
    DESCRIPTION "tmnxTestHdPayLdDesc is the textual description 
                entered by user for this payload"
    DEFVAL { ''H }
    ::= { tmnxTestHdPayLdEntry 3 }

tmnxTestHdPayLddataPattrn OBJECT-TYPE
    SYNTAX       OCTET STRING (SIZE (0..64))
    MAX-ACCESS   read-create
    STATUS       current
    DESCRIPTION
        "tmnxTestHdPayLddataPattrn is string of characters 0-9,a-f
        It is used to fill up the data field of the payload of the frame, 
        repeating it in the payload field as many time as need to fill 
        up the entire length of the payload"
    DEFVAL { "a1b2c3d4e5f6" }
    ::= { tmnxTestHdPayLdEntry 4 }

tmnxTestHdPayLdSrcIpv4Addr  OBJECT-TYPE
    SYNTAX      IpAddress
    MAX-ACCESS  read-create
    STATUS      current
    DESCRIPTION
        "tmnxTestHdPayLdSrcIpv4Addr is the source ip address to be used
        in frame payload"
    DEFVAL { 0 }
    ::= { tmnxTestHdPayLdEntry 5 }

    
tmnxTestHdPayLdDstIpv4Addr  OBJECT-TYPE
    SYNTAX      IpAddress
    MAX-ACCESS  read-create
    STATUS      current
    DESCRIPTION
        "tmnxTestHdPayLdDstIpv4Addr is the destination ip address to be used
        in frame payload"
    DEFVAL { 0 }
    ::= { tmnxTestHdPayLdEntry 6 }

    
tmnxTestHdPayLdDSCP OBJECT-TYPE
    SYNTAX       TDSCPNameOrEmpty
    MAX-ACCESS   read-create
    STATUS       current
    DESCRIPTION
        "tmnxTestHdPayLdDSCP is the dscp value  to be used in frame payload"
    DEFVAL { "be" }
    ::= { tmnxTestHdPayLdEntry 7 }

tmnxTestHdPayLdIpProto OBJECT-TYPE
    SYNTAX       INTEGER (0..255)
    MAX-ACCESS   read-create
    STATUS       current
    DESCRIPTION
        "tmnxTestHdPayLdIpProto is the ip protocal value  to be used in frame 
        payload"
    DEFVAL { 0 }
    ::= { tmnxTestHdPayLdEntry 8 }
    
tmnxTestHdPayLdIpTos OBJECT-TYPE
    SYNTAX       INTEGER (0..8)
    MAX-ACCESS   read-create
    STATUS       current
    DESCRIPTION
        "tmnxTestHdPayLdIpTos is the ip type of service value  to be used in frame 
        payload"
    DEFVAL { 0 }
    ::= { tmnxTestHdPayLdEntry 9 }
    
tmnxTestHdPayLdIpTTL OBJECT-TYPE
    SYNTAX       INTEGER (1..255)
    MAX-ACCESS   read-create
    STATUS       current
    DESCRIPTION
        "tmnxTestHdPayLdIpTTL is the ip time to live value  to be used in frame 
        payload"
    DEFVAL { 255 }
    ::= { tmnxTestHdPayLdEntry 10 }

tmnxTestHdPayLdSrcMac OBJECT-TYPE
    SYNTAX          MacAddress
    MAX-ACCESS      read-create
    STATUS          current
    DESCRIPTION
        "Source MAC to be used in the frame payload."
    DEFVAL { '000000000000'H }
    ::= { tmnxTestHdPayLdEntry 11 }


tmnxTestHdPayLdDstMac OBJECT-TYPE
    SYNTAX          MacAddress
    MAX-ACCESS      read-create
    STATUS          current
    DESCRIPTION
        "Destination MAC to be used in the frame payload."
    DEFVAL { '000000000000'H }
    ::= { tmnxTestHdPayLdEntry 12 }

tmnxTestHdPayLdSrcPort OBJECT-TYPE
    SYNTAX          INTEGER(0..65535)
    MAX-ACCESS      read-create
    STATUS          current
    DESCRIPTION
        "Source Port to be used in the frame payload."
    DEFVAL { 0 }
    ::= { tmnxTestHdPayLdEntry 13 }


tmnxTestHdPayLdDstPort OBJECT-TYPE
    SYNTAX          INTEGER(0..65535)
    MAX-ACCESS      read-create
    STATUS          current
    DESCRIPTION
        "Destination Port to be used in the frame payload."
    DEFVAL { 0 }
    ::= { tmnxTestHdPayLdEntry 14 }

tmnxTestHdPayLdLastChanged OBJECT-TYPE
    SYNTAX       TimeStamp
    MAX-ACCESS   read-only
    STATUS       current
    DESCRIPTION
        "The value tmnxTestHdPayLdLastChanged indicates the system 
        uptime when an entry in tmnxTestHdPayLdTable was last changed."
    ::= { tmnxTestHdPayLdEntry 15 }

tmnxTestHdPayLdType OBJECT-TYPE
    SYNTAX       INTEGER {
                          tcp-ipv4 (1), 
                          l2 (2),
                          udp-ipv4 (3),
                          ipv4 (4)
                        }
    MAX-ACCESS   read-create
    STATUS       current
    DESCRIPTION
        "tmnxTestHdPayLdType indicates the payload type for
        this frame payload."
    DEFVAL { tcp-ipv4 }
    ::= { tmnxTestHdPayLdEntry 16 }
       
tmnxTestHdPayLdVTagOne  OBJECT-TYPE
    SYNTAX      Integer32 (-1..4094)
    MAX-ACCESS  read-create
    STATUS      current
    DESCRIPTION
        "Vlan tag one to be used in payload , if set to -1 packets are sent out without
         vlan tag"
    DEFVAL { -1 }
    ::= { tmnxTestHdPayLdEntry 17 }

tmnxTestHdPayLdVTagOneTpid         OBJECT-TYPE
    SYNTAX      Unsigned32 ('600'H..'ffff'H)
    MAX-ACCESS  read-create
    STATUS      current
    DESCRIPTION
        "The tmnxTestHdPayLdVTagOneTpid variable indicates the ethertype to be set 
        in the payload."
    DEFVAL { '8100'H }
    ::= { tmnxTestHdPayLdEntry 18 }

tmnxTestHdPayLdVTagOneDot1p OBJECT-TYPE
    SYNTAX          Dot1PPriority
    MAX-ACCESS      read-create
    STATUS          current
    DESCRIPTION
         "IEEE 802.1p priority value for this frame payload.
         "
    DEFVAL { 0 }
    ::= { tmnxTestHdPayLdEntry 19 }

tmnxTestHdPayLdVTagTwo  OBJECT-TYPE
    SYNTAX      Integer32 (-1..4094)
    MAX-ACCESS  read-create
    STATUS      current
    DESCRIPTION
        "Vlan tag two to be used in payload , if set to -1 packets are sent out without
         vlan tag"
    DEFVAL { -1 }        
    ::= { tmnxTestHdPayLdEntry 20 }

tmnxTestHdPayLdVTagTwoTpid         OBJECT-TYPE
    SYNTAX      Unsigned32 ('600'H..'ffff'H)
    MAX-ACCESS  read-create
    STATUS      current
    DESCRIPTION
        "The tmnxTestHdPayLdVTagTwoTpid variable indicates the ethertype to be set 
        in the payload."
    DEFVAL { '8100'H }
    ::= { tmnxTestHdPayLdEntry 21 }

tmnxTestHdPayLdVTagTwoDot1p OBJECT-TYPE
    SYNTAX          Dot1PPriority
    MAX-ACCESS      read-create
    STATUS          current
    DESCRIPTION
         "IEEE 802.1p priority value for this frame payload.
         "
    DEFVAL { 0 }
    ::= { tmnxTestHdPayLdEntry 22 }

tmnxTestHdPayLdEthertype         OBJECT-TYPE
    SYNTAX      Unsigned32 ('600'H..'ffff'H)
    MAX-ACCESS  read-create
    STATUS      current
    DESCRIPTION
        "The tmnxTestHdPayLdEthertype variable indicates the ethertype to be set 
        in the payload."
    DEFVAL { '800'H }
    ::= { tmnxTestHdPayLdEntry 23 }

    
tmnxTestHdAccCritTable OBJECT-TYPE
    SYNTAX       SEQUENCE OF TmnxTestHdAccCritEntry
    MAX-ACCESS   not-accessible
    STATUS       current
    DESCRIPTION
        "This table maintains the mapping of a particular
         forwarding class traffic into the specified queue."
    ::= { tmnxTestHdProfObjects 3 }

tmnxTestHdAccCritEntry OBJECT-TYPE
    SYNTAX       TmnxTestHdAccCritEntry
    MAX-ACCESS   not-accessible
    STATUS       current
    DESCRIPTION
        "Information about a particular sap-ingress policy's
         forwarding class mappings to queues.

         Entries are created and deleted by user. They have
         a presumed StorageType of nonVolatile."
    INDEX { tmnxTestHdProfIndex, tmnxTestHdAccCritIndex }
    ::= { tmnxTestHdAccCritTable 1 }

TmnxTestHdAccCritEntry ::= SEQUENCE
    {
        tmnxTestHdAccCritIndex             INTEGER,
        tmnxTestHdAccCritRowStatus         RowStatus,
        tmnxTestHdAccCritJittrRiseThres    INTEGER,        
        tmnxTestHdAccCritLatRiseThres      INTEGER,
        tmnxTestHdAccCritLossRiseThres     INTEGER,
        tmnxTestHdAccCritLastChanged       TimeStamp,
        tmnxTestHdAccCritLossRiseThresIn   INTEGER,
        tmnxTestHdAccCritLossRiseThresOut  INTEGER,
        tmnxTestHdAccCritCirThres          INTEGER,
        tmnxTestHdAccCritPirThres          INTEGER,
        tmnxTestHdAccCritLatRiseThresIn    INTEGER,
        tmnxTestHdAccCritLatRiseThresOut   INTEGER,
        tmnxTestHdAccCritJittrRiseThresIn  INTEGER,
        tmnxTestHdAccCritJittrRiseThresOut INTEGER
     }

tmnxTestHdAccCritIndex OBJECT-TYPE
    SYNTAX       INTEGER (1..4)
    MAX-ACCESS   accessible-for-notify
    STATUS       current
    DESCRIPTION
        ""
    ::= { tmnxTestHdAccCritEntry 1 }

tmnxTestHdAccCritRowStatus OBJECT-TYPE
    SYNTAX       RowStatus
    MAX-ACCESS   read-create
    STATUS       current
    DESCRIPTION
        "Row Status for this entry."
    ::= { tmnxTestHdAccCritEntry 2 }
    
tmnxTestHdAccCritJittrRiseThres OBJECT-TYPE
    SYNTAX      INTEGER (-1 | 0..2147483000)
    UNITS       "microseconds"
    MAX-ACCESS   read-create
    STATUS       current
    DESCRIPTION 
        "tmnxTestHdAccCritJittrRiseThres is the acceptance criteria
        jitter rising threshold to be used for test run"
    DEFVAL { -1 }
    ::= { tmnxTestHdAccCritEntry 3 }

tmnxTestHdAccCritLatRiseThres OBJECT-TYPE
    SYNTAX      INTEGER (-1 | 0..2147483000)
    UNITS       "microseconds"
    MAX-ACCESS   read-create
    STATUS       current
    DESCRIPTION
        "tmnxTestHdAccCritLatRiseThres is the acceptance criteria
        latency rising threshold to be used for test run"
    DEFVAL { -1 }
    ::= { tmnxTestHdAccCritEntry 4 }

tmnxTestHdAccCritLossRiseThres OBJECT-TYPE
    SYNTAX      INTEGER (-1 | 0..1000000)
    UNITS       "10000th of a percent"
    MAX-ACCESS   read-create
    STATUS       current
    DESCRIPTION
        "tmnxTestHdAccCritLossRiseThres is the acceptance criteria
        loss rising threshold to be used for test run"    
    DEFVAL { -1 }
    ::= { tmnxTestHdAccCritEntry 5 }

tmnxTestHdAccCritLastChanged OBJECT-TYPE
    SYNTAX       TimeStamp
    MAX-ACCESS   read-only
    STATUS       current
    DESCRIPTION
        "The value tmnxTestHdAccCritLastChanged indicates the system 
        uptime when an entry in tmnxTestHdAccCritTable was last changed."
    ::= { tmnxTestHdAccCritEntry 6 }

tmnxTestHdAccCritLossRiseThresIn OBJECT-TYPE
    SYNTAX      INTEGER (-1 | 0..1000000)
    UNITS       "10000th of a percent"
    MAX-ACCESS   read-create
    STATUS       current
    DESCRIPTION
        "tmnxTestHdAccCritLossRiseThresIn is the acceptance criteria
        loss rising threshold in to be used for test run"    
    DEFVAL { -1 }
    ::= { tmnxTestHdAccCritEntry 7 }

tmnxTestHdAccCritLossRiseThresOut OBJECT-TYPE
    SYNTAX      INTEGER (-1 | 0..1000000)
    UNITS       "10000th of a percent"
    MAX-ACCESS   read-create
    STATUS       current
    DESCRIPTION
        "tmnxTestHdAccCritLossRiseThresOut is the acceptance criteria
        out loss rising threshold to be used for test run"    
    DEFVAL { -1 }
    ::= { tmnxTestHdAccCritEntry 8 }
    
tmnxTestHdAccCritCirThres OBJECT-TYPE
    SYNTAX      INTEGER (-1 | 0..1000000)
    MAX-ACCESS   read-create
    STATUS       current
    DESCRIPTION
        "tmnxTestHdAccCritCirThres is the acceptance criteria
        cir threshold to be used for test run"    
    DEFVAL { -1 }
    ::= { tmnxTestHdAccCritEntry 9 }

tmnxTestHdAccCritPirThres OBJECT-TYPE
    SYNTAX      INTEGER (-1 | 0..1000000)
    MAX-ACCESS   read-create
    STATUS       current
    DESCRIPTION
        "tmnxTestHdAccCritPirThres is the acceptance criteria
        pir threshold to be used for test run"    
    DEFVAL { -1 }
    ::= { tmnxTestHdAccCritEntry 10 }

tmnxTestHdAccCritLatRiseThresIn OBJECT-TYPE
    SYNTAX      INTEGER (-1 | 0..2147483000)
    UNITS       "microseconds"
    MAX-ACCESS   read-create
    STATUS       current
    DESCRIPTION
        "tmnxTestHdAccCritLatRiseThresIn is the acceptance criteria
        latency rising threshold-in to be used for test run"
    DEFVAL { -1 }
    ::= { tmnxTestHdAccCritEntry 11 }

tmnxTestHdAccCritLatRiseThresOut OBJECT-TYPE
    SYNTAX      INTEGER (-1 | 0..2147483000)
    UNITS       "microseconds"
    MAX-ACCESS   read-create
    STATUS       current
    DESCRIPTION
        "tmnxTestHdAccCritLatRiseThresOut is the acceptance criteria
        latency rising threshold out to be used for test run"
    DEFVAL { -1 }
    ::= { tmnxTestHdAccCritEntry 12 }

tmnxTestHdAccCritJittrRiseThresIn OBJECT-TYPE
    SYNTAX      INTEGER (-1 | 0..2147483000)
    UNITS       "microseconds"
    MAX-ACCESS   read-create
    STATUS       current
    DESCRIPTION 
        "tmnxTestHdAccCritJittrRiseThresIn is the acceptance criteria
        jitter rising threshold-in to be used for test run"
    DEFVAL { -1 }
    ::= { tmnxTestHdAccCritEntry 13 }

tmnxTestHdAccCritJittrRiseThresOut OBJECT-TYPE
    SYNTAX      INTEGER (-1 | 0..2147483000)
    UNITS       "microseconds"
    MAX-ACCESS   read-create
    STATUS       current
    DESCRIPTION 
        "tmnxTestHdAccCritJittrRiseThresOut is the acceptance criteria
        jitter rising threshold-out to be used for test run"
    DEFVAL { -1 }
    ::= { tmnxTestHdAccCritEntry 14 }


--

tmnxTestHdSessTable OBJECT-TYPE
    SYNTAX       SEQUENCE OF TmnxTestHdSessEntry
    MAX-ACCESS   not-accessible
    STATUS       current
    DESCRIPTION
        "This table maintains the mapping of a particular
         forwarding class traffic into the specified queue."
    ::= { tmnxTestHdProfObjects 4 }

tmnxTestHdSessEntry OBJECT-TYPE
    SYNTAX       TmnxTestHdSessEntry
    MAX-ACCESS   not-accessible
    STATUS       current
    DESCRIPTION
        "Information about a particular test head result.
        
         Entries are read-only for the user."
    INDEX { tmnxTestHdSessOwnerName, tmnxTestHdSessTestName  }
    ::= { tmnxTestHdSessTable 1 }

TmnxTestHdSessEntry ::= SEQUENCE
    {
        tmnxTestHdSessOwnerName                   SnmpAdminString,
        tmnxTestHdSessTestName                    SnmpAdminString,
        tmnxTestHdSessStartTime                   DateAndTime,
        tmnxTestHdSessCompletedTime               DateAndTime,
        tmnxTestHdSessTotalTime                   INTEGER,
        tmnxTestHdSessFc                          TFCName,
        tmnxTestHdSessCompleted                   TruthValue,
        tmnxTestHdSessStopped                     TruthValue,
        tmnxTestHdSessProfId                      INTEGER,
        tmnxTestHdSessPayLdId                     INTEGER,
        tmnxTestHdSessAccCritId                   INTEGER,
        tmnxTestHdSessSapPortId                   TmnxPortID,
        tmnxTestHdSessSapEncapValue               TmnxEncapVal,
        tmnxTestHdSessTransCount                  Counter64,
        tmnxTestHdSessRecvCount                   Counter64,
        tmnxTestHdSessMinLatency                  Counter64,
        tmnxTestHdSessMaxLatency                  Counter64,
        tmnxTestHdSessMeasuredLatency             Counter64,
        tmnxTestHdSessMeasuredJitter              INTEGER
    }

tmnxTestHdSessOwnerName OBJECT-TYPE
    SYNTAX      SnmpAdminString (SIZE(1..32))
    MAX-ACCESS  not-accessible
    STATUS      current
    DESCRIPTION
        "The test name index of this Test head test session.
         "
    ::= { tmnxTestHdSessEntry 1 }

tmnxTestHdSessTestName OBJECT-TYPE
    SYNTAX      SnmpAdminString (SIZE(1..32))
    MAX-ACCESS  not-accessible
    STATUS      current
    DESCRIPTION
        "The test name index of this Test head test session.
         "
    ::= { tmnxTestHdSessEntry 2 }

tmnxTestHdSessStartTime OBJECT-TYPE
    SYNTAX      DateAndTime
    MAX-ACCESS  read-only
    STATUS      current
    DESCRIPTION
        "tmnxTestHdSessStartTime test head start time for this session"
    ::= { tmnxTestHdSessEntry 3 }


tmnxTestHdSessCompletedTime OBJECT-TYPE
    SYNTAX      DateAndTime
    MAX-ACCESS  read-only
    STATUS      current
    DESCRIPTION
        "tmnxTestHdSessCompletedTime is the time stamp at which this 
        test head run session has completed."
    ::= { tmnxTestHdSessEntry 4 }
    

tmnxTestHdSessTotalTime OBJECT-TYPE
    SYNTAX      INTEGER
    UNITS       "seconds"
    MAX-ACCESS  read-only
    STATUS      current
    DESCRIPTION
        "tmnxTestHdSessTotalTime is the total time since test head test 
        has started"
    ::= { tmnxTestHdSessEntry 5 }
    
tmnxTestHdSessFc OBJECT-TYPE
    SYNTAX       TFCName
    MAX-ACCESS   read-only
    STATUS       current
    DESCRIPTION
        "tmnxTestHdFc is the fc used in this test head session"        
    ::= { tmnxTestHdSessEntry 6 }

tmnxTestHdSessCompleted OBJECT-TYPE
    SYNTAX       TruthValue 
    MAX-ACCESS   read-only
    STATUS       current
    DESCRIPTION 
        "tmnxTestHdSessCompleted is true if the test is completed else it is
        false. "
    ::= { tmnxTestHdSessEntry 7 }

tmnxTestHdSessStopped OBJECT-TYPE
    SYNTAX       TruthValue 
    MAX-ACCESS   read-only
    STATUS       current
    DESCRIPTION
        "tmnxTestHdStopped is true if the test is stopped midway else it is
        false. "
    ::= { tmnxTestHdSessEntry 8 }
    
tmnxTestHdSessProfId OBJECT-TYPE
    SYNTAX       INTEGER (0..10)
    MAX-ACCESS   read-only
    STATUS       current
    DESCRIPTION
        "tmnxTestHdSessProfId is the profile index for this session"
    ::= { tmnxTestHdSessEntry 9 }


tmnxTestHdSessPayLdId OBJECT-TYPE
    SYNTAX       INTEGER (1..4)
    MAX-ACCESS   read-only
    STATUS       current
    DESCRIPTION
        "tmnxTestHdSessPayLdId is the payload index used for this session"
    ::= { tmnxTestHdSessEntry 10 }

tmnxTestHdSessAccCritId OBJECT-TYPE
    SYNTAX       INTEGER (1..4)
    MAX-ACCESS   read-only
    STATUS       current
    DESCRIPTION
        "tmnxTestHdSessAccCritId is the acceptance criteria id used for
        this test run"
    ::= { tmnxTestHdSessEntry 11 }

tmnxTestHdSessSapPortId OBJECT-TYPE
    SYNTAX          TmnxPortID
    MAX-ACCESS      read-only
    STATUS          current
    DESCRIPTION     "The sap port id ID used in for this test run."
    ::= { tmnxTestHdSessEntry 12 }

tmnxTestHdSessSapEncapValue OBJECT-TYPE
    SYNTAX          TmnxEncapVal
    MAX-ACCESS      read-only
    STATUS          current
    DESCRIPTION     "The sap encap value used in this test run."
    ::= { tmnxTestHdSessEntry 13 }

tmnxTestHdSessTransCount OBJECT-TYPE
    SYNTAX          Counter64
    MAX-ACCESS      read-only
    STATUS          current
    DESCRIPTION     "The total number of packets injected"
    ::= { tmnxTestHdSessEntry 14 }


tmnxTestHdSessRecvCount OBJECT-TYPE
    SYNTAX          Counter64
    MAX-ACCESS      read-only
    STATUS          current
    DESCRIPTION     "The total number of packets received"
    ::= { tmnxTestHdSessEntry 15 }

tmnxTestHdSessMinLatency OBJECT-TYPE
    SYNTAX          Counter64
    UNITS           "microseconds"
    MAX-ACCESS      read-only
    STATUS          current
    DESCRIPTION     "The Latency measured minimum for this test"
    ::= { tmnxTestHdSessEntry 16 }

tmnxTestHdSessMaxLatency OBJECT-TYPE
    SYNTAX          Counter64
    UNITS           "microseconds"
    MAX-ACCESS      read-only
    STATUS          current
    DESCRIPTION     "The Latency measured maximum for this test"
    ::= { tmnxTestHdSessEntry 17 }

tmnxTestHdSessMeasuredLatency OBJECT-TYPE
    SYNTAX          Counter64
    UNITS           "microseconds"
    MAX-ACCESS      read-only
    STATUS          current
    DESCRIPTION     "The Latency measured for this test"
    ::= { tmnxTestHdSessEntry 18 }


tmnxTestHdSessMeasuredJitter OBJECT-TYPE
    SYNTAX          INTEGER
    UNITS           "microseconds"
    MAX-ACCESS      read-only
    STATUS          current
    DESCRIPTION     "The Jitter measured for this test"
    ::= { tmnxTestHdSessEntry 19 }

--

tmnxTestHdResultsTable OBJECT-TYPE
    SYNTAX       SEQUENCE OF TmnxTestHdResultsEntry
    MAX-ACCESS   not-accessible
    STATUS       current
    DESCRIPTION
        "This table maintains the mapping of a particular
         forwarding class traffic into the specified queue."
    ::= { tmnxTestHdProfObjects 5 }

tmnxTestHdResultsEntry OBJECT-TYPE
    SYNTAX       TmnxTestHdResultsEntry
    MAX-ACCESS   not-accessible
    STATUS       current
    DESCRIPTION
        "Information about a particular test head result.
        
         Entries are read-only for the user."
    INDEX { tmnxTestHdOwnerName, tmnxTestHdTestName  }
    ::= { tmnxTestHdResultsTable 1 }

TmnxTestHdResultsEntry ::= SEQUENCE
    {
        tmnxTestHdOwnerName                   SnmpAdminString,
        tmnxTestHdTestName                    SnmpAdminString,
        tmnxTestHdResProfId                   INTEGER,
        tmnxTestHdResProfPayLdId              INTEGER,
        tmnxTestHdResProfAccCritId            INTEGER,
        tmnxTestHdResTransCount               Counter64,
        tmnxTestHdResRecvCount                Counter64,
        tmnxTestHdResMeasuredThruput          INTEGER,
        tmnxTestHdResMeasuredFLR              INTEGER,
        tmnxTestHdResMeasuredLatency          Counter64,
        tmnxTestHdResLatencyAccptanceResult   INTEGER,
        tmnxTestHdResMeasuredJitter           INTEGER,
        tmnxTestHdResJitterAccptanceResult    INTEGER,
        tmnxTestHdResSapPortId                TmnxPortID,
        tmnxTestHdResSapEncapValue            TmnxEncapVal,
        tmnxTestHdResFLRAccptanceResult       INTEGER,
        tmnxTestHdResMinLatency               Counter64,
        tmnxTestHdResMaxLatency               Counter64
    }

tmnxTestHdOwnerName OBJECT-TYPE
    SYNTAX      SnmpAdminString (SIZE(1..32))
    MAX-ACCESS  not-accessible
    STATUS      current
    DESCRIPTION
        "The owner name index of the Test head test.
         "
    ::= { tmnxTestHdResultsEntry 1 }

tmnxTestHdTestName OBJECT-TYPE
    SYNTAX      SnmpAdminString (SIZE(1..32))
    MAX-ACCESS  not-accessible
    STATUS      current
    DESCRIPTION
        "The test name index of the Test head test.
         "
    ::= { tmnxTestHdResultsEntry 2 }
    
tmnxTestHdResProfId OBJECT-TYPE
    SYNTAX          INTEGER
    MAX-ACCESS      read-only
    STATUS          current
    DESCRIPTION     "The Testhead profile Id used for this test"
    ::= { tmnxTestHdResultsEntry 3 }

tmnxTestHdResProfPayLdId OBJECT-TYPE
    SYNTAX          INTEGER
    MAX-ACCESS      read-only
    STATUS          current
    DESCRIPTION     "The Testhead profile Pay Load Id used for this 
                     test"
    ::= { tmnxTestHdResultsEntry 4 }

tmnxTestHdResProfAccCritId OBJECT-TYPE
    SYNTAX          INTEGER
    MAX-ACCESS      read-only
    STATUS          current
    DESCRIPTION     "The Testhead profile Acceptance Criteria Id used 
                     for this test"
    ::= { tmnxTestHdResultsEntry 5 }

tmnxTestHdResTransCount OBJECT-TYPE
    SYNTAX          Counter64
    MAX-ACCESS      read-only
    STATUS          current
    DESCRIPTION     "The total number of packets injected"
    ::= { tmnxTestHdResultsEntry 6 }


tmnxTestHdResRecvCount OBJECT-TYPE
    SYNTAX          Counter64
    MAX-ACCESS      read-only
    STATUS          current
    DESCRIPTION     "The total number of packets received"
    ::= { tmnxTestHdResultsEntry 7 }

tmnxTestHdResMeasuredThruput OBJECT-TYPE
    SYNTAX          INTEGER
    UNITS           "kbps"
    MAX-ACCESS      read-only
    STATUS          current
    DESCRIPTION     "The throughput measured for this test"
    ::= { tmnxTestHdResultsEntry 8 }

tmnxTestHdResMeasuredFLR OBJECT-TYPE
    SYNTAX          INTEGER
    UNITS           "10000th of a percent"
    MAX-ACCESS      read-only
    STATUS          current
    DESCRIPTION     "The frame loss ratio measured for this test, if
                     set to -1 tmnxTestHdResMeasuredFLR is not applicable
                     for this test"
    ::= { tmnxTestHdResultsEntry 9 }

tmnxTestHdResMeasuredLatency OBJECT-TYPE
    SYNTAX          Counter64
    UNITS           "microseconds"
    MAX-ACCESS      read-only
    STATUS          current
    DESCRIPTION     "The Latency measured for this test"
    ::= { tmnxTestHdResultsEntry 10 }

tmnxTestHdResLatencyAccptanceResult OBJECT-TYPE
    SYNTAX          INTEGER {
                        pass (1),
                        fail (2),
                        not-applicable(3)
                    }
    MAX-ACCESS      read-only
    STATUS          current
    DESCRIPTION     "The Latency Acceptance for this test"
    ::= { tmnxTestHdResultsEntry 11 }

tmnxTestHdResMeasuredJitter OBJECT-TYPE
    SYNTAX          INTEGER
    UNITS           "microseconds"
    MAX-ACCESS      read-only
    STATUS          current
    DESCRIPTION     "The Jitter measured for this test"
    ::= { tmnxTestHdResultsEntry 12 }

tmnxTestHdResJitterAccptanceResult OBJECT-TYPE
    SYNTAX          INTEGER {
                        pass (1),
                        fail (2),
                        not-applicable(3)
                    }
    MAX-ACCESS      read-only
    STATUS          current
    DESCRIPTION     "The Jitter Acceptance for this test"
    ::= { tmnxTestHdResultsEntry 13 }

tmnxTestHdResSapPortId OBJECT-TYPE
    SYNTAX          TmnxPortID
    MAX-ACCESS      read-only
    STATUS          current
    DESCRIPTION     "The sap port id ID used in for this test run."
    ::= { tmnxTestHdResultsEntry 14 }

tmnxTestHdResSapEncapValue OBJECT-TYPE
    SYNTAX          TmnxEncapVal
    MAX-ACCESS      read-only
    STATUS          current
    DESCRIPTION     "The sap encap value used in this test run."
    ::= { tmnxTestHdResultsEntry 15 }

tmnxTestHdResFLRAccptanceResult OBJECT-TYPE
    SYNTAX          INTEGER {
                        pass (1),
                        fail (2),
                        not-applicable(3)
                    }
    MAX-ACCESS      read-only
    STATUS          current
    DESCRIPTION     "The FLR Acceptance for this test"
    ::= { tmnxTestHdResultsEntry 16 }


tmnxTestHdResMinLatency OBJECT-TYPE
    SYNTAX          Counter64
    UNITS           "microseconds"
    MAX-ACCESS      read-only
    STATUS          current
    DESCRIPTION     "The Latency measured minimum for this test"
    ::= { tmnxTestHdResultsEntry 17 }

tmnxTestHdResMaxLatency OBJECT-TYPE
    SYNTAX          Counter64
    UNITS           "microseconds"
    MAX-ACCESS      read-only
    STATUS          current
    DESCRIPTION     "The Latency measured maximum for this test"
    ::= { tmnxTestHdResultsEntry 18 }

tmnxTestHdProfScalarObjs OBJECT IDENTIFIER       ::= { tmnxTestHdProfObjects 6 }

tmnxTestHdName OBJECT-TYPE
    SYNTAX      SnmpAdminString (SIZE(1..32))
    MAX-ACCESS  read-write
    STATUS      current
    DESCRIPTION
        "tmnxTestHdName is a mandatory parameter that needs to be 
        set along with tmnxTestHdAdminStatus to start a test head 
        test.
        "
    ::= { tmnxTestHdProfScalarObjs 1 }


tmnxTestHdOwner OBJECT-TYPE
    SYNTAX      SnmpAdminString (SIZE(1..32))
    MAX-ACCESS  read-write
    STATUS      current
    DESCRIPTION
        "tmnxTestHdOwner is a mandatory parameter that needs to be 
        set along with tmnxTestHdAdminStatus to start a test head 
        test."
    ::= { tmnxTestHdProfScalarObjs 2 }

tmnxTestHdStartTime OBJECT-TYPE
    SYNTAX      DateAndTime
    MAX-ACCESS  accessible-for-notify
    STATUS      current
    DESCRIPTION
        "tmnxTestHdStartTime test head start time sent in the trap 
        message"
    ::= { tmnxTestHdProfScalarObjs 3 }

tmnxTestHdElapsedTime OBJECT-TYPE
    SYNTAX      INTEGER
    UNITS       "seconds"    
    MAX-ACCESS  accessible-for-notify
    STATUS      current
    DESCRIPTION
        "tmnxTestHdElapsedTime is the elapsed time since test head test 
        has started"
    ::= { tmnxTestHdProfScalarObjs 4 }
    
tmnxTestHdFc OBJECT-TYPE
    SYNTAX       TFCName
    MAX-ACCESS   read-write
    STATUS       current
    DESCRIPTION
        "tmnxTestHdFc is an  optional parameter that needs to be 
        set along with tmnxTestHdAdminStatus to start a test head 
        test.If tmnxTestHdFc is not given along with 
        tmnxTestHdAdminStatus default forwarding class 'be' would be
        used"        
    DEFVAL { "be" }
    ::= { tmnxTestHdProfScalarObjs 5 }

tmnxTestHdAvgLatency OBJECT-TYPE
    SYNTAX      INTEGER (0..2147483000)
    UNITS       "microseconds"
    MAX-ACCESS   accessible-for-notify
    STATUS       current
    DESCRIPTION 
        "tmnxTestHdAvgLatency is the measured average latency in the
        test head run. tmnxTestHdAvgLatency is sent in the trap upon 
        test completion"
    ::= { tmnxTestHdProfScalarObjs 6 }


tmnxTestHdFrLossRatio OBJECT-TYPE
    SYNTAX      INTEGER (0..10000000)
    UNITS       "10000th of a percent"
    MAX-ACCESS   accessible-for-notify
    STATUS       current
    DESCRIPTION 
        "tmnxTestHdFrLossRatio is the measured frame loss ratio 
        in the test head run. tmnxTestHdFrLossRatio is sent in the 
        trap upon test completion"
    ::= { tmnxTestHdProfScalarObjs 7 }

tmnxTestHdJitter OBJECT-TYPE
    SYNTAX      INTEGER (0..2147483000)
    UNITS       "microseconds"
    MAX-ACCESS   accessible-for-notify
    STATUS       current
    DESCRIPTION 
        "tmnxTestHdJitter is the measured jitter  in the test head run. 
        tmnxTestHdJitter is sent in the trap upon test completion"    
    ::= { tmnxTestHdProfScalarObjs 8 }

tmnxTestHdDsiredThrpt OBJECT-TYPE
    SYNTAX      INTEGER 
    MAX-ACCESS   accessible-for-notify
    STATUS       current
    DESCRIPTION
        "tmnxTestHdDsiredThrpt is the desired through put in the test head 
        run. tmnxTestHdDsiredThrpt is sent in the trap upon test completion"
    ::= { tmnxTestHdProfScalarObjs 9 }


tmnxTestHdAchvdThrpt OBJECT-TYPE
    SYNTAX      INTEGER 
    MAX-ACCESS   accessible-for-notify
    STATUS       current
    DESCRIPTION 
        "tmnxTestHdAchvdThrpt is the acheived through put in the test head 
        run. tmnxTestHdAchvdThrpt is sent in the trap upon test completion"
    ::= { tmnxTestHdProfScalarObjs 10 }
    
tmnxTestHdCompleted OBJECT-TYPE
    SYNTAX      TruthValue 
    MAX-ACCESS   accessible-for-notify
    STATUS       current
    DESCRIPTION 
        "tmnxTestHdCompleted is true if the test is completed else it is
        false. tmnxTestHdCompleted is sent in the trap upon test completion"    
    ::= { tmnxTestHdProfScalarObjs 11 }

tmnxTestHdStopped OBJECT-TYPE
    SYNTAX      TruthValue 
    MAX-ACCESS   accessible-for-notify
    STATUS       current
    DESCRIPTION
        "tmnxTestHdStopped is true if the test is stopped midway else it is
        false. tmnxTestHdStopped is sent in the trap upon test completion"        
    ::= { tmnxTestHdProfScalarObjs 12 }

tmnxTestHdTestStatus OBJECT-TYPE
    SYNTAX      INTEGER { 
                    pass (1),
                    fail (2),
                    not-available(3)
                }
    MAX-ACCESS   accessible-for-notify
    STATUS       current
    DESCRIPTION
        "tmnxTestHdTestStatus is sent in the trap upon test completion.
        tmnxTestHdTestStatus is pass if the desired test results are 
        acheived."
    ::= { tmnxTestHdProfScalarObjs 13 }

tmnxTestHdCompletedTime OBJECT-TYPE
    SYNTAX      DateAndTime
    MAX-ACCESS  accessible-for-notify
    STATUS      current
    DESCRIPTION
        "tmnxTestHdCompletedTime is the time at which test head run
        has completed. tmnxTestHdCompletedTime is sent in the trap upon 
        test completion."
    ::= { tmnxTestHdProfScalarObjs 14 }
    
tmnxTestHdSapPortId OBJECT-TYPE
    SYNTAX          TmnxPortID
    MAX-ACCESS      read-write
    STATUS          current
    DESCRIPTION     
         "The Sap Port ID to be used for the test run, it has to be supplied
         along with tmnxTestHdSapEncapValue when the test is started.
         "
    ::= { tmnxTestHdProfScalarObjs 15 }

tmnxTestHdSapEncapValue OBJECT-TYPE
    SYNTAX          TmnxEncapVal
    MAX-ACCESS      read-write
    STATUS          current
    DESCRIPTION     
         "The Sap Encap value to be used for the test run, it has to be supplied
         along with tmnxTestHdSapPortId when the test is started.
         "
    ::= { tmnxTestHdProfScalarObjs 16 }
    
tmnxTestHdAdminStatus OBJECT-TYPE
    SYNTAX      INTEGER {
                          enabled(1), -- test should be started
                          disabled(2) -- test should be stopped
                        }
    MAX-ACCESS  read-write
    STATUS      current
    DESCRIPTION
        "Reflects the desired state that a Test Head should be
         in:

           enabled(1)  - Attempt to activate the test as defined by
            tmnxTestHdName, tmnxTestHdOwner, tmnxTestHdProfId, 
            tmnxTestHdPayLdId, tmnxTestHdAccCritId, tmnxTestHdSapPortId,
            tmnxTestHdSapEncapValue, tmnxTestHdFc
                         .
           disabled(2) - Deactivate the test as defined by this
                         tmnxOamPingCtlEntry.

         An attempt to set tmnxOamPingCtlAdminStatus to 'enabled' will fail
         if the parameters required by a particular TestHead test have
         not been set along with tmnxTestHdAdminStatus  Upon completion of 
         a Test head test, he agent will reset the value of this object to 
         'disabled'. When this object has the value 'enabled' an attempt to modify
         any of the test parameters will fail with an inconsistentValue
         error."
    DEFVAL { disabled }
    ::= { tmnxTestHdProfScalarObjs 17 }

tmnxTestHdProfId OBJECT-TYPE
    SYNTAX       INTEGER (0..10)
    MAX-ACCESS   read-write
    STATUS       current
    DESCRIPTION
         "tmnxTestHdProfId is the test head profile to be used for 
         the test run, it has to be supplied along with tmnxTestHdAdminStatus
         when the test is started. tmnxTestHdProfEntry corresponding to 
         tmnxTestHdProfId should be creted before starting the test.
         "
    ::= { tmnxTestHdProfScalarObjs 18 }

tmnxTestHdAccCritId OBJECT-TYPE
    SYNTAX       INTEGER (1..4)
    MAX-ACCESS   read-write
    STATUS       current
    DESCRIPTION
         "tmnxTestHdAccCritId is the acceptance criteria to be used for 
         the test run, it is an optional parameter to be supplied along 
         with tmnxTestHdAdminStatus when the test is started. 
         tmnxTestHdAccCritEntry corresponding to tmnxTestHdAccCritId 
         should be creted before starting the test.
         "
    ::= { tmnxTestHdProfScalarObjs 19 }

tmnxTestHdPayLdId OBJECT-TYPE
    SYNTAX       INTEGER (1..4)
    MAX-ACCESS   read-write
    STATUS       current
    DESCRIPTION
         "tmnxTestHdPayLd is the frame payload to be used for 
         the test run, it is an optional parameter to be supplied along 
         with tmnxTestHdAdminStatus when the test is started. 
         tmnxTestHdPayLdEntry corresponding to tmnxTestHdPayLdIndex 
         should be creted before starting the test.
         "
    ::= { tmnxTestHdProfScalarObjs 20 }
    
tmnxTestHdColorAware OBJECT-TYPE
    SYNTAX       TruthValue
    MAX-ACCESS   read-write
    STATUS       current
    DESCRIPTION
         "tmnxTestHdColorAware can be set to true to run when the test
         is started to run color-aware tests.
         "
    ::= { tmnxTestHdProfScalarObjs 21 }
    
tmnxOamTestHeadTestCompleted NOTIFICATION-TYPE
    OBJECTS {
        tmnxTestHdName,
        tmnxTestHdOwner,
        tmnxTestHdStartTime,
        tmnxTestHdCompletedTime,
        tmnxTestHdElapsedTime,
        tmnxTestHdProfIndex,
        tmnxTestHdAccCritIndex,
        tmnxTestHdPayLdIndex,
        svcId, 
        tmnxTestHdSapPortId, 
        tmnxTestHdSapEncapValue,        
        tmnxTestHdFc,
        tmnxTestHdDsiredThrpt,
        tmnxTestHdCompleted,
        tmnxTestHdStopped,
        tmnxTestHdTestStatus,
        tmnxTestHdAvgLatency,
        tmnxTestHdFrLossRatio,
        tmnxTestHdJitter,
        tmnxTestHdAchvdThrpt
    }
    STATUS  current
    DESCRIPTION
        "Generated at the completion of Test Head completion."
    ::= { tmnxSASOamNotifications 1 }

tmnxTestHdObjsV5v0Group OBJECT-GROUP
    OBJECTS {
       tmnxTestHdAccCritId,
       tmnxTestHdAccCritIndex,
       tmnxTestHdAccCritJittrRiseThres,
       tmnxTestHdAccCritLastChanged,
       tmnxTestHdAccCritLatRiseThres,
       tmnxTestHdAccCritLossRiseThres,
       tmnxTestHdAccCritRowStatus,
       tmnxTestHdAchvdThrpt,
       tmnxTestHdAdminStatus,
       tmnxTestHdAvgLatency,
       tmnxTestHdCompleted,
       tmnxTestHdCompletedTime,
       tmnxTestHdDsiredThrpt,
       tmnxTestHdElapsedTime,
       tmnxTestHdFc,
       tmnxTestHdFrLossRatio,
       tmnxTestHdJitter,
       tmnxTestHdLastChanged,
       tmnxTestHdName,
       tmnxTestHdOwner,
       tmnxTestHdPayLdDSCP,
       tmnxTestHdPayLdDesc,
       tmnxTestHdPayLdDstIpv4Addr,
       tmnxTestHdPayLdDstMac,
       tmnxTestHdPayLdDstPort,
       tmnxTestHdPayLdEthertype,
       tmnxTestHdPayLdId,
       tmnxTestHdPayLdIndex,
       tmnxTestHdPayLdIpProto,
       tmnxTestHdPayLdIpTTL,
       tmnxTestHdPayLdIpTos,
       tmnxTestHdPayLdLastChanged,
       tmnxTestHdPayLdRowStatus,
       tmnxTestHdPayLdSrcIpv4Addr,
       tmnxTestHdPayLdSrcMac,
       tmnxTestHdPayLdSrcPort,
       tmnxTestHdPayLdType,
       tmnxTestHdPayLdVTagOne,
       tmnxTestHdPayLdVTagOneDot1p,
       tmnxTestHdPayLdVTagOneTpid,
       tmnxTestHdPayLdVTagTwo,
       tmnxTestHdPayLdVTagTwoDot1p,
       tmnxTestHdPayLdVTagTwoTpid,
       tmnxTestHdPayLddataPattrn,
       tmnxTestHdProfAdminCIR,
       tmnxTestHdProfOperCIR,
       tmnxTestHdProfCIR,
       tmnxTestHdProfCIRAdaptation,
       tmnxTestHdProfDescription,
       tmnxTestHdProfDurHr,
       tmnxTestHdProfDurMin,
       tmnxTestHdProfDurSec,
       tmnxTestHdProfFrameSize,
       tmnxTestHdProfId,
       tmnxTestHdProfIndex,
       tmnxTestHdProfRowStatus,
       tmnxTestHdProfTrapEnable,
       tmnxTestHdResFLRAccptanceResult,
       tmnxTestHdResJitterAccptanceResult,
       tmnxTestHdResLatencyAccptanceResult,
       tmnxTestHdResMaxLatency,
       tmnxTestHdResMeasuredFLR,
       tmnxTestHdResMeasuredJitter,
       tmnxTestHdResMeasuredLatency,
       tmnxTestHdResMeasuredThruput,
       tmnxTestHdResMinLatency,
       tmnxTestHdResProfAccCritId,
       tmnxTestHdResProfId,
       tmnxTestHdResProfPayLdId,
       tmnxTestHdResRecvCount,
       tmnxTestHdResSapEncapValue,
       tmnxTestHdResSapPortId,
       tmnxTestHdResTransCount,
       tmnxTestHdSapEncapValue,
       tmnxTestHdSapPortId,
       tmnxTestHdSessAccCritId,
       tmnxTestHdSessCompleted,
       tmnxTestHdSessCompletedTime,
       tmnxTestHdSessFc,
       tmnxTestHdSessPayLdId,
       tmnxTestHdSessProfId,
       tmnxTestHdSessSapEncapValue,
       tmnxTestHdSessSapPortId,
       tmnxTestHdSessStartTime,
       tmnxTestHdSessStopped,
       tmnxTestHdSessTotalTime,
       tmnxTestHdStartTime,
       tmnxTestHdStopped,
       tmnxTestHdTestStatus,
       tmnxTestHdAccCritLossRiseThresIn,
       tmnxTestHdAccCritLossRiseThresOut,
       tmnxTestHdAccCritCirThres,
       tmnxTestHdAccCritPirThres,
       tmnxTestHdAccCritLatRiseThresIn,
       tmnxTestHdAccCritLatRiseThresOut,
       tmnxTestHdAccCritJittrRiseThresIn,
       tmnxTestHdAccCritJittrRiseThresOut,
       tmnxTestHdProfDot1pIn,
       tmnxTestHdProfDot1pOut,
       tmnxTestHdProfOperPIR,
       tmnxTestHdProfAdminPIR,
       tmnxTestHdColorAware,
       tmnxTestHdProfActiveTests,
       tmnxTestHdProfCompetedTests
    }
    STATUS      current
    DESCRIPTION
        "The group of Test Head objects supported in 7210 5.0
         release"
    ::= { tmnxTestHdObjsGroups 1 }

tmnxTestHdNotifyV5v0Group NOTIFICATION-GROUP
    NOTIFICATIONS {
        tmnxOamTestHeadTestCompleted
   }
    STATUS    current
    DESCRIPTION
        "The group of notifications supported in 7210 5.0 release"
    ::= { tmnxTestHdObjsGroups 2 }

END
