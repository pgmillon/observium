TIMETRA-SAS-BGP-MIB DEFINITIONS ::= BEGIN

IMPORTS
    MODULE-IDENTITY, OBJECT-TYPE, NOTIFICATION-TYPE,
    IpAddress, Unsigned32, Gauge32, Counter32, Integer32,
    Counter64                                           FROM SNMPv2-SMI

    MODULE-COMPLIANCE, OBJECT-GROUP,
    NOTIFICATION-GROUP                                  FROM SNMPv2-CONF

    TEXTUAL-CONVENTION, RowStatus, DisplayString,
    TruthValue, TimeStamp, TestAndIncr                  FROM SNMPv2-TC

    timetraSASObjs, timetraSASNotifyPrefix, 
    timetraSASConfs, timetraSASModules                  FROM TIMETRA-SAS-GLOBAL-MIB

    tBgpPeerNgParamsEntry                               FROM TIMETRA-BGP-MIB
    bgp4PathAttrEntry                                   FROM BGP4-MIB
    ;

--
--
--
timetraSASBgpMIBModule  MODULE-IDENTITY
        LAST-UPDATED "201102010000Z"
        ORGANIZATION "Alcatel-Lucent"
        CONTACT-INFO
            "Alcatel-Lucent SROS Support
             Web: http://support.alcatel-lucent.com "
        DESCRIPTION
        "This document is the SNMP MIB module for Alcatel-Lucent's 
        implementation of BGP.

        Copyright 2003-2014 Alcatel-Lucent. All rights reserved.
        Reproduction of this document is authorized on the condition that
        the foregoing copyright notice is included.

        This SNMP MIB module (Specification) embodies Alcatel-Lucent's
        proprietary intellectual property.  Alcatel-Lucent retains
        all title and ownership in the Specification, including any
        revisions.

        Alcatel-Lucent grants all interested parties a non-exclusive
        license to use and distribute an unmodified copy of this
        Specification in connection with management of Alcatel-Lucent
        products, and without fee, provided this copyright notice and
        license appear on all copies.

        This Specification is supplied 'as is', and Alcatel-Lucent
        makes no warranty, either express or implied, as to the use,
        operation, condition, or performance of the Specification.

        There is one BGP instance per virtual router.  Each BGP instance
        can have a number of peer groups.

        The MIB objects here are organized in to four groups:
        - global objects (nothing there for now)
        - per-instance objects
        - per-peer-group objects
        - per-peer objects

        The value of most BGP configuration objects can be defaulted at three
        levels: at the per-peer level, at the peer group level, and at the
        BGP instance level.  The per-peer object values are set:
        - first by the peer object value, if set;
        - second, if not set then by the peer-group object value, if that is
          set;
        - third, if not set, by the instance object value.

        "
        REVISION        "1311010000Z"
        DESCRIPTION     "Rev 1.0                1 Nov 2013 00:00
                         0.0 release of the TIMETRA-SAS-BGP-MIB."


        ::= { timetraSASModules 15 }


    tmnxSASBgpObjects                OBJECT IDENTIFIER ::= { timetraSASObjs 18 }
    tBgpSASPeerObjects               OBJECT IDENTIFIER ::= { tmnxSASBgpObjects 1 }
    tmnxSASBgpConformance            OBJECT IDENTIFIER ::= { timetraSASConfs 14 }
    tmnxSASBgpGroups                 OBJECT IDENTIFIER ::= { tmnxSASBgpConformance 1 }
    
tBgpPeerNgParamsExtnTable OBJECT-TYPE
    SYNTAX     SEQUENCE OF TBgpPeerNgParamsExtnEntry
    MAX-ACCESS not-accessible
    STATUS     current
    DESCRIPTION
        "tBgpPeerNgParamsExtnTable provides information about the
         attributes configured for the BGP instance."
    ::= { tBgpSASPeerObjects 10 }

tBgpPeerNgParamsExtnEntry OBJECT-TYPE
    SYNTAX     TBgpPeerNgParamsExtnEntry
    MAX-ACCESS not-accessible
    STATUS     current
    DESCRIPTION
        "An entry in the tBgpPeerNgParamsExtnTable. Each entry
         maintains the attributes configured for BGP instance that
         are supported in addition to objects in tBgpPeerNgParamsTable."
    AUGMENTS  { tBgpPeerNgParamsEntry }
    ::= { tBgpPeerNgParamsExtnTable 1 }

TBgpPeerNgParamsExtnEntry ::= SEQUENCE {
    tBgpPeerNgUseSvcRoutes       TruthValue
}

tBgpPeerNgUseSvcRoutes OBJECT-TYPE
    SYNTAX      TruthValue
    MAX-ACCESS  read-create
    STATUS      current
    DESCRIPTION
        "The value of tBgpPeerNgUseSvcRoutes specifies whether to use
        service routers for this neighbor"
    DEFVAL { false }
    ::= { tBgpPeerNgParamsExtnEntry 1 }

    
bgp4PathAttrExtnTable OBJECT-TYPE
    SYNTAX     SEQUENCE OF Bgp4PathAttrExtnEntry
    MAX-ACCESS not-accessible
    STATUS     current
    DESCRIPTION
         "The BGP-4 Received Path Attribute Table
           contains information about paths to
           destination networks received from all
           BGP4 peers in addition to bgp4PathAttrTable."
   ::= { tBgpSASPeerObjects 11 }

bgp4PathAttrExtnEntry OBJECT-TYPE
    SYNTAX     Bgp4PathAttrExtnEntry
    MAX-ACCESS not-accessible
    STATUS     current
    DESCRIPTION
     "Information about a path to a network."
     AUGMENTS {   bgp4PathAttrEntry }
       ::= { bgp4PathAttrExtnTable 1 }

Bgp4PathAttrExtnEntry ::= SEQUENCE {
     bgp4PathUseSvcRoutesOpt     TruthValue
}

bgp4PathUseSvcRoutesOpt OBJECT-TYPE
    SYNTAX      TruthValue
    MAX-ACCESS  read-only
    STATUS      current
    DESCRIPTION
        "The value of bgp4PathUseSvcRoutesOpt specifies whether 3107 optimisation has been done or not. "
    ::= { bgp4PathAttrExtnEntry 1 }


tmnxSASBgpGlobalV7v0Group OBJECT-GROUP
     OBJECTS {   
                 tBgpPeerNgUseSvcRoutes
             }
     STATUS  current
     DESCRIPTION
         "The group of objects supporting management of extended BGP
          on Alcatel-Lucent 7210 series systems release 7.0."
     ::= { tmnxSASBgpGroups 1 }


END
