--       TIMETRA MCAST (MultiCast) PATH MGMT (Management) 
--       Management Information Base

TIMETRA-MCAST-PATH-MGMT-MIB DEFINITIONS ::= BEGIN

IMPORTS
    MODULE-IDENTITY, OBJECT-TYPE, NOTIFICATION-TYPE,
    Unsigned32, Gauge32
        FROM SNMPv2-SMI

    MODULE-COMPLIANCE, OBJECT-GROUP, NOTIFICATION-GROUP
        FROM SNMPv2-CONF

    RowStatus, TimeStamp, TruthValue, 
    TEXTUAL-CONVENTION
        FROM SNMPv2-TC

    InetPortNumber,
    InetAddress, InetAddressType                
        FROM INET-ADDRESS-MIB

    timetraSRMIBModules, tmnxSRObjs,
    tmnxSRConfs, tmnxSRNotifyPrefix
        FROM TIMETRA-GLOBAL-MIB

    TmnxAdminState,
    TNamedItem, TItemDescription, TmnxVdoGrpId, TNamedItemOrEmpty,
    TmnxEnabledDisabled, TmnxEnabledDisabledOrInherit, 
    TmnxVdoGrpIdOrInherit, TmnxVdoFccServerMode, TmnxVdoPortNumber,
    TmnxVdoAnalyzerAlarm
        FROM TIMETRA-TC-MIB

    vRtrID 
        FROM TIMETRA-VRTR-MIB

    tmnxChassisIndex, tmnxCardSlotNum, tmnxMDASlotNum,
    TmnxChassisIndex, TmnxSlotNum 
        FROM TIMETRA-CHASSIS-MIB
    ;

timetraMcastPathMgmtMIBModule   MODULE-IDENTITY
        LAST-UPDATED "201102010000Z"
        ORGANIZATION "Alcatel-Lucent"
        CONTACT-INFO
            "Alcatel-Lucent SROS Support
             Web: http://support.alcatel-lucent.com"
        DESCRIPTION
        "This is the SNMP MIB module for ingress multicast path management
         policy on Alcatel-Lucent SROS equipment.

         Copyright 2008-2012 Alcatel-Lucent. All rights reserved.
         Reproduction of this document is authorized on the condition that
         the foregoing copyright notice is included.

         This SNMP MIB module (Specification) embodies Alcatel-Lucent's
         proprietary intellectual property.  Alcatel-Lucent retains 
         all title and ownership in the Specification, including any 
         revisions.

         Alcatel-Lucent grants all interested parties a non-exclusive 
         license to use and distribute an unmodified copy of this 
         Specification in connection with management of Alcatel-Lucent
         products, and without fee, provided this copyright notice and 
         license appear on all copies.

         This Specification is supplied 'as is', and Alcatel-Lucent 
         makes no warranty, either express or implied, as to the use, 
         operation, condition, or performance of the Specification."

--
--  Revision History
--
        REVISION        "1102010000Z"
        DESCRIPTION     "Rev 9.0                1 Feb 2011 00:00
                         9.0 release of the TIMETRA-MCAST-PATH-MGMT-MIB."

        REVISION        "0902280000Z"
        DESCRIPTION     "Rev 7.0                28 Feb 2009 00:00
                         7.0 release of the TIMETRA-MCAST-PATH-MGMT-MIB."

        REVISION        "0807010000Z"
        DESCRIPTION     "Rev 6.1                01 Jul 2008 00:00
                         6.1 release of the TIMETRA-MCAST-PATH-MGMT-MIB."

        REVISION        "0801010000Z"
        DESCRIPTION     "Rev 0.1                01 Jan 2008 00:00
                         Initial version of the TIMETRA-MCAST-PATH-MGMT-MIB."

        ::= { timetraSRMIBModules 54 }

--%%%%%%%%%%%%%%%%%%%%%%%%%%%%%%%%%%%%%%%%%%%%%%%%%%%%%%%%%%%%%%%%%%%%%%
--
--  Alcatel-Lucent SROS series multicast management policy objects
--

tmnxMcPathObjs            OBJECT IDENTIFIER ::= { tmnxSRObjs 54 }    
    tmnxMcPathGlobalObjs    OBJECT IDENTIFIER ::= { tmnxMcPathObjs 1 }
    tmnxMcPathNotifyObjs    OBJECT IDENTIFIER ::= { tmnxMcPathObjs 2 }

tmnxMcPathConformance      OBJECT IDENTIFIER ::= { tmnxSRConfs 54 }
   tmnxMcPathCompliances   OBJECT IDENTIFIER ::= { tmnxMcPathConformance 1 }
   tmnxMcPathGroups          OBJECT IDENTIFIER ::= { tmnxMcPathConformance 2 }
   

tmnxMcPathNotifyPrefix OBJECT IDENTIFIER ::= { tmnxSRNotifyPrefix 54 }
    tmnxMcPathNotifications OBJECT IDENTIFIER ::= { tmnxMcPathNotifyPrefix 0 }
    
 --
 -- Textual Conventions
 --

TmnxMcPathChlSfPathTypeTc ::= TEXTUAL-CONVENTION 
     STATUS      current 
     DESCRIPTION 
         "The value TmnxMcPathChlSfPathTypeTc data type is an enumerated integer 
          that describes  the values used to identify the type of ingress switch 
          fabric multicast path." 
     SYNTAX      INTEGER { 
                     none (0),
                     primary  (1),
                     secondary (2),
                     ancillary (3),
                     blackhole (4)
                 } 

TmnxMcPathBwActivityTc     ::= TEXTUAL-CONVENTION 
        STATUS      current 
        DESCRIPTION 
            "The value TmnxMcPathBwActivityTc data type is an enumerated integer 
             that describes the values used to define how the multicast 
             ingress path manager determines the amount of bandwidth required by
             a multicast channel." 
        SYNTAX      INTEGER 
                    {
                        none (0),    
                        use-admin-bw (1),
                        dynamic (2)
                    }

TmnxMcPathRtrType      ::= TEXTUAL-CONVENTION 
        STATUS      current 
        DESCRIPTION 
            "The value TmnxMcPathRtrType data type is an enumerated integer 
             that describes the type of virtual router." 
        SYNTAX      INTEGER 
                    {
                        vRtr (0),    
                        service (1)
                    }

TmnxMcPathVdoChlType      ::= TEXTUAL-CONVENTION
        STATUS      current
        DESCRIPTION
            "The TmnxMcPathVdoChlType data type is an enumerated
             integer that describes the video channel type. It identifies
             whether the video channel is High Definition (HD), Standard
             Definition (SD) or Picture-in-Picture (PIP)."
        SYNTAX      INTEGER
                    {
                        default    (1),
                        hd      (2),
                        sd      (3),
                        pip     (4)
                    }

TmnxMcPathVdoChlTypeOrInherit ::= TEXTUAL-CONVENTION
        STATUS      current
        DESCRIPTION
            "The TmnxMcPathVdoChlTypeOrInherit data type is an enumerated
             integer that describes the video channel type. It identifies
             whether the video channel type is High Definition (HD), Standard
             Definition (SD), Picture-in-Picture (PIP) or inherited from 
             another object that is usually in another mib table."
        SYNTAX      INTEGER
                    {
                        inherit (0),
                        default (1),
                        hd      (2),
                        sd      (3),
                        pip     (4)
                    }

TmnxMcPathVdoPayloadType      ::= TEXTUAL-CONVENTION    
        STATUS      current     
        DESCRIPTION     
            "The TmnxMcPathVdoPayloadType data type describes the format to     
             be used by Retransmission (RT) server to send retransmission   
             packets.   

             The value '33' indicates that the frames will be sent as   
             originally received.
                              
             The default value '99' indicates that the frames will be sent in 
             the RFC 4588 format.
    
             A value between 96 and 127 indicates the dynamic payload type value    
             (as per RFC 3551) to be used for RFC 4588 formatted retransmission     
             packets."      
        SYNTAX      Unsigned32 (33 | 96..127)

TmnxMcPathVdoBufferSize      ::= TEXTUAL-CONVENTION
        STATUS      current
        DESCRIPTION 
            "The TmnxMcPathVdoBufferSize describes the buffer size that stores
             the number of milliseconds worth of channel packets for the
             Retransmission (RT) server."
        SYNTAX      Unsigned32 (300..8000)

TmnxMcPathVdoBwLimit      ::= TEXTUAL-CONVENTION
        STATUS      current
        DESCRIPTION 
            "The TmnxMcPathVdoBwLimit data type describes the per-subscriber
             egress bandwidth limit in kilobits per second (kbps) for the 
             combined Retransmission (RT) and Fast Channel Change (FCC). If the 
             bandwidth for a request exceeds the bandwidth limit, the request 
             is logged and dropped."
        SYNTAX      Unsigned32 (1..4294967295)

TmnxMcPathVdoReorderAudio  ::=  TEXTUAL-CONVENTION
        STATUS      current
        DESCRIPTION 
            "The TmnxMcPathVdoReorderAudio data type describes the time, in 
             milliseconds, by which the audio packets are reordered in the 
             ad stream."
        SYNTAX      Unsigned32 (0..1000)

TmnxMcPathVdoFccMinDuration  ::=  TEXTUAL-CONVENTION
        STATUS      current
        DESCRIPTION 
            "The TmnxMcPathVdoFccMinDuration data type describes the time 
             duration, in milliseconds, of the Fast Channel Change (FCC)
             burst."
        SYNTAX      Unsigned32 (300..8000)

TmnxMcPathVdoFccMinDurationOrZero  ::=  TEXTUAL-CONVENTION
        STATUS      current
        DESCRIPTION 
            "The TmnxMcPathVdoFccMinDurationOrZero data type describes the 
             time duration, in milliseconds, of the Fast Channel Change (FCC)
             burst."
        SYNTAX      Unsigned32 (0 | 300..8000)

TmnxMcPathKeepAliveOverrideTimer    ::=  TEXTUAL-CONVENTION
        STATUS      current
        DESCRIPTION 
            "The TmnxMcPathKeepAliveOverrideTimer data type describes the time, 
             in seconds, used to override the PIM instance Keep Alive Timer."
        SYNTAX      Unsigned32 (0 | 10..300)

-- ------------------------------------------------
-- mib objects
-- ------------------------------------------------

-- ------------------------------------------------
-- multicast bandwidth policy table
-- ------------------------------------------------

tmnxMcPathBwPlcyTableLastChanged OBJECT-TYPE
    SYNTAX      TimeStamp
    MAX-ACCESS  read-only
    STATUS      current
    DESCRIPTION
        "The value of tmnxMcPathBwPlcyTableLastChanged indicates the sysUpTime 
         at the time of the last modification to tmnxMcPathBwPlcyTable by 
         adding, deleting an entry or change to a writable object in the table.

         If no changes were made to the table since the last re-initialization 
         of the local network management subsystem, then this object contains a 
         zero value."
    ::= { tmnxMcPathGlobalObjs 1 } 

tmnxMcPathBwPlcyTable OBJECT-TYPE
    SYNTAX      SEQUENCE OF TmnxMcPathBwPlcyEntry
    MAX-ACCESS  not-accessible
    STATUS      current
    DESCRIPTION
        "The tmnxMcPathBwPlcyTable has an entry for each multicast bandwidth
         policy configured on this system."
    ::= { tmnxMcPathObjs 3 }

tmnxMcPathBwPlcyEntry    OBJECT-TYPE
    SYNTAX      TmnxMcPathBwPlcyEntry
    MAX-ACCESS  not-accessible
    STATUS      current
    DESCRIPTION
        "Each row entry represents a particular multicast bandwidth policy.
         Entries are created/deleted by the user."
    INDEX { tmnxMcPathBwPlcyName }
    ::= { tmnxMcPathBwPlcyTable 1}

TmnxMcPathBwPlcyEntry ::= SEQUENCE
   {
       tmnxMcPathBwPlcyName               TNamedItem,
       tmnxMcPathBwPlcyRowStatus          RowStatus,
       tmnxMcPathBwPlcyLastChanged        TimeStamp,
       tmnxMcPathBwPlcyDescription        TItemDescription,
       tmnxMcPathBwPlcyFallPercentReset   Unsigned32,
       tmnxMcPathBwPlcyAdminBwThd         Unsigned32,
       tmnxMcPathBwPlcyMcPoolPercentTot   Unsigned32, 
       tmnxMcPathBwPlcyMcPoolResvCbs      Unsigned32, 
       tmnxMcPathBwPlcyMcPoolSlopePlcy    TNamedItem
   }

tmnxMcPathBwPlcyName              OBJECT-TYPE
    SYNTAX      TNamedItem
    MAX-ACCESS  not-accessible
    STATUS      current
    DESCRIPTION
        "The value of tmnxMcPathBwPlcyName indicates the name of the multicast 
         bandwidth policy."
    ::= { tmnxMcPathBwPlcyEntry 1 }

tmnxMcPathBwPlcyRowStatus       OBJECT-TYPE
    SYNTAX      RowStatus
    MAX-ACCESS  read-create
    STATUS      current
    DESCRIPTION
        "The value of tmnxMcPathBwPlcyRowStatus is used for creation/deletion of
         multicast bandwidth policies."
    ::= { tmnxMcPathBwPlcyEntry 2 }

tmnxMcPathBwPlcyLastChanged  OBJECT-TYPE
    SYNTAX      TimeStamp
    MAX-ACCESS  read-only
    STATUS      current
    DESCRIPTION
        "The value of tmnxMcPathBwPlcyLastChanged indicates the timestamp of 
         last change to this row in tmnxMcPathBwPlcyTable."
    ::= { tmnxMcPathBwPlcyEntry 3 }

tmnxMcPathBwPlcyDescription    OBJECT-TYPE
    SYNTAX      TItemDescription
    MAX-ACCESS  read-create
    STATUS      current
    DESCRIPTION
        "The value of tmnxMcPathBwPlcyDescription specifies the textual 
         description of this multicast bandwidth policy."
    DEFVAL      { "" } 
    ::= { tmnxMcPathBwPlcyEntry 4 }    

tmnxMcPathBwPlcyFallPercentReset    OBJECT-TYPE
    SYNTAX      Unsigned32 (1..100)
    UNITS       "percentage"
    MAX-ACCESS  read-create
    STATUS      current
    DESCRIPTION
        "The value of tmnxMcPathBwPlcyFallPercentReset specifies the percentage
         of bandwidth decrease that must occur to reset the dynamic bandwidth
         monitoring function for a multicast channel."
    DEFVAL      { 50 } 
    ::= { tmnxMcPathBwPlcyEntry 5 }    

tmnxMcPathBwPlcyAdminBwThd    OBJECT-TYPE
    SYNTAX      Unsigned32 (1..40000000)
    UNITS       "kbps"
    MAX-ACCESS  read-create
    STATUS      current
    DESCRIPTION
        "The value of tmnxMcPathBwPlcyAdminBwThd specifies at which bandwidth 
         rate a multicast channel configured to use an administrative rate will 
         start and stop using that rate as the in-use ingress bandwidth when 
         managing ingress multicast paths."
    DEFVAL      { 10 } 
    ::= { tmnxMcPathBwPlcyEntry 6 }    

tmnxMcPathBwPlcyMcPoolPercentTot    OBJECT-TYPE
    SYNTAX      Unsigned32 (1..50)
    UNITS       "percentage"
    MAX-ACCESS  read-create
    STATUS      current
    DESCRIPTION
        "The value of tmnxMcPathBwPlcyMcPoolPercentTot specifies how much of the
         total ingress buffer pool space for the MDA (Media Dependent Adapter)
         is dedicated for multicast channels managed by the bandwidth policy."
    DEFVAL      { 10 } 
    ::= { tmnxMcPathBwPlcyEntry 7 } 

tmnxMcPathBwPlcyMcPoolResvCbs    OBJECT-TYPE
    SYNTAX      Unsigned32 (1..100)
    UNITS       "percentage"
    MAX-ACCESS  read-create
    STATUS      current
    DESCRIPTION
        "The value of tmnxMcPathBwPlcyMcPoolResvCbs specifies the percentage of 
         the pool that will be reserved for multicast path queues within their 
         Committed Buffer Size (CBS) threshold."
    DEFVAL      { 50 } 
    ::= { tmnxMcPathBwPlcyEntry 8 } 

tmnxMcPathBwPlcyMcPoolSlopePlcy    OBJECT-TYPE
    SYNTAX      TNamedItem
    MAX-ACCESS  read-create
    STATUS      current
    DESCRIPTION
        "The value of tmnxMcPathBwPlcyMcPoolSlopePlcy specifies the named policy
         which will be used to configure the WRED (Weighted Random Early 
         Discard) slopes within the multicast pool. Once a slope policy is 
         associated with a buffer pool, it cannot be deleted."
    DEFVAL      { "default"} 
    ::= { tmnxMcPathBwPlcyEntry 9} 


-- ------------------------------------------------
-- multicast bandwidth policy path table
-- ------------------------------------------------

tmnxMcPathBwPlcyPathTable OBJECT-TYPE
    SYNTAX      SEQUENCE OF TmnxMcPathBwPlcyPathEntry
    MAX-ACCESS  not-accessible
    STATUS      current
    DESCRIPTION
        "The tmnxMcPathBwPlcyPathTable has an entry for each of the three 
         ingress multicast paths into the switch fabric. An entry is created in 
         this table whenever a entry for a bandwidth policy is created in 
         tmnxMcPathBwPlcyTable."
    ::= { tmnxMcPathObjs 4 }

tmnxMcPathBwPlcyPathEntry    OBJECT-TYPE
    SYNTAX      TmnxMcPathBwPlcyPathEntry
    MAX-ACCESS  not-accessible
    STATUS      current
    DESCRIPTION
        "Each row entry represents a particular ingress multicast path."
    INDEX { tmnxMcPathBwPlcyName, tmnxMcPathBwPlcyPathType }
    ::= { tmnxMcPathBwPlcyPathTable 1}

TmnxMcPathBwPlcyPathEntry ::= SEQUENCE
   {
       tmnxMcPathBwPlcyPathType        TmnxMcPathChlSfPathTypeTc,
       tmnxMcPathBwPlcyPathLimit       Unsigned32,
       tmnxMcPathBwPlcyPathCbs         Unsigned32,
       tmnxMcPathBwPlcyPathMbs         Unsigned32,
       tmnxMcPathBwPlcyPathHighPrio    Unsigned32 
   }

tmnxMcPathBwPlcyPathType  OBJECT-TYPE
    SYNTAX      TmnxMcPathChlSfPathTypeTc
    MAX-ACCESS  not-accessible
    STATUS      current
    DESCRIPTION
        "The value of tmnxMcPathBwPlcyPathType specifies the type of the path."
    ::= { tmnxMcPathBwPlcyPathEntry 1 }    

tmnxMcPathBwPlcyPathLimit    OBJECT-TYPE
    SYNTAX      Unsigned32 (1..5000)
    UNITS       "mega-bits-per-second"
    MAX-ACCESS  read-create
    STATUS      current
    DESCRIPTION
        "The value of tmnxMcPathBwPlcyPathLimit overrides the default path limit
         for each of the three ingress multicast paths into the switch fabric.
         The default value of tmnxMcPathBwPlcyPathLimit is the default value of 
         path limit for the primary path.  The default value of 
         tmnxMcPathBwPlcyPathLimit for the secondary and ancillary path is 1500 
         and 5000 respectively."
    DEFVAL { 2000 } 
    ::= { tmnxMcPathBwPlcyPathEntry 2 }    

tmnxMcPathBwPlcyPathCbs      OBJECT-TYPE
    SYNTAX      Unsigned32 (0..10000)
    UNITS       "hundredths of a percent"
    MAX-ACCESS  read-create
    STATUS      current
    DESCRIPTION
        "The value of tmnxMcPathBwPlcyPathCbs overrides the default CBS for each
         individual path's queue.  The default value of tmnxMcPathBwPlcyPathCbs
         is the default value of primary path's queue.  The default value of 
         tmnxMcPathBwPlcyPathCbs for the secondary and ancillary path is 3000 
         and 6500 respectively."
    DEFVAL { 500 } 
    ::= { tmnxMcPathBwPlcyPathEntry 3 }     

tmnxMcPathBwPlcyPathMbs      OBJECT-TYPE
    SYNTAX      Unsigned32 (0..10000)
    UNITS       "hundredths of a percent"
    MAX-ACCESS  read-create
    STATUS      current
    DESCRIPTION
        "The value of tmnxMcPathBwPlcyPathMbs overrides the default Maximum 
         Buffer Size(MBS) for each individual path's queue.  The default value 
         of tmnxMcPathBwPlcyPathMbs is the default value of primary path's 
         queue. The default value of tmnxMcPathBwPlcyPathMbs for the secondary 
         and ancillary path is 4000 and 8000 respectively."
    DEFVAL { 700 } 
    ::= { tmnxMcPathBwPlcyPathEntry 4 }     

tmnxMcPathBwPlcyPathHighPrio            OBJECT-TYPE
    SYNTAX      Unsigned32 (0..100)
    UNITS       "percentage"
    MAX-ACCESS  read-create
    STATUS      current
    DESCRIPTION
        "The value of tmnxMcPathBwPlcyPathHighPrio overrides the default 
         percentage value used to determine the low priority MBS value for the
         queue. By default, 10 percent of the queue depth is reserved for high 
         congestion priority traffic and this default value is same for 
         secondary and ancillary paths also."
    DEFVAL { 10 }         
    ::= { tmnxMcPathBwPlcyPathEntry 5 }  

-- ------------------------------------------------
-- multicast policy table
-- ------------------------------------------------

tmnxMcPathPlcyTableLastChanged OBJECT-TYPE
    SYNTAX      TimeStamp
    MAX-ACCESS  read-only
    STATUS      current
    DESCRIPTION
        "The value of tmnxMcPathPlcyTableLastChanged indicates the sysUpTime at 
         the time of the last modification to tmnxMcPathPlcyTable by adding, 
         deleting an entry or change to a writable object in the table.

         If no changes were made to the table since the last re-initialization 
         of the local network management subsystem, then this object contains a 
         zero value."
    ::= { tmnxMcPathGlobalObjs 2 } 

tmnxMcPathPlcyTable OBJECT-TYPE
    SYNTAX      SEQUENCE OF TmnxMcPathPlcyEntry
    MAX-ACCESS  not-accessible
    STATUS      current
    DESCRIPTION
        "The tmnxMcPathPlcyTable has an entry for each multicast information 
         policy configured on this system."
    ::= { tmnxMcPathObjs 5 }

tmnxMcPathPlcyEntry    OBJECT-TYPE
    SYNTAX      TmnxMcPathPlcyEntry
    MAX-ACCESS  not-accessible
    STATUS      current
    DESCRIPTION
        "Each row entry represents a particular multicast information policy.
         Entries are created/deleted by the user."
    INDEX { tmnxMcPathPlcyName }
    ::= { tmnxMcPathPlcyTable 1}

TmnxMcPathPlcyEntry ::= SEQUENCE
   {
       tmnxMcPathPlcyName               TNamedItem,
       tmnxMcPathPlcyRowStatus          RowStatus,
       tmnxMcPathPlcyLastChanged        TimeStamp,
       tmnxMcPathPlcyDescription        TItemDescription
   }

tmnxMcPathPlcyName              OBJECT-TYPE
    SYNTAX      TNamedItem
    MAX-ACCESS  not-accessible
    STATUS      current
    DESCRIPTION
        "The value of tmnxMcPathPlcyName indicates the name of the multicast 
         information policy."
    ::= { tmnxMcPathPlcyEntry 1 }

tmnxMcPathPlcyRowStatus       OBJECT-TYPE
    SYNTAX      RowStatus
    MAX-ACCESS  read-create
    STATUS      current
    DESCRIPTION
        "The value of tmnxMcPathPlcyRowStatus is used for creation/deletion of 
         multicast information policies."
    ::= { tmnxMcPathPlcyEntry 2 }

tmnxMcPathPlcyLastChanged  OBJECT-TYPE
    SYNTAX      TimeStamp
    MAX-ACCESS  read-only
    STATUS      current
    DESCRIPTION
        "The value of tmnxMcPathPlcyLastChanged indicates the timestamp of 
         last change to this row in tmnxMcPathPlcyTable."
    ::= { tmnxMcPathPlcyEntry 3 }

tmnxMcPathPlcyDescription    OBJECT-TYPE
    SYNTAX      TItemDescription
    MAX-ACCESS  read-create
    STATUS      current
    DESCRIPTION
        "The value of tmnxMcPathPlcyDescription specifies the textual 
         description of this multicast information policy."
    DEFVAL      { "" } 
    ::= { tmnxMcPathPlcyEntry 4 }    

-- ------------------------------------------------
-- multicast information policy bundle table
-- ------------------------------------------------

tmnxMcPathBdlTableLastChanged OBJECT-TYPE
    SYNTAX      TimeStamp
    MAX-ACCESS  read-only
    STATUS      current
    DESCRIPTION
        "The value of tmnxMcPathBdlTableLastChanged indicates the sysUpTime at 
         the time of the last modification to tmnxMcPathBdlTable by adding, 
         deleting an entry or change to a writable object in the table.

         If no changes were made to the table since the last re-initialization 
         of the local network management subsystem, then this object contains a 
         zero value."
    ::= { tmnxMcPathGlobalObjs 3 } 

tmnxMcPathBdlTable    OBJECT-TYPE
    SYNTAX      SEQUENCE OF TmnxMcPathBdlEntry
    MAX-ACCESS  not-accessible
    STATUS      current
    DESCRIPTION
        "The tmnxMcPathBdlTable has an entry for each multicast information
         policy bundle configured on this system."
    ::= { tmnxMcPathObjs 7 }

tmnxMcPathBdlEntry    OBJECT-TYPE
    SYNTAX      TmnxMcPathBdlEntry
    MAX-ACCESS  not-accessible
    STATUS      current
    DESCRIPTION
        "Each row entry represents a particular multicast information 
         policy bundle. Entries are created/deleted by the user."
    INDEX { tmnxMcPathPlcyName, 
            tmnxMcPathBdlName 
          }
    ::= { tmnxMcPathBdlTable 1}

TmnxMcPathBdlEntry ::= SEQUENCE
   {
       tmnxMcPathBdlName                TNamedItem,
       tmnxMcPathBdlStatus              RowStatus,
       tmnxMcPathBdlLastChanged         TimeStamp,
       tmnxMcPathBdlDescription         TItemDescription,
       tmnxMcPathBdlCongPriorityThd     Unsigned32,
       tmnxMcPathBdlEcmpOptThd          Unsigned32,
       tmnxMcPathBdlDefChlAdminBw       Unsigned32,
       tmnxMcPathBdlDefChlPref          Unsigned32,
       tmnxMcPathBdlDefChlBwActivity    TmnxMcPathBwActivityTc,
       tmnxMcPathBdlDefChlBwFallDelay   Unsigned32,
       tmnxMcPathBdlDefChlBwBlackHoleRt Unsigned32,
       tmnxMcPathBdlDefChlExSfPath      TmnxMcPathChlSfPathTypeTc,
       tmnxMcPathBdlVdoFCCState         TmnxEnabledDisabled,
       tmnxMcPathBdlVdoRTState          TmnxEnabledDisabled,
       tmnxMcPathBdlVdoChlType          TmnxMcPathVdoChlType,
       tmnxMcPathBdlVdoRTAddrType       InetAddressType,
       tmnxMcPathBdlVdoRTAddress        InetAddress,
       tmnxMcPathBdlVdoRTPort           TmnxVdoPortNumber,
       tmnxMcPathBdlVdoRTBufferSize     TmnxMcPathVdoBufferSize,
       tmnxMcPathBdlVdoLocalRTPort      TmnxVdoPortNumber,
       tmnxMcPathBdlVdoLocalFccPort     TmnxVdoPortNumber,
       tmnxMcPathBdlVdoGroupId          TmnxVdoGrpId,
       tmnxMcPathBdlTunnelIfLspName     TNamedItemOrEmpty,
       tmnxMcPathBdlTunIfSdAddrType     InetAddressType,
       tmnxMcPathBdlTunIfSdAddr         InetAddress,
       tmnxMcPathBdlVdoSourcePort       TmnxVdoPortNumber,
       tmnxMcPathBdlVdoLocalRTState     TmnxEnabledDisabled,
       tmnxMcPathBdlVdoReorderAudio     TmnxMcPathVdoReorderAudio,
       tmnxMcPathBdlVdoFccMinDuration   TmnxMcPathVdoFccMinDuration,
       tmnxMcPathBdlKAOverrideTimer     TmnxMcPathKeepAliveOverrideTimer,
       tmnxMcPathBdlP2MPId              Unsigned32,
       tmnxMcPathBdlVdoAnalyzer         TruthValue,
       tmnxMcPathBdlVdoAnalyzerDesc     TItemDescription,
       tmnxMcPathBdlVdoStrSelSrc1Type   InetAddressType,
       tmnxMcPathBdlVdoStrSelSrc1       InetAddress,
       tmnxMcPathBdlVdoStrSelIntf1      TNamedItemOrEmpty,
       tmnxMcPathBdlVdoStrSelSrc2Type   InetAddressType,
       tmnxMcPathBdlVdoStrSelSrc2       InetAddress, 
       tmnxMcPathBdlVdoStrSelIntf2      TNamedItemOrEmpty
   }

tmnxMcPathBdlName               OBJECT-TYPE
    SYNTAX      TNamedItem
    MAX-ACCESS  not-accessible
    STATUS      current
    DESCRIPTION
        "The value of tmnxMcPathBdlName indicates the name of the multicast 
         information policy bundle."
    ::= { tmnxMcPathBdlEntry 1 }

tmnxMcPathBdlStatus        OBJECT-TYPE
    SYNTAX      RowStatus
    MAX-ACCESS  read-create
    STATUS      current
    DESCRIPTION
        "The value of tmnxMcPathBdlStatus along with value of tmnxMcPathPlcyName
         is used for creation of multicast information policy bundle."
    ::= { tmnxMcPathBdlEntry 2 }

tmnxMcPathBdlLastChanged  OBJECT-TYPE
    SYNTAX      TimeStamp
    MAX-ACCESS  read-only
    STATUS      current
    DESCRIPTION
        "The value of tmnxMcPathBdlLastChanged indicates the timestamp of 
         last change to this row in tmnxMcPathBdlTable."
    ::= { tmnxMcPathBdlEntry 3 }

tmnxMcPathBdlDescription     OBJECT-TYPE
    SYNTAX      TItemDescription
    MAX-ACCESS  read-create
    STATUS      current
    DESCRIPTION
        "The value of tmnxMcPathBdlDescription specifies the textual 
         description of this multicast information policy bundle."
    DEFVAL { "" } 
    ::= { tmnxMcPathBdlEntry 4 }    

tmnxMcPathBdlCongPriorityThd      OBJECT-TYPE
    SYNTAX      Unsigned32 (0..7)
    MAX-ACCESS  read-create
    STATUS      current
    DESCRIPTION
        "The value of tmnxMcPathBdlCongPriorityThd specifies the preference 
         level threshold where records change from low congestion priority to 
         high congestion priority."
    DEFVAL { 4 } 
    ::= { tmnxMcPathBdlEntry 5 }     

tmnxMcPathBdlEcmpOptThd            OBJECT-TYPE
    SYNTAX      Unsigned32 (0..7)
    MAX-ACCESS  read-create
    STATUS      current
    DESCRIPTION
        "The value of tmnxMcPathBdlEcmpOptThd specifies the preference level
         threshold where multicast ECMP path management is allowed to 
         dynamically optimize channels based on topology or bandwidth events."
    DEFVAL { 7 }         
    ::= { tmnxMcPathBdlEntry 6 }  

tmnxMcPathBdlDefChlAdminBw            OBJECT-TYPE
    SYNTAX      Unsigned32 (0..40000000)
    UNITS       "kbps"
    MAX-ACCESS  read-create
    STATUS      current
    DESCRIPTION
        "The value of tmnxMcPathBdlDefChlAdminBw specifies the multicast 
         channel's administrative bandwidth in kilo-bits per second(kbps)."
    DEFVAL { 0 }         
    ::= { tmnxMcPathBdlEntry 7 }

tmnxMcPathBdlDefChlPref        OBJECT-TYPE
    SYNTAX      Unsigned32 (0..7) 
    MAX-ACCESS  read-create
    STATUS      current
    DESCRIPTION
        "The value of tmnxMcPathBdlDefChlPref specifies the relative preference
         level for multicast channels.  The preference of a channel specifies 
         its relative importance over other multicast channels.  Eight levels of 
         preference are supported; 0 through 7. Preference value 7 indicates the
         highest preference level."
    DEFVAL { 0 }                  
    ::= { tmnxMcPathBdlEntry 8 }

tmnxMcPathBdlDefChlBwActivity            OBJECT-TYPE
    SYNTAX      TmnxMcPathBwActivityTc
    MAX-ACCESS  read-create
    STATUS      current
    DESCRIPTION
        "The value of tmnxMcPathBdlDefChlBwActivity specifies how the multicast
         ingress path manager determines the amount of bandwidth required by a 
         multicast channel. This object can have value 'use-admin-bw' only if
         tmnxMcPathBdlDefChlAdminBw is non-zero."
    DEFVAL { dynamic }         
    ::= { tmnxMcPathBdlEntry 10 }

tmnxMcPathBdlDefChlBwFallDelay        OBJECT-TYPE
    SYNTAX      Unsigned32 (10..3600)
    UNITS       "seconds" 
    MAX-ACCESS  read-create
    STATUS      current
    DESCRIPTION
        "The value of tmnxMcPathBdlDefChlBwFallDelay specifies the value the
         bandwidth manager uses the falling-delay threshold to hold on to the 
         previous highest bandwidth until the delay time has expired while 
         operating in dynamic bandwidth mode.  This allows the bandwidth manager
         to ignore momentary drops in channel bandwidth. This value can only be
         set if tmnxMcPathBdlDefChlBwActivity is not set to 'none'."
    DEFVAL { 30 }                  
    ::= { tmnxMcPathBdlEntry 11 }

tmnxMcPathBdlDefChlBwBlackHoleRt         OBJECT-TYPE
    SYNTAX      Unsigned32 (0|1..40000000)
    UNITS       "kbps"
    MAX-ACCESS  read-create
    STATUS      current
    DESCRIPTION
        "The value of tmnxMcPathBdlDefChlBwBlackHoleRt specifies at which 
         current rate a channel should be placed in the black-hole state. 
         This value can only be set if tmnxMcPathBdlDefChlBwActivity is
         not set to 'none'."
    DEFVAL { 0 }                  
    ::= { tmnxMcPathBdlEntry 12 }

tmnxMcPathBdlDefChlExSfPath         OBJECT-TYPE
    SYNTAX      TmnxMcPathChlSfPathTypeTc
    MAX-ACCESS  read-create
    STATUS      current
    DESCRIPTION
        "The value of tmnxMcPathBdlDefChlExSfPath specifies an explicit ingress
         switch fabric multicast path assigned to a multicast channel."
    DEFVAL { none }                  
    ::= { tmnxMcPathBdlEntry 13 }

tmnxMcPathBdlVdoFCCState            OBJECT-TYPE
    SYNTAX         TmnxEnabledDisabled
    MAX-ACCESS     read-create
    STATUS         current
    DESCRIPTION 
        "The value of tmnxMcPathBdlVdoFCCState indicates whether or not 
         Fast Channel Change (FCC) server is enabled on this multicast 
         information policy bundle."
    DEFVAL { disabled }
    ::= { tmnxMcPathBdlEntry 14 }

tmnxMcPathBdlVdoRTState             OBJECT-TYPE
    SYNTAX          TmnxEnabledDisabled
    MAX-ACCESS      read-create
    STATUS          current
    DESCRIPTION
        "The value of tmnxMcPathBdlVdoRTState indicates whether or not
         Retransmission (RT) Server is enabled on this multicast
         information policy bundle."
    DEFVAL { disabled }
    ::= { tmnxMcPathBdlEntry 15 }

tmnxMcPathBdlVdoChlType             OBJECT-TYPE
    SYNTAX          TmnxMcPathVdoChlType
    MAX-ACCESS      read-create
    STATUS          current
    DESCRIPTION
        "The value of tmnxMcPathBdlVdoChlType specifies the video
         channel type. It identifies whether the video channel is
         High Definition (HD), Standard Definition (SD) or 
         Picture-in-Picture (PIP)."
    DEFVAL { hd }
    ::= { tmnxMcPathBdlEntry 16 }

tmnxMcPathBdlVdoRTAddrType          OBJECT-TYPE
    SYNTAX          InetAddressType
    MAX-ACCESS      read-create
    STATUS          current
    DESCRIPTION
        "The value of tmnxMcPathBdlVdoRTAddrType specifies the address type
         of tmnxMcPathBdlVdoRTAddress."
    DEFVAL { unknown }
    ::= { tmnxMcPathBdlEntry 17 }

tmnxMcPathBdlVdoRTAddress           OBJECT-TYPE
    SYNTAX          InetAddress (SIZE(0|4|16))
    MAX-ACCESS      read-create
    STATUS          current
    DESCRIPTION
        "The value of tmnxMcPathBdlVdoRTAddress specifies the IP address
         of the Retransmission (RT) server."
    DEFVAL { ''H }
    ::= { tmnxMcPathBdlEntry 18 }

tmnxMcPathBdlVdoRTPort              OBJECT-TYPE
    SYNTAX          TmnxVdoPortNumber
    MAX-ACCESS      read-create
    STATUS          current
    DESCRIPTION
        "The value of tmnxMcPathBdlVdoRTPort specifies the port of the 
         Retransmission (RT) server."
    DEFVAL { 4096 }
    ::= { tmnxMcPathBdlEntry 19 }

tmnxMcPathBdlVdoRTBufferSize        OBJECT-TYPE
    SYNTAX          TmnxMcPathVdoBufferSize
    UNITS           "milliseconds"
    MAX-ACCESS      read-create
    STATUS          current
    DESCRIPTION
        "The value of tmnxMcPathBdlVdoRTBufferSize specifies the number
         of milliseconds worth of channel packets to store for the
         Retransmission (RT) server."
    DEFVAL { 300 }
    ::= { tmnxMcPathBdlEntry 20 }

tmnxMcPathBdlVdoLocalRTPort         OBJECT-TYPE
    SYNTAX          TmnxVdoPortNumber
    MAX-ACCESS      read-create
    STATUS          current
    DESCRIPTION
        "The value of tmnxMcPathBdlVdoLocalRTPort specifies the local port 
         on which Retransmission (RT) requests are received. The value of 
         this object can only be set for the default bundle and will be used 
         by all bundles and channels."
    DEFVAL { 4096 }
    ::= { tmnxMcPathBdlEntry 21 }

tmnxMcPathBdlVdoLocalFccPort        OBJECT-TYPE
    SYNTAX          TmnxVdoPortNumber
    MAX-ACCESS      read-create
    STATUS          current
    DESCRIPTION
        "The value of tmnxMcPathBdlVdoLocalFccPort specifies the local port on 
         which Fast Channel Change (FCC) requests are received. The value of 
         this object can only be set for the default bundle and will be used 
         by all bundles and channels."
    DEFVAL { 4098 }
    ::= { tmnxMcPathBdlEntry 22 }

tmnxMcPathBdlVdoGroupId               OBJECT-TYPE
    SYNTAX          TmnxVdoGrpId
    MAX-ACCESS      read-create
    STATUS          current
    DESCRIPTION
        "The value of tmnxMcPathBdlVdoGroupId specifies the row index in the
         TIMETRA-VIDEO-MIB::tmnxVdoGrpTable for the video group information
         for this multicast information policy bundle.

         A value '0' indicates that no video-group is assigned to this 
         multicast information policy bundle."
    DEFVAL { 0 }
    ::= { tmnxMcPathBdlEntry 23 }

tmnxMcPathBdlTunnelIfLspName       OBJECT-TYPE
    SYNTAX      TNamedItemOrEmpty
    MAX-ACCESS  read-create
    STATUS      current
    DESCRIPTION
        "The value of tmnxMcPathBdlTunnelIfLspName specifies the name of the 
         RSVP point to multipoint (P2MP) lsp name associated with this tunnel 
         interface."
    DEFVAL { ''H }    
    ::= { tmnxMcPathBdlEntry 24 }

tmnxMcPathBdlTunIfSdAddrType        OBJECT-TYPE
    SYNTAX      InetAddressType
    MAX-ACCESS  read-create
    STATUS      current
    DESCRIPTION
        "The value of tmnxMcPathBdlTunIfSdAddrType specifies the type for
         tmnxMcPathBdlTunIfSdAddr."
    DEFVAL { unknown }     
    ::= { tmnxMcPathBdlEntry 25 } 

tmnxMcPathBdlTunIfSdAddr        OBJECT-TYPE
    SYNTAX      InetAddress (SIZE (0|4|16))
    MAX-ACCESS  read-create
    STATUS      current
    DESCRIPTION
        "The value of tmnxMcPathBdlTunIfSdAddr specifies the sender IP address
         of the ingress LER."
    DEFVAL { ''H }     
    ::= { tmnxMcPathBdlEntry 26 }        

tmnxMcPathBdlVdoSourcePort      OBJECT-TYPE
    SYNTAX      TmnxVdoPortNumber
    MAX-ACCESS  read-create
    STATUS      obsolete
    DESCRIPTION
        "The value of tmnxMcPathBdlVdoSourcePort specifies the UDP source port 
         to be used in upstream retransmission (RT) requests. The value of 
         this object can only be set for the default bundle and will be used 
         by all bundles and channels.

         This object was obsoleted from release 7.0R4."
    DEFVAL { 4097 }     
    ::= { tmnxMcPathBdlEntry 27 }   

tmnxMcPathBdlVdoLocalRTState    OBJECT-TYPE
    SYNTAX          TmnxEnabledDisabled
    MAX-ACCESS      read-create
    STATUS          current
    DESCRIPTION
        "The value of tmnxMcPathBdlVdoLocalRTState specifies whether or not
         local Retransmission (RT) Server is enabled on this multicast
         information policy bundle."
    DEFVAL { disabled }
    ::= { tmnxMcPathBdlEntry 28 }

tmnxMcPathBdlVdoReorderAudio    OBJECT-TYPE
    SYNTAX          TmnxMcPathVdoReorderAudio
    UNITS           "milliseconds"
    MAX-ACCESS      read-create
    STATUS          current
    DESCRIPTION
        "The value of tmnxMcPathBdlVdoReorderAudio specifies the time, 
         in milliseconds, by which the audio packets are reordered in the 
         ad stream. 

         If the value of this object is set to '0', then audio reordering is 
         disabled."
    DEFVAL { 0 }
    ::= { tmnxMcPathBdlEntry 29 }

tmnxMcPathBdlVdoFccMinDuration    OBJECT-TYPE
    SYNTAX          TmnxMcPathVdoFccMinDuration
    UNITS           "milliseconds"
    MAX-ACCESS      read-create
    STATUS          current
    DESCRIPTION
        "The value of tmnxMcPathBdlVdoFccMinDuration specifies the minimum 
         time duration, in milliseconds, of the Fast Channel Change (FCC)
         burst. 

         The value of this object determines the starting point of the FCC
         burst. If the current Group of Pictures (GOP) has less than the 
         minimum duration worth of data, FCC burst begins from the 
         previous GOP."
    DEFVAL { 300 }
    ::= { tmnxMcPathBdlEntry 30 }

tmnxMcPathBdlKAOverrideTimer     OBJECT-TYPE
    SYNTAX          TmnxMcPathKeepAliveOverrideTimer
    UNITS           "seconds"
    MAX-ACCESS      read-create
    STATUS          current
    DESCRIPTION
        "The value of tmnxMcPathBdlKAOverrideTimer specifies the time, 
         in seconds, used to override the keep alive timer for all (S,G) 
         entries that fall under this bundle except for (S,G) entries where 
         Keep Alive Timer Override is also configured under channel or 
         source-override.

         If the value of this object is set to '0', then Keep Alive Timer 
         Override for the bundle is disabled."
    DEFVAL  { 0 }
    ::= { tmnxMcPathBdlEntry 31 }

tmnxMcPathBdlP2MPId     OBJECT-TYPE
    SYNTAX          Unsigned32
    MAX-ACCESS      read-create
    STATUS          current
    DESCRIPTION
        "The value of tmnxMcPathBdlP2MPId specifies the identifier  
         of a Point to Multipoint (P2MP) Label Switch Path (LSP)
         associated with this tunnel interface."
    DEFVAL  { 0 }
    ::= { tmnxMcPathBdlEntry 32 }

tmnxMcPathBdlVdoAnalyzer     OBJECT-TYPE
    SYNTAX          TruthValue
    MAX-ACCESS      read-create
    STATUS          current
    DESCRIPTION
        "The value of tmnxMcPathBdlVdoAnalyzer specifies whether or not 
         the analyzer is enabled for video."
    DEFVAL  { false }
    ::= { tmnxMcPathBdlEntry 33 }

tmnxMcPathBdlVdoAnalyzerDesc     OBJECT-TYPE
    SYNTAX          TItemDescription
    MAX-ACCESS      read-create
    STATUS          current
    DESCRIPTION
        "The value of tmnxMcPathBdlVdoAnalyzerDesc specifies the description  
         for the video analyzer."
    DEFVAL { ''H }      -- the empty string
    ::= { tmnxMcPathBdlEntry 34 }

tmnxMcPathBdlVdoStrSelSrc1Type     OBJECT-TYPE
    SYNTAX          InetAddressType
    MAX-ACCESS      read-create
    STATUS          current
    DESCRIPTION
        "The value of tmnxMcPathBdlVdoStrSelSrc1Type specifies the address 
         type of tmnxMcPathBdlVdoStrSelSrc1."
    DEFVAL  { unknown }
    ::= { tmnxMcPathBdlEntry 35 }

tmnxMcPathBdlVdoStrSelSrc1     OBJECT-TYPE
    SYNTAX          InetAddress (SIZE (0|4|16))
    MAX-ACCESS      read-create
    STATUS          current
    DESCRIPTION
        "The value of tmnxMcPathBdlVdoStrSelSrc1 specifies the address of the 
         first source in stream selection."
    DEFVAL { ''H }      -- the empty string
    ::= { tmnxMcPathBdlEntry 36 }

tmnxMcPathBdlVdoStrSelIntf1    OBJECT-TYPE
    SYNTAX          TNamedItemOrEmpty
    MAX-ACCESS      read-create
    STATUS          current
    DESCRIPTION
        "The value of tmnxMcPathBdlVdoStrSelIntf1 specifies the interface 
         on which multicast traffic from 'tmnxMcPathBdlVdoStrSelSrc1' arrives."
    DEFVAL { ''H }      -- the empty string
    ::= { tmnxMcPathBdlEntry 37 }

tmnxMcPathBdlVdoStrSelSrc2Type     OBJECT-TYPE
    SYNTAX          InetAddressType
    MAX-ACCESS      read-create
    STATUS          current
    DESCRIPTION
        "The value of tmnxMcPathBdlVdoStrSelSrc2Type specifies the address 
         type of tmnxMcPathBdlVdoStrSelSrc2."
    DEFVAL   { unknown }
    ::= { tmnxMcPathBdlEntry 38 }

tmnxMcPathBdlVdoStrSelSrc2     OBJECT-TYPE
    SYNTAX          InetAddress (SIZE (0|4|16))
    MAX-ACCESS      read-create
    STATUS          current
    DESCRIPTION
        "The value of tmnxMcPathBdlVdoStrSelSrc2 specifies the address of the 
         second source in stream selection."
    DEFVAL { ''H }      -- the empty string
    ::= { tmnxMcPathBdlEntry 39 }

tmnxMcPathBdlVdoStrSelIntf2     OBJECT-TYPE
    SYNTAX          TNamedItemOrEmpty
    MAX-ACCESS      read-create
    STATUS          current
    DESCRIPTION
        "The value of tmnxMcPathBdlVdoStrSelIntf2 specifies the interface 
         on which multicast traffic from 'tmnxMcPathBdlVdoStrSelSrc2' arrives."
    DEFVAL { ''H }      -- the empty string
    ::= { tmnxMcPathBdlEntry 40 }

-- ------------------------------------------------
-- multicast information policy bundle channel table
-- ------------------------------------------------

tmnxMcPathBdlChlTblLastChanged OBJECT-TYPE
    SYNTAX      TimeStamp
    MAX-ACCESS  read-only
    STATUS      current
    DESCRIPTION
        "The value of tmnxMcPathBdlChlTblLastChanged indicates the sysUpTime 
         at the time of the last modification to tmnxMcPathBwPlcyTable by 
         adding, deleting an entry or change to a writable object in the table.

         If no changes were made to the table since the last re-initialization 
         of the local network management subsystem, then this object contains a 
         zero value."
    ::= { tmnxMcPathGlobalObjs 4 } 

tmnxMcPathBdlChlTable    OBJECT-TYPE
    SYNTAX      SEQUENCE OF TmnxMcPathBdlChlEntry
    MAX-ACCESS  not-accessible
    STATUS      current
    DESCRIPTION
        "The tmnxMcPathBdlChlTable has an entry for each multicast 
         information policy bundle channel configured on this system."
    ::= { tmnxMcPathObjs 9 }

tmnxMcPathBdlChlEntry    OBJECT-TYPE
    SYNTAX      TmnxMcPathBdlChlEntry
    MAX-ACCESS  not-accessible
    STATUS      current
    DESCRIPTION
        "Each row entry represents a particular multicast information policy 
         bundle channel. Entries are created/deleted by the user."
    INDEX { tmnxMcPathPlcyName, 
            tmnxMcPathBdlName, 
            tmnxMcPathBdlChlStartAddrType, 
            tmnxMcPathBdlChlStartAddr,
            tmnxMcPathBdlChlEndAddrType, 
            tmnxMcPathBdlChlEndAddr 
          }
    ::= { tmnxMcPathBdlChlTable 1}

TmnxMcPathBdlChlEntry ::= SEQUENCE
   {
       tmnxMcPathBdlChlStartAddrType        InetAddressType,
       tmnxMcPathBdlChlStartAddr            InetAddress,
       tmnxMcPathBdlChlEndAddrType          InetAddressType,
       tmnxMcPathBdlChlEndAddr              InetAddress,
       tmnxMcPathBdlChlRowStatus            RowStatus,
       tmnxMcPathBdlChlLastChanged          TimeStamp,
       tmnxMcPathBdlChlAdminBw              Unsigned32,
       tmnxMcPathBdlChlPref                 Unsigned32,
       tmnxMcPathBdlChlBwActivity           TmnxMcPathBwActivityTc,
       tmnxMcPathBdlChlBwFallDelay          Unsigned32,
       tmnxMcPathBdlChlBwBlackHoleRt        Unsigned32,
       tmnxMcPathBdlChlExSfPath             TmnxMcPathChlSfPathTypeTc,
       tmnxMcPathBdlChlVdoFCCState          TmnxEnabledDisabledOrInherit,
       tmnxMcPathBdlChlVdoRTState           TmnxEnabledDisabledOrInherit,
       tmnxMcPathBdlChlVdoChlType           TmnxMcPathVdoChlTypeOrInherit,
       tmnxMcPathBdlChlVdoRTAddrType        InetAddressType,
       tmnxMcPathBdlChlVdoRTAddress         InetAddress,
       tmnxMcPathBdlChlVdoRTPort            TmnxVdoPortNumber,
       tmnxMcPathBdlChlVdoRTBufferSize      TmnxMcPathVdoBufferSize,
       tmnxMcPathBdlChlVdoLocalRTPort       TmnxVdoPortNumber,
       tmnxMcPathBdlChlVdoLocalFccPort      TmnxVdoPortNumber,
       tmnxMcPathBdlChlVdoGroupId           TmnxVdoGrpIdOrInherit,
       tmnxMcPathBdlChlTunnelIfLspName      TNamedItemOrEmpty,
       tmnxMcPathBdlChlTunIfSdAddrType      InetAddressType,
       tmnxMcPathBdlChlTunIfSdAddr          InetAddress,
       tmnxMcPathBdlChlVdoLocalRTState      TmnxEnabledDisabledOrInherit,
       tmnxMcPathBdlChlVdoReorderAudio      TmnxMcPathVdoReorderAudio,
       tmnxMcPathBdlChlVdoFccMinDuratn      TmnxMcPathVdoFccMinDurationOrZero,
       tmnxMcPathBdlChlKAOverrideTimer      TmnxMcPathKeepAliveOverrideTimer,
       tmnxMcPathBdlChlP2MPId               Unsigned32,
       tmnxMcPathBdlChlVdoAnalyzer          TruthValue,
       tmnxMcPathBdlChlVdoAnalyzerDesc      TItemDescription,
       tmnxMcPathBdlChlVdoStrSelSrc1Typ     InetAddressType,
       tmnxMcPathBdlChlVdoStrSelSrc1        InetAddress,
       tmnxMcPathBdlChlVdoStrSelIntf1       TNamedItemOrEmpty,
       tmnxMcPathBdlChlVdoStrSelSrc2Typ     InetAddressType,
       tmnxMcPathBdlChlVdoStrSelSrc2        InetAddress,
       tmnxMcPathBdlChlVdoStrSelIntf2       TNamedItemOrEmpty
   }

tmnxMcPathBdlChlStartAddrType   OBJECT-TYPE
    SYNTAX      InetAddressType
    MAX-ACCESS  not-accessible
    STATUS      current
    DESCRIPTION
        "The value of tmnxMcPathBdlChlStartAddrType indicates the address type 
         of tmnxMcPathBdlChlStartAddr."
    ::= { tmnxMcPathBdlChlEntry 1 }

tmnxMcPathBdlChlStartAddr         OBJECT-TYPE
    SYNTAX      InetAddress (SIZE (4|16|20))
    MAX-ACCESS  not-accessible
    STATUS      current
    DESCRIPTION
        "The value of tmnxMcPathBdlChlStartAddr indicates the start address of 
         the multicast channel.  Its type is specified by 
         tmnxMcPathBdlChlStartAddrType."
    ::= { tmnxMcPathBdlChlEntry 2 }

tmnxMcPathBdlChlEndAddrType   OBJECT-TYPE
    SYNTAX      InetAddressType
    MAX-ACCESS  not-accessible
    STATUS      current
    DESCRIPTION
        "The value of tmnxMcPathBdlChlEndAddrType indicates the address type 
         of tmnxMcPathBdlChlEndAddr."
    ::= { tmnxMcPathBdlChlEntry 3}

tmnxMcPathBdlChlEndAddr         OBJECT-TYPE
    SYNTAX      InetAddress (SIZE (4|16|20))
    MAX-ACCESS  not-accessible
    STATUS      current
    DESCRIPTION
        "The value of tmnxMcPathBdlChlEndAddr indicates the end address of the 
         multicast channel. Its type is specified by 
         tmnxMcPathBdlChlEndAddrType.
         
         The value of tmnxMcPathBdlChlEndAddr should always be greater than or 
         equal to tmnxMcPathBdlChlStartAddr."
    ::= { tmnxMcPathBdlChlEntry 4 }

tmnxMcPathBdlChlRowStatus  OBJECT-TYPE
    SYNTAX      RowStatus
    MAX-ACCESS  read-create
    STATUS      current
    DESCRIPTION
        "The value of tmnxMcPathBdlChlRowStatus is used for creation/deletion of
         multicast channel in an information policy bundle."
    ::= { tmnxMcPathBdlChlEntry 5 }

tmnxMcPathBdlChlLastChanged  OBJECT-TYPE
    SYNTAX      TimeStamp
    MAX-ACCESS  read-only
    STATUS      current
    DESCRIPTION
        "The value of tmnxMcPathBdlChlLastChanged indicates the timestamp of 
         last change to this row in tmnxMcPathBdlChlTable."
    ::= { tmnxMcPathBdlChlEntry 6 }

tmnxMcPathBdlChlAdminBw            OBJECT-TYPE
    SYNTAX      Unsigned32 (0..40000000)
    UNITS       "kbps"
    MAX-ACCESS  read-create
    STATUS      current
    DESCRIPTION
        "The value of tmnxMcPathBdlChlAdminBw specifies the multicast channel's
         administrative bandwidth in kilo-bits per second(kbps)."
    DEFVAL { 0 }         
    ::= { tmnxMcPathBdlChlEntry 7 }

tmnxMcPathBdlChlPref        OBJECT-TYPE
    SYNTAX      Unsigned32 (0..7) 
    MAX-ACCESS  read-create
    STATUS      current
    DESCRIPTION
        "The value of tmnxMcPathBdlChlPref specifies specifies the relative 
         preference level for multicast channels.  tmnxMcPathBdlChlPref 
         specifies its relative importance over other multicast channels. Eight
         levels of preference are supported; 0 through 7. Preference value 7 
         indicates the highest preference level."
    DEFVAL { 0 }                  
    ::= { tmnxMcPathBdlChlEntry 8 }

tmnxMcPathBdlChlBwActivity            OBJECT-TYPE
    SYNTAX      TmnxMcPathBwActivityTc
    MAX-ACCESS  read-create
    STATUS      current
    DESCRIPTION
        "The value of tmnxMcPathBdlChlBwActivity specifies how the multicast
         ingress path manager determines the amount of bandwidth required by a 
         multicast channel. This object can have value 'use-admin-bw' only if
         tmnxMcPathBdlChlAdminBw is non-zero."
    DEFVAL { none }         
    ::= { tmnxMcPathBdlChlEntry 10 }

tmnxMcPathBdlChlBwFallDelay        OBJECT-TYPE
    SYNTAX      Unsigned32 (0|10..3600)
    UNITS       "seconds" 
    MAX-ACCESS  read-create
    STATUS      current
    DESCRIPTION
        "The value of tmnxMcPathBdlChlBwFallDelay specifies the value the
         bandwidth manager uses the falling-delay threshold to hold on to the 
         previous highest bandwidth until the delay time has expired while 
         operating in dynamic bandwidth mode.  This allows the bandwidth manager
         ignore momentary drops in channel bandwidth. This value can only be set
         if tmnxMcPathBdlChlBwActivity is not set to 'none'.
        
         The default value of '0' means that there is no channel override and
         tmnxMcPathBdlDefChlBwFallDelay should be used."
    DEFVAL { 0 }                  
    ::= { tmnxMcPathBdlChlEntry 11 }

tmnxMcPathBdlChlBwBlackHoleRt         OBJECT-TYPE
    SYNTAX      Unsigned32 (0..40000000)
    UNITS       "kbps"
    MAX-ACCESS  read-create
    STATUS      current
    DESCRIPTION
        "The value of tmnxMcPathBdlChlBwBlackHoleRt specifies at which current 
         rate a channel should be placed in the black-hole state. This value 
         can only be set if tmnxMcPathBdlChlBwActivity is not set to 'none'."
    DEFVAL { 0 }                  
    ::= { tmnxMcPathBdlChlEntry 12 }

tmnxMcPathBdlChlExSfPath         OBJECT-TYPE
    SYNTAX      TmnxMcPathChlSfPathTypeTc
    MAX-ACCESS  read-create
    STATUS      current
    DESCRIPTION
        "The value of tmnxMcPathBdlChlExSfPath specifies an explicit ingress
         switch fabric multicast path assigned to a multicast channel."
    DEFVAL { none }               
    ::= { tmnxMcPathBdlChlEntry 13 }

tmnxMcPathBdlChlVdoFCCState            OBJECT-TYPE
    SYNTAX         TmnxEnabledDisabledOrInherit
    MAX-ACCESS     read-create
    STATUS         current
    DESCRIPTION
        "The value of tmnxMcPathBdlChlVdoFCCState specifies the state of Fast 
         Channel Change (FCC) server on this multicast channel. 

         When this object has a value of 'enabled', FCC server is enabled. When 
         its value is 'disabled', FCC server is disabled. When its value is 
         'inherit', state of FCC server is inherited from the value of 
         tmnxMcPathBdlVdoFCCState which specifies the state of FCC server at 
         the bundle level."
    DEFVAL { inherit }
    ::= { tmnxMcPathBdlChlEntry 14 }

tmnxMcPathBdlChlVdoRTState             OBJECT-TYPE
    SYNTAX          TmnxEnabledDisabledOrInherit
    MAX-ACCESS      read-create
    STATUS          current
    DESCRIPTION
        "The value of tmnxMcPathBdlChlVdoRTState specifies the state of 
         Retransmission (RT) Server on this multicast channel. 

         When this object has a value of 'enabled', RT server is enabled. When 
         its value is 'disabled', RT server is disabled. When its value is 
         'inherit', state of RT server is inherited from the value of 
         tmnxMcPathBdlVdoRTState which specifies the state of RT server at 
         the bundle level."
    DEFVAL { inherit }
    ::= { tmnxMcPathBdlChlEntry 15 }

tmnxMcPathBdlChlVdoChlType             OBJECT-TYPE
    SYNTAX          TmnxMcPathVdoChlTypeOrInherit
    MAX-ACCESS      read-create
    STATUS          current
    DESCRIPTION
        "The value of tmnxMcPathBdlChlVdoChlType specifies the video
         channel type. It identifies whether the video channel is
         High Definition (HD), Standard Definition (SD) or
         Picture-in-Picture (PIP).

         When this object has a value of 'inherit', video channel type is 
         inherited from the value of tmnxMcPathBdlVdoChlType which specifies 
         the video channel type at bundle level."
    DEFVAL { inherit }
    ::= { tmnxMcPathBdlChlEntry 16 }

tmnxMcPathBdlChlVdoRTAddrType          OBJECT-TYPE
    SYNTAX          InetAddressType
    MAX-ACCESS      read-create
    STATUS          current
    DESCRIPTION
        "The value of tmnxMcPathBdlChlVdoRTAddrType specifies the address type
         of tmnxMcPathBdlChlVdoRTAddress."
    DEFVAL { unknown }
    ::= { tmnxMcPathBdlChlEntry 17 }

tmnxMcPathBdlChlVdoRTAddress           OBJECT-TYPE
    SYNTAX          InetAddress (SIZE(0|4|16))
    MAX-ACCESS      read-create
    STATUS          current
    DESCRIPTION
        "The value of tmnxMcPathBdlChlVdoRTAddress specifies the IP address
         of the Retransmission (RT) server."
    DEFVAL { ''H }
    ::= { tmnxMcPathBdlChlEntry 18 }

tmnxMcPathBdlChlVdoRTPort              OBJECT-TYPE
    SYNTAX          TmnxVdoPortNumber
    MAX-ACCESS      read-create
    STATUS          current
    DESCRIPTION
        "The value of tmnxMcPathBdlChlVdoRTPort specifies the port of the
         Retransmission (RT) server."
    DEFVAL { 4096 }
    ::= { tmnxMcPathBdlChlEntry 19 }

tmnxMcPathBdlChlVdoRTBufferSize        OBJECT-TYPE
    SYNTAX          TmnxMcPathVdoBufferSize
    UNITS           "milliseconds"
    MAX-ACCESS      read-create
    STATUS          current
    DESCRIPTION
        "The value of tmnxMcPathBdlChlVdoRTBufferSize specifies the number
         of milliseconds worth of channel packets to store for the
         Retransmission (RT) server."
    DEFVAL { 300 }     
    ::= { tmnxMcPathBdlChlEntry 20 }

tmnxMcPathBdlChlVdoLocalRTPort         OBJECT-TYPE
    SYNTAX          TmnxVdoPortNumber
    MAX-ACCESS      read-create
    STATUS          obsolete
    DESCRIPTION
        "The value of tmnxMcPathBdlChlVdoLocalRTPort specifies the local port
         on which Retransmission (RT) requests are received.  The value of 
         this object can only be set for the default bundle and will be used 
         by all channels.

         This object was obsoleted from release 7.0R4."
    DEFVAL { 4096 }
    ::= { tmnxMcPathBdlChlEntry 21 }

tmnxMcPathBdlChlVdoLocalFccPort        OBJECT-TYPE
    SYNTAX          TmnxVdoPortNumber
    MAX-ACCESS      read-create
    STATUS          obsolete
    DESCRIPTION
        "The value of tmnxMcPathBdlChlVdoLocalFccPort specifies the local port 
         on which Fast Channel Change (FCC) requests are received.  The value of 
         this object can only be set for the default bundle and will be used 
         by all channels.

         This object was obsoleted from release 7.0R4."
    DEFVAL { 4098 }
    ::= { tmnxMcPathBdlChlEntry 22 }

tmnxMcPathBdlChlVdoGroupId               OBJECT-TYPE
    SYNTAX          TmnxVdoGrpIdOrInherit
    MAX-ACCESS      read-create
    STATUS          current
    DESCRIPTION
        "The value of tmnxMcPathBdlChlVdoGroupId specifies the row index in the
         TIMETRA-VIDEO-MIB::tmnxVdoGrpTable for the video group information
         for this multicast information policy bundle.

         A value '0' indicates that no video-group is assigned to this
         multicast channel.  A value of '-1' indicates that video-group 
         information is inherited from the value of tmnxMcPathBdlVdoGroupId 
         which specifies the video-group information at the bundle level."
    DEFVAL { -1 }
    ::= { tmnxMcPathBdlChlEntry 23 }

tmnxMcPathBdlChlTunnelIfLspName       OBJECT-TYPE
    SYNTAX      TNamedItemOrEmpty
    MAX-ACCESS  read-create
    STATUS      current
    DESCRIPTION
        "The value of tmnxMcPathBdlChlTunnelIfLspName specifies the name of the 
         RSVP point to multipoint (P2MP) lsp name associated with this tunnel 
         interface."
    DEFVAL { ''H }    
    ::= { tmnxMcPathBdlChlEntry 24 }

tmnxMcPathBdlChlTunIfSdAddrType        OBJECT-TYPE
    SYNTAX      InetAddressType
    MAX-ACCESS  read-create
    STATUS      current
    DESCRIPTION
        "The value of tmnxMcPathBdlChlTunIfSdAddrType specifies the type for
         tmnxMcPathBdlChlTunIfSdAddr."
     DEFVAL { unknown }     
    ::= { tmnxMcPathBdlChlEntry 25 } 

tmnxMcPathBdlChlTunIfSdAddr        OBJECT-TYPE
    SYNTAX      InetAddress (SIZE (0|4|16))
    MAX-ACCESS  read-create
    STATUS      current
    DESCRIPTION
        "The value of tmnxMcPathBdlChlTunIfSdAddr specifies the sender address."
    DEFVAL { ''H }  
    ::= { tmnxMcPathBdlChlEntry 26 }     

tmnxMcPathBdlChlVdoLocalRTState    OBJECT-TYPE
    SYNTAX          TmnxEnabledDisabledOrInherit
    MAX-ACCESS      read-create
    STATUS          current
    DESCRIPTION
        "The value of tmnxMcPathBdlChlVdoLocalRTState specifies the state of 
         local Retransmission (RT) Server on this multicast channel. 

         When this object has a value of 'enabled', local RT server is enabled. 
         When its value is 'disabled', local RT server is disabled. When its 
         value is 'inherit', state of local RT server is inherited from the 
         value of tmnxMcPathBdlVdoLocalRTState which specifies the state of 
         local RT server at the bundle level."
    DEFVAL { inherit }
    ::= { tmnxMcPathBdlChlEntry 27 }

tmnxMcPathBdlChlVdoReorderAudio    OBJECT-TYPE
    SYNTAX          TmnxMcPathVdoReorderAudio
    UNITS           "milliseconds"
    MAX-ACCESS      read-create
    STATUS          current
    DESCRIPTION
        "The value of tmnxMcPathBdlChlVdoReorderAudio specifies the time, 
         in milliseconds, by which the audio packets are reordered in the 
         ad stream. 

         If the value of this object is set to '0', then audio reordering is 
         disabled."
    DEFVAL { 0 }
    ::= { tmnxMcPathBdlChlEntry 28 }

tmnxMcPathBdlChlVdoFccMinDuratn    OBJECT-TYPE
    SYNTAX          TmnxMcPathVdoFccMinDurationOrZero
    UNITS           "milliseconds"
    MAX-ACCESS      read-create
    STATUS          current
    DESCRIPTION
        "The value of tmnxMcPathBdlChlVdoFccMinDuratn specifies the minimum 
         time duration, in milliseconds, of the Fast Channel Change (FCC)
         burst. 

         The value of this object determines the starting point of the FCC
         burst. If the current Group of Pictures (GOP) has less than the 
         minimum duration worth of data, FCC burst begins from the 
         previous GOP. When the value of this object is set to '0', then the 
         minimum time duration will be inherited from the value of 
         tmnxMcPathBdlVdoFccMinDuration at the bundle level."
    DEFVAL { 0 }
    ::= { tmnxMcPathBdlChlEntry 29 }

tmnxMcPathBdlChlKAOverrideTimer     OBJECT-TYPE
    SYNTAX          TmnxMcPathKeepAliveOverrideTimer
    UNITS           "seconds"
    MAX-ACCESS      read-create
    STATUS          current
    DESCRIPTION
        "The value of tmnxMcPathBdlChlKAOverrideTimer specifies the time, 
         in seconds, used to override the keep alive timer for all (S,G) 
         entries that fall under a channel (a group or a group range) except
         for (S,G) entries where Keep Alive Timer Override is also configured 
         under the source-override.

         If the value of this object is set to '0', then Keep Alive Timer 
         Override for the channel is disabled."
    DEFVAL  { 0 }
    ::= { tmnxMcPathBdlChlEntry 30 }

tmnxMcPathBdlChlP2MPId     OBJECT-TYPE
    SYNTAX          Unsigned32
    MAX-ACCESS      read-create
    STATUS          current
    DESCRIPTION
        "The value of tmnxMcPathBdlChlP2MPId specifies the identifier  
         of a Point to Multipoint (P2MP) Label Switch Path (LSP)
         associated with this tunnel interface."
    DEFVAL  { 0 }
    ::= { tmnxMcPathBdlChlEntry 31 }

tmnxMcPathBdlChlVdoAnalyzer     OBJECT-TYPE
    SYNTAX          TruthValue
    MAX-ACCESS      read-create
    STATUS          current
    DESCRIPTION
        "The value of tmnxMcPathBdlChlVdoAnalyzer specifies whether or not 
         the analyzer is enabled for video."
    DEFVAL  { false }
    ::= { tmnxMcPathBdlChlEntry 32 }

tmnxMcPathBdlChlVdoAnalyzerDesc     OBJECT-TYPE
    SYNTAX          TItemDescription
    MAX-ACCESS      read-create
    STATUS          current
    DESCRIPTION
        "The value of tmnxMcPathBdlChlVdoAnalyzerDesc specifies the description  
         for the video analyzer."
    DEFVAL { ''H }      -- the empty string
    ::= { tmnxMcPathBdlChlEntry 33 }

tmnxMcPathBdlChlVdoStrSelSrc1Typ     OBJECT-TYPE
    SYNTAX          InetAddressType
    MAX-ACCESS      read-create
    STATUS          current
    DESCRIPTION
        "The value of tmnxMcPathBdlChlVdoStrSelSrc1Typ specifies the address 
         type of tmnxMcPathBdlChlVdoStrSelSrc1."
    DEFVAL  { unknown }
    ::= { tmnxMcPathBdlChlEntry 34 }

tmnxMcPathBdlChlVdoStrSelSrc1     OBJECT-TYPE
    SYNTAX          InetAddress (SIZE (0|4|16))
    MAX-ACCESS      read-create
    STATUS          current
    DESCRIPTION
        "The value of tmnxMcPathBdlChlVdoStrSelSrc1 specifies the address of the 
         first source in stream selection."
    DEFVAL { ''H }      -- the empty string
    ::= { tmnxMcPathBdlChlEntry 35 }

tmnxMcPathBdlChlVdoStrSelIntf1     OBJECT-TYPE
    SYNTAX          TNamedItemOrEmpty
    MAX-ACCESS      read-create
    STATUS          current
    DESCRIPTION
        "The value of tmnxMcPathBdlChlVdoStrSelIntf1 specifies the interface 
         on which multicast traffic from 'tmnxMcPathBdlChlVdoStrSelSrc1' 
         arrives."
    DEFVAL { ''H }      -- the empty string
    ::= { tmnxMcPathBdlChlEntry 36 }

tmnxMcPathBdlChlVdoStrSelSrc2Typ    OBJECT-TYPE
    SYNTAX          InetAddressType
    MAX-ACCESS      read-create
    STATUS          current
    DESCRIPTION
        "The value of tmnxMcPathBdlChlVdoStrSelSrc2Typ specifies the address 
         type of tmnxMcPathBdlChlVdoStrSelSrc2."
    DEFVAL   { unknown }
    ::= { tmnxMcPathBdlChlEntry 37 }

tmnxMcPathBdlChlVdoStrSelSrc2     OBJECT-TYPE
    SYNTAX          InetAddress (SIZE (0|4|16))
    MAX-ACCESS      read-create
    STATUS          current
    DESCRIPTION
        "The value of tmnxMcPathBdlChlVdoStrSelSrc2 specifies the address of the 
         second source in stream selection."
    DEFVAL { ''H }      -- the empty string
    ::= { tmnxMcPathBdlChlEntry 38 }

tmnxMcPathBdlChlVdoStrSelIntf2     OBJECT-TYPE
    SYNTAX          TNamedItemOrEmpty
    MAX-ACCESS      read-create
    STATUS          current
    DESCRIPTION
        "The value of tmnxMcPathBdlChlVdoStrSelIntf2 specifies the interface  
         on which multicast traffic from 'tmnxMcPathBdlChlVdoStrSelSrc2' 
         arrives."
    DEFVAL { ''H }      -- the empty string
    ::= { tmnxMcPathBdlChlEntry 39 }

-- ------------------------------------------------
-- multicast policy bundle channel source-override table
-- ------------------------------------------------

tmnxMcPathChlSrcTableLastChanged OBJECT-TYPE
    SYNTAX      TimeStamp
    MAX-ACCESS  read-only
    STATUS      current
    DESCRIPTION
        "The value of tmnxMcPathChlSrcTableLastChanged indicates the sysUpTime 
         at the time of the last modification to tmnxMcPathChlSrcTable by 
         adding, deleting an entry or change to a writable object in the table.

         If no changes were made to the table since the last re-initialization 
         of the local network management subsystem, then this object contains a 
         zero value."
    ::= { tmnxMcPathGlobalObjs 5 } 

tmnxMcPathChlSrcTable    OBJECT-TYPE
    SYNTAX      SEQUENCE OF TmnxMcPathChlSrcEntry
    MAX-ACCESS  not-accessible
    STATUS      current
    DESCRIPTION
        "The tmnxMcPathChlSrcTable has an entry for each specified sender 
         override context from the multicast information policy bundle channel 
         range configured on this system."
    ::= { tmnxMcPathObjs 11 }

tmnxMcPathChlSrcEntry    OBJECT-TYPE
    SYNTAX      TmnxMcPathChlSrcEntry
    MAX-ACCESS  not-accessible
    STATUS      current
    DESCRIPTION
        "Each row entry represents a specified sender configured for multicast
         bundle channel. Entries are created/deleted by the user."
    INDEX { tmnxMcPathPlcyName, 
            tmnxMcPathBdlName, 
            tmnxMcPathBdlChlStartAddrType, 
            tmnxMcPathBdlChlStartAddr,
            tmnxMcPathBdlChlEndAddrType, 
            tmnxMcPathBdlChlEndAddr,
            tmnxMcPathChlSrcSourceAddrType,
            tmnxMcPathChlSrcSourceAddr
          }
    ::= { tmnxMcPathChlSrcTable 1}

TmnxMcPathChlSrcEntry ::= SEQUENCE
   {
       tmnxMcPathChlSrcSourceAddrType       InetAddressType,
       tmnxMcPathChlSrcSourceAddr           InetAddress,
       tmnxMcPathChlSrcRowStatus            RowStatus,
       tmnxMcPathChlSrcLastChanged          TimeStamp,
       tmnxMcPathChlSrcAdminBw              Unsigned32,
       tmnxMcPathChlSrcPref                 Unsigned32,
       tmnxMcPathChlSrcBwActivity           TmnxMcPathBwActivityTc,
       tmnxMcPathChlSrcBwFallDelay          Unsigned32,
       tmnxMcPathChlSrcBwBlackHoleRt        Unsigned32,
       tmnxMcPathChlSrcExSfPath             TmnxMcPathChlSfPathTypeTc,
       tmnxMcPathChlSrcVdoFCCState          TmnxEnabledDisabledOrInherit,
       tmnxMcPathChlSrcVdoRTState           TmnxEnabledDisabledOrInherit,
       tmnxMcPathChlSrcVdoChlType           TmnxMcPathVdoChlTypeOrInherit,
       tmnxMcPathChlSrcVdoRTAddrType        InetAddressType,
       tmnxMcPathChlSrcVdoRTAddress         InetAddress,
       tmnxMcPathChlSrcVdoRTPort            TmnxVdoPortNumber,
       tmnxMcPathChlSrcVdoRTBufferSize      TmnxMcPathVdoBufferSize,
       tmnxMcPathChlSrcVdoLocalRTPort       TmnxVdoPortNumber,
       tmnxMcPathChlSrcVdoLocalFccPort      TmnxVdoPortNumber,
       tmnxMcPathChlSrcVdoGroupId           TmnxVdoGrpIdOrInherit,
       tmnxMcPathChlSrcTunnelIfLspName      TNamedItemOrEmpty,
       tmnxMcPathChlSrcTunIfSdAddrType      InetAddressType,
       tmnxMcPathChlSrcTunIfSdAddr          InetAddress,
       tmnxMcPathChlSrcVdoLocalRTState      TmnxEnabledDisabledOrInherit,
       tmnxMcPathChlSrcVdoReorderAudio      TmnxMcPathVdoReorderAudio,
       tmnxMcPathChlSrcVdoFccMinDuratn      TmnxMcPathVdoFccMinDurationOrZero,
       tmnxMcPathChlSrcKAOverrideTimer      TmnxMcPathKeepAliveOverrideTimer,
       tmnxMcPathChlSrcP2MPId               Unsigned32,
       tmnxMcPathChlSrcVdoAnalyzer          TruthValue,
       tmnxMcPathChlSrcVdoAnalyzerDesc      TItemDescription,
       tmnxMcPathChlSrcVdoStSeSrc1Type      InetAddressType,       
       tmnxMcPathChlSrcVdoStSeSrc1          InetAddress,
       tmnxMcPathChlSrcVdoStSeIntf1         TNamedItemOrEmpty,
       tmnxMcPathChlSrcVdoStSeSrc2Type      InetAddressType,
       tmnxMcPathChlSrcVdoStSeSrc2          InetAddress,
       tmnxMcPathChlSrcVdoStSeIntf2         TNamedItemOrEmpty
   }

tmnxMcPathChlSrcSourceAddrType   OBJECT-TYPE
    SYNTAX      InetAddressType
    MAX-ACCESS  not-accessible
    STATUS      current
    DESCRIPTION
        "The value of tmnxMcPathChlSrcSourceAddrType indicates the address type 
         of tmnxMcPathChlSrcSourceAddr."
    ::= { tmnxMcPathChlSrcEntry 1 }

tmnxMcPathChlSrcSourceAddr         OBJECT-TYPE
    SYNTAX      InetAddress (SIZE (4|16|20))
    MAX-ACCESS  not-accessible
    STATUS      current
    DESCRIPTION
        "The value of tmnxMcPathChlSrcSourceAddr indicates the start address of 
         the multicast channel. Its type is specified by 
         tmnxMcPathChlSrcSourceAddrType."
    ::= { tmnxMcPathChlSrcEntry 2 }

tmnxMcPathChlSrcRowStatus  OBJECT-TYPE
    SYNTAX      RowStatus
    MAX-ACCESS  read-create
    STATUS      current
    DESCRIPTION
        "The value of tmnxMcPathChlSrcRowStatus is used for creation/deletion of
         a specified sender override context for the multicast bundle."
    ::= { tmnxMcPathChlSrcEntry 3 }

tmnxMcPathChlSrcLastChanged  OBJECT-TYPE
    SYNTAX      TimeStamp
    MAX-ACCESS  read-only
    STATUS      current
    DESCRIPTION
        "The value of tmnxMcPathChlSrcLastChanged indicates the timestamp of 
         last change to this row in tmnxMcPathChlSrcTable."
    ::= { tmnxMcPathChlSrcEntry 4 }

tmnxMcPathChlSrcAdminBw            OBJECT-TYPE
    SYNTAX      Unsigned32 (0..40000000)
    UNITS       "kbps"
    MAX-ACCESS  read-create
    STATUS      current
    DESCRIPTION
        "The value of tmnxMcPathChlSrcAdminBw specifies the multicast channel's
         administrative bandwidth in kilo-bits per second(kbps)."
    DEFVAL { 0 }         
    ::= { tmnxMcPathChlSrcEntry 5 }

tmnxMcPathChlSrcPref        OBJECT-TYPE
    SYNTAX      Unsigned32 (0..7) 
    MAX-ACCESS  read-create
    STATUS      current
    DESCRIPTION
        "The value of tmnxMcPathChlSrcPref specifies the channel's relative 
         preference level for multicast channels.  tmnxMcPathBdlChlPref 
         specifies its relative importance over other multicast channels.  Eight
         levels of preference are supported; 0 through 7. Preference value 7 
         indicates the highest preference level."
    DEFVAL { 0 }                  
    ::= { tmnxMcPathChlSrcEntry 6 }

tmnxMcPathChlSrcBwActivity            OBJECT-TYPE
    SYNTAX      TmnxMcPathBwActivityTc
    MAX-ACCESS  read-create
    STATUS      current
    DESCRIPTION
        "The value of tmnxMcPathChlSrcBwActivity specifies how the multicast
         ingress path manager determines the amount of bandwidth required by a 
         multicast channel. This object can have value 'use-admin-bw' only if
         tmnxMcPathChlSrcAdminBw is non-zero."
    DEFVAL { none }         
    ::= { tmnxMcPathChlSrcEntry 8 }

tmnxMcPathChlSrcBwFallDelay        OBJECT-TYPE
    SYNTAX      Unsigned32 (0|10..3600)
    UNITS       "seconds" 
    MAX-ACCESS  read-create
    STATUS      current
    DESCRIPTION
        "The value of tmnxMcPathChlSrcBwFallDelay specifies the value the
         bandwidth manager uses the falling-delay threshold to hold on to the 
         previous highest bandwidth until the delay time has expired while 
         operating in dynamic bandwidth mode.  This allows the bandwidth manager
         ignore momentary drops in channel bandwidth. This value can only be set
         if tmnxMcPathChlSrcBwActivity is not set to 'none'.

         The default value of '0' means that there is no source override and
         tmnxMcPathBdlChlBwFallDelay should be used."
    DEFVAL { 0 }                  
    ::= { tmnxMcPathChlSrcEntry 9 }

tmnxMcPathChlSrcBwBlackHoleRt         OBJECT-TYPE
    SYNTAX      Unsigned32 (0..40000000)
    UNITS       "kbps"
    MAX-ACCESS  read-create
    STATUS      current
    DESCRIPTION
        "The value of tmnxMcPathChlSrcBwBlackHoleRt specifies at which 
         current rate a channel should be placed in the black-hole state.
         This value can only be set if tmnxMcPathChlSrcBwActivity is not 
         set to 'none'."
    DEFVAL { 0 }                  
    ::= { tmnxMcPathChlSrcEntry 10 }

tmnxMcPathChlSrcExSfPath         OBJECT-TYPE
    SYNTAX      TmnxMcPathChlSfPathTypeTc
    MAX-ACCESS  read-create
    STATUS      current
    DESCRIPTION
        "The value of tmnxMcPathChlSrcExSfPath specifies an explicit ingress
         switch fabric multicast path assigned to a multicast channel."
    DEFVAL { none }                  
    ::= { tmnxMcPathChlSrcEntry 11 }

tmnxMcPathChlSrcVdoFCCState            OBJECT-TYPE
    SYNTAX         TmnxEnabledDisabledOrInherit
    MAX-ACCESS     read-create
    STATUS         current
    DESCRIPTION        
        "The value of tmnxMcPathChlSrcVdoFCCState specifies the state of Fast 
         Channel Change (FCC) server for this sender override context. 

         When this object has a value of 'enabled', FCC server is enabled. When 
         its value is 'disabled', FCC server is disabled. When its value is 
         'inherit', state of FCC server is inherited from the value of 
         tmnxMcPathBdlChlVdoFCCState which specifies the state of FCC server at 
         the channel level."
    DEFVAL { inherit }
    ::= { tmnxMcPathChlSrcEntry 12 }

tmnxMcPathChlSrcVdoRTState             OBJECT-TYPE
    SYNTAX          TmnxEnabledDisabledOrInherit
    MAX-ACCESS      read-create
    STATUS          current
    DESCRIPTION
        "The value of tmnxMcPathChlSrcVdoRTState specifies the state of 
         Retransmission (RT) Server for this sender override context. 

         When this object has a value of 'enabled', RT server is enabled. When 
         its value is 'disabled', RT server is disabled. When its value is 
         'inherit', state of RT server is inherited from the value of 
         tmnxMcPathBdlChlVdoRTState which specifies the state of RT server at 
         the channel level."
    DEFVAL { inherit }
    ::= { tmnxMcPathChlSrcEntry 13 }

tmnxMcPathChlSrcVdoChlType             OBJECT-TYPE
    SYNTAX          TmnxMcPathVdoChlTypeOrInherit
    MAX-ACCESS      read-create
    STATUS          current
    DESCRIPTION
        "The value of tmnxMcPathChlSrcVdoChlType specifies the video
         channel type. It identifies whether the video channel is
         High Definition (HD), Standard Definition (SD) or
         Picture-in-Picture (PIP).

         When this object has a value of 'inherit', video channel type is 
         inherited from the value of tmnxMcPathBdlChlVdoChlType which specifies 
         the video channel type at channel level."
    DEFVAL { inherit }
    ::= { tmnxMcPathChlSrcEntry 14 }

tmnxMcPathChlSrcVdoRTAddrType          OBJECT-TYPE
    SYNTAX          InetAddressType
    MAX-ACCESS      read-create
    STATUS          current
    DESCRIPTION
        "The value of tmnxMcPathChlSrcVdoRTAddrType specifies the address type
         of tmnxMcPathChlSrcVdoRTAddress."
    DEFVAL { unknown }
    ::= { tmnxMcPathChlSrcEntry 15 }

tmnxMcPathChlSrcVdoRTAddress           OBJECT-TYPE
    SYNTAX          InetAddress (SIZE(0|4|16))
    MAX-ACCESS      read-create
    STATUS          current
    DESCRIPTION
        "The value of tmnxMcPathChlSrcVdoRTAddress specifies the IP address
         of the Retransmission (RT) server."
    DEFVAL { ''H }
    ::= { tmnxMcPathChlSrcEntry 16 }

tmnxMcPathChlSrcVdoRTPort              OBJECT-TYPE
    SYNTAX          TmnxVdoPortNumber
    MAX-ACCESS      read-create
    STATUS          current
    DESCRIPTION
        "The value of tmnxMcPathChlSrcVdoRTPort specifies the port of the
         Retransmission (RT) server."
    DEFVAL { 4096 }
    ::= { tmnxMcPathChlSrcEntry 17 }

tmnxMcPathChlSrcVdoRTBufferSize        OBJECT-TYPE
    SYNTAX          TmnxMcPathVdoBufferSize
    UNITS           "milliseconds"
    MAX-ACCESS      read-create
    STATUS          current
    DESCRIPTION
        "The value of tmnxMcPathChlSrcVdoRTBufferSize specifies the number
         of milliseconds worth of channel packets to store for the
         Retransmission (RT) server."
    DEFVAL { 300 }
    ::= { tmnxMcPathChlSrcEntry 18 }

tmnxMcPathChlSrcVdoLocalRTPort         OBJECT-TYPE
    SYNTAX          TmnxVdoPortNumber
    MAX-ACCESS      read-create
    STATUS          obsolete
    DESCRIPTION
        "The value of tmnxMcPathChlSrcVdoLocalRTPort specifies the local port
         on which Retransmission (RT) requests are received.  The value of 
         this object can only be set for the default bundle.

         This object was obsoleted from release 7.0R4."
    DEFVAL { 4096 }
    ::= { tmnxMcPathChlSrcEntry 19 }

tmnxMcPathChlSrcVdoLocalFccPort        OBJECT-TYPE
    SYNTAX          TmnxVdoPortNumber
    MAX-ACCESS      read-create
    STATUS          obsolete
    DESCRIPTION
        "The value of tmnxMcPathChlSrcVdoLocalFccPort specifies the local port 
         on which Fast Channel Change (FCC) requests are received.  The value of 
         this object can only be set for the default bundle.

         This object was obsoleted from release 7.0R4."
    DEFVAL { 4098 }
    ::= { tmnxMcPathChlSrcEntry 20 }

tmnxMcPathChlSrcVdoGroupId               OBJECT-TYPE
    SYNTAX          TmnxVdoGrpIdOrInherit
    MAX-ACCESS      read-create
    STATUS          current
    DESCRIPTION
        "The value of tmnxMcPathChlSrcVdoGroupId specifies the row index in the
         TIMETRA-VIDEO-MIB::tmnxVdoGrpTable for the video group information
         for this multicast information policy bundle.

         A value '0' indicates that no video-group is assigned to this
         multicast channel source. A value of '-1' indicates that video-group 
         information is inherited from the value of tmnxMcPathBdlChlVdoGroupId 
         which specifies the video-group information at the channel level."
    DEFVAL { -1 }
    ::= { tmnxMcPathChlSrcEntry 21 }

tmnxMcPathChlSrcTunnelIfLspName       OBJECT-TYPE
    SYNTAX      TNamedItemOrEmpty
    MAX-ACCESS  read-create
    STATUS      current
    DESCRIPTION
        "The value of tmnxMcPathChlSrcTunnelIfLspName specifies the name of the 
         RSVP point to multipoint (P2MP) lsp name associated with this tunnel 
         interface."
    DEFVAL { ''H }    
    ::= { tmnxMcPathChlSrcEntry 22 }

tmnxMcPathChlSrcTunIfSdAddrType        OBJECT-TYPE
    SYNTAX      InetAddressType
    MAX-ACCESS  read-create
    STATUS      current
    DESCRIPTION
        "The value of tmnxMcPathChlSrcTunIfSdAddrType specifies the type for
         tmnxMcPathChlSrcTunIfSdAddr."
     DEFVAL { unknown }     
    ::= { tmnxMcPathChlSrcEntry 23 } 

tmnxMcPathChlSrcTunIfSdAddr        OBJECT-TYPE
    SYNTAX      InetAddress (SIZE (0|4|16))
    MAX-ACCESS  read-create
    STATUS      current
    DESCRIPTION
        "The value of tmnxMcPathChlSrcTunIfSdAddr specifies the sender address."
    DEFVAL { ''H }      
    ::= { tmnxMcPathChlSrcEntry 24 }    

tmnxMcPathChlSrcVdoLocalRTState        OBJECT-TYPE
    SYNTAX          TmnxEnabledDisabledOrInherit
    MAX-ACCESS      read-create
    STATUS          current
    DESCRIPTION
        "The value of tmnxMcPathChlSrcVdoLocalRTState specifies the state of 
         local Retransmission (RT) Server for this sender override context. 

         When this object has a value of 'enabled', local RT server is enabled. 
         When its value is 'disabled', local RT server is disabled. When its 
         value is 'inherit', state of local RT server is inherited from the 
         value of tmnxMcPathBdlChlVdoLocalRTState which specifies the state of 
         local RT server at the channel level."
    DEFVAL { inherit }
    ::= { tmnxMcPathChlSrcEntry 25 }

tmnxMcPathChlSrcVdoReorderAudio    OBJECT-TYPE
    SYNTAX          TmnxMcPathVdoReorderAudio
    UNITS           "milliseconds"
    MAX-ACCESS      read-create
    STATUS          current
    DESCRIPTION
        "The value of tmnxMcPathChlSrcVdoReorderAudio specifies the time, 
         in milliseconds, by which the audio packets are reordered in the 
         ad stream. 

         If the value of this object is set to '0', then audio reordering is 
         disabled."
    DEFVAL { 0 }
    ::= { tmnxMcPathChlSrcEntry 26 }

tmnxMcPathChlSrcVdoFccMinDuratn    OBJECT-TYPE
    SYNTAX          TmnxMcPathVdoFccMinDurationOrZero
    UNITS           "milliseconds"
    MAX-ACCESS      read-create
    STATUS          current
    DESCRIPTION
        "The value of tmnxMcPathChlSrcVdoFccMinDuratn specifies the minimum 
         time duration, in milliseconds, of the Fast Channel Change (FCC)
         burst. 
    
         The value of this object determines the starting point of the FCC
         burst. If the current Group of Pictures (GOP) has less than the 
         minimum duration worth of data, FCC burst begins from the 
         previous GOP. When the value of this object is set to '0', then the 
         minimum time duration will be inherited from the value of 
         tmnxMcPathBdlChlVdoFccMinDuratn at the channel level."
    DEFVAL { 0 }
    ::= { tmnxMcPathChlSrcEntry 27 }

tmnxMcPathChlSrcKAOverrideTimer     OBJECT-TYPE
    SYNTAX          TmnxMcPathKeepAliveOverrideTimer
    UNITS           "seconds"
    MAX-ACCESS      read-create
    STATUS          current
    DESCRIPTION
        "The value of tmnxMcPathChlSrcKAOverrideTimer specifies the time, 
         in seconds, used to override the keep alive timer for all (S,G) 
         entries that fall under the source-override in the PIM instance.
    
         If the value of this object is set to '0', then Keep Alive Timer 
         Override under source-override is disabled."
    DEFVAL  { 0 }
    ::= { tmnxMcPathChlSrcEntry 28 }

tmnxMcPathChlSrcP2MPId     OBJECT-TYPE
    SYNTAX          Unsigned32
    MAX-ACCESS      read-create
    STATUS          current
    DESCRIPTION
        "The value of tmnxMcPathChlSrcP2MPId specifies the identifier  
         of a Point to Multipoint (P2MP) Label Switch Path (LSP)
         associated with this tunnel interface."
    DEFVAL  { 0 }
    ::= { tmnxMcPathChlSrcEntry 29 }

tmnxMcPathChlSrcVdoAnalyzer     OBJECT-TYPE
    SYNTAX          TruthValue
    MAX-ACCESS      read-create
    STATUS          current
    DESCRIPTION
        "The value of tmnxMcPathChlSrcVdoAnalyzer specifies whether or not 
         the analyzer is enabled for video."
    DEFVAL  { false }
    ::= { tmnxMcPathChlSrcEntry 30 }

tmnxMcPathChlSrcVdoAnalyzerDesc     OBJECT-TYPE
    SYNTAX          TItemDescription
    MAX-ACCESS      read-create
    STATUS          current
    DESCRIPTION
        "The value of tmnxMcPathChlSrcVdoAnalyzerDesc specifies the description  
         for the video analyzer."
    DEFVAL { ''H }      -- the empty string
    ::= { tmnxMcPathChlSrcEntry 31 }

tmnxMcPathChlSrcVdoStSeSrc1Type     OBJECT-TYPE
    SYNTAX          InetAddressType
    MAX-ACCESS      read-create
    STATUS          current
    DESCRIPTION
        "The value of tmnxMcPathChlSrcVdoStSeSrc1Type specifies the address 
         type of tmnxMcPathChlSrcVdoStSeSrc1."
    DEFVAL  { unknown }
    ::= { tmnxMcPathChlSrcEntry 32 }

tmnxMcPathChlSrcVdoStSeSrc1     OBJECT-TYPE
    SYNTAX          InetAddress (SIZE (0|4|16))
    MAX-ACCESS      read-create
    STATUS          current
    DESCRIPTION
        "The value of tmnxMcPathChlSrcVdoStSeSrc1 specifies the address of the 
         first source in stream selection."
    DEFVAL { ''H }      -- the empty string
    ::= { tmnxMcPathChlSrcEntry 33 }

tmnxMcPathChlSrcVdoStSeIntf1     OBJECT-TYPE
    SYNTAX          TNamedItemOrEmpty
    MAX-ACCESS      read-create
    STATUS          current
    DESCRIPTION
        "The value of tmnxMcPathChlSrcVdoStSeIntf1 specifies the interface 
         on which multicast traffic from 'tmnxMcPathChlSrcVdoStSeSrc1' arrives."
    DEFVAL { ''H }      -- the empty string
    ::= { tmnxMcPathChlSrcEntry 34 }

tmnxMcPathChlSrcVdoStSeSrc2Type   OBJECT-TYPE
    SYNTAX          InetAddressType
    MAX-ACCESS      read-create
    STATUS          current
    DESCRIPTION
        "The value of tmnxMcPathChlSrcVdoStSeSrc2Type specifies the address 
         type of tmnxMcPathChlSrcVdoStSeSrc2."
    DEFVAL   { unknown }
    ::= { tmnxMcPathChlSrcEntry 35 }

tmnxMcPathChlSrcVdoStSeSrc2     OBJECT-TYPE
    SYNTAX          InetAddress (SIZE (0|4|16))
    MAX-ACCESS      read-create
    STATUS          current
    DESCRIPTION
        "The value of tmnxMcPathChlSrcVdoStSeSrc2 specifies the address of the 
         second source in stream selection."
    DEFVAL { ''H }      -- the empty string
    ::= { tmnxMcPathChlSrcEntry 36 }

tmnxMcPathChlSrcVdoStSeIntf2     OBJECT-TYPE
    SYNTAX          TNamedItemOrEmpty
    MAX-ACCESS      read-create
    STATUS          current
    DESCRIPTION
        "The value of tmnxMcPathChlSrcVdoStSeIntf2 specifies the interface  
         on which multicast traffic from 'tmnxMcPathChlSrcVdoStSeSrc2' arrives."
    DEFVAL { ''H }      -- the empty string
    ::= { tmnxMcPathChlSrcEntry 37 }

-- ------------------------------------------------

-- ------------------------------------------------
-- multicast management policy operational channel table
-- ------------------------------------------------

tmnxMcPathOperChlTable    OBJECT-TYPE
    SYNTAX      SEQUENCE OF TmnxMcPathOperChlEntry
    MAX-ACCESS  not-accessible
    STATUS      current
    DESCRIPTION
        "The tmnxMcPathOperChlTable listing the (S,G) entries for the
         multicast information policy bundle channel range on this system."
    ::= { tmnxMcPathObjs 12 }

tmnxMcPathOperChlEntry    OBJECT-TYPE
    SYNTAX      TmnxMcPathOperChlEntry
    MAX-ACCESS  not-accessible
    STATUS      current
    DESCRIPTION
        "An entry in the tmnxMcPathOperChlTable. This is a read-only table."
    INDEX { tmnxMcPathOperChlRtrType,
            vRtrID,
            tmnxMcPathOperChlGrpAddrType, 
            tmnxMcPathOperChlGrpAddr,
            tmnxMcPathOperChlSrcAddrType, 
            tmnxMcPathOperChlSrcAddr,
            tmnxChassisIndex,
            tmnxCardSlotNum, 
            tmnxMDASlotNum
          }
    ::= { tmnxMcPathOperChlTable 1}

TmnxMcPathOperChlEntry ::= SEQUENCE
   {
       tmnxMcPathOperChlRtrType          TmnxMcPathRtrType,
       tmnxMcPathOperChlGrpAddrType      InetAddressType,
       tmnxMcPathOperChlGrpAddr          InetAddress,
       tmnxMcPathOperChlSrcAddrType      InetAddressType,
       tmnxMcPathOperChlSrcAddr          InetAddress,
       tmnxMcPathOperChlBandwidth        Gauge32,
       tmnxMcPathOperChlCurrentPath      TmnxMcPathChlSfPathTypeTc,
       tmnxMcPathOperChlExplicit         TruthValue,
       tmnxMcPathOperChlAdminBw          Gauge32,
       tmnxMcPathOperChlPref             Gauge32,
       tmnxMcPathOperChlBwBlackHole      TruthValue, 
       tmnxMcPathOperChlBwBlackHoleRt    Gauge32,
       tmnxMcPathOperChlIngLastHighest   Gauge32,
       tmnxMcPathOperChlIngSecHighest    Gauge32,
       tmnxMcPathOperChlTimeRemaining    Unsigned32,
       tmnxMcPathOperChlCurrentPlane     Unsigned32
   }

tmnxMcPathOperChlRtrType  OBJECT-TYPE
    SYNTAX      TmnxMcPathRtrType
    MAX-ACCESS  not-accessible
    STATUS      current
    DESCRIPTION
        "The value of vRtrType specifies the type of virtual router."
    ::= { tmnxMcPathOperChlEntry 1 }

tmnxMcPathOperChlGrpAddrType   OBJECT-TYPE
    SYNTAX      InetAddressType
    MAX-ACCESS  not-accessible
    STATUS      current
    DESCRIPTION
        "The value of tmnxMcPathOperChlGrpAddrType indicates the address type 
         of tmnxMcPathOperChlGrpAddr."
    ::= { tmnxMcPathOperChlEntry 2 }

tmnxMcPathOperChlGrpAddr         OBJECT-TYPE
    SYNTAX      InetAddress (SIZE (4|16|20))
    MAX-ACCESS  not-accessible
    STATUS      current
    DESCRIPTION
        "The value of tmnxMcPathOperChlGrpAddr indicates the group address of 
         the multicast channel. Its type is specified by 
         tmnxMcPathOperChlGrpAddrType."
    ::= { tmnxMcPathOperChlEntry 3 }

tmnxMcPathOperChlSrcAddrType   OBJECT-TYPE
    SYNTAX      InetAddressType
    MAX-ACCESS  not-accessible
    STATUS      current
    DESCRIPTION
        "The value of tmnxMcPathOperChlSrcAddrType indicates the address type 
         of tmnxMcPathOperChlSrcAddr."
    ::= { tmnxMcPathOperChlEntry 4 }

tmnxMcPathOperChlSrcAddr         OBJECT-TYPE
    SYNTAX      InetAddress (SIZE (4|16|20))
    MAX-ACCESS  not-accessible
    STATUS      current
    DESCRIPTION
        "The value of tmnxMcPathOperChlSrcAddr indicates the source address of 
         the multicast channel. Its type is specified by 
         tmnxMcPathOperChlSrcAddrType."
    ::= { tmnxMcPathOperChlEntry 5 }

tmnxMcPathOperChlBandwidth            OBJECT-TYPE
    SYNTAX      Gauge32
    UNITS       "kbps"
    MAX-ACCESS  read-only
    STATUS      current
    DESCRIPTION
        "The value of tmnxMcPathOperChlBandwidth indicates the multicast 
         channel's channel's current bandwidth in kilo-bits-per-second."    
    ::= { tmnxMcPathOperChlEntry 6 }

tmnxMcPathOperChlCurrentPath         OBJECT-TYPE
    SYNTAX      TmnxMcPathChlSfPathTypeTc
    MAX-ACCESS  read-only
    STATUS      current
    DESCRIPTION
        "The value of tmnxMcPathOperChlCurrentPath indicates an explicit ingress
         switch fabric multicast path assigned to a multicast channel."
    ::= { tmnxMcPathOperChlEntry 7 }

tmnxMcPathOperChlExplicit             OBJECT-TYPE
    SYNTAX      TruthValue
    MAX-ACCESS  read-only
    STATUS      current
    DESCRIPTION
        "The value of tmnxMcPathOperChlExplicit indicates how the multicast
         ingress path manager determines the amount of bandwidth required by a 
         multicast channel."
    ::= { tmnxMcPathOperChlEntry 8 }

tmnxMcPathOperChlAdminBw            OBJECT-TYPE
    SYNTAX      Gauge32
    UNITS       "kbps"
    MAX-ACCESS  read-only
    STATUS      current
    DESCRIPTION
        "The value of tmnxMcPathOperChlAdminBw indicates the multicast channel's
         administrative bandwidth value taking into account the inheritance of 
         the field i.e. if the administrative bandwidth is not configured at the
         channel level, it will inherit it from the bundle and thus its 
         operational administrative bandwidth value will be that of the bundle."
    ::= { tmnxMcPathOperChlEntry 9 }

tmnxMcPathOperChlPref        OBJECT-TYPE
    SYNTAX      Gauge32
    MAX-ACCESS  read-only
    STATUS      current
    DESCRIPTION
        "The value of tmnxMcPathOperChlPref indicates the channel's relative 
         preference level for multicast channels.  tmnxMcPathBdlChlPref 
         indicates its relative importance over other multicast channels. Eight
         levels of preference are supported; 0 through 7. Preference value 7 
         indicates the highest preference level."
    ::= { tmnxMcPathOperChlEntry 10 }

tmnxMcPathOperChlBwBlackHole         OBJECT-TYPE
    SYNTAX      TruthValue
    MAX-ACCESS  read-only
    STATUS      current
    DESCRIPTION
        "The value of tmnxMcPathOperChlBwBlackHole indicates if the 
         source,group (S,G) is in black-hole state."
    ::= { tmnxMcPathOperChlEntry 11 }

tmnxMcPathOperChlBwBlackHoleRt         OBJECT-TYPE
    SYNTAX      Gauge32
    UNITS       "kbps"
    MAX-ACCESS  read-only
    STATUS      current
    DESCRIPTION
        "The value of tmnxMcPathOperChlBwBlackHoleRt indicates at which 
         current rate a channel should be placed in the black-hole state."
    ::= { tmnxMcPathOperChlEntry 12 }

tmnxMcPathOperChlIngLastHighest   OBJECT-TYPE
    SYNTAX      Gauge32
    MAX-ACCESS  read-only
    STATUS      current
    DESCRIPTION
        "The value of tmnxMcPathOperChlIngLastHighest indicates the value of the
         multicast bandwidth that is currently being accounted for the channel 
         on its forwarding path on the MDA. The value is computed based on 
         periodic polling of statistics and represents the last highest 
         bandwidth value since the bandwidth update timer for the channel was 
         (re)started. This field inherits the value of 
         tmnxMcPathOperChlIngSecHighest when the bandwidth update timer expires.
         This indicates that the bandwidth of the channel is lower than that 
         recorded when the bandwidth update timer was last started. Before the 
         bandwidth update timer expires, if the polled value of the bandwidth is 
         greater than or equal to the current value, the current value is 
         updated to the new value if necessary and the bandwidth update timer 
         is restarted."
    ::= { tmnxMcPathOperChlEntry 13 }

tmnxMcPathOperChlIngSecHighest OBJECT-TYPE
    SYNTAX      Gauge32
    MAX-ACCESS  read-only
    STATUS      current
    DESCRIPTION
        "The value of tmnxMcPathOperChlIngSecHighest indicates the 
         value of the second highest multicast bandwidth recorded for the 
         channel on the MDA since the bandwidth update timer for the channel 
         was (re)started. This value is computed based on periodic polling of 
         statistics and is reset to zero everytime the bandwidth update timer 
         for the channel is restarted."
    ::= { tmnxMcPathOperChlEntry 14 }

tmnxMcPathOperChlTimeRemaining        OBJECT-TYPE
    SYNTAX      Unsigned32 
    UNITS       "seconds"
    MAX-ACCESS  read-only
    STATUS      current
    DESCRIPTION
        "The value of tmnxMcPathOperChlTimeRemaining indicates the time 
         remaining before the bandwidth update timer for the channel on the MDA 
         expires. The bandwidth update timer determines how often multicast 
         bandwidth is updated for a channel. When the value of this field 
         becomes zero indicating that the bandwidth timer has expired, the 
         bandwidth of the channel represented by the field 
         tmnxMcPathOperChlIngLastHighest is updated to the value of the field 
         tmnxMcPathOperChlIngSecHighest. If the timer is restarted, it 
         indicates that the current bandwidth of the channel has either stayed 
         the same or increased since the last poll."
    ::= { tmnxMcPathOperChlEntry 15 }

tmnxMcPathOperChlCurrentPlane OBJECT-TYPE
    SYNTAX      Unsigned32
    MAX-ACCESS  read-only
    STATUS      current
    DESCRIPTION
        "The value of tmnxMcPathOperChlCurrentPlane indicates the plane used to
         forward this channel."
    ::= { tmnxMcPathOperChlEntry 16 }

-- ------------------------------------------------
-- multicast management policy mda operational table
-- ------------------------------------------------

tmnxMcPathMdaOperChlTable    OBJECT-TYPE
    SYNTAX      SEQUENCE OF TmnxMcPathMdaOperChlEntry
    MAX-ACCESS  not-accessible
    STATUS      current
    DESCRIPTION
        "The tmnxMcPathMdaOperChlTable listing the (S,G) entries for the
         multicast information policy bundle channel range on this system."
    ::= { tmnxMcPathObjs 13 }

tmnxMcPathMdaOperChlEntry    OBJECT-TYPE
    SYNTAX      TmnxMcPathMdaOperChlEntry
    MAX-ACCESS  not-accessible
    STATUS      current
    DESCRIPTION
        "An entry in the tmnxMcPathMdaOperChlTable. This is a read-only table."
    INDEX { tmnxChassisIndex,
            tmnxCardSlotNum, 
            tmnxMDASlotNum,
            tmnxMcPathMdaOperChlRtrType,
            vRtrID, 
            tmnxMcPathMdaOperChlGrpAddrType, 
            tmnxMcPathMdaOperChlGrpAddr,
            tmnxMcPathMdaOperChlSrcAddrType, 
            tmnxMcPathMdaOperChlSrcAddr            
          }
    ::= { tmnxMcPathMdaOperChlTable 1}

TmnxMcPathMdaOperChlEntry ::= SEQUENCE
   {
       tmnxMcPathMdaOperChlRtrType          TmnxMcPathRtrType,
       tmnxMcPathMdaOperChlGrpAddrType      InetAddressType,
       tmnxMcPathMdaOperChlGrpAddr          InetAddress,
       tmnxMcPathMdaOperChlSrcAddrType      InetAddressType,
       tmnxMcPathMdaOperChlSrcAddr          InetAddress,
       tmnxMcPathMdaOperChlBandwidth        Gauge32,
       tmnxMcPathMdaOperChlCurrentPath      TmnxMcPathChlSfPathTypeTc,
       tmnxMcPathMdaOperChlExplicit         TruthValue,
       tmnxMcPathMdaOperChlAdminBw          Gauge32,
       tmnxMcPathMdaOperChlPref             Gauge32,
       tmnxMcPathMdaOperChlBwBlackHole      TruthValue, 
       tmnxMcPathMdaOperChlBwBlackHoleRt    Gauge32,
       tmnxMcPathMdaOperChlIngLastHigh      Gauge32,
       tmnxMcPathMdaOperChlIngSecHigh       Gauge32,
       tmnxMcPathMdaOperChlTimeRemain       Unsigned32,
       tmnxMcPathMdaOperChlCurrentPlane     Unsigned32
   }

tmnxMcPathMdaOperChlRtrType  OBJECT-TYPE
    SYNTAX      TmnxMcPathRtrType
    MAX-ACCESS  not-accessible
    STATUS      current
    DESCRIPTION
        "The value of vRtrType specifies the type of virtual router."
    ::= { tmnxMcPathMdaOperChlEntry 1 }

tmnxMcPathMdaOperChlGrpAddrType   OBJECT-TYPE
    SYNTAX      InetAddressType
    MAX-ACCESS  not-accessible
    STATUS      current
    DESCRIPTION
        "The value of tmnxMcPathMdaOperChlGrpAddrType indicates the address type 
         of tmnxMcPathMdaOperChlGrpAddr."
    ::= { tmnxMcPathMdaOperChlEntry 2 }

tmnxMcPathMdaOperChlGrpAddr         OBJECT-TYPE
    SYNTAX      InetAddress (SIZE (4|16|20))
    MAX-ACCESS  not-accessible
    STATUS      current
    DESCRIPTION
        "The value of tmnxMcPathMdaOperChlGrpAddr indicates the group address of
         the multicast channel. Its type is specified by 
         tmnxMcPathMdaOperChlGrpAddrType."
    ::= { tmnxMcPathMdaOperChlEntry 3 }

tmnxMcPathMdaOperChlSrcAddrType   OBJECT-TYPE
    SYNTAX      InetAddressType
    MAX-ACCESS  not-accessible
    STATUS      current
    DESCRIPTION
        "The value of tmnxMcPathMdaOperChlSrcAddrType indicates the address type 
         of tmnxMcPathMdaOperChlSrcAddr."
    ::= { tmnxMcPathMdaOperChlEntry 4 }

tmnxMcPathMdaOperChlSrcAddr         OBJECT-TYPE
    SYNTAX      InetAddress (SIZE (4|16|20))
    MAX-ACCESS  not-accessible
    STATUS      current
    DESCRIPTION
        "The value of tmnxMcPathMdaOperChlSrcAddr indicates the source address 
         of the multicast channel. Its type is specified by 
         tmnxMcPathMdaOperChlSrcAddrType."
    ::= { tmnxMcPathMdaOperChlEntry 5 }

tmnxMcPathMdaOperChlBandwidth            OBJECT-TYPE
    SYNTAX      Gauge32
    UNITS       "kbps"
    MAX-ACCESS  read-only
    STATUS      current
    DESCRIPTION
        "The value of tmnxMcPathMdaOperChlBandwidth indicates the multicast 
         channel's current bandwidth in kilo-bits per second(kbps)."
    ::= { tmnxMcPathMdaOperChlEntry 6 }

tmnxMcPathMdaOperChlCurrentPath         OBJECT-TYPE
    SYNTAX      TmnxMcPathChlSfPathTypeTc
    MAX-ACCESS  read-only
    STATUS      current
    DESCRIPTION
        "The value of tmnxMcPathMdaOperChlCurrentPath indicates an explicit
         ingress switch fabric multicast path assigned to a multicast channel."
    ::= { tmnxMcPathMdaOperChlEntry 7 }

tmnxMcPathMdaOperChlExplicit            OBJECT-TYPE
    SYNTAX      TruthValue
    MAX-ACCESS  read-only
    STATUS      current
    DESCRIPTION
        "The value of tmnxMcPathMdaOperChlExplicit indicates how the multicast
         ingress path manager determines the amount of bandwidth required by a 
         multicast channel."
    ::= { tmnxMcPathMdaOperChlEntry 8 }

tmnxMcPathMdaOperChlAdminBw            OBJECT-TYPE
    SYNTAX      Gauge32
    UNITS       "kbps"
    MAX-ACCESS  read-only
    STATUS      current
    DESCRIPTION
        "The value of tmnxMcPathMdaOperChlAdminBw indicates the multicast 
         channel's administrative bandwidth value taking into account the 
         inheritance of the field i.e. if the administrative bandwidth is not 
         configured at the channel level, it will inherit it from the bundle 
         and thus its operational administrative bandwidth value will be that 
         of the bundle."
    ::= { tmnxMcPathMdaOperChlEntry 9 }

tmnxMcPathMdaOperChlPref        OBJECT-TYPE
    SYNTAX      Gauge32
    MAX-ACCESS  read-only
    STATUS      current
    DESCRIPTION
        "The value of tmnxMcPathMdaOperChlPref indicates the channel's relative 
         preference level for multicast channels.  tmnxMcPathBdlChlPref 
         indicates its relative importance over other multicast channels.  Eight
         levels of preference are supported; 0 through 7. Preference value 7 
         indicates the highest preference level."
    ::= { tmnxMcPathMdaOperChlEntry 10 }

tmnxMcPathMdaOperChlBwBlackHole         OBJECT-TYPE
    SYNTAX      TruthValue
    MAX-ACCESS  read-only
    STATUS      current
    DESCRIPTION
        "The value of tmnxMcPathMdaOperChlBwBlackHole indicates if the 
         source,group (S,G) is in black-hole state."
    ::= { tmnxMcPathMdaOperChlEntry 11 }

tmnxMcPathMdaOperChlBwBlackHoleRt         OBJECT-TYPE
    SYNTAX      Gauge32
    UNITS       "kbps"
    MAX-ACCESS  read-only
    STATUS      current
    DESCRIPTION
        "The value of tmnxMcPathMdaOperChlBwBlackHoleRt indicates at which 
         current rate a channel should be placed in the black-hole state."
    ::= { tmnxMcPathMdaOperChlEntry 12 }

tmnxMcPathMdaOperChlIngLastHigh   OBJECT-TYPE
    SYNTAX      Gauge32
    MAX-ACCESS  read-only
    STATUS      current
    DESCRIPTION
        "The value of tmnxMcPathMdaOperChlIngLastHigh indicates the value of the
         multicast bandwidth that is currently being accounted for the channel 
         on its forwarding path on the MDA. The value is computed based on 
         periodic polling of statistics and represents the last highest 
         bandwidth value since the bandwidth update timer for the channel was 
         (re)started. This field inherits the value of 
         tmnxMcPathOperChlIngSecHighest when the bandwidth update timer expires.
         This indicates that the bandwidth of the channel is lower than that 
         recorded when the bandwidth update timer was last started. Before the 
         bandwidth update timer expires, if the polled value of the bandwidth 
         is greater than or equal to the current value, the current value is 
         updated to the new value if necessary and the bandwidth update timer 
         is restarted."
    ::= { tmnxMcPathMdaOperChlEntry 13 }

tmnxMcPathMdaOperChlIngSecHigh OBJECT-TYPE
    SYNTAX      Gauge32
    MAX-ACCESS  read-only
    STATUS      current
    DESCRIPTION
        "The value of tmnxMcPathMdaOperChlIngSecHigh indicates the 
         value of the second highest multicast bandwidth recorded for the 
         channel on the MDA since the bandwidth update timer for the channel 
         was (re)started. This value is computed based on periodic polling of 
         statistics and is reset to zero everytime the bandwidth update timer 
         for the channel is restarted."
    ::= { tmnxMcPathMdaOperChlEntry 14 }

tmnxMcPathMdaOperChlTimeRemain        OBJECT-TYPE
    SYNTAX      Unsigned32 
    UNITS       "seconds"
    MAX-ACCESS  read-only
    STATUS      current
    DESCRIPTION
        "The value of tmnxMcPathMdaOperChlTimeRemain indicates the time 
         remaining before the bandwidth update timer for the channel on the MDA 
         expires. The bandwidth update timer determines how often multicast 
         bandwidth is updated for a channel. When the value of this field 
         becomes zero indicating that the bandwidth timer has expired, the 
         bandwidth of the channel represented by the field 
         tmnxMcPathOperChlIngLastHighest is updated to the value of the field 
         tmnxMcPathOperChlIngSecHighest. If the timer is restarted, it indicates 
         that the current bandwidth of the channel has either stayed the same 
         or increased since the last poll."
    ::= { tmnxMcPathMdaOperChlEntry 15 }

tmnxMcPathMdaOperChlCurrentPlane OBJECT-TYPE
    SYNTAX      Unsigned32
    MAX-ACCESS  read-only
    STATUS      current
    DESCRIPTION
        "The value of tmnxMcPathMdaOperChlCurrentPlane indicates the plane used
         to forward this channel."
    ::= { tmnxMcPathMdaOperChlEntry 16 }

-- ------------------------------------------------
-- multicast chassis level table
-- ------------------------------------------------

tmnxMcPathChassisLevelInfo     OBJECT IDENTIFIER ::= { tmnxMcPathGlobalObjs 6 }

tmnxMcPathChassisPlaneLimit    OBJECT-TYPE
    SYNTAX      Unsigned32
    UNITS       "mega-bits-per-second"
    MAX-ACCESS  read-write
    STATUS      current
    DESCRIPTION
        "The value of tmnxMcPathChassisPlaneLimit specifies total multicast 
         bandwidth for the chassis forwarding plane.

         This object was deprecated in the 10.0 release."
    DEFVAL { 2000 }
    ::= { tmnxMcPathChassisLevelInfo 1 }

tmnxMcPathChassisSecPlaneLimit    OBJECT-TYPE
    SYNTAX      Unsigned32
    UNITS       "mega-bits-per-second"
    MAX-ACCESS  read-write
    STATUS      current
    DESCRIPTION
        "The value of tmnxMcPathChassisSecPlaneLimit specifies multicast 
         bandwidth for secondary paths on the chassis forwarding plane.
         The value must be less than tmnxMcPathChassisPlaneLimit.

         This object was deprecated in the 10.0 release."
    DEFVAL { 1800 }
    ::= { tmnxMcPathChassisLevelInfo 2 }

tmnxMcPathChassisDualPlaneLimit    OBJECT-TYPE
    SYNTAX      Unsigned32
    UNITS       "mega-bits-per-second"
    MAX-ACCESS  read-write
    STATUS      current
    DESCRIPTION
        "The value of tmnxMcPathChassisDualPlaneLimit specifies total multicast
         bandwidth for the chassis forwarding plane in dual-sfm mode.

         This object was deprecated in the 10.0 release."
    DEFVAL { 2000 }
    ::= { tmnxMcPathChassisLevelInfo 3 }

tmnxMcPathChassisDualSecPlaneLmt    OBJECT-TYPE
    SYNTAX      Unsigned32
    UNITS       "mega-bits-per-second"
    MAX-ACCESS  read-write
    STATUS      current
    DESCRIPTION
        "The value of tmnxMcPathChassisDualSecPlaneLmt specifies bandwidth for
         secondary paths on the chassis forwarding plane in dual-sfm mode. 
         The value must be less than tmnxMcPathChassisDualPlaneLimit.

         This object was deprecated in the 10.0 release."
    DEFVAL { 1800 }
    ::= { tmnxMcPathChassisLevelInfo 4 }

tmnxMcPathChassisMmrpAdminMode    OBJECT-TYPE
    SYNTAX      TruthValue
    MAX-ACCESS  read-write
    STATUS      current
    DESCRIPTION
        "The value of tmnxMcPathChassisMmrpAdminMode specifies that Ingress 
         Multicast Path Management (IMPM) does not monitor PIM and IGMP 
         trafic. It monitors only Multiple MAC Registration Protocol (MMRP)
         trafic. The flag setting can be changed at anytime. The new setting 
         will take effect after reboot or reset of the system."
    DEFVAL { false }
    ::= { tmnxMcPathChassisLevelInfo 5 }

tmnxMcPathChassisMmrpOperMode    OBJECT-TYPE
    SYNTAX      TruthValue
    MAX-ACCESS  read-only
    STATUS      current
    DESCRIPTION
        "The value of tmnxMcPathChassisMmrpOperMode indicates that Ingress 
         Multicast Path Management (IMPM) does not monitor PIM and IGMP 
         trafic. It monitors only Multiple MAC Registration Protocol (MMRP)
         trafic. Changing the value of tmnxMcPathChassisMmrpAdminMode will 
         result in tmnxMcPathChassisMmrpAdminMode indicating the new mode while 
         tmnxMcPathChassisMmrpOperMode indicates previous mode until the 
         configuration is saved and the system is rebooted. After the reboot, 
         both tmnxMcPathChassisMmrpAdminMode and tmnxMcPathChassisMmrpOperMode 
         will indicate the new mode."
    ::= { tmnxMcPathChassisLevelInfo 6 }

tmnxMcPathChassisRRInactiveRec    OBJECT-TYPE
    SYNTAX      TruthValue
    MAX-ACCESS  read-write
    STATUS      current
    DESCRIPTION
        "The value of tmnxMcPathChassisRRInactiveRec specifies whether 
         initially inactive multicast records use the IOM default secondary 
         multicast path or not. 

         If the value of tmnxMcPathChassisRRInactiveRec is 'true' the system
         redistributes newly populated inactive records among all available
         IOM multicast paths and multicast switch fabric planes.  
                                                                  
         If the value of tmnxMcPathChassisRRInactiveRec is 'false' the system 
         continues to set all initially inactive multicast records to use 
         the IOM default secondary multicast path." 
    DEFVAL { false }
    ::= { tmnxMcPathChassisLevelInfo 7 }

tmnxMcPathChassisPlnLimTotal    OBJECT-TYPE
    SYNTAX      Unsigned32 (0|2000|4000|5250)
    MAX-ACCESS  read-write
    STATUS      current
    DESCRIPTION
        "The value of tmnxMcPathChassisPlnLimTotal specifies the total  
         bandwidth of the chassis forwarding plane.

         A value of 0 indicates the system will auto-detect the applicable 
         bandwidth.

         The default value is 0 when removable switch-fabric is supported and
         2000 otherwise."
    ::= { tmnxMcPathChassisLevelInfo 8 }

tmnxMcPathChassisPlnLimDynTotal    OBJECT-TYPE
    SYNTAX      Unsigned32 (2000|4000)
    MAX-ACCESS  read-only
    STATUS      current
    DESCRIPTION
        "The value of tmnxMcPathChassisPlnLimDynTotal indicates the total  
         bandwidth of the chassis forwarding plane that is currently in use."
    ::= { tmnxMcPathChassisLevelInfo 9 }

tmnxMcPathChassisPlnLimPriCap    OBJECT-TYPE
    SYNTAX      Unsigned32 (1..10000)
    UNITS       "hundredths of a percent"
    MAX-ACCESS  read-write
    STATUS      current
    DESCRIPTION
        "The value of tmnxMcPathChassisPlnLimPriCap specifies the part of the
         total chassis forwarding bandwidth that can be used for multicast when
         not all switch cards are functional.

         The default value is 8750 when removable switch-fabric is supported and
         10000 otherwise."
    ::= { tmnxMcPathChassisLevelInfo 10 }
     
tmnxMcPathChassisPlnLimSecCap    OBJECT-TYPE
    SYNTAX      Unsigned32 (1..10000)
    UNITS       "hundredths of a percent"
    MAX-ACCESS  read-write
    STATUS      current
    DESCRIPTION
        "The value of tmnxMcPathChassisPlnLimSecCap specifies the part of the
         total chassis forwarding bandwidth that can be used for multicast 
         secondary paths when not all switch cards are functional.

         The value must be less than or equal to the value of
         tmnxMcPathChassisPlnLimPriCap.

         The default value is 8750 when removable switch-fabric is supported and
         9000 otherwise."
    ::= { tmnxMcPathChassisLevelInfo 11 }
     
tmnxMcPathChassisPlnLimPriCapRed    OBJECT-TYPE
    SYNTAX      Unsigned32 (1..10000)
    UNITS       "hundredths of a percent"
    MAX-ACCESS  read-write
    STATUS      current
    DESCRIPTION
        "The value of tmnxMcPathChassisPlnLimPriCapRed specifies the part of the
         total chassis forwarding bandwidth that can be used for multicast
         when all switch cards are functional.

         The default value is 8750 when removable switch-fabric is supported and
         10000 otherwise."
    ::= { tmnxMcPathChassisLevelInfo 12 }

tmnxMcPathChassisPlnLimSecCapRed    OBJECT-TYPE
    SYNTAX      Unsigned32 (1..10000)
    UNITS       "hundredths of a percent"
    MAX-ACCESS  read-write
    STATUS      current
    DESCRIPTION
        "The value of tmnxMcPathChassisPlnLimSecCapRed specifies the part of the
         total chassis forwarding bandwidth that can be used for multicast 
         secondary paths when all switch cards are functional.

         The value must be less than or equal to the value of
         tmnxMcPathChassisPlnLimPriCapRed.

         The default value is 8750 when removable switch-fabric is supported and
         9000 otherwise."
    ::= { tmnxMcPathChassisLevelInfo 13 }

-- ------------------------------------------------
-- multicast bandwidth policy t2-path table
-- ------------------------------------------------

tmnxMcPathBwPlcyT2PathTable OBJECT-TYPE
    SYNTAX      SEQUENCE OF TmnxMcPathBwPlcyT2PathEntry
    MAX-ACCESS  not-accessible
    STATUS      current
    DESCRIPTION
        "The tmnxMcPathBwPlcyT2PathTable has an entry for the primary and 
         secondary ingress multicast paths. An entry is created in this table 
         whenever an entry for a bandwidth policy is created in the 
         tmnxMcPathBwPlcyTable. This entry is relevant only for IOM3."
    ::= { tmnxMcPathObjs 14 }

tmnxMcPathBwPlcyT2PathEntry    OBJECT-TYPE
    SYNTAX      TmnxMcPathBwPlcyT2PathEntry
    MAX-ACCESS  not-accessible
    STATUS      current
    DESCRIPTION
        "Each row entry represents a particular ingress multicast path 
         configuration."
    INDEX { tmnxMcPathBwPlcyName, tmnxMcPathBwPlcyT2PathType }
    ::= { tmnxMcPathBwPlcyT2PathTable 1}

TmnxMcPathBwPlcyT2PathEntry ::= SEQUENCE
    {
        tmnxMcPathBwPlcyT2PathType          TmnxMcPathChlSfPathTypeTc,
        tmnxMcPathBwPlcyT2PathCbs           Unsigned32,
        tmnxMcPathBwPlcyT2PathMbs           Unsigned32,
        tmnxMcPathBwPlcyT2PathHighPrio      Unsigned32,
        tmnxMcPathBwPlcyT2PathPaths         Unsigned32,
        tmnxMcPathBwPlcyT2PathDualPaths     Unsigned32,
        tmnxMcPathBwPlcyT2PathLastChanged  TimeStamp
   }

tmnxMcPathBwPlcyT2PathType  OBJECT-TYPE
    SYNTAX      TmnxMcPathChlSfPathTypeTc
    MAX-ACCESS  not-accessible
    STATUS      current
    DESCRIPTION
        "The value of tmnxMcPathBwPlcyT2PathType specifies the type of the path.
         Only two types supported for T2-paths - 'primary' and 'secondary'."
    ::= { tmnxMcPathBwPlcyT2PathEntry 1 }

tmnxMcPathBwPlcyT2PathCbs      OBJECT-TYPE
    SYNTAX      Unsigned32 (0..10000)
    UNITS       "hundredths of a percent"
    MAX-ACCESS  read-create
    STATUS      current
    DESCRIPTION
        "The value of tmnxMcPathBwPlcyT2PathCbs specifies committed buffer 
         size(CBS). The value of tmnxMcPathBwPlcyT2PathCbs overrides the default
         CBS for each individual path's queue. The default value of
         tmnxMcPathBwPlcyT2PathCbs is the default value of primary path's queue.  
         The default value of tmnxMcPathBwPlcyT2PathCbs for the secondary path
         is 3000."
    DEFVAL { 500 }
    ::= { tmnxMcPathBwPlcyT2PathEntry 2 }

tmnxMcPathBwPlcyT2PathMbs      OBJECT-TYPE
    SYNTAX      Unsigned32 (0..10000)
    UNITS       "hundredths of a percent"
    MAX-ACCESS  read-create
    STATUS      current
    DESCRIPTION
        "The value of tmnxMcPathBwPlcyT2PathMbs specifies Maximum Buffer 
         Size(MBS). The value of tmnxMcPathBwPlcyT2PathMbs overrides the default
         MBS for each individual path's queue.  The default value of
         tmnxMcPathBwPlcyT2PathMbs is the default value of primary path's queue.
         The default value of tmnxMcPathBwPlcyT2PathMbs for the secondary path 
         is 4000."
    DEFVAL { 700 }
    ::= { tmnxMcPathBwPlcyT2PathEntry 3 }

tmnxMcPathBwPlcyT2PathHighPrio            OBJECT-TYPE
    SYNTAX      Unsigned32 (0..100)
    UNITS       "percentage"
    MAX-ACCESS  read-create
    STATUS      current
    DESCRIPTION
        "The value of tmnxMcPathBwPlcyT2PathHighPrio specifies percent of queue 
         depth reserved for high congestion priority traffic. The value of 
         tmnxMcPathBwPlcyT2PathHighPrio overrides the default percentage value
         used to determine the low priority MBS value for the queue.
         By default, 10 percent of the queue depth is reserved for high
         congestion priority traffic and this default value is same for
         secondary paths."
    DEFVAL { 10 }
    ::= { tmnxMcPathBwPlcyT2PathEntry 4 }

tmnxMcPathBwPlcyT2PathPaths     OBJECT-TYPE
    SYNTAX     Unsigned32 (1..15)
    MAX-ACCESS read-create
    STATUS     current
    DESCRIPTION
        "The value of tmnxMcPathBwPlcyT2PathPaths specifies the number of paths
         for the secondary path index only." 
    DEFVAL { 1 }
    ::= { tmnxMcPathBwPlcyT2PathEntry 5 }

tmnxMcPathBwPlcyT2PathDualPaths     OBJECT-TYPE
    SYNTAX     Unsigned32 (1..15)
    MAX-ACCESS read-create
    STATUS     current
    DESCRIPTION
        "The value of tmnxMcPathBwPlcyT2PathDualPaths specifies the number of 
         paths for the secondary path index for dual-sfm mode."
    DEFVAL { 1 }
    ::= { tmnxMcPathBwPlcyT2PathEntry 6 }

tmnxMcPathBwPlcyT2PathLastChanged  OBJECT-TYPE
    SYNTAX      TimeStamp
    MAX-ACCESS  read-only
    STATUS      current
    DESCRIPTION
        "The value of tmnxMcPathBwPlcyT2PathLastChanged indicates the timestamp 
         of last change to this row in tmnxMcPathBwPlcyT2PathTable."
    ::= { tmnxMcPathBwPlcyT2PathEntry 7 }

-- ------------------------------------------------
-- multicast video policy table
-- ------------------------------------------------

tmnxMcPathVdoPlcyTblLastChanged OBJECT-TYPE
    SYNTAX      TimeStamp
    MAX-ACCESS  read-only
    STATUS      current
    DESCRIPTION
        "The value of tmnxMcPathVdoPlcyTblLastChanged indicates the sysUpTime at
         the time of the last modification to tmnxMcPathVdoPlcyTable by adding,
         deleting an entry or change to a writable object in the table.

         If no changes were made to the table since the last re-initialization
         of the local network management subsystem, then this object contains a
         zero value."
    ::= { tmnxMcPathGlobalObjs 7 }

tmnxMcPathVdoPlcyTable OBJECT-TYPE
    SYNTAX      SEQUENCE OF TmnxMcPathVdoPlcyEntry
    MAX-ACCESS  not-accessible
    STATUS      current
    DESCRIPTION
        "The tmnxMcPathVdoPlcyTable has an entry for each multicast video
         policy configured on this system."
    ::= { tmnxMcPathObjs 15 }

tmnxMcPathVdoPlcyEntry    OBJECT-TYPE
    SYNTAX      TmnxMcPathVdoPlcyEntry
    MAX-ACCESS  not-accessible
    STATUS      current
    DESCRIPTION
        "Each row entry represents a particular multicast video policy.
         Entries can be created/deleted by the user."
    INDEX { tmnxMcPathPlcyName,
            tmnxMcPathVdoPlcyIfAddrType,
            tmnxMcPathVdoPlcyIfAddress,
            tmnxMcPathVdoPlcyChlType 
    }
    ::= { tmnxMcPathVdoPlcyTable 1}

TmnxMcPathVdoPlcyEntry ::= SEQUENCE
   {
        tmnxMcPathVdoPlcyIfAddrType       InetAddressType,
        tmnxMcPathVdoPlcyIfAddress        InetAddress,
        tmnxMcPathVdoPlcyChlType          TmnxMcPathVdoChlType,
        tmnxMcPathVdoPlcyRowStatus        RowStatus,
        tmnxMcPathVdoPlcyLastChanged      TimeStamp,
        tmnxMcPathVdoPlcyLclRTSvrState    TruthValue,
        tmnxMcPathVdoPlcyRTRate           Unsigned32,
        tmnxMcPathVdoPlcySubBwLimit       TmnxMcPathVdoBwLimit,
        tmnxMcPathVdoPlcyFCCSvrMode       TmnxVdoFccServerMode,
        tmnxMcPathVdoPlcyFCCBurst         Unsigned32,
        tmnxMcPathVdoPlcyFCCMcHandover    Unsigned32,
        tmnxMcPathVdoPlcyFCCDentThd       Unsigned32,
        tmnxMcPathVdoPlcyRTPayloadType    TmnxMcPathVdoPayloadType,
        tmnxMcPathVdoPlcyMaxClntSessions  Unsigned32,
        tmnxMcPathVdoPlcyMaxIgmpLatency   Unsigned32
   }

tmnxMcPathVdoPlcyIfAddrType       OBJECT-TYPE
    SYNTAX        InetAddressType
    MAX-ACCESS    not-accessible
    STATUS        current
    DESCRIPTION
        "The value of tmnxMcPathVdoPlcyIfAddrType specifies the address type
         of tmnxMcPathVdoPlcyIfAddress."
    ::= { tmnxMcPathVdoPlcyEntry 1 }

tmnxMcPathVdoPlcyIfAddress        OBJECT-TYPE
    SYNTAX        InetAddress (SIZE(4|16))
    MAX-ACCESS    not-accessible
    STATUS        current
    DESCRIPTION
        "The value of tmnxMcPathVdoPlcyIfAddress specifies the IP address of 
         the video interface. The IP address of video interface can be 
         configured within the context of a service to which this multicast 
         video policy is assigned. If the IP address does not match the IP 
         address assigned to a video interface, the parameters defined within
         this context have no effect."
    ::= { tmnxMcPathVdoPlcyEntry 2 }

tmnxMcPathVdoPlcyChlType          OBJECT-TYPE
    SYNTAX        TmnxMcPathVdoChlType
    MAX-ACCESS    not-accessible
    STATUS        current
    DESCRIPTION
        "The value of tmnxMcPathVdoPlcyChlType specifies the video
         channel type. It identifies whether the video channel is
         High Definition (HD), Standard Definition (SD) or
         Picture-in-Picture (PIP).

         A value of 'default' indicates that this is default video policy for
         High Definition (HD), Standard Definition (SD) or 
         Picture-in-Picture (PIP)."
    ::= { tmnxMcPathVdoPlcyEntry 3 }

tmnxMcPathVdoPlcyRowStatus        OBJECT-TYPE
    SYNTAX        RowStatus
    MAX-ACCESS    read-create
    STATUS        current
    DESCRIPTION
        "The value of tmnxMcPathVdoPlcyRowStatus specifies the row status of 
         this row. It is used for creation/deletion of multicast video policy."
    ::= { tmnxMcPathVdoPlcyEntry 4 }

tmnxMcPathVdoPlcyLastChanged      OBJECT-TYPE
    SYNTAX        TimeStamp
    MAX-ACCESS    read-only
    STATUS        current
    DESCRIPTION
        "The value of tmnxMcPathVdoPlcyLastChanged indicates the timestamp of
         last change to this row in tmnxMcPathVdoPlcyTable."
    ::= { tmnxMcPathVdoPlcyEntry 5 }

tmnxMcPathVdoPlcyLclRTSvrState    OBJECT-TYPE
    SYNTAX        TruthValue
    MAX-ACCESS    read-create
    STATUS        current
    DESCRIPTION
        "The value of tmnxMcPathVdoPlcyLclRTSvrState specifies whether or not
         local Retransmission (RT) server is enabled. It indicates whether 
         to process the Retransmission (RT) requests from the client. 
         
         The value of tmnxMcPathVdoPlcyLclRTSvrState is only applicable when
         tmnxMcPathVdoPlcyChlType is set to 'hd (2)', 'sd (3)', 
         or 'pip (4)'."
    DEFVAL { false }
    ::= { tmnxMcPathVdoPlcyEntry 6 }

tmnxMcPathVdoPlcyRTRate           OBJECT-TYPE
    SYNTAX        Unsigned32 (1..100)
    UNITS         "percent"
    MAX-ACCESS    read-create
    STATUS        current
    DESCRIPTION
        "The value of tmnxMcPathVdoPlcyRTRate specifies the rate at which
         retransmission packets are sent to the client. 

         A default value of '5' indicates that retransmission rate is set to
         5% above nominal bandwidth."
    DEFVAL { 5 }
    ::= { tmnxMcPathVdoPlcyEntry 7 }

tmnxMcPathVdoPlcySubBwLimit       OBJECT-TYPE
    SYNTAX        TmnxMcPathVdoBwLimit
    UNITS         "kbps"
    MAX-ACCESS    read-create
    STATUS        current
    DESCRIPTION
        "The value of tmnxMcPathVdoPlcySubBwLimit specifies the per-subscriber
         egress bandwidth limit for the combined Retransmission (RT) and
         Fast Channel Change (FCC). If the bandwidth for a request will
         exceed the bandwidth limit, the request is logged and dropped.
         
         The value of tmnxMcPathVdoPlcySubBwLimit is only applicable when
         tmnxMcPathVdoPlcyChlType is set to 'default (1)'."
    DEFVAL { 4294967295 }
    ::= { tmnxMcPathVdoPlcyEntry 8 }

tmnxMcPathVdoPlcyFCCSvrMode       OBJECT-TYPE
    SYNTAX        TmnxVdoFccServerMode
    MAX-ACCESS    read-create
    STATUS        current
    DESCRIPTION
        "The value of tmnxMcPathVdoPlcyFCCSvrMode specifies the mode of the
         Fast Channel Change (FCC) server. It indicates how the FCC server 
         will send unicast stream to the client.
         
         The value of tmnxMcPathVdoPlcyFCCSvrMode is only applicable when
         tmnxMcPathVdoPlcyChlType is set to 'hd (2)', 'sd (3)',
         or 'pip (4)'."
    DEFVAL { none }
    ::= { tmnxMcPathVdoPlcyEntry 9 }

tmnxMcPathVdoPlcyFCCBurst         OBJECT-TYPE
    SYNTAX        Unsigned32 (0..600) 
    UNITS         "percent"
    MAX-ACCESS    read-create
    STATUS        current
    DESCRIPTION
        "The value of tmnxMcPathVdoPlcyFCCBurst specifies the burst rate at
         which the Fast Channel Change (FCC) server will send unicast data
         to the client above the received rate to allow client to catch-up to
         the multicast stream. The value is only applicable if
         tmnxMcPathVdoPlcyFCCSvrMode is set to 'burst (1)' or 'hybrid (3)'
         and tmnxMcPathVdoPlcyChlType is set to 'hd (2)', 'sd (3)',
         or 'pip (4)'.

         A default value of '25' indicates that FCC burst rate is set to 25%
         above received rate."
    DEFVAL { 25 }
    ::= { tmnxMcPathVdoPlcyEntry 10 }

tmnxMcPathVdoPlcyFCCMcHandover       OBJECT-TYPE
    SYNTAX        Unsigned32 (0..600)
    UNITS         "percent"
    MAX-ACCESS    read-create
    STATUS        current
    DESCRIPTION
        "The value of tmnxMcPathVdoPlcyFCCMcHandover specifies the rate at which
         the Fast Channel Change (FCC) server will send unicast data to the 
         client during the handover to the multicast stream.

         The value of tmnxMcPathVdoPlcyFCCMcHandover is only applicable when
         tmnxMcPathVdoPlcyChlType is set to 'hd (2)', 'sd (3)', or 'pip (4)'.

         Additionaly, when the value of tmnxMcPathVdoPlcyChlType is 'hd (2)',
         the maximum value of tmnxMcPathVdoPlcyFCCMcHandover is 100."
    DEFVAL { 25 }
    ::= { tmnxMcPathVdoPlcyEntry 11 }

tmnxMcPathVdoPlcyFCCDentThd         OBJECT-TYPE
    SYNTAX        Unsigned32 (1..31)
    MAX-ACCESS    read-create
    STATUS        current
    DESCRIPTION
        "The value of tmnxMcPathVdoPlcyFCCDentThd specifies the dent
         threshold with which the Fast Channel Change (FCC) server will send
         unicast data to the client. The value is only applicable if
         the value of tmnxMcPathVdoPlcyFCCSvrMode is set to 'dent (2)' or
         'hybrid (3)' and tmnxMcPathVdoPlcyChlType is set to 'hd (2)',
         'sd (3)', or 'pip (4)'."
    DEFVAL { 16 }
    ::= { tmnxMcPathVdoPlcyEntry 12 }

tmnxMcPathVdoPlcyRTPayloadType OBJECT-TYPE
    SYNTAX          TmnxMcPathVdoPayloadType
    MAX-ACCESS      read-create 
    STATUS          current
    DESCRIPTION            
        "The value of tmnxMcPathVdoPlcyRTPayloadType specifies the format to
         be used by Retransmission (RT) server to send retransmission packets.
  
         The default value '99' indicates that the frames will be sent in the 
         RFC 4588 format.
  
         A value between 96 and 127 indicates the dynamic payload type value
         (as per RFC 3551) to be used for RFC 4588 formatted retransmission
         packets. A value of 33 indicates a mpeg-ts payload.
         
         The value of tmnxMcPathVdoPlcyRTPayloadType is only applicable when
         tmnxMcPathVdoPlcyChlType is set to 'default (1)'."
    DEFVAL { 99 }
    ::= { tmnxMcPathVdoPlcyEntry 13 }

tmnxMcPathVdoPlcyMaxClntSessions  OBJECT-TYPE
    SYNTAX      Unsigned32 (1..65536)
    MAX-ACCESS  read-create
    STATUS      current
    DESCRIPTION
        "The value of tmnxMcPathVdoPlcyMaxClntSessions specifies the maximum
         number of RTCP sessions supported per client IP address.
         
         The value of tmnxMcPathVdoPlcyMaxClntSessions is only applicable when
         tmnxMcPathVdoPlcyChlType is set to 'default (1)'."
    DEFVAL { 256 }
    ::= { tmnxMcPathVdoPlcyEntry 14 }

tmnxMcPathVdoPlcyMaxIgmpLatency  OBJECT-TYPE
    SYNTAX      Unsigned32 (10..1000)
    UNITS       "milliseconds"
    MAX-ACCESS  read-create
    STATUS      current
    DESCRIPTION
        "The value of tmnxMcPathVdoPlcyMaxIgmpLatency specifies the maximum 
         duration from the time a client sends an IGMP join to the time it 
         receives the first multicast packet.
         
         The value of tmnxMcPathVdoPlcyMaxIgmpLatency is only applicable when
         tmnxMcPathVdoPlcyChlType is set to 'default (1)'."
    DEFVAL { 100 }
    ::= { tmnxMcPathVdoPlcyEntry 15 }

-- ------------------------------------------------------
-- multicast information policy bundle video alarm table
-- ------------------------------------------------------

tmnxMcPathBdlExtTableLastChgd OBJECT-TYPE
    SYNTAX      TimeStamp
    MAX-ACCESS  read-only
    STATUS      current
    DESCRIPTION
        "The value of tmnxMcPathBdlExtTableLastChgd indicates the sysUpTime at 
         the time of the last modification to tmnxMcPathBdlExtTable by adding, 
         deleting an entry or change to a writable object in the table.

         If no changes were made to the table since the last re-initialization 
         of the local network management subsystem, then this object contains a 
         zero value."
    ::= { tmnxMcPathGlobalObjs 8 } 

tmnxMcPathBdlExtTable    OBJECT-TYPE
    SYNTAX      SEQUENCE OF TmnxMcPathBdlExtEntry
    MAX-ACCESS  not-accessible
    STATUS      current
    DESCRIPTION
        "The tmnxMcPathBdlExtTable has an entry for each multicast information
         policy bundle configured on this system."
    ::= { tmnxMcPathObjs 16 }

tmnxMcPathBdlExtEntry    OBJECT-TYPE
    SYNTAX      TmnxMcPathBdlExtEntry
    MAX-ACCESS  not-accessible
    STATUS      current
    DESCRIPTION
        "A row entry is created or deleted in this table when the corresponding 
         operation on a row is done in tmnxMcPathBdlTable. Entries in 
         tmnxMcPathBdlTable are created or deleted by the user. Each row entry 
         represents a particular multicast information policy bundle."
    AUGMENTS { tmnxMcPathBdlEntry }
    ::= { tmnxMcPathBdlExtTable 1}

TmnxMcPathBdlExtEntry ::= SEQUENCE
   {
       tmnxMcPathBdlVdoLastChanged        TimeStamp,
       tmnxMcPathBdlVdoCcError            TruthValue,
       tmnxMcPathBdlVdoPatRepError        TruthValue,
       tmnxMcPathBdlVdoTncPatRep          Unsigned32,
       tmnxMcPathBdlVdoQosPatRep          Unsigned32,
       tmnxMcPathBdlVdoPoaPatRep          Unsigned32,
       tmnxMcPathBdlVdoPatSyntax          TruthValue,
       tmnxMcPathBdlVdoPcrRepError        TruthValue,
       tmnxMcPathBdlVdoTncPcrRep          Unsigned32,
       tmnxMcPathBdlVdoQosPcrRep          Unsigned32,
       tmnxMcPathBdlVdoPoaPcrRep          Unsigned32,
       tmnxMcPathBdlVdoVidPIDAbsent       Unsigned32,
       tmnxMcPathBdlVdoPIDPmtUnref        TruthValue,
       tmnxMcPathBdlVdoPmtRepError        TruthValue,
       tmnxMcPathBdlVdoTncPmtRep          Unsigned32,
       tmnxMcPathBdlVdoQosPmtRep          Unsigned32,
       tmnxMcPathBdlVdoPoaPmtRep          Unsigned32,
       tmnxMcPathBdlVdoPmtSyntax          TruthValue,
       tmnxMcPathBdlVdoScte35Error        TruthValue,
       tmnxMcPathBdlVdoTeiError           TruthValue,
       tmnxMcPathBdlVdoTsSyncLoss         TruthValue,
       tmnxMcPathBdlVdoNonVidPIDAbsent    Unsigned32,
       tmnxMcPathBdlVdoReportAlarm        TmnxVdoAnalyzerAlarm         
   }

tmnxMcPathBdlVdoLastChanged  OBJECT-TYPE
    SYNTAX      TimeStamp
    MAX-ACCESS  read-only
    STATUS      current
    DESCRIPTION
        "The value of tmnxMcPathBdlVdoLastChanged  indicates the timestamp of 
         the last change to this row in tmnxMcPathBdlExtTable."
    ::= { tmnxMcPathBdlExtEntry 1 } 

tmnxMcPathBdlVdoCcError        OBJECT-TYPE
    SYNTAX      TruthValue
    MAX-ACCESS  read-create
    STATUS      current
    DESCRIPTION
        "The value of tmnxMcPathBdlVdoCcError specifies whether or not
         the continuity counter error is enabled for the video stream."
    DEFVAL { false }    
    ::= { tmnxMcPathBdlExtEntry 2 }

tmnxMcPathBdlVdoPatRepError       OBJECT-TYPE
    SYNTAX      TruthValue
    MAX-ACCESS  read-create
    STATUS      current
    DESCRIPTION
        "The value of tmnxMcPathBdlVdoPatRepError specifies whether or not
         PAT (Program Association Table) repetition error is enabled for the 
         video stream."
    DEFVAL { false }    
    ::= { tmnxMcPathBdlExtEntry 3}

tmnxMcPathBdlVdoTncPatRep        OBJECT-TYPE
    SYNTAX      Unsigned32 (100..800)
    UNITS       "milliseconds" 
    MAX-ACCESS  read-create
    STATUS      current
    DESCRIPTION
        "The value of tmnxMcPathBdlVdoTncPatRep specifies the value of
         TNC (Tech Non-Conformant) in milli-seconds for PAT repitition and 
         should always be a multiple of 100."
    DEFVAL { 100 } 
    ::= { tmnxMcPathBdlExtEntry 4}

tmnxMcPathBdlVdoQosPatRep        OBJECT-TYPE
    SYNTAX      Unsigned32 (200..900)
    UNITS       "milliseconds"
    MAX-ACCESS  read-create
    STATUS      current
    DESCRIPTION
        "The value of tmnxMcPathBdlVdoQosPatRep specifies the value of
         QOS (Quality of Service) in milli-seconds for PAT repitition and should 
         always be a multiple of 100. The value of 'tmnxMcPathBdlVdoQosPatRep' 
         must also be greater than the value of 'tmnxMcPathBdlVdoTncPatRep'."
    DEFVAL { 200 } 
    ::= { tmnxMcPathBdlExtEntry 5}

tmnxMcPathBdlVdoPoaPatRep        OBJECT-TYPE
    SYNTAX      Unsigned32 (300..1000)
    UNITS       "milliseconds"
    MAX-ACCESS  read-create
    STATUS      current
    DESCRIPTION
        "The value of tmnxMcPathBdlVdoPoaPatRep specifies the value of
         POA (Program off Air) in milli-seconds for PAT repitition and 
         should always be a multiple of 100. The value of 
         'tmnxMcPathBdlVdoPoaPatRep' must also be greater than the value of 
         'tmnxMcPathBdlVdoQosPatRep'."
    DEFVAL { 500 } 
    ::= { tmnxMcPathBdlExtEntry 6 }

tmnxMcPathBdlVdoPatSyntax        OBJECT-TYPE
    SYNTAX      TruthValue
    MAX-ACCESS  read-create
    STATUS      current
    DESCRIPTION
        "The value of tmnxMcPathBdlVdoPatSyntax specifies whether or not
         PAT syntax error is enabled for the video stream."
    DEFVAL { false }    
    ::= { tmnxMcPathBdlExtEntry 7 }

tmnxMcPathBdlVdoPcrRepError        OBJECT-TYPE
    SYNTAX      TruthValue
    MAX-ACCESS  read-create
    STATUS      current
    DESCRIPTION
        "The value of tmnxMcPathBdlVdoPcrRepError specifies whether or not
         PCR (Program Clock Reference) repetition error is enabled for the 
         video stream."
    DEFVAL { false } 
    ::= { tmnxMcPathBdlExtEntry 8 }

tmnxMcPathBdlVdoTncPcrRep        OBJECT-TYPE
    SYNTAX      Unsigned32 (100..800)
    UNITS       "milliseconds"
    MAX-ACCESS  read-create
    STATUS      current
    DESCRIPTION
        "The value of tmnxMcPathBdlVdoTncPcrRep specifies the value of
         TNC (Tech Non-Conformant) in milli-seconds for PCR repitition and 
         should always be a multiple of 100."
    DEFVAL { 100 } 
    ::= { tmnxMcPathBdlExtEntry 9 }

tmnxMcPathBdlVdoQosPcrRep        OBJECT-TYPE
    SYNTAX      Unsigned32 (200..900)
    UNITS       "milliseconds"
    MAX-ACCESS  read-create
    STATUS      current
    DESCRIPTION
        "The value of tmnxMcPathBdlVdoQosPcrRep specifies the value of
         QOS (Quality of Service) in milli-seconds for PCR repitition and should 
         always be a multiple of 100. The value of 'tmnxMcPathBdlVdoQosPcrRep' 
         must also be greater than the value of 'tmnxMcPathBdlVdoTncPcrRep'."
    DEFVAL { 200 } 
    ::= { tmnxMcPathBdlExtEntry 10 }

tmnxMcPathBdlVdoPoaPcrRep        OBJECT-TYPE
    SYNTAX      Unsigned32 (300..1000)
    UNITS       "milliseconds"
    MAX-ACCESS  read-create
    STATUS      current
    DESCRIPTION
        "The value of tmnxMcPathBdlVdoPoaPcrRep specifies the value of
         POA (Program off Air) in milli-seconds for PAT repitition and should 
         always be a multiple of 100. The value of 'tmnxMcPathBdlVdoPoaPcrRep' 
         must also be greater than the value of 'tmnxMcPathBdlVdoQosPcrRep'."
    DEFVAL { 500 } 
    ::= { tmnxMcPathBdlExtEntry 11 }

tmnxMcPathBdlVdoVidPIDAbsent        OBJECT-TYPE
    SYNTAX      Unsigned32 (0..5000)
    UNITS       "milliseconds"
    MAX-ACCESS  read-create
    STATUS      current
    DESCRIPTION
        "The value of tmnxMcPathBdlVdoVidPIDAbsent specifies the counting 
         interval for 'TIMETRA-VIDEO-MIB::tmnxVdoPIDAbsentErrSecs' which 
         accumulates the number of video PID absent errors for the video PID 
         stream. It has a default value of 0 which means no error counting. Its 
         value can only be changed by increments or decrements of 100 
         milliseconds otherwise a 'wrongValue' error is returned."
    DEFVAL { 0 } 
    ::= { tmnxMcPathBdlExtEntry 12 }

tmnxMcPathBdlVdoPIDPmtUnref        OBJECT-TYPE
    SYNTAX      TruthValue
    MAX-ACCESS  read-create
    STATUS      current
    DESCRIPTION
        "The value of tmnxMcPathBdlVdoPIDPmtUnref specifies whether or not 
         unreferenced PID (i.e. PIDs not specified in the PMT) error is enabled 
         for the video stream."
    DEFVAL { false } 
    ::= { tmnxMcPathBdlExtEntry 13 }

tmnxMcPathBdlVdoPmtRepError        OBJECT-TYPE
    SYNTAX      TruthValue
    MAX-ACCESS  read-create
    STATUS      current
    DESCRIPTION
        "The value of tmnxMcPathBdlVdoPmtRepError specifies whether or not
         PMT (Program Map Table) repetition error is enabled for the 
         video stream."
    DEFVAL { false } 
    ::= { tmnxMcPathBdlExtEntry 14 }

tmnxMcPathBdlVdoTncPmtRep        OBJECT-TYPE
    SYNTAX      Unsigned32 (100..4800)
    UNITS       "milliseconds"
    MAX-ACCESS  read-create
    STATUS      current
    DESCRIPTION
        "The value of tmnxMcPathBdlVdoTncPmtRep specifies the value of
         TNC (Tech Non-Conformance) in milli-seconds for PMT repitition and 
         should always be a multiple of 100."
    DEFVAL { 400 } 
    ::= { tmnxMcPathBdlExtEntry 15 }

tmnxMcPathBdlVdoQosPmtRep        OBJECT-TYPE
    SYNTAX      Unsigned32 (200..4900)
    UNITS       "milliseconds"
    MAX-ACCESS  read-create
    STATUS      current
    DESCRIPTION
        "The value of tmnxMcPathBdlVdoQosPmtRep specifies the value of
         QOS (Quality of Service) in milli-seconds for PMT repitition and should 
         always be a multiple of 100. The value of 'tmnxMcPathBdlVdoQosPmtRep' 
         must also be greater than the value of 'tmnxMcPathBdlVdoTncPmtRep'."
    DEFVAL { 800 } 
    ::= { tmnxMcPathBdlExtEntry 16 }

tmnxMcPathBdlVdoPoaPmtRep        OBJECT-TYPE
    SYNTAX      Unsigned32 (300..5000)
    UNITS       "milliseconds"
    MAX-ACCESS  read-create
    STATUS      current
    DESCRIPTION
        "The value of tmnxMcPathBdlVdoPoaPmtRep specifies the value of
         POA (Program off Air) in milli-seconds for PMT repitition and should 
         always be a multiple of 100. The value of 'tmnxMcPathBdlVdoPoaPmtRep' 
         must also be greater than the value of 'tmnxMcPathBdlVdoQosPmtRep'."
    DEFVAL { 2000 } 
    ::= { tmnxMcPathBdlExtEntry 17 }

tmnxMcPathBdlVdoPmtSyntax        OBJECT-TYPE
    SYNTAX      TruthValue
    MAX-ACCESS  read-create
    STATUS      current
    DESCRIPTION
        "The value of tmnxMcPathBdlVdoPmtSyntax specifies whether or not
         PMT syntax error is enabled for the video stream."
    DEFVAL { false } 
    ::= { tmnxMcPathBdlExtEntry 18 }

tmnxMcPathBdlVdoScte35Error        OBJECT-TYPE
    SYNTAX      TruthValue
    MAX-ACCESS  read-create
    STATUS      obsolete
    DESCRIPTION
        "The value of tmnxMcPathBdlVdoScte35Error specifies whether or not
         SCTE35 (Society of Cable Telecommunications Engineers) errors
         are enabled for the video stream.

         This object was obsoleted in the 9.0 release."
    DEFVAL { false } 
    ::= { tmnxMcPathBdlExtEntry 19 }

tmnxMcPathBdlVdoTeiError        OBJECT-TYPE
    SYNTAX      TruthValue
    MAX-ACCESS  read-create
    STATUS      current
    DESCRIPTION
        "The value of tmnxMcPathBdlVdoTeiError specifies whether or not TEI
        (Transport Error Indicator) error is enabled for the video stream."
    DEFVAL { false } 
    ::= { tmnxMcPathBdlExtEntry 20 }

tmnxMcPathBdlVdoTsSyncLoss        OBJECT-TYPE
    SYNTAX      TruthValue
    MAX-ACCESS  read-create
    STATUS      current
    DESCRIPTION
        "The value of tmnxMcPathBdlVdoTsSyncLoss specifies whether or not sync 
         loss error is enabled for the video stream."
    DEFVAL { false } 
    ::= { tmnxMcPathBdlExtEntry 21 }

tmnxMcPathBdlVdoNonVidPIDAbsent        OBJECT-TYPE
    SYNTAX      Unsigned32 (0..5000)
    UNITS       "milliseconds"
    MAX-ACCESS  read-create
    STATUS      current
    DESCRIPTION
        "The value of tmnxMcPathBdlVdoNonVidPIDAbsent specifies the counting 
         interval for 'TIMETRA-VIDEO-MIB::tmnxVdoPIDAbsentErrSecs' which 
         accumulates the number of non-video PID absent errors for the video 
         PID stream. It has a default value of 0 which means no error counting. 
         Its value can only be changed by increments or decrements of 100 
         milliseconds otherwise a 'wrongValue' error is returned."
    DEFVAL { 0 } 
    ::= { tmnxMcPathBdlExtEntry 22 }

tmnxMcPathBdlVdoReportAlarm        OBJECT-TYPE
    SYNTAX      TmnxVdoAnalyzerAlarm
    MAX-ACCESS  read-create
    STATUS      current
    DESCRIPTION
        "The value of tmnxMcPathBdlVdoReportAlarm specifies the severity of 
         the analyzer state alarm for the video stream."
    DEFVAL { none } 
    ::= { tmnxMcPathBdlExtEntry 23 }

-- -------------------------------------------------------------
-- multicast information policy bundle channel video alarm table
-- -------------------------------------------------------------

tmnxMcPathBdlChlExtTableLastChgd OBJECT-TYPE
    SYNTAX      TimeStamp
    MAX-ACCESS  read-only
    STATUS      current
    DESCRIPTION
        "The value of tmnxMcPathBdlChlExtTableLastChgd indicates the sysUpTime  
         at the time of the last modification to tmnxMcPathBdlChlExtTable by 
         adding, deleting an entry or change to a writable object in the table.

         If no changes were made to the table since the last re-initialization 
         of the local network management subsystem, then this object contains a 
         zero value."
    ::= { tmnxMcPathGlobalObjs 9 } 

tmnxMcPathBdlChlExtTable    OBJECT-TYPE
    SYNTAX      SEQUENCE OF TmnxMcPathBdlChlExtEntry
    MAX-ACCESS  not-accessible
    STATUS      current
    DESCRIPTION
        "The tmnxMcPathBdlChlExtTable has an entry for each multicast 
         information policy bundle configured on this system."
    ::= { tmnxMcPathObjs 17 }

tmnxMcPathBdlChlExtEntry    OBJECT-TYPE
    SYNTAX      TmnxMcPathBdlChlExtEntry
    MAX-ACCESS  not-accessible
    STATUS      current
    DESCRIPTION
        "A row entry is created or deleted in this table when the corresponding 
         operation on a row is done in tmnxMcPathBdlChlTable. Entries in 
         tmnxMcPathBdlChlTable are created or deleted by the user. Each row 
         entry represents a particular multicast information policy bundle 
         channel."
    AUGMENTS { tmnxMcPathBdlChlEntry }
    ::= { tmnxMcPathBdlChlExtTable 1}

TmnxMcPathBdlChlExtEntry ::= SEQUENCE
   {
        tmnxMcPathBdlChlVdoLastChanged     TimeStamp,
        tmnxMcPathBdlChlVdoCcError         TruthValue,
        tmnxMcPathBdlChlVdoPatRepError     TruthValue,
        tmnxMcPathBdlChlVdoTncPatRep       Unsigned32,
        tmnxMcPathBdlChlVdoQosPatRep       Unsigned32,
        tmnxMcPathBdlChlVdoPoaPatRep       Unsigned32,
        tmnxMcPathBdlChlVdoPatSyntax       TruthValue,
        tmnxMcPathBdlChlVdoPcrRepError     TruthValue,
        tmnxMcPathBdlChlVdoTncPcrRep       Unsigned32,
        tmnxMcPathBdlChlVdoQosPcrRep       Unsigned32,
        tmnxMcPathBdlChlVdoPoaPcrRep       Unsigned32,
        tmnxMcPathBdlChlVdoVidPIDAbs       Unsigned32,
        tmnxMcPathBdlChlVdoPIDPmtUnref     TruthValue,
        tmnxMcPathBdlChlVdoPmtRepError     TruthValue,
        tmnxMcPathBdlChlVdoTncPmtRep       Unsigned32,
        tmnxMcPathBdlChlVdoQosPmtRep       Unsigned32,
        tmnxMcPathBdlChlVdoPoaPmtRep       Unsigned32,
        tmnxMcPathBdlChlVdoPmtSyntax       TruthValue,
        tmnxMcPathBdlChlVdoScte35Error     TruthValue,
        tmnxMcPathBdlChlVdoTeiError        TruthValue,
        tmnxMcPathBdlChlVdoTsSyncLoss      TruthValue,
        tmnxMcPathBdlChlVdoNonVidPIDAbs    Unsigned32,
        tmnxMcPathBdlChlVdoReportAlarm     TmnxVdoAnalyzerAlarm                    
   }

tmnxMcPathBdlChlVdoLastChanged  OBJECT-TYPE
    SYNTAX      TimeStamp
    MAX-ACCESS  read-only
    STATUS      current
    DESCRIPTION
        "The value of tmnxMcPathBdlChlVdoLastChanged  indicates the timestamp of 
         the last change to this row in tmnxMcPathBdlChlExtTable."
    ::= { tmnxMcPathBdlChlExtEntry 1 } 

tmnxMcPathBdlChlVdoCcError        OBJECT-TYPE
    SYNTAX      TruthValue
    MAX-ACCESS  read-create
    STATUS      current
    DESCRIPTION
        "The value of tmnxMcPathBdlChlVdoCcError specifies whether or not
         the continuity counter error is enabled for the video stream."
    DEFVAL { false }    
    ::= { tmnxMcPathBdlChlExtEntry 2 }

tmnxMcPathBdlChlVdoPatRepError       OBJECT-TYPE
    SYNTAX      TruthValue
    MAX-ACCESS  read-create
    STATUS      current
    DESCRIPTION
        "The value of tmnxMcPathBdlChlVdoPatRepError specifies whether or not
         PAT (Program Association Table) repetition error is enabled for the 
         video stream."
    DEFVAL { false }    
    ::= { tmnxMcPathBdlChlExtEntry 3}

tmnxMcPathBdlChlVdoTncPatRep        OBJECT-TYPE
    SYNTAX      Unsigned32 (100..800)
    UNITS       "milliseconds" 
    MAX-ACCESS  read-create
    STATUS      current
    DESCRIPTION
        "The value of tmnxMcPathBdlChlVdoTncPatRep specifies the value of
         TNC (Tech Non-Conformant) in milli-seconds for PAT repitition and 
         should always be a multiple of 100."
    DEFVAL { 100 } 
    ::= { tmnxMcPathBdlChlExtEntry 4}

tmnxMcPathBdlChlVdoQosPatRep        OBJECT-TYPE
    SYNTAX      Unsigned32 (200..900)
    UNITS       "milliseconds"
    MAX-ACCESS  read-create
    STATUS      current
    DESCRIPTION
        "The value of tmnxMcPathBdlChlVdoQosPatRep specifies the value of
         QOS (Quality of Service) in milli-seconds for PAT repitition and should 
         always be a multiple of 100. The value of 
         'tmnxMcPathBdlChlVdoQosPatRep' must also be greater than the value of 
         'tmnxMcPathBdlChlVdoTncPatRep'."
    DEFVAL { 200 } 
    ::= { tmnxMcPathBdlChlExtEntry 5}

tmnxMcPathBdlChlVdoPoaPatRep        OBJECT-TYPE
    SYNTAX      Unsigned32 (300..1000)
    UNITS       "milliseconds"
    MAX-ACCESS  read-create
    STATUS      current
    DESCRIPTION
        "The value of tmnxMcPathBdlChlVdoPoaPatRep specifies the value of
         POA (Program off Air) in milli-seconds for PAT repitition and 
         should always be a multiple of 100. The value of 
         'tmnxMcPathBdlChlVdoPoaPatRep' must also be greater than the value of 
         'tmnxMcPathBdlChlVdoQosPatRep'."
    DEFVAL { 500 } 
    ::= { tmnxMcPathBdlChlExtEntry 6 }

tmnxMcPathBdlChlVdoPatSyntax        OBJECT-TYPE
    SYNTAX      TruthValue
    MAX-ACCESS  read-create
    STATUS      current
    DESCRIPTION
        "The value of tmnxMcPathBdlChlVdoPatSyntax specifies whether or not
         PAT syntax error is enabled for the video stream."
    DEFVAL { false }    
    ::= { tmnxMcPathBdlChlExtEntry 7 }

tmnxMcPathBdlChlVdoPcrRepError        OBJECT-TYPE
    SYNTAX      TruthValue
    MAX-ACCESS  read-create
    STATUS      current
    DESCRIPTION
        "The value of tmnxMcPathBdlChlVdoPcrRepError specifies whether or not
         PCR (Program Clock Reference) repetition error is enabled for the 
         video stream."
    DEFVAL { false } 
    ::= { tmnxMcPathBdlChlExtEntry 8 }

tmnxMcPathBdlChlVdoTncPcrRep        OBJECT-TYPE
    SYNTAX      Unsigned32 (100..800)
    UNITS       "milliseconds"
    MAX-ACCESS  read-create
    STATUS      current
    DESCRIPTION
        "The value of tmnxMcPathBdlChlVdoTncPcrRep specifies the value of
         TNC (Tech Non-Conformant) in milli-seconds for PCR repitition and 
         should always be a multiple of 100."
    DEFVAL { 100 } 
    ::= { tmnxMcPathBdlChlExtEntry 9 }

tmnxMcPathBdlChlVdoQosPcrRep        OBJECT-TYPE
    SYNTAX      Unsigned32 (200..900)
    UNITS       "milliseconds"
    MAX-ACCESS  read-create
    STATUS      current
    DESCRIPTION
        "The value of tmnxMcPathBdlChlVdoQosPcrRep specifies the value of
         QOS (Quality of Service) in milli-seconds for PCR repitition and should 
         always be a multiple of 100. The value of 
         'tmnxMcPathBdlChlVdoQosPcrRep' must also be greater than the value of 
         'tmnxMcPathBdlChlVdoTncPcrRep'."
    DEFVAL { 200 } 
    ::= { tmnxMcPathBdlChlExtEntry 10 }

tmnxMcPathBdlChlVdoPoaPcrRep        OBJECT-TYPE
    SYNTAX      Unsigned32 (300..1000)
    UNITS       "milliseconds"
    MAX-ACCESS  read-create
    STATUS      current
    DESCRIPTION
        "The value of tmnxMcPathBdlChlVdoPoaPcrRep specifies the value of
         POA (Program off Air) in milli-seconds for PAT repitition and should 
         always be a multiple of 100. The value of 
         'tmnxMcPathBdlChlVdoPoaPcrRep' must also be greater than the value of 
         'tmnxMcPathBdlChlVdoQosPcrRep'."
    DEFVAL { 500 } 
    ::= { tmnxMcPathBdlChlExtEntry 11 }

tmnxMcPathBdlChlVdoVidPIDAbs      OBJECT-TYPE
    SYNTAX      Unsigned32 (0..5000)
    UNITS       "milliseconds"
    MAX-ACCESS  read-create
    STATUS      current
    DESCRIPTION
        "The value of tmnxMcPathBdlChlVdoVidPIDAbs specifies the counting 
         interval for 'TIMETRA-VIDEO-MIB::tmnxVdoPIDAbsentErrSecs' which 
         accumulates the number of video PID absent errors for the video PID 
         stream. It has a default value of 0 which means no error counting. 
         Its value can only be changed by increments or decrements of 100 
         milliseconds otherwise a 'wrongValue' error is returned."
    DEFVAL { 0 } 
    ::= { tmnxMcPathBdlChlExtEntry 12 }

tmnxMcPathBdlChlVdoPIDPmtUnref        OBJECT-TYPE
    SYNTAX      TruthValue
    MAX-ACCESS  read-create
    STATUS      current
    DESCRIPTION
        "The value of tmnxMcPathBdlChlVdoPIDPmtUnref specifies whether or not 
         unreferenced PID (i.e. PIDs not specified in the PMT) error is enabled 
         for the video stream."
    DEFVAL { false } 
    ::= { tmnxMcPathBdlChlExtEntry 13 }

tmnxMcPathBdlChlVdoPmtRepError        OBJECT-TYPE
    SYNTAX      TruthValue
    MAX-ACCESS  read-create
    STATUS      current
    DESCRIPTION
        "The value of tmnxMcPathBdlChlVdoPmtRepError specifies whether or not
         PMT (Program Map Table) repetition error is enabled for the 
         video stream."
    DEFVAL { false } 
    ::= { tmnxMcPathBdlChlExtEntry 14 }

tmnxMcPathBdlChlVdoTncPmtRep        OBJECT-TYPE
    SYNTAX      Unsigned32 (100..4800)
    UNITS       "milliseconds"
    MAX-ACCESS  read-create
    STATUS      current
    DESCRIPTION
        "The value of tmnxMcPathBdlChlVdoTncPmtRep specifies the value of
         TNC (Tech Non-Conformance) in milli-seconds for PMT repitition and 
         should always be a multiple of 100."
    DEFVAL { 400 } 
    ::= { tmnxMcPathBdlChlExtEntry 15 }

tmnxMcPathBdlChlVdoQosPmtRep        OBJECT-TYPE
    SYNTAX      Unsigned32 (200..4900)
    UNITS       "milliseconds"
    MAX-ACCESS  read-create
    STATUS      current
    DESCRIPTION
        "The value of tmnxMcPathBdlChlVdoQosPmtRep specifies the value of
         QOS (Quality of Service) in milli-seconds for PMT repitition and should 
         always be a multiple of 100. The value of 
         'tmnxMcPathBdlChlVdoQosPmtRep' must also be greater than the value of 
         'tmnxMcPathBdlChlVdoTncPmtRep'."
    DEFVAL { 800 } 
    ::= { tmnxMcPathBdlChlExtEntry 16 }

tmnxMcPathBdlChlVdoPoaPmtRep        OBJECT-TYPE
    SYNTAX      Unsigned32 (300..5000)
    UNITS       "milliseconds"
    MAX-ACCESS  read-create
    STATUS      current
    DESCRIPTION
        "The value of tmnxMcPathBdlChlVdoPoaPmtRep specifies the value of
         POA (Program off Air) in milli-seconds for PMT repitition and should 
         always be a multiple of 100. The value of 
         'tmnxMcPathBdlChlVdoPoaPmtRep' must also be greater than the value of 
         'tmnxMcPathBdlChlVdoQosPmtRep'."
    DEFVAL { 2000 } 
    ::= { tmnxMcPathBdlChlExtEntry 17 }

tmnxMcPathBdlChlVdoPmtSyntax        OBJECT-TYPE
    SYNTAX      TruthValue
    MAX-ACCESS  read-create
    STATUS      current
    DESCRIPTION
        "The value of tmnxMcPathBdlChlVdoPmtSyntax specifies whether or not
         PMT syntax error is enabled for the video stream."
    DEFVAL { false } 
    ::= { tmnxMcPathBdlChlExtEntry 18 }

tmnxMcPathBdlChlVdoScte35Error        OBJECT-TYPE
    SYNTAX      TruthValue
    MAX-ACCESS  read-create
    STATUS      obsolete
    DESCRIPTION
        "The value of tmnxMcPathBdlChlVdoScte35Error specifies whether or not
         SCTE35 (Society of Cable Telecommunications Engineers) errors
         are enabled for the video stream.

         This object was obsoleted in the 9.0 release."
    DEFVAL { false } 
    ::= { tmnxMcPathBdlChlExtEntry 19 }

tmnxMcPathBdlChlVdoTeiError        OBJECT-TYPE
    SYNTAX      TruthValue
    MAX-ACCESS  read-create
    STATUS      current
    DESCRIPTION
        "The value of tmnxMcPathBdlChlVdoTeiError specifies whether or not TEI
        (Transport Error Indicator) error is enabled for the video stream."
    DEFVAL { false } 
    ::= { tmnxMcPathBdlChlExtEntry 20 }

tmnxMcPathBdlChlVdoTsSyncLoss        OBJECT-TYPE
    SYNTAX      TruthValue
    MAX-ACCESS  read-create
    STATUS      current
    DESCRIPTION
        "The value of tmnxMcPathBdlChlVdoTsSyncLoss specifies whether or not 
         sync loss error is enabled for the video stream."
    DEFVAL { false } 
    ::= { tmnxMcPathBdlChlExtEntry 21 }

tmnxMcPathBdlChlVdoNonVidPIDAbs      OBJECT-TYPE
    SYNTAX      Unsigned32 (0..5000)
    UNITS       "milliseconds"
    MAX-ACCESS  read-create
    STATUS      current
    DESCRIPTION
        "The value of tmnxMcPathBdlChlVdoNonVidPIDAbs specifies the counting 
         interval for 'TIMETRA-VIDEO-MIB::tmnxVdoPIDAbsentErrSecs' which 
         accumulates the number of non-video PID absent errors for the video 
         PID stream. It has a default value of 0 which means no error counting.
         Its value can only be changed by increments or decrements of 100 
         milliseconds otherwise a 'wrongValue' error is returned."
    DEFVAL { 0 } 
    ::= { tmnxMcPathBdlChlExtEntry 22 }

tmnxMcPathBdlChlVdoReportAlarm        OBJECT-TYPE
    SYNTAX      TmnxVdoAnalyzerAlarm
    MAX-ACCESS  read-create
    STATUS      current
    DESCRIPTION
        "The value of tmnxMcPathBdlChlVdoReportAlarm specifies the severity of 
         the analyzer state alarm for the video stream."
    DEFVAL { none } 
    ::= { tmnxMcPathBdlChlExtEntry 23 }

-- -----------------------------------------------------------------------------
-- multicast information policy bundle channel source-override video alarm table
-- -----------------------------------------------------------------------------

tmnxMcPathChlSrcExtTableLastChgd OBJECT-TYPE
    SYNTAX      TimeStamp
    MAX-ACCESS  read-only
    STATUS      current
    DESCRIPTION
        "The value of tmnxMcPathChlSrcExtTableLastChgd indicates the sysUpTime  
         at the time of the last modification to tmnxMcPathBdlExtTable by 
         adding, deleting an entry or change to a writable object in the table.

         If no changes were made to the table since the last re-initialization 
         of the local network management subsystem, then this object contains a 
         zero value."
    ::= { tmnxMcPathGlobalObjs 10 } 

tmnxMcPathChlSrcExtTable    OBJECT-TYPE
    SYNTAX      SEQUENCE OF TmnxMcPathChlSrcExtEntry
    MAX-ACCESS  not-accessible
    STATUS      current
    DESCRIPTION
        "The tmnxMcPathBdlExtTable has an entry for each multicast information
         policy bundle configured on this system."
    ::= { tmnxMcPathObjs 18 }

tmnxMcPathChlSrcExtEntry    OBJECT-TYPE
    SYNTAX      TmnxMcPathChlSrcExtEntry
    MAX-ACCESS  not-accessible
    STATUS      current
    DESCRIPTION
        "A row entry is created or deleted in this table when the corresponding 
         operation on a row is done in tmnxMcPathChlSrcTable. Entries in 
         tmnxMcPathChlSrcTable are created or deleted by the user. Each row 
         entry represents a specified sender configured for multicast
         bundle channel."
    AUGMENTS { tmnxMcPathChlSrcEntry }
    ::= { tmnxMcPathChlSrcExtTable 1}

TmnxMcPathChlSrcExtEntry ::= SEQUENCE
   {
       tmnxMcPathChlSrcVdoLastChanged     TimeStamp,
       tmnxMcPathChlSrcVdoCcError         TruthValue,
       tmnxMcPathChlSrcVdoPatRepError     TruthValue,
       tmnxMcPathChlSrcVdoTncPatRep       Unsigned32,
       tmnxMcPathChlSrcVdoQosPatRep       Unsigned32,
       tmnxMcPathChlSrcVdoPoaPatRep       Unsigned32,
       tmnxMcPathChlSrcVdoPatSyntax       TruthValue,
       tmnxMcPathChlSrcVdoPcrRepError     TruthValue,
       tmnxMcPathChlSrcVdoTncPcrRep       Unsigned32,
       tmnxMcPathChlSrcVdoQosPcrRep       Unsigned32,
       tmnxMcPathChlSrcVdoPoaPcrRep       Unsigned32,
       tmnxMcPathChlSrcVdoVidPIDAbs       Unsigned32,
       tmnxMcPathChlSrcVdoPIDPmtUnref     TruthValue,
       tmnxMcPathChlSrcVdoPmtRepError     TruthValue,
       tmnxMcPathChlSrcVdoTncPmtRep       Unsigned32,
       tmnxMcPathChlSrcVdoQosPmtRep       Unsigned32,
       tmnxMcPathChlSrcVdoPoaPmtRep       Unsigned32,
       tmnxMcPathChlSrcVdoPmtSyntax       TruthValue,
       tmnxMcPathChlSrcVdoScte35Error     TruthValue,
       tmnxMcPathChlSrcVdoTeiError        TruthValue,
       tmnxMcPathChlSrcVdoTsSyncLoss      TruthValue,
       tmnxMcPathChlSrcVdoNonVidPIDAbs    Unsigned32,
       tmnxMcPathChlSrcVdoReportAlarm     TmnxVdoAnalyzerAlarm            
   }

tmnxMcPathChlSrcVdoLastChanged  OBJECT-TYPE
    SYNTAX      TimeStamp
    MAX-ACCESS  read-only
    STATUS      current
    DESCRIPTION
        "The value of tmnxMcPathChlSrcVdoLastChanged  indicates the timestamp of 
         the last change to this row in tmnxMcPathChlSrcExtTable."
    ::= { tmnxMcPathChlSrcExtEntry 1 }

tmnxMcPathChlSrcVdoCcError        OBJECT-TYPE
    SYNTAX      TruthValue
    MAX-ACCESS  read-create
    STATUS      current
    DESCRIPTION
        "The value of tmnxMcPathChlSrcVdoCcError specifies whether or not
         the continuity counter error is enabled for the video stream."
    DEFVAL { false }    
    ::= { tmnxMcPathChlSrcExtEntry 2 }

tmnxMcPathChlSrcVdoPatRepError       OBJECT-TYPE
    SYNTAX      TruthValue
    MAX-ACCESS  read-create
    STATUS      current
    DESCRIPTION
        "The value of tmnxMcPathChlSrcVdoPatRepError specifies whether or not
         PAT (Program Association Table) repetition error is enabled for the 
         video stream."
    DEFVAL { false }    
    ::= { tmnxMcPathChlSrcExtEntry 3}

tmnxMcPathChlSrcVdoTncPatRep        OBJECT-TYPE
    SYNTAX      Unsigned32 (100..800)
    UNITS       "milliseconds" 
    MAX-ACCESS  read-create
    STATUS      current
    DESCRIPTION
        "The value of tmnxMcPathChlSrcVdoTncPatRep specifies the value of
         TNC (Tech Non-Conformant) in milli-seconds for PAT repitition and 
         should always be a multiple of 100."
    DEFVAL { 100 } 
    ::= { tmnxMcPathChlSrcExtEntry 4}

tmnxMcPathChlSrcVdoQosPatRep        OBJECT-TYPE
    SYNTAX      Unsigned32 (200..900)
    UNITS       "milliseconds"
    MAX-ACCESS  read-create
    STATUS      current
    DESCRIPTION
        "The value of tmnxMcPathChlSrcVdoQosPatRep specifies the value of
         QOS (Quality of Service) in milli-seconds for PAT repitition and should 
         always be a multiple of 100. The value of 
         'tmnxMcPathChlSrcVdoQosPatRep' must also be greater than the value of 
         'tmnxMcPathChlSrcVdoTncPatRep'."
    DEFVAL { 200 } 
    ::= { tmnxMcPathChlSrcExtEntry 5}

tmnxMcPathChlSrcVdoPoaPatRep        OBJECT-TYPE
    SYNTAX      Unsigned32 (300..1000)
    UNITS       "milliseconds"
    MAX-ACCESS  read-create
    STATUS      current
    DESCRIPTION
        "The value of tmnxMcPathChlSrcVdoPoaPatRep specifies the value of
         POA (Program off Air) in milli-seconds for PAT repitition and 
         should always be a multiple of 100. The value of 
         'tmnxMcPathChlSrcVdoPoaPatRep' must also be greater than the value of 
         'tmnxMcPathChlSrcVdoQosPatRep'."
    DEFVAL { 500 } 
    ::= { tmnxMcPathChlSrcExtEntry 6 }

tmnxMcPathChlSrcVdoPatSyntax        OBJECT-TYPE
    SYNTAX      TruthValue
    MAX-ACCESS  read-create
    STATUS      current
    DESCRIPTION
        "The value of tmnxMcPathChlSrcVdoPatSyntax specifies whether or not
         PAT syntax error is enabled for the video stream."
    DEFVAL { false }    
    ::= { tmnxMcPathChlSrcExtEntry 7 }

tmnxMcPathChlSrcVdoPcrRepError        OBJECT-TYPE
    SYNTAX      TruthValue
    MAX-ACCESS  read-create
    STATUS      current
    DESCRIPTION
        "The value of tmnxMcPathChlSrcVdoPcrRepError specifies whether or not
         PCR (Program Clock Reference) repetition error is enabled for the 
         video stream."
    DEFVAL { false } 
    ::= { tmnxMcPathChlSrcExtEntry 8 }

tmnxMcPathChlSrcVdoTncPcrRep        OBJECT-TYPE
    SYNTAX      Unsigned32 (100..800)
    UNITS       "milliseconds"
    MAX-ACCESS  read-create
    STATUS      current
    DESCRIPTION
        "The value of tmnxMcPathChlSrcVdoTncPcrRep specifies the value of
         TNC (Tech Non-Conformant) in milli-seconds for PCR repitition and 
         should always be a multiple of 100."
    DEFVAL { 100 } 
    ::= { tmnxMcPathChlSrcExtEntry 9 }

tmnxMcPathChlSrcVdoQosPcrRep        OBJECT-TYPE
    SYNTAX      Unsigned32 (200..900)
    UNITS       "milliseconds"
    MAX-ACCESS  read-create
    STATUS      current
    DESCRIPTION
        "The value of tmnxMcPathChlSrcVdoQosPcrRep specifies the value of
         QOS (Quality of Service) in milli-seconds for PCR repitition and should 
         always be a multiple of 100. The value of 
         'tmnxMcPathChlSrcVdoQosPcrRep' must also be greater than the value of 
         'tmnxMcPathChlSrcVdoTncPcrRep'."
    DEFVAL { 200 } 
    ::= { tmnxMcPathChlSrcExtEntry 10 }

tmnxMcPathChlSrcVdoPoaPcrRep        OBJECT-TYPE
    SYNTAX      Unsigned32 (300..1000)
    UNITS       "milliseconds"
    MAX-ACCESS  read-create
    STATUS      current
    DESCRIPTION
        "The value of tmnxMcPathChlSrcVdoPoaPcrRep specifies the value of
         POA (Program off Air) in milli-seconds for PAT repitition and should 
         always be a multiple of 100. The value of 
         'tmnxMcPathChlSrcVdoPoaPcrRep' must also be greater than the value of 
         'tmnxMcPathChlSrcVdoQosPcrRep'."
    DEFVAL { 500 } 
    ::= { tmnxMcPathChlSrcExtEntry 11 }

tmnxMcPathChlSrcVdoVidPIDAbs        OBJECT-TYPE
    SYNTAX      Unsigned32 (0..5000)
    UNITS       "milliseconds"
    MAX-ACCESS  read-create
    STATUS      current
    DESCRIPTION
        "The value of tmnxMcPathChlSrcVdoVidPIDAbs specifies the counting 
         interval for 'TIMETRA-VIDEO-MIB::tmnxVdoPIDAbsentErrSecs' which 
         accumulates the number of video PID absent errors for the video PID 
         stream. It has a default value of 0 which means no error counting. Its 
         value can only be changed by increments or decrements of 100 
         milliseconds otherwise a 'wrongValue' error is returned."
    DEFVAL { 0 } 
    ::= { tmnxMcPathChlSrcExtEntry 12 }

tmnxMcPathChlSrcVdoPIDPmtUnref        OBJECT-TYPE
    SYNTAX      TruthValue
    MAX-ACCESS  read-create
    STATUS      current
    DESCRIPTION
        "The value of tmnxMcPathChlSrcVdoPIDPmtUnref specifies whether or not 
         unreferenced PID (i.e. PIDs not specified in the PMT) error is enabled 
         for the video stream."
    DEFVAL { false } 
    ::= { tmnxMcPathChlSrcExtEntry 13 }

tmnxMcPathChlSrcVdoPmtRepError        OBJECT-TYPE
    SYNTAX      TruthValue
    MAX-ACCESS  read-create
    STATUS      current
    DESCRIPTION
        "The value of tmnxMcPathChlSrcVdoPmtRepError specifies whether or not
         PMT (Program Map Table) repetition error is enabled for the 
         video stream."
    DEFVAL { false } 
    ::= { tmnxMcPathChlSrcExtEntry 14 }

tmnxMcPathChlSrcVdoTncPmtRep        OBJECT-TYPE
    SYNTAX      Unsigned32 (100..4800)
    UNITS       "milliseconds"
    MAX-ACCESS  read-create
    STATUS      current
    DESCRIPTION
        "The value of tmnxMcPathChlSrcVdoTncPmtRep specifies the value of
         TNC (Tech Non-Conformance) in milli-seconds for PMT repitition and 
         should always be a multiple of 100."
    DEFVAL { 400 } 
    ::= { tmnxMcPathChlSrcExtEntry 15 }

tmnxMcPathChlSrcVdoQosPmtRep        OBJECT-TYPE
    SYNTAX      Unsigned32 (200..4900)
    UNITS       "milliseconds"
    MAX-ACCESS  read-create
    STATUS      current
    DESCRIPTION
        "The value of tmnxMcPathChlSrcVdoQosPmtRep specifies the value of
         QOS (Quality of Service) in milli-seconds for PMT repitition and should 
         always be a multiple of 100. The value of 
         'tmnxMcPathChlSrcVdoQosPmtRep' must also be greater than the value of 
         'tmnxMcPathChlSrcVdoTncPmtRep'."
    DEFVAL { 800 } 
    ::= { tmnxMcPathChlSrcExtEntry 16 }

tmnxMcPathChlSrcVdoPoaPmtRep        OBJECT-TYPE
    SYNTAX      Unsigned32 (300..5000)
    UNITS       "milliseconds"
    MAX-ACCESS  read-create
    STATUS      current
    DESCRIPTION
        "The value of tmnxMcPathChlSrcVdoPoaPmtRep specifies the value of
         POA (Program off Air) in milli-seconds for PMT repitition and should 
         always be a multiple of 100. The value of 
         'tmnxMcPathChlSrcVdoPoaPmtRep' must also be greater than the value of 
         'tmnxMcPathChlSrcVdoQosPmtRep'."
    DEFVAL { 2000 } 
    ::= { tmnxMcPathChlSrcExtEntry 17 }

tmnxMcPathChlSrcVdoPmtSyntax        OBJECT-TYPE
    SYNTAX      TruthValue
    MAX-ACCESS  read-create
    STATUS      current
    DESCRIPTION
        "The value of tmnxMcPathChlSrcVdoPmtSyntax specifies whether or not
         PMT syntax error is enabled for the video stream."
    DEFVAL { false } 
    ::= { tmnxMcPathChlSrcExtEntry 18 }

tmnxMcPathChlSrcVdoScte35Error        OBJECT-TYPE
    SYNTAX      TruthValue
    MAX-ACCESS  read-create
    STATUS      obsolete
    DESCRIPTION
        "The value of tmnxMcPathChlSrcVdoScte35Error specifies whether or not
         SCTE35 (Society of Cable Telecommunications Engineers) errors
         are enabled for the video stream.

         This object was obsoleted in the 9.0 release."
    DEFVAL { false } 
    ::= { tmnxMcPathChlSrcExtEntry 19 }

tmnxMcPathChlSrcVdoTeiError        OBJECT-TYPE
    SYNTAX      TruthValue
    MAX-ACCESS  read-create
    STATUS      current
    DESCRIPTION
        "The value of tmnxMcPathChlSrcVdoTeiError specifies whether or not TEI
        (Transport Error Indicator) error is enabled for the video stream."
    DEFVAL { false } 
    ::= { tmnxMcPathChlSrcExtEntry 20 }

tmnxMcPathChlSrcVdoTsSyncLoss        OBJECT-TYPE
    SYNTAX      TruthValue
    MAX-ACCESS  read-create
    STATUS      current
    DESCRIPTION
        "The value of tmnxMcPathChlSrcVdoTsSyncLoss specifies whether or not sync 
         loss error is enabled for the video stream."
    DEFVAL { false } 
    ::= { tmnxMcPathChlSrcExtEntry 21 }

tmnxMcPathChlSrcVdoNonVidPIDAbs        OBJECT-TYPE
    SYNTAX      Unsigned32 (0..5000)
    UNITS       "milliseconds"
    MAX-ACCESS  read-create
    STATUS      current
    DESCRIPTION
        "The value of tmnxMcPathChlSrcVdoNonVidPIDAbs specifies the counting 
         interval for 'TIMETRA-VIDEO-MIB::tmnxVdoPIDAbsentErrSecs' which 
         accumulates the number of non-video PID absent errors for the video 
         PID stream. It has a default value of 0 which means no error counting. 
         Its value can only be changed by increments or decrements of 100 
         milliseconds otherwise a 'wrongValue' error is returned."
    DEFVAL { 0 } 
    ::= { tmnxMcPathChlSrcExtEntry 22 }

tmnxMcPathChlSrcVdoReportAlarm        OBJECT-TYPE
    SYNTAX      TmnxVdoAnalyzerAlarm
    MAX-ACCESS  read-create
    STATUS      current
    DESCRIPTION
        "The value of tmnxMcPathChlSrcVdoReportAlarm specifies the severity of 
         the analyzer state alarm for the video stream."
    DEFVAL { none } 
    ::= { tmnxMcPathChlSrcExtEntry 23 }

-- ------------------------------------------------
-- multicast reporting destinations table
-- ------------------------------------------------

tmnxMcPathRprtDestTblLastChanged OBJECT-TYPE
    SYNTAX      TimeStamp
    MAX-ACCESS  read-only
    STATUS      current
    DESCRIPTION
        "The value of tmnxMcPathRprtDestTblLastChanged indicates the sysUpTime 
         at the time of the last modification to tmnxMcPathRprtDestTable by 
         adding, deleting an entry or change to a writable object in the table.

         If no changes were made to the table since the last re-initialization 
         of the local network management subsystem, then this object contains a 
         zero value."
    ::= { tmnxMcPathGlobalObjs 11 } 

tmnxMcPathRprtDestTable OBJECT-TYPE
    SYNTAX      SEQUENCE OF TmnxMcPathRprtDestEntry
    MAX-ACCESS  not-accessible
    STATUS      current
    DESCRIPTION
        "The tmnxMcPathRprtDestTable has an entry for each multicast reporting
         destination configured on this system."
    ::= { tmnxMcPathObjs 19 }

tmnxMcPathRprtDestEntry    OBJECT-TYPE
    SYNTAX      TmnxMcPathRprtDestEntry
    MAX-ACCESS  not-accessible
    STATUS      current
    DESCRIPTION
        "Each row entry represents a particular multicast reporting destination.
         Entries are created/deleted by the user."
    INDEX { tmnxMcPathRprtDestName }
    ::= { tmnxMcPathRprtDestTable 1 }

TmnxMcPathRprtDestEntry ::= SEQUENCE
   {
       tmnxMcPathRprtDestName             TNamedItem,
       tmnxMcPathRprtDestRowStatus        RowStatus,
       tmnxMcPathRprtDestLastChanged      TimeStamp,
       tmnxMcPathRprtDestDescription      TItemDescription,
       tmnxMcPathRprtDestAddrType         InetAddressType,
       tmnxMcPathRprtDestAddress          InetAddress,
       tmnxMcPathRprtDestUdpDstPort       InetPortNumber,
       tmnxMcPathRprtDestMaxTxDelay       Unsigned32,
       tmnxMcPathRprtDestAdminState       TmnxAdminState,
       
       tmnxMcPathRprtDestFrmsSent         Unsigned32,
       tmnxMcPathRprtDestFrmsLost         Unsigned32,
       tmnxMcPathRprtDestRecsSent         Unsigned32,
       tmnxMcPathRprtDestRecsLost         Unsigned32
   }

tmnxMcPathRprtDestName              OBJECT-TYPE
    SYNTAX      TNamedItem
    MAX-ACCESS  not-accessible
    STATUS      current
    DESCRIPTION
        "The value of tmnxMcPathRprtDestName indicates the name of the multicast 
         reporting destination."
    ::= { tmnxMcPathRprtDestEntry 1 }

tmnxMcPathRprtDestRowStatus       OBJECT-TYPE
    SYNTAX      RowStatus
    MAX-ACCESS  read-create
    STATUS      current
    DESCRIPTION
        "The value of tmnxMcPathRprtDestRowStatus is used for creation/deletion of
         multicast reporting destinations."
    ::= { tmnxMcPathRprtDestEntry 2 }

tmnxMcPathRprtDestLastChanged  OBJECT-TYPE
    SYNTAX      TimeStamp
    MAX-ACCESS  read-only
    STATUS      current
    DESCRIPTION
        "The value of tmnxMcPathRprtDestLastChanged indicates the timestamp of 
         last change to this row in tmnxMcPathRprtDestTable."
    ::= { tmnxMcPathRprtDestEntry 3 }

tmnxMcPathRprtDestDescription    OBJECT-TYPE
    SYNTAX      TItemDescription
    MAX-ACCESS  read-create
    STATUS      current
    DESCRIPTION
        "The value of tmnxMcPathRprtDestDescription specifies the textual 
         description of this multicast reporting destination."
    DEFVAL      { "" } 
    ::= { tmnxMcPathRprtDestEntry 4 }    

tmnxMcPathRprtDestAddrType          OBJECT-TYPE
    SYNTAX          InetAddressType
    MAX-ACCESS      read-create
    STATUS          current
    DESCRIPTION
        "The value of tmnxMcPathRprtDestAddrType specifies the address type
         of tmnxMcPathRprtDestAddress."
    DEFVAL { unknown }
    ::= { tmnxMcPathRprtDestEntry 5 }

tmnxMcPathRprtDestAddress           OBJECT-TYPE
    SYNTAX          InetAddress (SIZE(0|4|16))
    MAX-ACCESS      read-create
    STATUS          current
    DESCRIPTION
        "The value of tmnxMcPathRprtDestAddress specifies the IP address
         of the multicast reporting destination."
    DEFVAL { ''H }
    ::= { tmnxMcPathRprtDestEntry 6 }

tmnxMcPathRprtDestUdpDstPort    OBJECT-TYPE
    SYNTAX      InetPortNumber
    MAX-ACCESS  read-create
    STATUS      current
    DESCRIPTION
        "The value of tmnxMcPathRprtDestUdpDstPort specifies the UDP port
         at tmnxMcPathRprtDestAddress where to send multicast reports to."
    DEFVAL      { 1037 } 
    ::= { tmnxMcPathRprtDestEntry 7 }    

tmnxMcPathRprtDestMaxTxDelay    OBJECT-TYPE
    SYNTAX      Unsigned32 (0..100)
    UNITS       "deci-seconds"
    MAX-ACCESS  read-create
    STATUS      current
    DESCRIPTION
        "The value of tmnxMcPathRprtDestMaxTxDelay specifies the maximum 
         delay after which any cached reports will be flushed to the reporting
         destination. 
         
         A value of 0 means the reports will not be cached, thus every report
         will trigger an ougtoing message"
    DEFVAL      { 1 } 
    ::= { tmnxMcPathRprtDestEntry 8 }    

tmnxMcPathRprtDestAdminState OBJECT-TYPE
    SYNTAX          TmnxAdminState
    MAX-ACCESS      read-create
    STATUS          current
    DESCRIPTION
        "The value of tmnxMcPathRprtDestAdminState indicates the administrative
         state of the mcast reporting destination."
    DEFVAL { outOfService }
    ::= { tmnxMcPathRprtDestEntry 9 }

tmnxMcPathRprtDestFrmsSent OBJECT-TYPE
    SYNTAX      Unsigned32
    MAX-ACCESS  read-only
    STATUS      current
    DESCRIPTION
        "The value of tmnxMcPathRprtDestFrmsSent specifies the number of frames
         sent to this mcast reporting destination."
    DEFVAL      { 0 } 
    ::= { tmnxMcPathRprtDestEntry 10 }    

tmnxMcPathRprtDestFrmsLost OBJECT-TYPE
    SYNTAX      Unsigned32
    MAX-ACCESS  read-only
    STATUS      current
    DESCRIPTION
        "The value of tmnxMcPathRprtDestFrmsLost specifies the number of frames
         lost for this mcast reporting destination."
    DEFVAL      { 0 } 
    ::= { tmnxMcPathRprtDestEntry 11 }    

tmnxMcPathRprtDestRecsSent OBJECT-TYPE
    SYNTAX      Unsigned32
    MAX-ACCESS  read-only
    STATUS      current
    DESCRIPTION
        "The value of tmnxMcPathRprtDestRecsSent specifies the number of records
         sent to this mcast reporting destination."
    DEFVAL      { 0 } 
    ::= { tmnxMcPathRprtDestEntry 12 }    

tmnxMcPathRprtDestRecsLost OBJECT-TYPE
    SYNTAX      Unsigned32
    MAX-ACCESS  read-only
    STATUS      current
    DESCRIPTION
        "The value of tmnxMcPathRprtDestRecsLost specifies the number of records
         lost for this mcast reporting destination."
    DEFVAL      { 0 } 
    ::= { tmnxMcPathRprtDestEntry 13 }    


--
-- Notification Control Objects section
--

tmnxMcPathChlGrpAddrType   OBJECT-TYPE
    SYNTAX      InetAddressType
    MAX-ACCESS  accessible-for-notify
    STATUS      current
    DESCRIPTION
        "The value of tmnxMcPathChlGrpAddrType indicates the address type 
         of tmnxMcPathChlGrpAddr."
    ::= { tmnxMcPathNotifyObjs 1 }

tmnxMcPathChlGrpAddr         OBJECT-TYPE
    SYNTAX      InetAddress (SIZE (4|16|20))
    MAX-ACCESS  accessible-for-notify
    STATUS      current
    DESCRIPTION
        "The value of tmnxMcPathChlGrpAddr indicates the group address of the 
         multicast channel. Its type is specified by tmnxMcPathChlGrpAddrType."
    ::= { tmnxMcPathNotifyObjs 2 }

tmnxMcPathChlSrcAddrType   OBJECT-TYPE
    SYNTAX      InetAddressType
    MAX-ACCESS  accessible-for-notify
    STATUS      current
    DESCRIPTION
        "The value of tmnxMcPathChlSrcAddrType indicates the address type 
         of tmnxMcPathChlSrcAddr."
    ::= { tmnxMcPathNotifyObjs 3 }

tmnxMcPathChlSrcAddr         OBJECT-TYPE
    SYNTAX      InetAddress (SIZE (4|16|20))
    MAX-ACCESS  accessible-for-notify
    STATUS      current
    DESCRIPTION
        "The value of tmnxMcPathChlSrcAddr indicates the source address of the 
         multicast channel. Its type is specified by tmnxMcPathChlSrcAddrType."
    ::= { tmnxMcPathNotifyObjs 4 }

tmnxMcPathChlPathType         OBJECT-TYPE
    SYNTAX      TmnxMcPathChlSfPathTypeTc
    MAX-ACCESS  accessible-for-notify
    STATUS      current
    DESCRIPTION
        "The value of tmnxMcPathChlPathType indicates the path type for an 
         explicit ingress switch fabric multicast path assigned to a multicast 
         channel."
    ::= { tmnxMcPathNotifyObjs 5 }
             
tmnxMcPathChassisIndex    OBJECT-TYPE
    SYNTAX      TmnxChassisIndex
    MAX-ACCESS  accessible-for-notify
    STATUS      current
    DESCRIPTION
        "The unique value which identifies this chassis in the system. 
         The first release of the product only supports a single chassis 
         in the system."
    ::= { tmnxMcPathNotifyObjs 6 }  

tmnxMcPathCardSlotNum     OBJECT-TYPE
    SYNTAX      TmnxSlotNum
    MAX-ACCESS  accessible-for-notify
    STATUS      current
    DESCRIPTION
        "The unique value which identifies this IOM slot within a chassis 
         in the system."
    ::= { tmnxMcPathNotifyObjs 7 }

tmnxMcPathMDASlotNum     OBJECT-TYPE
    SYNTAX      Unsigned32 (0..16)
    MAX-ACCESS  accessible-for-notify
    STATUS      current
    DESCRIPTION
        "The unique value which identifies this MDA slot within a
         specific IOM card in the system.  Rows with a tmnxMDASlotNum
         value of zero (0) represent the special case of an IOM card
         without MDA slots but that instead has its ports directly
         on the IOM card itself.  In that case, there should be only
         that one row entry in the tmnxMDATable for that IOM card."
    ::= { tmnxMcPathNotifyObjs 8 }                           

tmnxMcPathChlRtrType  OBJECT-TYPE
    SYNTAX      TmnxMcPathRtrType
    MAX-ACCESS  accessible-for-notify
    STATUS      current
    DESCRIPTION
        "The value of tmnxMcPathChlRtrType specifies the type of virtual 
         router."
    ::= { tmnxMcPathNotifyObjs 9 }

--
-- Notification Definition section
--

tmnxMcPathSrcGrpBlkHole NOTIFICATION-TYPE
    OBJECTS { tmnxMcPathChlGrpAddrType,
              tmnxMcPathChlGrpAddr,
              tmnxMcPathChlSrcAddrType,
              tmnxMcPathChlSrcAddr,
              tmnxMcPathChlRtrType,
              vRtrID,
              tmnxMcPathChassisIndex,
              tmnxMcPathCardSlotNum, 
              tmnxMcPathMDASlotNum              
               }
    STATUS     current
    DESCRIPTION
        "The tmnxMcPathSrcGrpBlkHole event is generated whenever a source, 
         group(S,G) goes into a black-hole state."
    ::= { tmnxMcPathNotifications 1 }

tmnxMcPathSrcGrpBlkHoleClear NOTIFICATION-TYPE
    OBJECTS { tmnxMcPathChlGrpAddrType,
              tmnxMcPathChlGrpAddr,
              tmnxMcPathChlSrcAddrType,
              tmnxMcPathChlSrcAddr,
              tmnxMcPathChlRtrType,
              vRtrID,
              tmnxMcPathChassisIndex,
              tmnxMcPathCardSlotNum, 
              tmnxMcPathMDASlotNum   
             }
    STATUS     current
    DESCRIPTION
        "The tmnxMcPathSrcGrpBlkHoleClear event is generated whenever a source, 
         group(S,G) comes out of black-hole state."
    ::= { tmnxMcPathNotifications 2 }

tmnxMcPathAvailBwLimitReached NOTIFICATION-TYPE
    OBJECTS { tmnxMcPathChassisIndex,
              tmnxMcPathCardSlotNum, 
              tmnxMcPathMDASlotNum,
              tmnxMcPathChlPathType
              }
    STATUS     current
    DESCRIPTION
        "The tmnxMcPathAvailBwLimitReached event is generated when the available
         bandwidth limit has reached."
    ::= { tmnxMcPathNotifications 3 }

tmnxMcPathAvailBwValWithinRange NOTIFICATION-TYPE
    OBJECTS { tmnxMcPathChassisIndex,
              tmnxMcPathCardSlotNum, 
              tmnxMcPathMDASlotNum,
              tmnxMcPathChlPathType
             }
    STATUS     current
    DESCRIPTION
        "The tmnxMcPathAvailBwValWithinRange event is generated when the 
         available bandwidth limit falls below the maximum limit and is within
         the permitted range."
    ::= { tmnxMcPathNotifications 4 }

-- ----------------------------------------------
-- Compliance Statements
-- ----------------------------------------------

tmnxMcPathV6v0Compliance   MODULE-COMPLIANCE
    STATUS      obsolete
    DESCRIPTION
        "The compliance statement for management of multicast management 
         policies on version 6.0 of the Alcatel-Lucent SROS series systems."
    MODULE      --this module
        MANDATORY-GROUPS {
            tmnxMcPathGlobalGroup,
            tmnxMcPathPlcyV6v0Group,
            tmnxMcPathBdlV6v0Group,
            tmnxMcPathBdlChlV6v0Group,
            tmnxMcPathChlSrcV6v0Group,
            tmnxMcPathOperChlV6v0Group,
            tmnxMcPathNotificationGroup
        }
    ::= { tmnxMcPathCompliances 1 }

tmnxMcPath7x50V6v1Compliance   MODULE-COMPLIANCE
    STATUS      obsolete
    DESCRIPTION
        "The compliance statement for management of multicast management 
         policies on version 6.1 of the Alcatel-Lucent SROS series systems."
    MODULE      --this module
        MANDATORY-GROUPS {
            tmnxMcPathGlobalGroup,
            tmnxMcPathPlcyV6v0Group,
            tmnxMcPathBdlV6v0Group,
            tmnxMcPathBdlChlV6v0Group,
            tmnxMcPathChlSrcV6v0Group,
            tmnxMcPathOperChlV6v0Group,
            tmnxMcPathNotificationGroup,
            tmnxMcPathGlobalV6v1Group,
            tmnxMcPathPlcyV6v1Group,
            tmnxMcPathGlobalExtV6v1Group
        }
    ::= { tmnxMcPathCompliances 2 }

tmnxMcPath7710V6v1Compliance   MODULE-COMPLIANCE
    STATUS      current
    DESCRIPTION
        "The compliance statement for management of multicast management 
         policies on version 6.1 of the Alcatel-Lucent 7710 series systems."
    MODULE      --this module
        MANDATORY-GROUPS {
            tmnxMcPathGlobalGroup,
            tmnxMcPathPlcyV6v0Group,
            tmnxMcPathBdlV6v0Group,
            tmnxMcPathBdlChlV6v0Group,
            tmnxMcPathChlSrcV6v0Group,
            tmnxMcPathOperChlV6v0Group,
            tmnxMcPathNotificationGroup
        }
    ::= { tmnxMcPathCompliances 3 }

tmnxMcPath7x50V7v0Compliance   MODULE-COMPLIANCE
    STATUS     obsolete 
    DESCRIPTION
        "The compliance statement for management of multicast management 
         policies on version 7.0 of the Alcatel-Lucent SROS series systems."
    MODULE      --this module
        MANDATORY-GROUPS {
            tmnxMcPathGlobalGroup,
            tmnxMcPathPlcyV6v0Group,
            tmnxMcPathBdlV6v0Group,
            tmnxMcPathBdlChlV6v0Group,
            tmnxMcPathChlSrcV6v0Group,
            tmnxMcPathOperChlV6v0Group,
            tmnxMcPathNotificationGroup,
            tmnxMcPathGlobalV6v1Group,
            tmnxMcPathPlcyV6v1Group,
            tmnxMcPathVdoV7v0Group,
            tmnxMcPathTunnelIfV7v0Group,
            tmnxMcPathGlobalV7v0Group,
            tmnxMcPathGlobalExtV6v1Group
        }
    ::= { tmnxMcPathCompliances 4 }

tmnxMcPathV8v0Compliance   MODULE-COMPLIANCE
    STATUS      obsolete
    DESCRIPTION
        "The compliance statement for management of multicast management 
         policies on version 8.0 of the Alcatel-Lucent SROS series systems."
    MODULE      --this module
        MANDATORY-GROUPS {
            tmnxMcPathGlobalGroup,
            tmnxMcPathPlcyV6v0Group,
            tmnxMcPathBdlV6v0Group,
            tmnxMcPathBdlChlV6v0Group,
            tmnxMcPathChlSrcV6v0Group,
            tmnxMcPathOperChlV6v0Group,
            tmnxMcPathNotificationGroup,
            tmnxMcPathGlobalV6v1Group,
            tmnxMcPathPlcyV6v1Group,
            tmnxMcPathVdoV7v0Group,
            tmnxMcPathTunnelIfV7v0Group,
            tmnxMcPathGlobalV7v0Group,
            tmnxMcPathGlobalExtV6v1Group,
            tmnxMcPathGlobalV8v0Group,
            tmnxMcPathVdoV8v0Group
        }
    ::= { tmnxMcPathCompliances 5 }

tmnxMcPathV9v0Compliance   MODULE-COMPLIANCE
    STATUS      obsolete
    DESCRIPTION
        "The compliance statement for management of multicast management 
         policies on version 9.0 of the Alcatel-Lucent SROS series systems."
    MODULE      --this module
        MANDATORY-GROUPS {
            tmnxMcPathGlobalGroup,
            tmnxMcPathPlcyV6v0Group,
            tmnxMcPathBdlV6v0Group,
            tmnxMcPathBdlChlV6v0Group,
            tmnxMcPathChlSrcV6v0Group,
            tmnxMcPathOperChlV6v0Group,
            tmnxMcPathSwPlaneGroup,
            tmnxMcPathNotificationGroup,
            tmnxMcPathGlobalV6v1Group,
            tmnxMcPathPlcyV6v1Group,
            tmnxMcPathVdoV7v0Group,
            tmnxMcPathTunnelIfV7v0Group,
            tmnxMcPathGlobalV7v0Group,
            tmnxMcPathGlobalExtV6v1Group,
            tmnxMcPathGlobalV8v0Group,
            tmnxMcPathVdoV9v0Group,
            tmnxMcPathGlobalV9v0Group,
            tmnxMcPathRprtDestV9v0Group
        }
    ::= { tmnxMcPathCompliances 6 }

tmnxMcPathV10v0Compliance   MODULE-COMPLIANCE
    STATUS      current
    DESCRIPTION
        "The compliance statement for management of multicast management 
         policies on version 10.0 of the Alcatel-Lucent SROS series systems."
    MODULE      --this module
        MANDATORY-GROUPS {
            tmnxMcPathGlobalGroup,
            tmnxMcPathPlcyV6v0Group,
            tmnxMcPathBdlV6v0Group,
            tmnxMcPathBdlChlV6v0Group,
            tmnxMcPathChlSrcV6v0Group,
            tmnxMcPathOperChlV6v0Group,
            tmnxMcPathSwPlaneGroup,
            tmnxMcPathNotificationGroup,
            tmnxMcPathGlobalV6v1Group,
            tmnxMcPathPlcyV6v1Group,
            tmnxMcPathVdoV7v0Group,
            tmnxMcPathTunnelIfV7v0Group,
            tmnxMcPathGlobalV7v0Group,
            tmnxMcPathGlobalExtV6v1Group,
            tmnxMcPathGlobalV8v0Group,
            tmnxMcPathVdoV9v0Group,
            tmnxMcPathGlobalV9v0Group,
            tmnxMcPathRprtDestV9v0Group,
            tmnxMcPathGlobalV10v0Group
        }
    ::= { tmnxMcPathCompliances 7 }
    
-- ----------------------------------------------
-- Units of Conformance
-- ----------------------------------------------

tmnxMcPathGlobalGroup   OBJECT-GROUP
    OBJECTS {   
                 tmnxMcPathBwPlcyTableLastChanged,
                 tmnxMcPathBwPlcyLastChanged,
                 tmnxMcPathPlcyTableLastChanged,
                 tmnxMcPathPlcyLastChanged,
                 tmnxMcPathBdlTableLastChanged,
                 tmnxMcPathBdlLastChanged,
                 tmnxMcPathBdlChlTblLastChanged,
                 tmnxMcPathBdlChlLastChanged,
                 tmnxMcPathChlSrcTableLastChanged,
                 tmnxMcPathChlSrcLastChanged              
            }
    STATUS      current
    DESCRIPTION
        "The group of objects supporting management of global objects related to
         multicast path management information on version 6.0 of the 
         Alcatel-Lucent SROS series systems."
    ::= { tmnxMcPathGroups 1 }

tmnxMcPathPlcyV6v0Group       OBJECT-GROUP
    OBJECTS {
             tmnxMcPathBwPlcyRowStatus,
             tmnxMcPathBwPlcyDescription,
             tmnxMcPathBwPlcyFallPercentReset,
             tmnxMcPathBwPlcyAdminBwThd,
             tmnxMcPathBwPlcyMcPoolPercentTot, 
             tmnxMcPathBwPlcyMcPoolResvCbs, 
             tmnxMcPathBwPlcyMcPoolSlopePlcy,
             tmnxMcPathBwPlcyPathLimit,
             tmnxMcPathBwPlcyPathCbs,
             tmnxMcPathBwPlcyPathMbs,
             tmnxMcPathBwPlcyPathHighPrio,
             tmnxMcPathPlcyRowStatus,
             tmnxMcPathPlcyDescription
             }
    STATUS      current
    DESCRIPTION
        "The group of objects supporting multicast path management information 
         on version 6.0 of the Alcatel-Lucent SROS series systems."
    ::= { tmnxMcPathGroups 2 }


tmnxMcPathBdlV6v0Group       OBJECT-GROUP
    OBJECTS {
             tmnxMcPathBdlStatus,
             tmnxMcPathBdlDescription,
             tmnxMcPathBdlCongPriorityThd,
             tmnxMcPathBdlEcmpOptThd,
             tmnxMcPathBdlDefChlAdminBw,
             tmnxMcPathBdlDefChlPref,
             tmnxMcPathBdlDefChlBwActivity,
             tmnxMcPathBdlDefChlBwFallDelay,
             tmnxMcPathBdlDefChlBwBlackHoleRt,
             tmnxMcPathBdlDefChlExSfPath
             }
    STATUS      current
    DESCRIPTION
        "The group of objects supporting multicast path management information 
         for bundles on version 6.0 of the Alcatel-Lucent SROS series systems."
    ::= { tmnxMcPathGroups 3 }


tmnxMcPathBdlChlV6v0Group       OBJECT-GROUP
    OBJECTS {
             tmnxMcPathBdlChlRowStatus,
             tmnxMcPathBdlChlAdminBw,
             tmnxMcPathBdlChlPref,
             tmnxMcPathBdlChlBwActivity,
             tmnxMcPathBdlChlBwFallDelay,
             tmnxMcPathBdlChlBwBlackHoleRt,
             tmnxMcPathBdlChlExSfPath
            }
    STATUS      current
    DESCRIPTION
        "The group of objects supporting multicast path management information 
         for bundle channels on version 6.0 of the Alcatel-Lucent SROS series 
         systems."
    ::= { tmnxMcPathGroups 4 }


tmnxMcPathChlSrcV6v0Group       OBJECT-GROUP
    OBJECTS {
             tmnxMcPathChlSrcRowStatus,
             tmnxMcPathChlSrcAdminBw,
             tmnxMcPathChlSrcPref,
             tmnxMcPathChlSrcBwActivity,
             tmnxMcPathChlSrcBwFallDelay,
             tmnxMcPathChlSrcBwBlackHoleRt,
             tmnxMcPathChlSrcExSfPath
        }
    STATUS      current
    DESCRIPTION
        "The group of objects supporting multicast path management information 
         for channel sources which override multicast channel parameters 
         on version 6.0 of the Alcatel-Lucent SROS series systems."
    ::= { tmnxMcPathGroups 5 }

tmnxMcPathOperChlV6v0Group       OBJECT-GROUP
    OBJECTS {
            tmnxMcPathOperChlBandwidth,
            tmnxMcPathOperChlCurrentPath,
            tmnxMcPathOperChlExplicit,
            tmnxMcPathOperChlAdminBw,
            tmnxMcPathOperChlPref,
            tmnxMcPathOperChlBwBlackHole,
            tmnxMcPathOperChlBwBlackHoleRt,
            tmnxMcPathOperChlIngLastHighest,
            tmnxMcPathOperChlIngSecHighest,
            tmnxMcPathOperChlTimeRemaining,
            tmnxMcPathMdaOperChlBandwidth,
            tmnxMcPathMdaOperChlCurrentPath,
            tmnxMcPathMdaOperChlExplicit,
            tmnxMcPathMdaOperChlAdminBw,
            tmnxMcPathMdaOperChlPref,
            tmnxMcPathMdaOperChlBwBlackHole,
            tmnxMcPathMdaOperChlBwBlackHoleRt,
            tmnxMcPathMdaOperChlIngLastHigh,
            tmnxMcPathMdaOperChlIngSecHigh,
            tmnxMcPathMdaOperChlTimeRemain            
        }
    STATUS      current
    DESCRIPTION
        "The group of operational objects supporting multicast policy management
         on version 6.0 of the Alcatel-Lucent SROS series systems"
    ::= { tmnxMcPathGroups 6 }

tmnxMcPathNotificationGroup NOTIFICATION-GROUP
    NOTIFICATIONS {
        tmnxMcPathSrcGrpBlkHole,
        tmnxMcPathSrcGrpBlkHoleClear,
        tmnxMcPathAvailBwLimitReached,
        tmnxMcPathAvailBwValWithinRange
    }
    STATUS    current
    DESCRIPTION
        "The group of notifications supporting the multicast policy management 
         on Alcatel-Lucent SROS SR series systems."
    ::= { tmnxMcPathGroups 7 }

tmnxMcPathNotifyObjsGroup OBJECT-GROUP
   OBJECTS {
            tmnxMcPathChlGrpAddrType,
            tmnxMcPathChlGrpAddr,
            tmnxMcPathChlSrcAddrType,
            tmnxMcPathChlSrcAddr,
            tmnxMcPathChlPathType,
            tmnxMcPathChassisIndex,
            tmnxMcPathCardSlotNum,
            tmnxMcPathMDASlotNum,
            tmnxMcPathChlRtrType
    }
   STATUS    current
   DESCRIPTION
       "The group of objects used by notifications supporting the multicast 
        policy management on Alcatel-Lucent SROS series systems."
   ::= { tmnxMcPathGroups 8 }

tmnxMcPathGlobalV6v1Group   OBJECT-GROUP
    OBJECTS {   
                tmnxMcPathChassisPlaneLimit,
                tmnxMcPathChassisSecPlaneLimit,
                tmnxMcPathChassisDualPlaneLimit,
                tmnxMcPathChassisDualSecPlaneLmt 
            }
    STATUS      current
    DESCRIPTION
        "The group of objects supporting management of global objects related to
         multicast path management information on version 6.1 of the 
         Alcatel-Lucent SROS series systems."
    ::= { tmnxMcPathGroups 9 }

tmnxMcPathPlcyV6v1Group       OBJECT-GROUP
    OBJECTS {
                tmnxMcPathBwPlcyT2PathCbs,
                tmnxMcPathBwPlcyT2PathMbs,
                tmnxMcPathBwPlcyT2PathHighPrio,
                tmnxMcPathBwPlcyT2PathPaths,
                tmnxMcPathBwPlcyT2PathDualPaths,
                tmnxMcPathBwPlcyT2PathLastChanged
             }
    STATUS      current
    DESCRIPTION
        "The group of objects supporting multicast path management information
         on version 6.1 of the Alcatel-Lucent SROS series systems."
    ::= { tmnxMcPathGroups 10 }

tmnxMcPathVdoV7v0Group      OBJECT-GROUP
    OBJECTS {
                tmnxMcPathBdlVdoFCCState,
                tmnxMcPathBdlVdoRTState,
                tmnxMcPathBdlVdoChlType,
                tmnxMcPathBdlVdoRTAddrType,
                tmnxMcPathBdlVdoRTAddress,
                tmnxMcPathBdlVdoRTPort,
                tmnxMcPathBdlVdoRTBufferSize,
                tmnxMcPathBdlVdoLocalRTPort,
                tmnxMcPathBdlVdoLocalFccPort,
                tmnxMcPathBdlVdoGroupId,
                tmnxMcPathBdlChlVdoFCCState,
                tmnxMcPathBdlChlVdoRTState,
                tmnxMcPathBdlChlVdoChlType,
                tmnxMcPathBdlChlVdoRTAddrType,
                tmnxMcPathBdlChlVdoRTAddress,
                tmnxMcPathBdlChlVdoRTPort,
                tmnxMcPathBdlChlVdoRTBufferSize,
                tmnxMcPathBdlChlVdoGroupId,
                tmnxMcPathChlSrcVdoFCCState,
                tmnxMcPathChlSrcVdoRTState,
                tmnxMcPathChlSrcVdoChlType,
                tmnxMcPathChlSrcVdoRTAddrType,
                tmnxMcPathChlSrcVdoRTAddress,
                tmnxMcPathChlSrcVdoRTPort,
                tmnxMcPathChlSrcVdoRTBufferSize,
                tmnxMcPathChlSrcVdoGroupId,
                tmnxMcPathVdoPlcyLclRTSvrState,
                tmnxMcPathVdoPlcyRTRate,
                tmnxMcPathVdoPlcySubBwLimit,
                tmnxMcPathVdoPlcyFCCSvrMode,
                tmnxMcPathVdoPlcyFCCBurst,
                tmnxMcPathVdoPlcyFCCMcHandover,
                tmnxMcPathVdoPlcyFCCDentThd,
                tmnxMcPathVdoPlcyRowStatus,
                tmnxMcPathVdoPlcyTblLastChanged,
                tmnxMcPathVdoPlcyLastChanged,
                tmnxMcPathBdlVdoLocalRTState,
                tmnxMcPathBdlChlVdoLocalRTState,
                tmnxMcPathChlSrcVdoLocalRTState,
                tmnxMcPathBdlVdoReorderAudio,
                tmnxMcPathBdlChlVdoReorderAudio,
                tmnxMcPathChlSrcVdoReorderAudio,
                tmnxMcPathBdlVdoFccMinDuration,
                tmnxMcPathBdlChlVdoFccMinDuratn,
                tmnxMcPathChlSrcVdoFccMinDuratn
            }
    STATUS      current
    DESCRIPTION
        "The group of objects supporting video multicast path management 
         information on version 7.0 of the Alcatel-Lucent SROS series systems."
    ::= { tmnxMcPathGroups 11 }

tmnxMcPathTunnelIfV7v0Group       OBJECT-GROUP
    OBJECTS {
                tmnxMcPathBdlTunnelIfLspName,
                tmnxMcPathBdlTunIfSdAddrType,
                tmnxMcPathBdlTunIfSdAddr,
                tmnxMcPathBdlChlTunnelIfLspName,
                tmnxMcPathBdlChlTunIfSdAddrType,
                tmnxMcPathBdlChlTunIfSdAddr,
                tmnxMcPathChlSrcTunnelIfLspName,
                tmnxMcPathChlSrcTunIfSdAddrType,
                tmnxMcPathChlSrcTunIfSdAddr
             }
    STATUS      current
    DESCRIPTION
        "The group of objects supporting tunnel interfaces related to multicast 
         path management information on version 7.0 of the Alcatel-Lucent SROS 
         series systems."
    ::= { tmnxMcPathGroups 12 }

tmnxMcPathGlobalV7v0Group       OBJECT-GROUP
    OBJECTS {
                tmnxMcPathChassisMmrpAdminMode,
                tmnxMcPathChassisMmrpOperMode              
            }
    STATUS      current
    DESCRIPTION
        "The group of objects supporting management of global objects related to
         multicast path management information on version 7.0 of the 
         Alcatel-Lucent SROS series systems."
    ::= { tmnxMcPathGroups 13 }

tmnxMcPathObsoleteV7v0Group OBJECT-GROUP
    OBJECTS {   
                tmnxMcPathBdlChlVdoLocalRTPort,
                tmnxMcPathBdlChlVdoLocalFccPort,
                tmnxMcPathChlSrcVdoLocalRTPort,
                tmnxMcPathChlSrcVdoLocalFccPort,
                tmnxMcPathBdlVdoSourcePort
            }
   STATUS       current
   DESCRIPTION
       "The group of objects which are obsoleted in version 7.0 of the 
        Alcatel-Lucent SROS series systems."
   ::= { tmnxMcPathGroups 14 }
    
tmnxMcPathGlobalV8v0Group       OBJECT-GROUP
    OBJECTS {
                tmnxMcPathBdlChlKAOverrideTimer,
                tmnxMcPathChlSrcKAOverrideTimer,
                tmnxMcPathBdlKAOverrideTimer,
                tmnxMcPathBdlP2MPId,
                tmnxMcPathBdlChlP2MPId,
                tmnxMcPathChlSrcP2MPId
            }
    STATUS      current
    DESCRIPTION
        "The group of objects supporting management of global objects related to
         multicast path management information on version 8.0 of the 
         Alcatel-Lucent SROS series systems."
    ::= { tmnxMcPathGroups 15 }

tmnxMcPathVdoV8v0Group      OBJECT-GROUP
    OBJECTS {
                tmnxMcPathVdoPlcyRTPayloadType,
                tmnxMcPathVdoPlcyMaxClntSessions,
                tmnxMcPathVdoPlcyMaxIgmpLatency,
                tmnxMcPathBdlVdoAnalyzer,
                tmnxMcPathBdlVdoAnalyzerDesc,
                tmnxMcPathBdlVdoStrSelSrc1Type,
                tmnxMcPathBdlVdoStrSelSrc1,
                tmnxMcPathBdlVdoStrSelIntf1,
                tmnxMcPathBdlVdoStrSelSrc2Type,
                tmnxMcPathBdlVdoStrSelSrc2,
                tmnxMcPathBdlVdoStrSelIntf2,
                tmnxMcPathBdlExtTableLastChgd,
                tmnxMcPathBdlVdoLastChanged,
                tmnxMcPathBdlVdoCcError,
                tmnxMcPathBdlVdoPatRepError,
                tmnxMcPathBdlVdoTncPatRep,
                tmnxMcPathBdlVdoQosPatRep,
                tmnxMcPathBdlVdoPoaPatRep,
                tmnxMcPathBdlVdoPatSyntax,
                tmnxMcPathBdlVdoPcrRepError,
                tmnxMcPathBdlVdoTncPcrRep,
                tmnxMcPathBdlVdoQosPcrRep,
                tmnxMcPathBdlVdoPoaPcrRep,
                tmnxMcPathBdlVdoVidPIDAbsent,
                tmnxMcPathBdlVdoPIDPmtUnref,
                tmnxMcPathBdlVdoPmtRepError,
                tmnxMcPathBdlVdoTncPmtRep,
                tmnxMcPathBdlVdoQosPmtRep,
                tmnxMcPathBdlVdoPoaPmtRep,
                tmnxMcPathBdlVdoPmtSyntax,
                tmnxMcPathBdlVdoScte35Error,
                tmnxMcPathBdlVdoTeiError,
                tmnxMcPathBdlVdoTsSyncLoss,
                tmnxMcPathBdlVdoNonVidPIDAbsent,
                tmnxMcPathBdlVdoReportAlarm,
                tmnxMcPathBdlChlVdoAnalyzer,         
                tmnxMcPathBdlChlVdoAnalyzerDesc,
                tmnxMcPathBdlChlVdoStrSelSrc1Typ,
                tmnxMcPathBdlChlVdoStrSelSrc1,
                tmnxMcPathBdlChlVdoStrSelIntf1,
                tmnxMcPathBdlChlVdoStrSelSrc2Typ,
                tmnxMcPathBdlChlVdoStrSelSrc2,
                tmnxMcPathBdlChlVdoStrSelIntf2,
                tmnxMcPathBdlChlExtTableLastChgd,
                tmnxMcPathBdlChlVdoLastChanged,
                tmnxMcPathBdlChlVdoCcError,
                tmnxMcPathBdlChlVdoPatRepError,
                tmnxMcPathBdlChlVdoTncPatRep,
                tmnxMcPathBdlChlVdoQosPatRep,
                tmnxMcPathBdlChlVdoPoaPatRep,
                tmnxMcPathBdlChlVdoPatSyntax,
                tmnxMcPathBdlChlVdoPcrRepError,
                tmnxMcPathBdlChlVdoTncPcrRep,
                tmnxMcPathBdlChlVdoQosPcrRep,
                tmnxMcPathBdlChlVdoPoaPcrRep,
                tmnxMcPathBdlChlVdoVidPIDAbs,
                tmnxMcPathBdlChlVdoPIDPmtUnref,
                tmnxMcPathBdlChlVdoPmtRepError,
                tmnxMcPathBdlChlVdoTncPmtRep,
                tmnxMcPathBdlChlVdoQosPmtRep,
                tmnxMcPathBdlChlVdoPoaPmtRep,
                tmnxMcPathBdlChlVdoPmtSyntax,
                tmnxMcPathBdlChlVdoScte35Error,
                tmnxMcPathBdlChlVdoTeiError,
                tmnxMcPathBdlChlVdoTsSyncLoss,
                tmnxMcPathBdlChlVdoNonVidPIDAbs,
                tmnxMcPathBdlChlVdoReportAlarm,
                tmnxMcPathChlSrcVdoAnalyzer,
                tmnxMcPathChlSrcVdoAnalyzerDesc,
                tmnxMcPathChlSrcVdoStSeSrc1Type,       
                tmnxMcPathChlSrcVdoStSeSrc1,
                tmnxMcPathChlSrcVdoStSeIntf1,
                tmnxMcPathChlSrcVdoStSeSrc2Type,
                tmnxMcPathChlSrcVdoStSeSrc2,
                tmnxMcPathChlSrcVdoStSeIntf2,
                tmnxMcPathChlSrcExtTableLastChgd,
                tmnxMcPathChlSrcVdoLastChanged,
                tmnxMcPathChlSrcVdoCcError,
                tmnxMcPathChlSrcVdoPatRepError,
                tmnxMcPathChlSrcVdoTncPatRep,
                tmnxMcPathChlSrcVdoQosPatRep,
                tmnxMcPathChlSrcVdoPoaPatRep,
                tmnxMcPathChlSrcVdoPatSyntax,
                tmnxMcPathChlSrcVdoPcrRepError,
                tmnxMcPathChlSrcVdoTncPcrRep,
                tmnxMcPathChlSrcVdoQosPcrRep,          
                tmnxMcPathChlSrcVdoPoaPcrRep,          
                tmnxMcPathChlSrcVdoVidPIDAbs,          
                tmnxMcPathChlSrcVdoPIDPmtUnref,        
                tmnxMcPathChlSrcVdoPmtRepError,        
                tmnxMcPathChlSrcVdoTncPmtRep,          
                tmnxMcPathChlSrcVdoQosPmtRep,          
                tmnxMcPathChlSrcVdoPoaPmtRep,         
                tmnxMcPathChlSrcVdoPmtSyntax,        
                tmnxMcPathChlSrcVdoScte35Error,
                tmnxMcPathChlSrcVdoTeiError,
                tmnxMcPathChlSrcVdoTsSyncLoss,
                tmnxMcPathChlSrcVdoNonVidPIDAbs,
                tmnxMcPathChlSrcVdoReportAlarm                   
            }
    STATUS      obsolete
    DESCRIPTION
        "The group of objects supporting video multicast path management 
         information on version 8.0 of the Alcatel-Lucent SROS series systems."
    ::= { tmnxMcPathGroups 16 }

tmnxMcPathGlobalExtV6v1Group   OBJECT-GROUP
    OBJECTS {
                tmnxMcPathChassisRRInactiveRec
            }
    STATUS      current
    DESCRIPTION
        "The group of objects supporting management of global objects related to
         multicast path management information on version 6.1 of the 
         Alcatel-Lucent SROS series systems."
    ::= { tmnxMcPathGroups 17 }

tmnxMcPathGlobalV9v0Group       OBJECT-GROUP
    OBJECTS {
                tmnxMcPathRprtDestTblLastChanged
            }
    STATUS      current
    DESCRIPTION
        "The group of objects supporting management of global objects related to
         multicast path management information on version 9.0 of the 
         Alcatel-Lucent SROS series systems."
    ::= { tmnxMcPathGroups 18 }

tmnxMcPathRprtDestV9v0Group      OBJECT-GROUP
    OBJECTS {
        tmnxMcPathRprtDestRowStatus        ,
        tmnxMcPathRprtDestLastChanged      ,
        tmnxMcPathRprtDestDescription      ,
        tmnxMcPathRprtDestAddrType         ,
        tmnxMcPathRprtDestAddress          ,
        tmnxMcPathRprtDestUdpDstPort       ,
        tmnxMcPathRprtDestMaxTxDelay       ,
        tmnxMcPathRprtDestAdminState       ,
        tmnxMcPathRprtDestFrmsSent         ,
        tmnxMcPathRprtDestFrmsLost         ,
        tmnxMcPathRprtDestRecsSent         ,
        tmnxMcPathRprtDestRecsLost         
            }
    STATUS      current
    DESCRIPTION
        "The group of objects supporting multicast reporting on version 9.0 
         of the Alcatel-Lucent SROS series systems."
    ::= { tmnxMcPathGroups 19 }

tmnxMcPathVdoV9v0Group      OBJECT-GROUP
    OBJECTS {
                tmnxMcPathVdoPlcyRTPayloadType,
                tmnxMcPathVdoPlcyMaxClntSessions,
                tmnxMcPathVdoPlcyMaxIgmpLatency,
                tmnxMcPathBdlVdoAnalyzer,
                tmnxMcPathBdlVdoAnalyzerDesc,
                tmnxMcPathBdlVdoStrSelSrc1Type,
                tmnxMcPathBdlVdoStrSelSrc1,
                tmnxMcPathBdlVdoStrSelIntf1,
                tmnxMcPathBdlVdoStrSelSrc2Type,
                tmnxMcPathBdlVdoStrSelSrc2,
                tmnxMcPathBdlVdoStrSelIntf2,
                tmnxMcPathBdlExtTableLastChgd,
                tmnxMcPathBdlVdoLastChanged,
                tmnxMcPathBdlVdoCcError,
                tmnxMcPathBdlVdoPatRepError,
                tmnxMcPathBdlVdoTncPatRep,
                tmnxMcPathBdlVdoQosPatRep,
                tmnxMcPathBdlVdoPoaPatRep,
                tmnxMcPathBdlVdoPatSyntax,
                tmnxMcPathBdlVdoPcrRepError,
                tmnxMcPathBdlVdoTncPcrRep,
                tmnxMcPathBdlVdoQosPcrRep,
                tmnxMcPathBdlVdoPoaPcrRep,
                tmnxMcPathBdlVdoVidPIDAbsent,
                tmnxMcPathBdlVdoPIDPmtUnref,
                tmnxMcPathBdlVdoPmtRepError,
                tmnxMcPathBdlVdoTncPmtRep,
                tmnxMcPathBdlVdoQosPmtRep,
                tmnxMcPathBdlVdoPoaPmtRep,
                tmnxMcPathBdlVdoPmtSyntax,                
                tmnxMcPathBdlVdoTeiError,
                tmnxMcPathBdlVdoTsSyncLoss,
                tmnxMcPathBdlVdoNonVidPIDAbsent,
                tmnxMcPathBdlVdoReportAlarm,
                tmnxMcPathBdlChlVdoAnalyzer,         
                tmnxMcPathBdlChlVdoAnalyzerDesc,
                tmnxMcPathBdlChlVdoStrSelSrc1Typ,
                tmnxMcPathBdlChlVdoStrSelSrc1,
                tmnxMcPathBdlChlVdoStrSelIntf1,
                tmnxMcPathBdlChlVdoStrSelSrc2Typ,
                tmnxMcPathBdlChlVdoStrSelSrc2,
                tmnxMcPathBdlChlVdoStrSelIntf2,
                tmnxMcPathBdlChlExtTableLastChgd,
                tmnxMcPathBdlChlVdoLastChanged,
                tmnxMcPathBdlChlVdoCcError,
                tmnxMcPathBdlChlVdoPatRepError,
                tmnxMcPathBdlChlVdoTncPatRep,
                tmnxMcPathBdlChlVdoQosPatRep,
                tmnxMcPathBdlChlVdoPoaPatRep,
                tmnxMcPathBdlChlVdoPatSyntax,
                tmnxMcPathBdlChlVdoPcrRepError,
                tmnxMcPathBdlChlVdoTncPcrRep,
                tmnxMcPathBdlChlVdoQosPcrRep,
                tmnxMcPathBdlChlVdoPoaPcrRep,
                tmnxMcPathBdlChlVdoVidPIDAbs,
                tmnxMcPathBdlChlVdoPIDPmtUnref,
                tmnxMcPathBdlChlVdoPmtRepError,
                tmnxMcPathBdlChlVdoTncPmtRep,
                tmnxMcPathBdlChlVdoQosPmtRep,
                tmnxMcPathBdlChlVdoPoaPmtRep,
                tmnxMcPathBdlChlVdoPmtSyntax,                
                tmnxMcPathBdlChlVdoTeiError,
                tmnxMcPathBdlChlVdoTsSyncLoss,
                tmnxMcPathBdlChlVdoNonVidPIDAbs,
                tmnxMcPathBdlChlVdoReportAlarm,
                tmnxMcPathChlSrcVdoAnalyzer,
                tmnxMcPathChlSrcVdoAnalyzerDesc,
                tmnxMcPathChlSrcVdoStSeSrc1Type,       
                tmnxMcPathChlSrcVdoStSeSrc1,
                tmnxMcPathChlSrcVdoStSeIntf1,
                tmnxMcPathChlSrcVdoStSeSrc2Type,
                tmnxMcPathChlSrcVdoStSeSrc2,
                tmnxMcPathChlSrcVdoStSeIntf2,
                tmnxMcPathChlSrcExtTableLastChgd,
                tmnxMcPathChlSrcVdoLastChanged,
                tmnxMcPathChlSrcVdoCcError,
                tmnxMcPathChlSrcVdoPatRepError,
                tmnxMcPathChlSrcVdoTncPatRep,
                tmnxMcPathChlSrcVdoQosPatRep,
                tmnxMcPathChlSrcVdoPoaPatRep,
                tmnxMcPathChlSrcVdoPatSyntax,
                tmnxMcPathChlSrcVdoPcrRepError,
                tmnxMcPathChlSrcVdoTncPcrRep,
                tmnxMcPathChlSrcVdoQosPcrRep,          
                tmnxMcPathChlSrcVdoPoaPcrRep,          
                tmnxMcPathChlSrcVdoVidPIDAbs,          
                tmnxMcPathChlSrcVdoPIDPmtUnref,        
                tmnxMcPathChlSrcVdoPmtRepError,        
                tmnxMcPathChlSrcVdoTncPmtRep,          
                tmnxMcPathChlSrcVdoQosPmtRep,          
                tmnxMcPathChlSrcVdoPoaPmtRep,         
                tmnxMcPathChlSrcVdoPmtSyntax,                
                tmnxMcPathChlSrcVdoTeiError,
                tmnxMcPathChlSrcVdoTsSyncLoss,
                tmnxMcPathChlSrcVdoNonVidPIDAbs,
                tmnxMcPathChlSrcVdoReportAlarm                   
            }
    STATUS      current
    DESCRIPTION
        "The group of objects supporting video multicast path management 
         information on version 9.0 of the Alcatel-Lucent SROS series systems."
    ::= { tmnxMcPathGroups 20 }

tmnxMcPathVdoObsoletedV9v0Group      OBJECT-GROUP
    OBJECTS {
                tmnxMcPathBdlVdoScte35Error,
                tmnxMcPathBdlChlVdoScte35Error,
                tmnxMcPathChlSrcVdoScte35Error
            }
    STATUS      current
    DESCRIPTION
        "The group of objects obsoleted on version 9.0 of the Alcatel-Lucent 
         SROS series systems."
    ::= { tmnxMcPathGroups 21 }

tmnxMcPathSwPlaneGroup OBJECT-GROUP
    OBJECTS {
                tmnxMcPathOperChlCurrentPlane,
                tmnxMcPathMdaOperChlCurrentPlane            
            }
    STATUS      current
    DESCRIPTION
        "The group of objects supporting multicast policy management switch
         planes on the Alcatel-Lucent SROS series systems."
    ::= { tmnxMcPathGroups 22 }

tmnxMcPathGlobalV10v0Group   OBJECT-GROUP
    OBJECTS {   
                tmnxMcPathChassisPlnLimTotal,
                tmnxMcPathChassisPlnLimDynTotal,
                tmnxMcPathChassisPlnLimPriCap,
                tmnxMcPathChassisPlnLimSecCap,
                tmnxMcPathChassisPlnLimPriCapRed,
                tmnxMcPathChassisPlnLimSecCapRed
            }
    STATUS      current
    DESCRIPTION
        "The group of objects supporting management of global objects related to
         multicast path management information on version 10.0 of the 
         Alcatel-Lucent SROS series systems."
    ::= { tmnxMcPathGroups 23 }

END
