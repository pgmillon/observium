TIMETRA-SAS-ALARM-INPUT-MIB DEFINITIONS ::= BEGIN

   IMPORTS
     MODULE-IDENTITY, OBJECT-TYPE, TimeTicks, 
     NOTIFICATION-TYPE                        FROM SNMPv2-SMI

    MODULE-COMPLIANCE, OBJECT-GROUP,
    NOTIFICATION-GROUP                        FROM SNMPv2-CONF 
     
    TItemLongDescription                      FROM TIMETRA-TC-MIB
        
    timetraSASObjs, timetraSASNotifyPrefix, 
    timetraSASConfs, timetraSASModules
                                              FROM TIMETRA-SAS-GLOBAL-MIB;
          
    tmnxSasAlarmInputMIBModule MODULE-IDENTITY
        LAST-UPDATED "201004080000Z"
        ORGANIZATION "Alcatel-Lucent"
        CONTACT-INFO   

        "Alcatel 7x50 Support
         Web: http://www.alcatel.com/comps/pages/carrier_support.jhtml"


        DESCRIPTION
        "This  document  is the SNMP MIB module to manage and provision
        the various services of the Alcatel 7x50 SR system.

        Copyright  2003-2013 Alcatel-Lucent. All rights reserved. Reproduction
        of  this  document  is  authorized  on  the  condition that the
        foregoing copyright notice is included.

        This   SNMP   MIB  module  (Specification)  embodies  Alcatel's
        proprietary  intellectual  property.  Alcatel retains all title
        and ownership in the Specification, including any revisions.

        Alcatel  grants  all interested parties a non-exclusive license
        to  use and distribute an unmodified copy of this Specification
        in  connection with management of Alcatel products, and without
        fee,  provided  this copyright notice and license appear on all
        copies.

        This  Specification  is  supplied `as is', and Alcatel makes no
        warranty,  either express or implied, as to the use, operation,
        condition, or performance of the Specification."
        
-- --------------------------------------------------------------------
--  Revision History
-- --------------------------------------------------------------------
        REVISION     "201004080000Z"
        DESCRIPTION     "Rev 2.0                08 Apr 2010 00:00
                     2.0 release of the TIMETRA-SAS-ALARM-INPUT-MIB."
         
       ::= { timetraSASModules 10 }


-- --------------------------------------------------------------------
--      TIMETRA-SAS-ALARM-INPUT-MIB organisation
-- --------------------------------------------------------------------

tmnxSasAlarmInputObjs           OBJECT IDENTIFIER ::= { timetraSASObjs 9 }
tmnxSasAlarmInputNotifyObjs     OBJECT IDENTIFIER ::= { timetraSASObjs 10 }
tmnxSasAlarmInputNotifications  OBJECT IDENTIFIER ::= { timetraSASNotifyPrefix 10 }
tmnxSASAlarmInputConformance    OBJECT IDENTIFIER ::= { timetraSASConfs 6 }

-- --------------------------------------------------------------------
-- Objects in the TIMETRA-SAS-ALARM-INPUT-MIB
-- --------------------------------------------------------------------

-- --------------------------------------------------------------------
-- tmnxSasAlarmInputInfoTable
-- --------------------------------------------------------------------


tmnxSasAlarmInputInfoTable  OBJECT-TYPE
    SYNTAX SEQUENCE OF TmnxSasAlarmInputInfoEntry
    MAX-ACCESS not-accessible
    STATUS current
    DESCRIPTION
        "A table containing alarm input configuration and status."
    ::= { tmnxSasAlarmInputObjs 1 }

tmnxSasAlarmInputInfoEntry OBJECT-TYPE
    SYNTAX TmnxSasAlarmInputInfoEntry
    MAX-ACCESS not-accessible
    STATUS current
    DESCRIPTION
        "Each row represents one alarm input contact."
    INDEX  { tmnxSasAlarmInputId }
    ::= { tmnxSasAlarmInputInfoTable 1 }

TmnxSasAlarmInputInfoEntry ::= SEQUENCE 
    {
        tmnxSasAlarmInputId          INTEGER,
        tmnxSasAlarmInputDescription TItemLongDescription,
        tmnxSasAlarmInputAdminState  INTEGER,
        tmnxSasAlarmInputPolarity    INTEGER,
        tmnxSasAlarmOutputSeverity    INTEGER,
        tmnxSasAlarmInputStatus      INTEGER,
        tmnxSasAlarmInputLastChange  TimeTicks
    }

tmnxSasAlarmInputId OBJECT-TYPE
    SYNTAX INTEGER (1..4)
    MAX-ACCESS not-accessible
    STATUS current
    DESCRIPTION
        "Alarm contact ID."
    ::= { tmnxSasAlarmInputInfoEntry 1}

tmnxSasAlarmInputDescription OBJECT-TYPE
    SYNTAX TItemLongDescription
    MAX-ACCESS read-write
    STATUS current
    DESCRIPTION
        "Description of this alarm input."
    ::= { tmnxSasAlarmInputInfoEntry 2}


tmnxSasAlarmInputAdminState OBJECT-TYPE
    SYNTAX  INTEGER {
                up(1),
                down(2)
            }
    MAX-ACCESS read-write
    STATUS current
    DESCRIPTION
        "The administrative state of the alarm input."
    ::= { tmnxSasAlarmInputInfoEntry 3}


tmnxSasAlarmInputPolarity OBJECT-TYPE
    SYNTAX INTEGER {
               normally-open(1),
               normally-closed(2)
           }
    MAX-ACCESS read-write
    STATUS current
    DESCRIPTION
        "The polarity of the alarm input circuit."
    DEFVAL      { normally-open }        
    ::= { tmnxSasAlarmInputInfoEntry 4}

tmnxSasAlarmOutputSeverity OBJECT-TYPE
    SYNTAX INTEGER {
        none(1),
        minor(2),
        major(3),
        critical(4)
    }
    MAX-ACCESS read-write
    STATUS current
    DESCRIPTION
        "Configured output severity of the alarm."
    ::= { tmnxSasAlarmInputInfoEntry 5}

tmnxSasAlarmInputStatus OBJECT-TYPE
    SYNTAX INTEGER {
               no-alarm(1),
               alarm(2)
           }
    MAX-ACCESS read-only
    STATUS current
    DESCRIPTION
        "Current alarm status."
    DEFVAL  { no-alarm }
    ::= { tmnxSasAlarmInputInfoEntry 6 }


tmnxSasAlarmInputLastChange  OBJECT-TYPE
    SYNTAX TimeTicks
    MAX-ACCESS read-only
    STATUS current
    DESCRIPTION
        "The value of sysUpTime at the time of the last status change."
    ::= { tmnxSasAlarmInputInfoEntry 7}


-- --------------------------------------------------------------------
-- tmnxSasAlarmInputMessageTable
-- --------------------------------------------------------------------

tmnxSasAlarmInputMessageTable OBJECT-TYPE
    SYNTAX SEQUENCE OF TmnxSasAlarmInputMessageEntry
    MAX-ACCESS not-accessible
    STATUS current
    DESCRIPTION
        "A table containing user defined messages to be sent out with notifications."
    ::= { tmnxSasAlarmInputObjs 2 }

tmnxSasAlarmInputMessageEntry OBJECT-TYPE
    SYNTAX TmnxSasAlarmInputMessageEntry
    MAX-ACCESS not-accessible
    STATUS current
    DESCRIPTION
        "Each row represents one alarm input contact."
    INDEX  { tmnxSasAlarmInputId }
    ::= { tmnxSasAlarmInputMessageTable 1 }


TmnxSasAlarmInputMessageEntry ::=
    SEQUENCE {
        tmnxSasAlarmInputTriggerMessage OCTET STRING,
        tmnxSasAlarmInputClearMessage OCTET STRING
    }

tmnxSasAlarmInputTriggerMessage OBJECT-TYPE
    SYNTAX OCTET STRING
    MAX-ACCESS read-write
    STATUS current
    DESCRIPTION
        "A user defined message to be sent out when the alarm triggers."
    ::= { tmnxSasAlarmInputMessageEntry 1}


tmnxSasAlarmInputClearMessage OBJECT-TYPE
    SYNTAX OCTET STRING
    MAX-ACCESS read-write
    STATUS current
    DESCRIPTION
        "A user defined message to be sent out when the alarm clears."
    ::= { tmnxSasAlarmInputMessageEntry 2 }
    
tmnxSasAlarmInputPowerStatus OBJECT-TYPE
    SYNTAX INTEGER {
                                 off (0),
                                 on (1)
                               }
    MAX-ACCESS read-write
    STATUS current
    DESCRIPTION
        "This object allows the user to turn the power ON or OFF to the external devices connected to alarm-input PINs.
          Note that this object is global w.r.t to the alarm contact pins and hence cannot be included in tmnxSasAlarmInputInfoTable"
    ::= { tmnxSasAlarmInputObjs 3 }

-- --------------------------------------------------------------------
-- Alarm Input Notification Objects
-- --------------------------------------------------------------------

tmnxSasAlarmInputNotifyId OBJECT-TYPE
    SYNTAX INTEGER
    MAX-ACCESS accessible-for-notify
    STATUS current
    DESCRIPTION
        "The OID indicates the Alarm Input contact associated with the notification."
    ::= { tmnxSasAlarmInputNotifyObjs 1 }

tmnxSasAlarmInputNotifyMessage OBJECT-TYPE
    SYNTAX TItemLongDescription
    MAX-ACCESS accessible-for-notify
    STATUS current
    DESCRIPTION
        "The message to be sent out with the 'tmnxSasAlarminputStateChanged' trap."
    ::= { tmnxSasAlarmInputNotifyObjs 2 }

-- --------------------------------------------------------------------
-- Alarm Input Notifications
-- --------------------------------------------------------------------

tmnxSasAlarminput1StateChanged NOTIFICATION-TYPE
    OBJECTS {
        tmnxSasAlarmInputNotifyId,
        tmnxSasAlarmInputDescription,
        tmnxSasAlarmInputStatus,
        tmnxSasAlarmOutputSeverity,
        tmnxSasAlarmInputNotifyMessage
    }
    STATUS current
    DESCRIPTION
        "Send notification when status of the alarm input one changes."
    ::= { tmnxSasAlarmInputNotifications 1 }

tmnxSasAlarminput2StateChanged NOTIFICATION-TYPE
    OBJECTS {
        tmnxSasAlarmInputNotifyId,
        tmnxSasAlarmInputDescription,
        tmnxSasAlarmInputStatus,
        tmnxSasAlarmOutputSeverity,
        tmnxSasAlarmInputNotifyMessage
    }
    STATUS current
    DESCRIPTION
        "Send notification when status of the alarm input two changes."
    ::= { tmnxSasAlarmInputNotifications 2 }

tmnxSasAlarminput3StateChanged NOTIFICATION-TYPE
    OBJECTS {
        tmnxSasAlarmInputNotifyId,
        tmnxSasAlarmInputDescription,
        tmnxSasAlarmInputStatus,
        tmnxSasAlarmOutputSeverity,
        tmnxSasAlarmInputNotifyMessage
    }
    STATUS current
    DESCRIPTION
        "Send notification when status of the alarm input three changes."
    ::= { tmnxSasAlarmInputNotifications 3 }

tmnxSasAlarminput4StateChanged NOTIFICATION-TYPE
    OBJECTS {
        tmnxSasAlarmInputNotifyId,
        tmnxSasAlarmInputDescription,
        tmnxSasAlarmInputStatus,
        tmnxSasAlarmOutputSeverity,
        tmnxSasAlarmInputNotifyMessage
    }
    STATUS current
    DESCRIPTION
        "Send notification when status of the alarm input four changes."
    ::= { tmnxSasAlarmInputNotifications 4 }

tmnxSASAlarmInputCompliances OBJECT IDENTIFIER ::= { tmnxSASAlarmInputConformance 1 }
tmnxSASAlarmInputGroups      OBJECT IDENTIFIER ::= { tmnxSASAlarmInputConformance 2 }

tmnxSASAlarmInputV2v0Group OBJECT-GROUP
    OBJECTS    {
        tmnxSasAlarmInputDescription,
        tmnxSasAlarmInputAdminState,
        tmnxSasAlarmInputPolarity,
        tmnxSasAlarmOutputSeverity,
        tmnxSasAlarmInputStatus,
        tmnxSasAlarmInputLastChange,
        tmnxSasAlarmInputTriggerMessage,
        tmnxSasAlarmInputClearMessage,
        tmnxSasAlarmInputPowerStatus
    }
    STATUS      current 
    DESCRIPTION
           " sas group object definition "
       ::= { tmnxSASAlarmInputGroups 1 }


tmnxAlarmInputNotificationV2v0Group NOTIFICATION-GROUP
    NOTIFICATIONS   { 
                        tmnxSasAlarminput1StateChanged, 
                        tmnxSasAlarminput2StateChanged, 
                        tmnxSasAlarminput3StateChanged, 
                        tmnxSasAlarminput4StateChanged
                    }
    STATUS      current 
    DESCRIPTION
        "The group of notifications supporting the alarm input
         capabilities on Alcatel 7210 SAS series systems."
    ::= { tmnxSASAlarmInputGroups 2 }

tmnxSASAlarmInputComp7210V2v0  MODULE-COMPLIANCE
    STATUS  current
    DESCRIPTION
            "The compliance statement for revision 2.0 of 
             TIMETRA-SAS-ALARM-MIB."
    MODULE  -- this module
        MANDATORY-GROUPS { 
           tmnxSASAlarmInputV2v0Group,
           tmnxAlarmInputNotificationV2v0Group 
        }
    ::= { tmnxSASAlarmInputCompliances 1 }
END
