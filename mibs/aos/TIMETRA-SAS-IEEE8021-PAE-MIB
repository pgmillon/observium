TIMETRA-SAS-IEEE8021-PAE-MIB DEFINITIONS ::= BEGIN

IMPORTS
    IpAddress, MODULE-IDENTITY,
    OBJECT-TYPE, Unsigned32                     FROM SNMPv2-SMI

    MODULE-COMPLIANCE, OBJECT-GROUP             FROM SNMPv2-CONF

    RowStatus, TruthValue,
    TEXTUAL-CONVENTION                          FROM SNMPv2-TC

    timetraSASObjs, timetraSASNotifyPrefix, 
    timetraSASConfs, timetraSASModules          FROM TIMETRA-SAS-GLOBAL-MIB
        
    TPolicyStatementNameOrEmpty,
    ServiceAdminStatus,
    TNamedItem                                  FROM TIMETRA-TC-MIB

    dot1xAuthConfigEntry                        FROM IEEE8021-PAE-MIB              
    ;

timeraSASIEEE8021PaeMIBModule MODULE-IDENTITY
    LAST-UPDATED    "1207010000Z"
    ORGANIZATION    "Alcatel-Lucent"
    CONTACT-INFO
        "Alcatel-Lucent SROS Support
         Web: http://support.alcatel-lucent.com "
    DESCRIPTION
        "This  document  is  the  SNMP MIB module to manage and
         provision  the 7x50 extensions to the IEEE8021-PAE-MIB         
         (Port Access Entity nodule for managing IEEE 802.X) feature for
         the Alcatel 7210 device.

         Copyright 2004-2012 Alcatel-Lucent. All rights reserved.        
         Reproduction of this document is authorized on the condition that
         the foregoing copyright notice is included.

         This SNMP MIB module (Specification) embodies Alcatel-Lucent's
         proprietary intellectual property.  Alcatel-Lucent retains
         all title and ownership in the Specification, including any
         revisions.

         Alcatel-Lucent grants all interested parties a non-exclusive
         license to use and distribute an unmodified copy of this
         Specification in connection with management of Alcatel-Lucent
         products, and without fee, provided this copyright notice and
         license appear on all copies.

         This Specification is supplied 'as is', and Alcatel-Lucent
         makes no warranty, either express or implied, as to the use,
         operation, condition, or performance of the Specification."

   REVISION     "1207010000Z"
   DESCRIPTION  "Rev 1.0                03 Aug 2012 00:00   
                 1.0 release of the ALCATEL-SAS-IEEE8021-PAE-MIB."

   ::= { timetraSASModules 17 } 

-- ----------------------------------------------------------------------------
--
--  Alcatel 7210 series IEEE 802.1X PAE feature
--  MIB structure
--
-- ----------------------------------------------------------------------------
tmnxSASDot1xObjs                                OBJECT IDENTIFIER ::= { timetraSASObjs 16 }      
    tmnxSASDot1xAuthenticatorObjs               OBJECT IDENTIFIER ::= { tmnxSASDot1xObjs 1 }

tmnxSASDot1xConformance                         OBJECT IDENTIFIER ::= { timetraSASConfs 12 }
    tmnxDot1xSASCompliancs     OBJECT IDENTIFIER ::= { tmnxSASDot1xConformance 1 }
    tmnxDot1xSASGroups         OBJECT IDENTIFIER ::= { tmnxSASDot1xConformance 2 }

dot1xAuthConfigExtnTable OBJECT-TYPE
    SYNTAX          SEQUENCE OF Dot1xAuthConfigExtnEntry
    MAX-ACCESS      not-accessible
    STATUS          current
    DESCRIPTION
        "The  table dot1xAuthConfigExtnTable allows configuration of 
         RADIUS authentication parameters for the 802.1X PAE
         feature on port level." 
    ::= { tmnxSASDot1xAuthenticatorObjs 1 }

dot1xAuthConfigExtnEntry OBJECT-TYPE
    SYNTAX          Dot1xAuthConfigExtnEntry
    MAX-ACCESS      not-accessible
    STATUS          current
    DESCRIPTION
        "dot1xAuthConfigExtnEntry is an entry (conceptual row) in the
         dot1xAuthConfigExtnTable. Each entry represents the configuration
         for Radius Authentication on a port. Entries have a presumed
         StorageType of nonVolatile."
    AUGMENTS { dot1xAuthConfigEntry }
    ::= { dot1xAuthConfigExtnTable 1 }                                              
                                                                                  
Dot1xAuthConfigExtnEntry ::= SEQUENCE {                                             
     dot1xPortEtherTunnel   TruthValue     
}

dot1xPortEtherTunnel OBJECT-TYPE
    SYNTAX      TruthValue
    MAX-ACCESS  read-write
    STATUS      current
    DESCRIPTION
        "The value of tmnxPortEtherDot1xTunnel specifies whether the DOT1X
         packet tunneling for the ethernet port is enabled or disabled.
         When tunneling is enabled, the port will not process any DOT1X
         packets but will tunnel them through instead."
    DEFVAL { false }
    ::= { dot1xAuthConfigExtnEntry 150 }

dot1xAuthConfigExtnGroup  OBJECT-GROUP
    OBJECTS {
          dot1xPortEtherTunnel
        }
    STATUS      current
    DESCRIPTION
        "The  group  of  objects supporting management of Radius
         authentication   for  the  IEEE801.1X  PAE  feature  on
         Alcatel 7210 SR series systems."
    ::= { tmnxDot1xSASGroups 1 }

-- ----------------------------------------------------------------------------
-- 
--  Conformance information
--
-- ----------------------------------------------------------------------------
-- --------------------------------------------------------
-- 
--  Dot1x related Compliance statements
-- 
-- --------------------------------------------------------
dot1xAuthConfigExtnCompliance  MODULE-COMPLIANCE
    STATUS  current
    DESCRIPTION
            "The  compliance statement for management of Radius
             authentication  for  the  IEEE801.1X PAE feature on
             Alcatel 7210 SR series systems."
    MODULE  -- this module
        MANDATORY-GROUPS { 
            dot1xAuthConfigExtnGroup
        }
    ::= { tmnxDot1xSASCompliancs 1 }

END
