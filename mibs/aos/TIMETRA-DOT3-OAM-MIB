TIMETRA-DOT3-OAM-MIB DEFINITIONS ::= BEGIN

IMPORTS
        Integer32, MODULE-IDENTITY,
        OBJECT-TYPE, Counter32, Counter64,
        Unsigned32, NOTIFICATION-TYPE                 FROM SNMPv2-SMI

        RowStatus, TimeStamp,                   
        TruthValue, TEXTUAL-CONVENTION                FROM SNMPv2-TC

        MODULE-COMPLIANCE, OBJECT-GROUP, 
        NOTIFICATION-GROUP                            FROM SNMPv2-CONF

        dot3OamEntry, dot3OamLoopbackEntry,
        dot3OamPeerMacAddress                         FROM DOT3-OAM-MIB

        timetraSRMIBModules, tmnxSRObjs,
        tmnxSRNotifyPrefix, tmnxSRConfs               FROM TIMETRA-GLOBAL-MIB

        ifIndex                                       FROM IF-MIB;


timetraDOT3OAMMIBModule MODULE-IDENTITY
        LAST-UPDATED    "0807010000Z"
        ORGANIZATION    "Alcatel-Lucent"
        CONTACT-INFO    
            "Alcatel-Lucent SROS Support
             Web: http://support.alcatel-lucent.com"
        DESCRIPTION
        "This document is the SNMP MIB module to manage and provision Ethernet
        OAM (802.3ah) functionality for the Alcatel-Lucent SROS device. 
        This includes extensions to the DOT3-OAM-MIB defined in IEEE 802.3ah 
        to allow transmit interval configuration and other locally configured 
        modifications.

        Copyright 2006-2011 Alcatel-Lucent. All rights reserved.
        Reproduction of this document is authorized on the condition that
        the foregoing copyright notice is included.

        This SNMP MIB module (Specification) embodies Alcatel-Lucent's
        proprietary intellectual property.  Alcatel-Lucent retains
        all title and ownership in the Specification, including any
        revisions.

        Alcatel-Lucent grants all interested parties a non-exclusive
        license to use and distribute an unmodified copy of this
        Specification in connection with management of Alcatel-Lucent
        products, and without fee, provided this copyright notice and
        license appear on all copies.

        This Specification is supplied 'as is', and Alcatel-Lucent
        makes no warranty, either express or implied, as to the use,
        operation, condition, or performance of the Specification."
--
--  Revision History
--
        REVISION        "0807010000Z"
        DESCRIPTION     "Rev 6.1                01 Jul 2008 00:00
                         6.1 release of the TIMETRA-DOT3-OAM-MIB."

        REVISION        "0801010000Z"
        DESCRIPTION     "Rev 6.0                01 Jan 2008 00:00
                         6.0 release of the TIMETRA-DOT3-OAM-MIB."

        REVISION        "200608010000Z"
        DESCRIPTION     "Rev 0.1                01 Aug 2006 00:00
                         Initial version of the TIMETRA-DOT3-OAM-MIB."
                         
        ::= { timetraSRMIBModules 42 }

--%%%%%%%%%%%%%%%%%%%%%%%%%%%%%%%%%%%%%%%%%%%%%%%%%%%%%%%%%%%%%%%%%%%%%%
--
--  Alcatel 7750 SR series Ethernet OAM extensions
--

tmnxDot3OamObjs           OBJECT IDENTIFIER ::= { tmnxSRObjs 42 }
tmnxDot3OamMIBConformance OBJECT IDENTIFIER ::= { tmnxSRConfs 42 }
tmnxDot3OamEntryObjs      OBJECT IDENTIFIER ::= { tmnxDot3OamObjs 1 }
tmnxDot3OamLoopbackObjs    OBJECT IDENTIFIER ::= { tmnxDot3OamObjs 2 }

tmnxDot3OamNotifyPrefix    OBJECT IDENTIFIER ::= { tmnxSRNotifyPrefix 42 } 
tmnxDot3OamNotificationsPrefix      OBJECT IDENTIFIER ::= { tmnxDot3OamNotifyPrefix 42 } 
    tmnxDot3OamNotifications      OBJECT IDENTIFIER ::= { tmnxDot3OamNotificationsPrefix 0 } 


--
--  Alcatel 7750 SR series Ethernet OAM (802.3ah) Table
--
--  Augmententation of dot3OamTable in DOT3-OAM-MIB
--
--  The tmnxDot3OamTable is an augmentation of the dot3OamTable.
--  Use of AUGMENTS clause implies a one-to-one dependent relationship between
--  the base table, dot3OamTable, and the augmenting table, tmnxDot3OamTable. 
--  This in effect extends the dot3OamTable with additional columns.  
--  Creation (or deletion) of a row in the dot3OamTable results in the same 
--  fate for the row in the tmnxDot3OamTable

tmnxDot3OamTable OBJECT-TYPE
    SYNTAX        SEQUENCE OF TDot3OamEntry
    MAX-ACCESS    not-accessible
    STATUS        current
    DESCRIPTION
        "The tmnxDot3OamTable is used to store proprietary configuration
         information on a particular Ethernet like interface (OAM entity)
         in the system that supports the OAM functions defined in [802.3ah]."
    ::= { tmnxDot3OamEntryObjs 1 }
    
    tmnxDot3OamEntry OBJECT-TYPE
        SYNTAX        TDot3OamEntry
        MAX-ACCESS    not-accessible
        STATUS        current
        DESCRIPTION 
            "An entry in the tmnxDot3OamTable containing configuration
             information applicable to an OAM entity."
        AUGMENTS { dot3OamEntry }
        ::= { tmnxDot3OamTable 1 }
    
    TDot3OamEntry ::=
        SEQUENCE {
           tmnxDot3OamLastChanged  TimeStamp,
           tmnxDot3OamInterval     Unsigned32,
           tmnxDot3OamMultiplier   Unsigned32,
           tmnxDot3OamTunneling    TruthValue,
           tmnxDot3OamLooped       TruthValue,
           tmnxDot3OamHoldTime     Unsigned32
        }

     tmnxDot3OamLastChanged OBJECT-TYPE
        SYNTAX     TimeStamp
        MAX-ACCESS read-only
        STATUS     current
        DESCRIPTION
                "The value of tmnxDot3OamLastChanged indicates 
                 the sysUpTime value when this row was last modified."
        ::= { tmnxDot3OamEntry 1 }

    tmnxDot3OamInterval OBJECT-TYPE
        SYNTAX       Unsigned32 (1..600)
        UNITS        "100s of milliseconds"
        MAX-ACCESS   read-write
        STATUS       current
        DESCRIPTION
           "The value of tmnxDot3OamInterval specifies the number of 100ms
            time intervals between each periodic OAMPDU transmit and receive.
            A lower value implies that OAMPDUs will be transmitted more 
            frequently to the peer, and OAMPDUs must be received more frequently
            from the peer.  The default is set to 10, meaning 1 second between
            transmits and receives."
        DEFVAL { 10 }
        ::= { tmnxDot3OamEntry 2 }   

    tmnxDot3OamMultiplier OBJECT-TYPE
        SYNTAX       Unsigned32 (2..5)
        MAX-ACCESS   read-write
        STATUS       current
        DESCRIPTION
           "The value of tmnxDot3OamMultiplier specifies how many receive
            intervals may expire with no OAMPDU receive.  After the configured 
            number of intervals with OAMPDU receive have passed, the OAM 
            negotiation process will restart."
        DEFVAL { 5 }
        ::= { tmnxDot3OamEntry 3 }   

    tmnxDot3OamTunneling OBJECT-TYPE
        SYNTAX       TruthValue
        MAX-ACCESS   read-write
        STATUS       current
        DESCRIPTION
           "The value of tmnxDot3OamTunneling specifies if OAMPDUs should
            be passed transparently through the OAM entity for processing
            by another OAM entity across the network, or if OAMPDUs should be
            terminated and processed at the local OAM entity.  This object 
            can only be set to 'true' if dot3OamAdminState is set to 'disabled'.
            Likewise, dot3OamAdminState can only be set to 'enabled' if this 
            object is set to 'false'.  It is not valid to try and enable both 
            OAMPDU processing and OAMPDU tunneling on the same OAM entity."
        DEFVAL { false }
        ::= { tmnxDot3OamEntry 4 }    

    tmnxDot3OamLooped OBJECT-TYPE
        SYNTAX       TruthValue
        MAX-ACCESS   read-only
        STATUS       current
        DESCRIPTION
           "The value of tmnxDot3OamLooped indicates if the OAM entity
            is receiving OAMPDUs that it transmitted.  A value of 'true'
            indicates that the OAM entity is receiving it's own OAMPDUs while
            a value of 'false' indicates it is not."
        DEFVAL { false }
        ::= { tmnxDot3OamEntry 5 }    

    tmnxDot3OamHoldTime OBJECT-TYPE
        SYNTAX       Unsigned32 (0..50)
        UNITS        "seconds"
        MAX-ACCESS   read-write
        STATUS       current
        DESCRIPTION
           "The value of tmnxDot3OamHoldTime specifies the number of seconds
            the efm-oam protocol should wait after dot3OamOperStatus transitions
            from 'operational (9)' to a non-operational state before going back to
            the 'operational (9)' state again.  Note that a transition to the
            'linkFault (2)' state does not cause tmnxDot3OamHoldTime to be used if
            dot3OamOperStatus was previously in the 'operational (9)' state."
        DEFVAL { 0 }
        ::= { tmnxDot3OamEntry 6 } 
--
--  Alcatel 7750 SR series Ethernet OAM (802.3ah) Loopback Table
--
--  Augmententation of dot3OamLoopbackTable in DOT3-OAM-MIB
--
--  The tmnxDot3OamLoopbackTable is an augmentation of the 
--  dot3OamLoopbackTable. Use of AUGMENTS clause implies a one-to-one dependent 
--  relationship between the base table, dot3OamLoopbackTable, and the 
--  augmenting table, tmnxDot3OamLoopbackTable.  This in effect extends the
--  dot3OamLoopbackTable with additional columns.  Creation (or deletion) of 
--  a row in the dot3OamLoopbackTable results in the same fate for the row in 
--  the tmnxDot3OamLoopbackTable.

tmnxDot3OamLoopbackTable OBJECT-TYPE
    SYNTAX        SEQUENCE OF TDot3OamLoopbackEntry
    MAX-ACCESS    not-accessible
    STATUS        current
    DESCRIPTION
        "The tmnxDot3OamLoopbackTable is used to store proprietary 
         loopback configuration information on a particular 
         Ethernet like interface (OAM entity) in the system that supports 
         the OAM functions defined in [802.3ah]."
    ::= { tmnxDot3OamLoopbackObjs 1 }
    
    tmnxDot3OamLoopbackEntry OBJECT-TYPE
        SYNTAX        TDot3OamLoopbackEntry
        MAX-ACCESS    not-accessible
        STATUS        current
        DESCRIPTION 
            "An entry in the tmnxDot3OamLoopbackTable containing 
             configuration information applicable to an OAM entity."
        AUGMENTS { dot3OamLoopbackEntry }
        ::= { tmnxDot3OamLoopbackTable 1 }
    
    TDot3OamLoopbackEntry ::=
        SEQUENCE {
           tmnxDot3OamLoopbackLastChanged     TimeStamp,
           tmnxDot3OamLoopbackLocalStatus     INTEGER
        }

    tmnxDot3OamLoopbackLastChanged OBJECT-TYPE
        SYNTAX     TimeStamp
        MAX-ACCESS read-only
        STATUS     current
        DESCRIPTION
                "The value of tmnxDot3OamLoopbackLastChanged indicates 
                 the sysUpTime value when this row was last modified."
        ::= { tmnxDot3OamLoopbackEntry 1 }

    tmnxDot3OamLoopbackLocalStatus OBJECT-TYPE
        SYNTAX      INTEGER { 
                      noLoopback (1), 
                      localLoopback (2)
                    }
        MAX-ACCESS   read-write
        STATUS       current
        DESCRIPTION
           "The value of tmnxDot3OamLoopbackLocalStatus indicates the local 
            loopback status of the OAM entity.  This attribute allows the user
            to manually set the local OAM entity loopback mode overriding the
            802.3ah protocol for loopback.  Setting the value to 'localLoopback'
            can only be done if dot3OamLoopbackStatus is set to 'noLoopback'.  
            If dot3OamLoopbackStatus is any value other than 'noLoopback', the 
            changes to tmnxDot3OamLoopbackLocalStatus will have no effect.  If 
            dot3OamLoopbackStatus is set to 'localLoopback', the OAM entity will
            act as if its peer put the OAM entity into local loopback.  This 
            entry allows the user to put an OAM entity into local loopback mode,
            even if dot3OamLoopbackIgnoreRx is set to 'ignore'."
        DEFVAL { noLoopback }
        ::= { tmnxDot3OamLoopbackEntry 2 }   


--
--  Alcatel 7750 SR series Ethernet OAM (802.3ah) Notifications
--

tmnxDot3OamPeerChanged NOTIFICATION-TYPE
    OBJECTS {
        dot3OamPeerMacAddress
    }
    STATUS  current
    DESCRIPTION
        "The tmnxDot3OamPeerChanged notification is generated 
         when the peer information (specifically the Peer MAC address)
         changes.  Note that this notification will only be sent out
         if the peer information was previously available and the
         information changed, and not when the peer information
         is first learned or becomes unavailable."
    ::= { tmnxDot3OamNotifications 1 }

tmnxDot3OamLoopDetected NOTIFICATION-TYPE
    OBJECTS {
        ifIndex
    }
    STATUS  current
    DESCRIPTION
        "The tmnxDot3OamLoopDetected notification is generated 
         when a port receives an 802.3ah PDU with a source MAC
         address that matches the MAC address of that port."
    ::= { tmnxDot3OamNotifications 2 }

tmnxDot3OamLoopCleared NOTIFICATION-TYPE
    OBJECTS {
        ifIndex
    }
    STATUS  current
    DESCRIPTION
        "The tmnxDot3OamLoopCleared notification is generated 
         when a port is no longer receiving 802.3ah PDUs with
         a source MAC address that matches the MAC address of
         that port."
    ::= { tmnxDot3OamNotifications 3 }

--
-- Conformance Information
--
tmnxDot3OamMIBCompliances OBJECT IDENTIFIER ::= { tmnxDot3OamMIBConformance 1 }
tmnxDot3OamMIBGroups      OBJECT IDENTIFIER ::= { tmnxDot3OamMIBConformance 2 }

tmnxDot3OamMIBCompliance  MODULE-COMPLIANCE
    STATUS  obsolete
    DESCRIPTION
            "The compliance statement for revision 5.0 of TIMETRA-DOT3-OAM-MIB."
    MODULE  -- this module
        MANDATORY-GROUPS { 
            tmnxDot3OamGroup,
            tmnxDot3OamLoopbackGroup,
            tmnxDot3OamNotificationGroup
        }
    ::= { tmnxDot3OamMIBCompliances 1 }

tmnxDot3OamMIBV6v0Compliance  MODULE-COMPLIANCE
    STATUS  obsolete
    DESCRIPTION
            "The compliance statement for revision 6.0 of TIMETRA-DOT3-OAM-MIB."
    MODULE  -- this module
        MANDATORY-GROUPS { 
            tmnxDot3OamV6v0Group,
            tmnxDot3OamLoopbackGroup,
            tmnxDot3OamNotificationV6v0Group
        }
    ::= { tmnxDot3OamMIBCompliances 2 }

tmnxDot3OamMIBV6v1Compliance  MODULE-COMPLIANCE
    STATUS  current
    DESCRIPTION
            "The compliance statement for revision 6.0 of TIMETRA-DOT3-OAM-MIB."
    MODULE  -- this module
        MANDATORY-GROUPS { 
            tmnxDot3OamV6v0Group,
            tmnxDot3OamV6v1Group,
            tmnxDot3OamLoopbackGroup,
            tmnxDot3OamNotificationV6v0Group
        }
    ::= { tmnxDot3OamMIBCompliances 3 }
-- units of conformance

tmnxDot3OamGroup           OBJECT-GROUP
    OBJECTS  {
          tmnxDot3OamLastChanged,
          tmnxDot3OamInterval,
          tmnxDot3OamMultiplier,
          tmnxDot3OamTunneling
        }
    STATUS   obsolete
    DESCRIPTION
        "The group of objects providing for management an Ethernet OAM
         entity on Alcatel 7750 SR series systems."
    ::= { tmnxDot3OamMIBGroups 1 }

tmnxDot3OamLoopbackGroup           OBJECT-GROUP
    OBJECTS  {
          tmnxDot3OamLoopbackLastChanged,
          tmnxDot3OamLoopbackLocalStatus
        }
    STATUS   current 
    DESCRIPTION
        "The group of objects providing for loopback management an 
         Ethernet OAM entity on Alcatel 7750 SR series systems."
    ::= { tmnxDot3OamMIBGroups 2 }

tmnxDot3OamNotificationGroup  NOTIFICATION-GROUP
    NOTIFICATIONS {
        tmnxDot3OamPeerChanged
    }
    STATUS    obsolete
    DESCRIPTION
        "The group of notifications supporting Ethernet OAM in on Alcatel 7x50 
         SR series systems."
    ::= { tmnxDot3OamMIBGroups 3 }

tmnxDot3OamNotificationV6v0Group  NOTIFICATION-GROUP
    NOTIFICATIONS {
        tmnxDot3OamPeerChanged,
        tmnxDot3OamLoopDetected,
        tmnxDot3OamLoopCleared
    }
    STATUS    current
    DESCRIPTION
        "The group of notifications supporting Ethernet OAM in on Alcatel 7x50 
         SR series systems release 6.0."
    ::= { tmnxDot3OamMIBGroups 4 }

tmnxDot3OamV6v0Group           OBJECT-GROUP
    OBJECTS  {
          tmnxDot3OamLastChanged,
          tmnxDot3OamInterval,
          tmnxDot3OamMultiplier,
          tmnxDot3OamTunneling,
          tmnxDot3OamLooped
        }
    STATUS   current 
    DESCRIPTION
        "The group of objects providing management for an Ethernet OAM
         entity on Alcatel 7750 SR series systems release 6.0."
    ::= { tmnxDot3OamMIBGroups 5 }

tmnxDot3OamV6v1Group           OBJECT-GROUP
    OBJECTS  {
          tmnxDot3OamHoldTime
        }
    STATUS   current 
    DESCRIPTION
        "The group of objects providing management for an Ethernet OAM
         entity on Alcatel 7750 SR series systems release 6.1."
    ::= { tmnxDot3OamMIBGroups 6 }
END
