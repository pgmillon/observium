TIMETRA-VIDEO-MIB DEFINITIONS ::= BEGIN

IMPORTS
   MODULE-IDENTITY, OBJECT-TYPE, NOTIFICATION-TYPE,
   Unsigned32, Counter32, Counter64, Gauge32
       FROM SNMPv2-SMI

   MODULE-COMPLIANCE, OBJECT-GROUP, NOTIFICATION-GROUP
       FROM SNMPv2-CONF

   RowStatus, TimeStamp, TruthValue, TEXTUAL-CONVENTION, DateAndTime
       FROM SNMPv2-TC

   InetAddress, InetAddressType, InetAddressPrefixLength, InetPortNumber
       FROM INET-ADDRESS-MIB

   timetraSRMIBModules, tmnxSRObjs, tmnxSRConfs, 
   tmnxSRNotifyPrefix
       FROM TIMETRA-GLOBAL-MIB

   TItemDescription, TmnxVdoGrpId, TmnxVdoGrpIdIndex, InterfaceIndex,
   TmnxAdminState, TmnxOperState, TNamedItem, TmnxVdoOutputFormat, 
   TSapIngressPolicyID, TSapEgressPolicyID, TmnxServId, TmnxStrSapId,
   TmnxVdoFccServerMode, TmnxVdoIfName, TCpmProtPolicyID, TmnxEnabledDisabled,
   TmnxVdoStatInt, TmnxVdoAnalyzerAlarmStates, TNamedItemOrEmpty, 
   TmnxVdoAnalyzerAlarm
       FROM TIMETRA-TC-MIB

   tmnxChassisIndex, tmnxCardSlotNum, tmnxMDASlotNum
       FROM TIMETRA-CHASSIS-MIB

   svcId                                       
       FROM TIMETRA-SERV-MIB

   TmnxMcPathVdoBufferSize, TmnxMcPathVdoChlType
       FROM TIMETRA-MCAST-PATH-MGMT-MIB

   TIPFilterID, TMACFilterID
       FROM TIMETRA-FILTER-MIB
   ;

timetraVideoMIBModule    MODULE-IDENTITY
    LAST-UPDATED "201102010000Z"
    ORGANIZATION "Alcatel-Lucent"
    CONTACT-INFO
        "Alcatel-Lucent SROS Support
         Web: http://support.alcatel-lucent.com"
    DESCRIPTION
    "This document is the SNMP MIB module to manage and provision
    the video-related features including Fast Channel Change (FCC),
    Reliable Delivery (RD) and Ad Insert (ADI) for the Alcatel-Lucent SROS 
    device.

    Copyright 2008-2011 Alcatel-Lucent. All rights reserved.
    Reproduction of this document is authorized on the condition that
    the foregoing copyright notice is included.

    This SNMP MIB module (Specification) embodies Alcatel-Lucent's
    proprietary intellectual property. Alcatel-Lucent retains all title and
    ownership in the Specification, including any revisions.

    Alcatel-Lucent grants all interested parties a non-exclusive
    license to use and distribute an unmodified copy of this
    Specification in connection with management of Alcatel-Lucent products,
    and without fee, provided this copyright notice and license appear
    on all copies.

    This Specification is supplied 'as is', and Alcatel-Lucent
    makes no warranty, either express or implied, as to the use,
    operation, condition, or performance of the Specification."

--
--  Revision History
--
    REVISION        "1102010000Z"
    DESCRIPTION     "Rev 9.0                1 Feb 2011 00:00
                     9.0 release of the TIMETRA-VIDEO-MIB.mib."

    REVISION        "0902280000Z"
    DESCRIPTION     "Rev 7.0                28 Feb 2009 00:00
                     7.0 release of the TIMETRA-VIDEO-MIB.mib."

    REVISION        "0807250000Z"
    DESCRIPTION     "Rev 0.1            15 July 2008 00:00
                     Initial version of the TIMETRA-VIDEO-MIB."

    ::= { timetraSRMIBModules 61 }

-- ----------------------------------------------------------------------------
--  Alcatel-Lucent SROS series VIDEO MIB structure
-- ----------------------------------------------------------------------------
tmnxVdo                      OBJECT IDENTIFIER ::= { tmnxSRObjs 61 }
    tmnxVdoObjs              OBJECT IDENTIFIER ::= { tmnxVdo 1 }
    tmnxVdoGlobalObjs        OBJECT IDENTIFIER ::= { tmnxVdo 2 }
    tmnxVdoNotificationObjs  OBJECT IDENTIFIER ::= { tmnxVdo 3 }

tmnxVdoConformance           OBJECT IDENTIFIER ::= { tmnxSRConfs 61 }
    tmnxVdoCompliances       OBJECT IDENTIFIER ::= { tmnxVdoConformance 1 }
    tmnxVdoGroups            OBJECT IDENTIFIER ::= { tmnxVdoConformance 2 }

tmnxVdoNotifyPrefix          OBJECT IDENTIFIER ::= { tmnxSRNotifyPrefix 61 }
    tmnxVdoNotifications     OBJECT IDENTIFIER ::= { tmnxVdoNotifyPrefix 0 }

--
-- Textual Conventions
--

TmnxVdoPIDType ::= TEXTUAL-CONVENTION
    STATUS      current
    DESCRIPTION
        "TmnxVdoPIDType is an enumerated integer whose value indicates the 
         type of stream carried by this PID.

         other  (0) - Unspecified stream type
         audio  (1) - audio stream
         video  (2) - video stream
         data   (3) - data stream
         ca     (4) - conditional access stream
         scte35 (5) - Society of Cable Telecommunications
                      Engineers 35 stream
         pat    (6) - program association table
         pcr    (7) - program clock reference
         pmt    (8) - program map table."
    SYNTAX      INTEGER {
                         other  (0),
                         audio  (1),
                         video  (2),
                         data   (3),
                         ca     (4),
                         scte35 (5),
                         pat    (6),
                         pcr    (7),
                         pmt    (8)
                    }

TmnxVdoPTS ::= TEXTUAL-CONVENTION
        STATUS     current
        DESCRIPTION
            "The data type describes the Presentation Timestamp (PTS) which            
             indicates the time of presentation in the system decoder of a 
             presentation unit of an elementary stream. The value of PTS is 
             measured in units of 90-KHz clock periods.

             Format of PTS is a 33-bit string, left bit first, where left is 
             the order in which bit strings are written in 13818-1 
             International Standard. The most significant 7 bits will be padded 
             with zeroes."
        REFERENCE  "ISO/IEC 13818-1:2000(E), Section 2.2.6"
        SYNTAX     OCTET STRING (SIZE (5))

TmnxMDILossRate ::= TEXTUAL-CONVENTION
        STATUS      current
        DESCRIPTION
            "TmnxMDILossRate is an octet string encoding of Media Delivery Index 
             (MDI) loss rate that is represented as an 64-bit unsigned 
             fixed-point number. The integer part is in the first 32 bits and 
             the fraction part is in the last 32 bits."
        REFERENCE "RFC-4445, April 2006, Section 3.2"
        SYNTAX     OCTET STRING (SIZE (8))

-- --------------------------
--  Mib objects
-- --------------------------

--
--  Video Interfaces Table
--

tmnxVdoIfTableLastChanged OBJECT-TYPE
    SYNTAX      TimeStamp
    MAX-ACCESS  read-only
    STATUS      current
    DESCRIPTION
        "The value of tmnxVdoIfTableLastChanged indicates the
         sysUpTime at the time of the last modification to
         tmnxVdoIfTable by adding, deleting an entry or change
         to a writable object in the table.

         If no changes were made to the table since the last
         re-initialization of the local network management subsystem,
         then this object contains a zero value."
    ::= { tmnxVdoGlobalObjs 1 }

tmnxVdoIfTable  OBJECT-TYPE
    SYNTAX      SEQUENCE OF TmnxVdoIfEntry
    MAX-ACCESS  not-accessible
    STATUS      current
    DESCRIPTION
        "The tmnxVdoIfTable has an entry for each video interface configured in
         the system."
    ::= { tmnxVdoObjs 1 }

tmnxVdoIfEntry  OBJECT-TYPE
    SYNTAX      TmnxVdoIfEntry
    MAX-ACCESS  not-accessible
    STATUS      current
    DESCRIPTION
        "Each row entry represents a video interface in the system. Entries
         can be created and deleted by the user."
    INDEX { svcId, 
            tmnxVdoIfName 
    }
    ::= { tmnxVdoIfTable 1 }

TmnxVdoIfEntry ::= SEQUENCE {
        tmnxVdoIfName                      TmnxVdoIfName,
        tmnxVdoIfRowStatus                 RowStatus,
        tmnxVdoIfLastChanged               TimeStamp,
        tmnxVdoIfAdminState                TmnxAdminState,
        tmnxVdoIfOperState                 TmnxOperState,
        tmnxVdoIfVrtrIfIndex               InterfaceIndex,
        tmnxVdoIfDescription               TItemDescription,
        tmnxVdoIfVdoGrpId                  TmnxVdoGrpId,
        tmnxVdoIfIngressQosPolicyId        TSapIngressPolicyID,
        tmnxVdoIfEgressQosPolicyId         TSapEgressPolicyID,
        tmnxVdoIfAdi                       TruthValue,
        tmnxVdoIfRTClientAddrType          InetAddressType,
        tmnxVdoIfRTClientAddr              InetAddress,
        tmnxVdoIfGatewayAddrType           InetAddressType,
        tmnxVdoIfGatewayAddr               InetAddress,
        tmnxVdoIfMcastSvcId                TmnxServId,
        tmnxVdoIfIngressIpFilterId         TIPFilterID,
        tmnxVdoIfIngressMacFilterId        TMACFilterID,
        tmnxVdoIfEgressIpFilterId          TIPFilterID,
        tmnxVdoIfEgressMacFilterId         TMACFilterID,
        tmnxVdoIfScte30ControlAddrType     InetAddressType,
        tmnxVdoIfScte30ControlAddr         InetAddress,
        tmnxVdoIfScte30DataAddrType        InetAddressType,
        tmnxVdoIfScte30DataAddr            InetAddress,
        tmnxVdoIfSapId                     TmnxStrSapId,
        tmnxVdoIfMcastProtocol             INTEGER,
        tmnxVdoIfSessions                  Unsigned32,
        tmnxVdoIfCpmProtectPolicyId        TCpmProtPolicyID,
        tmnxVdoIfRTMcastReply              TmnxEnabledDisabled,      
        tmnxVdoIfRTCount                   Unsigned32,   
        tmnxVdoIfRTInterval                Unsigned32,   
        tmnxVdoIfRTHoldTime                Unsigned32,
        tmnxVdoIfAcctPolicyId              Unsigned32,
        tmnxVdoIfOutputFormat              TmnxVdoOutputFormat
    }

tmnxVdoIfName                OBJECT-TYPE 
    SYNTAX         TmnxVdoIfName
    MAX-ACCESS     not-accessible
    STATUS         current
    DESCRIPTION 
        "The value of tmnxVdoIfName specifies the unique administrative name 
         for this video interface. The name must begin with a letter and 
         is restricted to a maximum length of 29 characters during row creation 
         using the 'tmnxVdoIfRowStatus' object. The remaining 3 characters are 
         used internally by the agent to distinguish between user created 
         video interfaces and agent created video interfaces. The agent created 
         video interfaces have the same name as the user created 
         video interfaces but are appended with a suffix of '-S' or '-S2'. These 
         agent created video interfaces can be viewed using SNMP operations only 
         in MIB tables that hold video interface statistical values namely - 
         'tmnxVdoGrpSrcStatTable', 'tmnxVdoPIDTable', 'tmnxVdoGrpSrcVqmTable' 
         and 'tmnxVdoGrpSrcVqmStatTable'."
    ::= { tmnxVdoIfEntry 1 }

tmnxVdoIfRowStatus                OBJECT-TYPE
    SYNTAX         RowStatus
    MAX-ACCESS     read-create
    STATUS         current
    DESCRIPTION
        "The value of tmnxVdoIfRowStatus specifies the row status of this row.
         It is used for creation/deletion of this video interface."
    ::= { tmnxVdoIfEntry 2 }

tmnxVdoIfLastChanged                OBJECT-TYPE
    SYNTAX         TimeStamp
    MAX-ACCESS     read-only
    STATUS         current
    DESCRIPTION
        "The value of tmnxVdoIfLastChanged indicates the timestamp of last
         change to this row in tmnxVdoIfTable."
    ::= { tmnxVdoIfEntry 3 }

tmnxVdoIfAdminState                OBJECT-TYPE
    SYNTAX         TmnxAdminState
    MAX-ACCESS     read-create
    STATUS         current
    DESCRIPTION
        "The value of tmnxVdoIfAdminState specifies the desired administrative
         state of this video interface."
    DEFVAL { outOfService }
    ::= { tmnxVdoIfEntry 4 }

tmnxVdoIfOperState                OBJECT-TYPE
    SYNTAX         TmnxOperState
    MAX-ACCESS     read-only
    STATUS         current
    DESCRIPTION
        "The value of tmnxVdoIfOperState specifies the current operational
         status of this video interface."
    ::= { tmnxVdoIfEntry 5 }

tmnxVdoIfVrtrIfIndex         OBJECT-TYPE
    SYNTAX         InterfaceIndex
    MAX-ACCESS     read-only
    STATUS         current
    DESCRIPTION
        "The value of tmnxVdoIfVrtrIfIndex specifies the secondary index in 
         the TIMETRA-VRTR-MIB::vRtrIfTable corresponding to this video
         interface. The value of svcId specifies the primary index in the
         TIMETRA-VRTR-MIB::vRtrIfTable."
    ::= { tmnxVdoIfEntry 6 }
               
tmnxVdoIfDescription                OBJECT-TYPE 
    SYNTAX         TItemDescription 
    MAX-ACCESS     read-create
    STATUS         current
    DESCRIPTION 
        "The value of tmnxVdoIfDescription specifies the user provided 
         description string for this video interface."
    DEFVAL { ''H }      -- the empty string
    ::= { tmnxVdoIfEntry 7 }
        
tmnxVdoIfVdoGrpId                OBJECT-TYPE 
    SYNTAX         TmnxVdoGrpId
    MAX-ACCESS     read-create
    STATUS         current
    DESCRIPTION 
        "The value of tmnxVdoIfVdoGrpId specifies the row index in the 
         TIMETRA-VIDEO-MIB::tmnxVdoGrpTable for the video group information
         for this multicast information policy bundle.

         A value '0' indicates that no video-group is assigned to this
         video interface."
    DEFVAL { 0 }
    ::= { tmnxVdoIfEntry 8 }
                   
tmnxVdoIfIngressQosPolicyId                OBJECT-TYPE 
    SYNTAX         TSapIngressPolicyID 
    MAX-ACCESS     read-create
    STATUS         current
    DESCRIPTION 
        "The value of tmnxVdoIfIngressQosPolicyId specifies the row index
         in the TIMETRA-QOS-MIB::tSapIngressTable corresponding to this
         ingress QoS policy. It has a value of '1' if no policy is specified.

         The value of this object can be set only when the value of 
         tmnxVdoIfVdoGrpId has been set to a value other than '0'."
    DEFVAL { 1 }
    ::= { tmnxVdoIfEntry 9 }
      
tmnxVdoIfEgressQosPolicyId                OBJECT-TYPE 
    SYNTAX         TSapEgressPolicyID 
    MAX-ACCESS     read-create
    STATUS         current
    DESCRIPTION 
        "The value of tmnxVdoIfEgressQosPolicyId specifies the row index
         in the TIMETRA-QOS-MIB::tSapEgressTable corresponding to this
         egress QoS policy. It has a value of '1' if no policy is specified.
    
         The value of this object can be set only when the value of 
         tmnxVdoIfVdoGrpId has been set to a value other than '0'."
    DEFVAL { 1 }
    ::= { tmnxVdoIfEntry 10 }
       
tmnxVdoIfAdi                OBJECT-TYPE
    SYNTAX          TruthValue
    MAX-ACCESS      read-create
    STATUS          current
    DESCRIPTION
        "The value of tmnxVdoIfAdi specifies whether Ad-Insertion (ADI) is
         enabled on this video interface."
    DEFVAL { false }
    ::= { tmnxVdoIfEntry 11 }

tmnxVdoIfRTClientAddrType OBJECT-TYPE
    SYNTAX     InetAddressType
    MAX-ACCESS read-create
    STATUS     current
    DESCRIPTION
        "The value of tmnxVdoIfRTClientAddrType specifies the type of 
         address represented by tmnxVdoIfRTClientAddr."
    DEFVAL { unknown }
    ::= { tmnxVdoIfEntry 12 }

tmnxVdoIfRTClientAddr OBJECT-TYPE
    SYNTAX     InetAddress (SIZE (0|4|16))
    MAX-ACCESS read-create
    STATUS     current
    DESCRIPTION
        "The value of tmnxVdoIfRTClientAddr specifies the IP address for the 
         retransmission (RT) client in the video interface within the service. 

         The RT client IP address is the originating address used for 
         communication with upstream RT servers. If no RT client address is 
         assigned, the RT client is operationally down as the RT client 
         configuration is incomplete. 
        
         For a VPLS service, the RT client address cannot be the same as an 
         existing address for the video interface, but it must be an address 
         within a video interface subnet. For IES and VPRN services, the RT 
         client address can be the same as an existing address for the video 
         interface or an address within a video interface subnet."
    DEFVAL { ''H }
    ::= { tmnxVdoIfEntry 13 }

tmnxVdoIfGatewayAddrType OBJECT-TYPE
    SYNTAX     InetAddressType
    MAX-ACCESS read-create
    STATUS     current
    DESCRIPTION
        "The value of tmnxVdoIfGatewayAddrType specifies the type of 
         address represented by tmnxVdoIfGatewayAddr."
    DEFVAL { unknown }
    ::= { tmnxVdoIfEntry 14 }

tmnxVdoIfGatewayAddr OBJECT-TYPE
    SYNTAX     InetAddress (SIZE (0|4|16))
    MAX-ACCESS read-create
    STATUS     current
    DESCRIPTION
        "The value of tmnxVdoIfGatewayAddr specifies the gateway IP address 
         for the video Interface within the VPLS service."
    DEFVAL { ''H }
    ::= { tmnxVdoIfEntry 15 }

tmnxVdoIfMcastSvcId OBJECT-TYPE
    SYNTAX     TmnxServId
    MAX-ACCESS read-create
    STATUS     current
    DESCRIPTION
        "The value of tmnxVdoIfMcastSvcId specifies the multicast service to 
         be used for sending replies in the multicast service instance. In 
         situations where multicast and unicast are carried in separate 
         service instances, the value of this object should be set on the 
         unicast video interface to form an association with the multicast 
         service.

         The default value of this object is same as the value of corresponding
         TIMETRA-SERV-MIB::svcId."
    ::= { tmnxVdoIfEntry 16 }

tmnxVdoIfIngressIpFilterId OBJECT-TYPE
    SYNTAX     TIPFilterID
    MAX-ACCESS read-create
    STATUS     current
    DESCRIPTION
        "The value of tmnxVdoIfIngressIpFilterId specifies the row index in 
         the TIMETRA-FILTER-MIB::tIPFilterTable corresponding to this ingress 
         filter. Filters control the forwarding and dropping of packets based 
         on IP criteria.  A value of zero (0) indicates that there is no 
         ip-filter-id associated with this interface.

         The value of this object can be set only when the value of 
         tmnxVdoIfVdoGrpId has been set to a value other than '0'."
    DEFVAL { 0 }
    ::= { tmnxVdoIfEntry 17 }

tmnxVdoIfIngressMacFilterId OBJECT-TYPE
    SYNTAX     TMACFilterID
    MAX-ACCESS read-create
    STATUS     current
    DESCRIPTION
        "The value of tmnxVdoIfIngressMacFilterId specifies the row index in 
         the TIMETRA-FILTER-MIB::tMacFilterTable corresponding to this ingress 
         filter. Filters control the forwarding and dropping of packets based 
         on IP criteria.  A value of zero (0) indicates that there is no 
         mac-filter-id associated with this interface.
         
         The value of this object can be set only when the value of 
         tmnxVdoIfVdoGrpId has been set to a value other than '0'."
    DEFVAL { 0 }
    ::= { tmnxVdoIfEntry 18 }

tmnxVdoIfEgressIpFilterId OBJECT-TYPE
    SYNTAX     TIPFilterID
    MAX-ACCESS read-create
    STATUS     current
    DESCRIPTION
        "The value of tmnxVdoIfEgressIpFilterId specifies the row index in 
         the TIMETRA-FILTER-MIB::tIPFilterTable corresponding to this egress 
         filter. Filters control the forwarding and dropping of packets based 
         on IP criteria.  A value of zero (0) indicates that there is no 
         ip-filter-id associated with this interface.
         
         The value of this object can be set only when the value of 
         tmnxVdoIfVdoGrpId has been set to a value other than '0'."
    DEFVAL { 0 }
    ::= { tmnxVdoIfEntry 19 }

tmnxVdoIfEgressMacFilterId OBJECT-TYPE
    SYNTAX     TMACFilterID
    MAX-ACCESS read-create
    STATUS     current
    DESCRIPTION
        "The value of tmnxVdoIfEgressMacFilterId specifies the row index in 
         the TIMETRA-FILTER-MIB::tMacFilterTable corresponding to this egress 
         filter. Filters control the forwarding and dropping of packets based 
         on IP criteria.  A value of zero (0) indicates that there is no 
         mac-filter-id associated with this interface.
         
         The value of this object can be set only when the value of 
         tmnxVdoIfVdoGrpId has been set to a value other than '0'."
    DEFVAL { 0 }
    ::= { tmnxVdoIfEntry 20 }

tmnxVdoIfScte30ControlAddrType OBJECT-TYPE
    SYNTAX     InetAddressType
    MAX-ACCESS read-create
    STATUS     current
    DESCRIPTION
        "The value of tmnxVdoIfScte30ControlAddrType specifies the type of 
         address represented by tmnxVdoIfScte30ControlAddr."
    DEFVAL { unknown }
    ::= { tmnxVdoIfEntry 21 }

tmnxVdoIfScte30ControlAddr OBJECT-TYPE
    SYNTAX     InetAddress (SIZE (0|4|16))
    MAX-ACCESS read-create
    STATUS     current
    DESCRIPTION
        "The value of tmnxVdoIfScte30ControlAddr specifies the local IP 
         address to which ad servers send Society of Cable Telecommunications 
         Engineers 30 (scte30) ad control streams. This address should be in the 
         same subnet as the ip address assigned to the video interface.

         The values of tmnxVdoIfScte30ControlAddr and tmnxVdoIfScte30DataAddr, 
         which specifies the local IP address to which ad servers send scte30 
         ad data streams, must be set together in the same SNMP request PDU 
         or else the set request will fail with an inconsistentValue error."
    DEFVAL { ''H }
    ::= { tmnxVdoIfEntry 22 }

tmnxVdoIfScte30DataAddrType OBJECT-TYPE
    SYNTAX     InetAddressType
    MAX-ACCESS read-create
    STATUS     current
    DESCRIPTION
        "The value of tmnxVdoIfScte30DataAddrType specifies the type of 
         address represented by tmnxVdoIfScte30DataAddr."
    DEFVAL { unknown }
    ::= { tmnxVdoIfEntry 23 }

tmnxVdoIfScte30DataAddr OBJECT-TYPE
    SYNTAX     InetAddress (SIZE (0|4|16))
    MAX-ACCESS read-create
    STATUS     current
    DESCRIPTION
        "The value of tmnxVdoIfScte30DataAddr specifies the local IP address 
         to which ad servers send Society of Cable Telecommunications 
         Engineers 30 (scte30) ad data streams. This address should be in the 
         same subnet as the ip address assigned to the video interface.

         The values of tmnxVdoIfScte30DataAddr and tmnxVdoIfScte30ControlAddr, 
         which specifies the local IP address to which ad servers send scte30 
         ad control streams, must be set together in the same SNMP request PDU 
         or else the set request will fail with an inconsistentValue error."
    DEFVAL { ''H }
    ::= { tmnxVdoIfEntry 24 }

tmnxVdoIfSapId OBJECT-TYPE
    SYNTAX     TmnxStrSapId
    MAX-ACCESS read-only
    STATUS     current
    DESCRIPTION
        "The value of tmnxVdoIfSapId indicates the control SAP for this video 
         interface."
    ::= { tmnxVdoIfEntry 25 }

tmnxVdoIfMcastProtocol  OBJECT-TYPE
    SYNTAX      INTEGER {
                         none (1),
                         pim  (2),
                         igmpSnooping (3)
                        }
    MAX-ACCESS  read-only
    STATUS      current
    DESCRIPTION
        "The value of tmnxVdoIfMcastProtocol indicates the multicast routing 
         protocol where this video interface is configured. For video control 
         and data traffic to flow correctly to the video ISA, the video 
         interface must be configured in the corresponding multicast routing 
         protocol. 

         In the VPLS case, the video sap is automatically added to IGMP-snooping
         and so the value of this object will be set to 'igmpSnooping'."
    DEFVAL { none }
    ::= { tmnxVdoIfEntry 26 }

tmnxVdoIfSessions OBJECT-TYPE
    SYNTAX     Unsigned32
    MAX-ACCESS read-only
    STATUS     current
    DESCRIPTION
        "The value of tmnxVdoIfSessions indicates the number of active sessions
         on this interface."
    ::= { tmnxVdoIfEntry 27 }

tmnxVdoIfCpmProtectPolicyId OBJECT-TYPE
    SYNTAX     TCpmProtPolicyID
    MAX-ACCESS read-create
    STATUS     current
    DESCRIPTION
        "The value of tmnxVdoIfCpmProtectPolicyId specifies the row index
         in the TIMETRA-SECURITY-MIB::tmnxCpmProtPolTable corresponding to the
         CPM Protection policy that would be applied to all RTCP control 
         traffic destined to this video interface. 

         If the value of this object is set to '0', then no CPM protection 
         policy has been provisioned for this video interface and the
         DOS protection is disabled."
    DEFVAL { 0 }
    ::= { tmnxVdoIfEntry 28 }

tmnxVdoIfRTMcastReply OBJECT-TYPE   
    SYNTAX          TmnxEnabledDisabled     
    MAX-ACCESS      read-create     
    STATUS          current     
    DESCRIPTION     
        "The value of tmnxVdoIfRTMcastReply specifies whether   
         or not the use of multicast retransmission packets is enabled      
         by the Retransmission Server in response to a number of identical      
         retransmission requests."      
    DEFVAL { disabled }     
    ::= { tmnxVdoIfEntry 29 }   
    
tmnxVdoIfRTCount OBJECT-TYPE    
    SYNTAX          Unsigned32 (2..1024)    
    MAX-ACCESS      read-create     
    STATUS          current     
    DESCRIPTION     
        "The value of tmnxVdoIfRTCount specifies the integer number    
         of identical retransmission requests received for a packet in a    
         sampling interval after which a reply will be sent as multicast    
         Payload Type 33."      
    DEFVAL { 5 }    
    ::= { tmnxVdoIfEntry 30 }   
    
tmnxVdoIfRTInterval OBJECT-TYPE     
    SYNTAX          Unsigned32 (100..8000)      
    UNITS           "milliseconds"      
    MAX-ACCESS      read-create     
    STATUS          current     
    DESCRIPTION     
        "The value of tmnxVdoIfRTInterval specifies the integer number      
         of milliseconds for a sampling interval."      
    DEFVAL { 100 }      
    ::= { tmnxVdoIfEntry 31 }   
    
tmnxVdoIfRTHoldTime OBJECT-TYPE     
    SYNTAX          Unsigned32 (0..1000)
    UNITS           "milliseconds"      
    MAX-ACCESS      read-create     
    STATUS          current     
    DESCRIPTION     
        "The value of tmnxVdoIfRTHoldTime specifies the integer number      
         of milliseconds after a multicast reply is sent that the Retransmission    
         Server will wait before starting a new sampling period."   
    DEFVAL { 50 }   
    ::= { tmnxVdoIfEntry 32 }

tmnxVdoIfAcctPolicyId OBJECT-TYPE     
    SYNTAX          Unsigned32 (0|1..99)      
    MAX-ACCESS      read-create     
    STATUS          current     
    DESCRIPTION     
        "The value of tmnxVdoIfAcctPolicyId specifies the accounting policy 
         associated with the given video interface.  The value 0 specifies that 
         no accounting policy is associated." 
    DEFVAL { 0 }     
    ::= { tmnxVdoIfEntry 33 }  

tmnxVdoIfOutputFormat OBJECT-TYPE     
    SYNTAX          TmnxVdoOutputFormat      
    MAX-ACCESS      read-create     
    STATUS          current     
    DESCRIPTION     
        "The value of tmnxVdoIfOutputFormat specifies the output format of the 
         associated video stream." 
    DEFVAL { rtp-udp }     
    ::= { tmnxVdoIfEntry 34 } 

--
--  Video Interface Address Table
--

tmnxVdoIfAddrTableLastChanged OBJECT-TYPE
    SYNTAX      TimeStamp
    MAX-ACCESS  read-only
    STATUS      current
    DESCRIPTION
        "The value of tmnxVdoIfAddrTableLastChanged indicates the
         sysUpTime at the time of the last modification to
         tmnxVdoIfAddrTable by adding, deleting an entry or change
         to a writable object in the table.

         If no changes were made to the table since the last
         re-initialization of the local network management subsystem,
         then this object contains a zero value."
    ::= { tmnxVdoGlobalObjs 2 }

tmnxVdoIfAddrTable  OBJECT-TYPE
    SYNTAX      SEQUENCE OF TmnxVdoIfAddrEntry
    MAX-ACCESS  not-accessible
    STATUS      current
    DESCRIPTION
        "The tmnxVdoIfAddrTable has an entry for each IP address configured 
         for a video interface in the system. Each interface may have more
         than one IP address assigned to it."
    ::= { tmnxVdoObjs 2 }

tmnxVdoIfAddrEntry  OBJECT-TYPE
    SYNTAX      TmnxVdoIfAddrEntry
    MAX-ACCESS  not-accessible
    STATUS      current
    DESCRIPTION
        "Each row entry represents an IP address assigned to a video interface.
         Entries can be created and deleted by the user."
    INDEX { svcId, 
            tmnxVdoIfName, 
            tmnxVdoIfAddrIpAddrType, 
            tmnxVdoIfAddrIpAddress, 
            tmnxVdoIfAddrPrefixLen 
    }
    ::= { tmnxVdoIfAddrTable 1 }

TmnxVdoIfAddrEntry ::= SEQUENCE {
        tmnxVdoIfAddrIpAddrType         InetAddressType,
        tmnxVdoIfAddrIpAddress          InetAddress,
        tmnxVdoIfAddrPrefixLen          InetAddressPrefixLength,
        tmnxVdoIfAddrRowStatus          RowStatus
    }

tmnxVdoIfAddrIpAddrType  OBJECT-TYPE
    SYNTAX      InetAddressType
    MAX-ACCESS  not-accessible
    STATUS      current
    DESCRIPTION
        "The value of tmnxVdoIfAddrIpAddrType specifies the type of the
         tmnxVdoIfAddrIpAddress address assigned to the video interface."
    ::= { tmnxVdoIfAddrEntry 1 }

tmnxVdoIfAddrIpAddress  OBJECT-TYPE
    SYNTAX      InetAddress (SIZE(4|16))
    MAX-ACCESS  not-accessible
    STATUS      current
    DESCRIPTION
        "The value of tmnxVdoIfAddrIpAddress specifies the IP address of
         the video interface."
    ::= { tmnxVdoIfAddrEntry 2 }

tmnxVdoIfAddrPrefixLen  OBJECT-TYPE
    SYNTAX      InetAddressPrefixLength
    MAX-ACCESS  not-accessible
    STATUS      current
    DESCRIPTION
        "The value of tmnxVdoIfAddrPrefixLen specifies the length of
         the IP netmask for this video interface address."
    ::= { tmnxVdoIfAddrEntry 3 }

tmnxVdoIfAddrRowStatus  OBJECT-TYPE
    SYNTAX      RowStatus
    MAX-ACCESS  read-create
    STATUS      current
    DESCRIPTION
        "The value of tmnxVdoIfAddrRowStatus specifies the row status of
         this row. The row status is used for creation, deletion or control
         of tmnxVdoIfAddrTable entries."
    ::= { tmnxVdoIfAddrEntry 4 }


--
-- Video ISA Group table
--

tmnxVdoGrpTableLastChanged OBJECT-TYPE
    SYNTAX      TimeStamp
    MAX-ACCESS  read-only
    STATUS      current
    DESCRIPTION
        "The value of tmnxVdoGrpTableLastChanged indicates the
         sysUpTime at the time of the last modification to
         tmnxVdoGrpTable by adding, deleting an entry or change
         to a writable object in the table.

         If no changes were made to the table since the last
         re-initialization of the local network management subsystem,
         then this object contains a zero value."
    ::= { tmnxVdoGlobalObjs 3 }

tmnxVdoGrpTable OBJECT-TYPE
    SYNTAX      SEQUENCE OF TmnxVdoGrpEntry
    MAX-ACCESS  not-accessible
    STATUS      current
    DESCRIPTION
        "tmnxVdoGrpTable has an entry for each video group configured 
         in the system.
         
         The table tmnxVdoGrpTable is used to create and remove Video ISA
         groups. A Video ISA group is used to configure properties relating to
         video interfaces and services." 
    ::= { tmnxVdoObjs 3 }

tmnxVdoGrpEntry OBJECT-TYPE
    SYNTAX      TmnxVdoGrpEntry
    MAX-ACCESS  not-accessible
    STATUS      current
    DESCRIPTION
        "Each row entry represents a video group in the system. Entries
         can be created and deleted by the user."
    INDEX { tmnxVdoGrpId }
    ::= { tmnxVdoGrpTable 1 }

TmnxVdoGrpEntry ::= SEQUENCE {
    tmnxVdoGrpId                     TmnxVdoGrpIdIndex,
    tmnxVdoGrpRowStatus              RowStatus,
    tmnxVdoGrpLastChanged            TimeStamp,
    tmnxVdoGrpAdminState             TmnxAdminState,
    tmnxVdoGrpOperState              TmnxOperState,
    tmnxVdoGrpDescription            TItemDescription,
    tmnxVdoGrpLocalRTServerState     TruthValue,
    tmnxVdoGrpFCCServerState         TruthValue,
    tmnxVdoGrpADIServerState         TruthValue,
    tmnxVdoGrpResvRet                Unsigned32,
    tmnxVdoGrpAnalyzerState          TruthValue,
    tmnxVdoGrpStreamSelectionState   TruthValue
}

tmnxVdoGrpId                 OBJECT-TYPE
    SYNTAX         TmnxVdoGrpIdIndex
    MAX-ACCESS     not-accessible
    STATUS         current
    DESCRIPTION
        "The value of tmnxVdoGrpId specifies the identifier for this 
         video group."
    ::= { tmnxVdoGrpEntry 1 }

tmnxVdoGrpRowStatus                 OBJECT-TYPE
    SYNTAX         RowStatus
    MAX-ACCESS     read-create
    STATUS         current
    DESCRIPTION
        "The value of tmnxVdoGrpRowStatus specifies the row status of this row.
         It is used for creation/deletion of a video group."
    ::= { tmnxVdoGrpEntry 2 }

tmnxVdoGrpLastChanged                 OBJECT-TYPE
    SYNTAX         TimeStamp
    MAX-ACCESS     read-only
    STATUS         current
    DESCRIPTION
        "The value of tmnxVdoGrpLastChanged indicates the timestamp of the 
         last change to this row in tmnxVdoGrpTable."
    ::= { tmnxVdoGrpEntry 3 }

tmnxVdoGrpAdminState                 OBJECT-TYPE
    SYNTAX         TmnxAdminState
    MAX-ACCESS     read-create
    STATUS         current
    DESCRIPTION
        "The value of tmnxVdoGrpAdminState specifies the desired administrative
         state of this video group."
    DEFVAL { outOfService }
    ::= { tmnxVdoGrpEntry 4 }

tmnxVdoGrpOperState                 OBJECT-TYPE
    SYNTAX         TmnxOperState
    MAX-ACCESS     read-only
    STATUS         current
    DESCRIPTION
        "The value of tmnxVdoGrpOperState specifies the current operational
         status of this video group."
    ::= { tmnxVdoGrpEntry 5 }

tmnxVdoGrpDescription                 OBJECT-TYPE
    SYNTAX         TItemDescription 
    MAX-ACCESS     read-create
    STATUS         current
    DESCRIPTION
        "The value of tmnxVdoGrpDescription specifies the user provided 
         description string for this video group."
    DEFVAL { ''H }      -- the empty string
    ::= { tmnxVdoGrpEntry 6 }

tmnxVdoGrpLocalRTServerState            OBJECT-TYPE
    SYNTAX         TruthValue
    MAX-ACCESS     read-create
    STATUS         current
    DESCRIPTION
        "The value of tmnxVdoGrpLocalRTServerState specifies whether or not 
         local Retransmission (RT) server is enabled on this video group."
    DEFVAL { false }
    ::= { tmnxVdoGrpEntry 7 }
          
tmnxVdoGrpFCCServerState            OBJECT-TYPE
    SYNTAX         TruthValue
    MAX-ACCESS     read-create
    STATUS         current
    DESCRIPTION
        "The value of tmnxVdoGrpFCCServerState specifies whether of not Fast
         Channel Change (FCC) server is enabled on this video group."
    DEFVAL { false }
    ::= { tmnxVdoGrpEntry 8 }
              
tmnxVdoGrpADIServerState                 OBJECT-TYPE
    SYNTAX         TruthValue
    MAX-ACCESS     read-create
    STATUS         current
    DESCRIPTION
        "The value of tmnxVdoGrpADIServerState specifies whether or not Ad
         Insert (ADI) server is enabled on this video group."
    DEFVAL { false }
    ::= { tmnxVdoGrpEntry 9 }

tmnxVdoGrpResvRet                 OBJECT-TYPE
    SYNTAX         Unsigned32
    UNITS          "mbps"
    MAX-ACCESS     read-create
    STATUS         current
    DESCRIPTION
        "The value of tmnxVdoGrpResvRet specifies to reserve egress bandwidth 
         for Retransmission (RET) in all the ISAs within a video group. If the 
         amount of egress bandwidth is less than the reserved amount, the Fast
         Channel Change (FCC) requests are discarded and only the Retransmission
         (RET) requests are processed."
    DEFVAL { 0 }
    ::= { tmnxVdoGrpEntry 10 }

tmnxVdoGrpAnalyzerState                 OBJECT-TYPE
    SYNTAX         TruthValue
    MAX-ACCESS     read-create
    STATUS         current
    DESCRIPTION
        "The value of tmnxVdoGrpAnalyzerState specifies whether or not the video 
         analyzer is enabled for all streams on this video group."
    DEFVAL { false }
    ::= { tmnxVdoGrpEntry 11 }

tmnxVdoGrpStreamSelectionState                 OBJECT-TYPE
    SYNTAX         TruthValue
    MAX-ACCESS     read-create
    STATUS         current
    DESCRIPTION
        "The value of tmnxVdoGrpStreamSelectionState specifies whether or not 
         stream selection is enabled on this video group."
    DEFVAL { false }
    ::= { tmnxVdoGrpEntry 12 }

--
--      Video ISA Group MDA table
--

tmnxVdoGrpMDATableLastChanged OBJECT-TYPE
    SYNTAX      TimeStamp
    MAX-ACCESS  read-only
    STATUS      current
    DESCRIPTION
        "The value of tmnxVdoGrpMDATableLastChanged indicates the
         sysUpTime at the time of the last modification to
         tmnxVdoGrpMDATable by adding, deleting an entry or change
         to a writable object in the table.

         If no changes were made to the table since the last
         re-initialization of the local network management subsystem,
         then this object contains a zero value."
    ::= { tmnxVdoGlobalObjs 4 }

tmnxVdoGrpMDATable OBJECT-TYPE
    SYNTAX      SEQUENCE OF TmnxVdoGrpMDAEntry
    MAX-ACCESS  not-accessible
    STATUS      current
    DESCRIPTION
        "The tmnxVdoGrpMDATable has an entry for each MDA configured for 
         the Video ISP Group in the system. A specific MDA is configured
         for only a tmnxVdoGrpId."
    ::= { tmnxVdoObjs 4 }

tmnxVdoGrpMDAEntry       OBJECT-TYPE
    SYNTAX      TmnxVdoGrpMDAEntry
    MAX-ACCESS  not-accessible
    STATUS      current
    DESCRIPTION
        "Each row entry represents an MDA configured for a Video ISA Group
         in the system. Entries are created and deleted by the user." 
    INDEX { tmnxVdoGrpId, 
            tmnxChassisIndex, 
            tmnxCardSlotNum, 
            tmnxMDASlotNum 
    }
    ::= { tmnxVdoGrpMDATable 1 }

TmnxVdoGrpMDAEntry ::= SEQUENCE {
        tmnxVdoGrpMdaRowStatus            RowStatus,
        tmnxVdoGrpMdaAdminState           TmnxAdminState,
        tmnxVdoGrpMdaOperState            TmnxOperState,
        tmnxVdoGrpMdaUsedMemory           Gauge32,
        tmnxVdoGrpMdaAvailableMemory      Gauge32,
        tmnxVdoGrpMdaChannels             Gauge32,
        tmnxVdoGrpMdaChannelAllocFails    Counter32,
        tmnxVdoGrpMdaMaxBwExceeded        Counter32,
        tmnxVdoGrpMdaBwInUse              Gauge32,
        tmnxVdoGrpMdaActiveRtcpSessions   Gauge32,
        tmnxVdoGrpMdaEgressStreamResets   Counter32,
        tmnxVdoGrpMdaIngressStreamResets  Counter32,
        tmnxVdoGrpMdaAdStreamResets       Counter32,
        tmnxVdoGrpMdaAdStreamAborts       Counter32,
        tmnxVdoGrpMdaSsrcCollisions       Counter32,
        tmnxVdoGrpMdaRxDataPackets        Counter64,
        tmnxVdoGrpMdaRxDataPacketsLow32   Counter32,
        tmnxVdoGrpMdaRxDataPacketsHigh32  Counter32,
        tmnxVdoGrpMdaRxDataOctets         Counter64,
        tmnxVdoGrpMdaRxDataOctetsLow32    Counter32,
        tmnxVdoGrpMdaRxDataOctetsHigh32   Counter32,
        tmnxVdoGrpMdaRxDataPacketErrors   Counter64,
        tmnxVdoGrpMdaRxDataPktErrsLow32   Counter32,
        tmnxVdoGrpMdaRxDataPktErrsHigh32  Counter32,
        tmnxVdoGrpMdaTxDataPackets        Counter64,
        tmnxVdoGrpMdaTxDataPacketsLow32   Counter32,
        tmnxVdoGrpMdaTxDataPacketsHigh32  Counter32,
        tmnxVdoGrpMdaTxDataOctets         Counter64,
        tmnxVdoGrpMdaTxDataOctetsLow32    Counter32,
        tmnxVdoGrpMdaTxDataOctetsHigh32   Counter32,
        tmnxVdoGrpMdaTxDataPacketErrors   Counter64,
        tmnxVdoGrpMdaTxDataPktErrsLow32   Counter32,
        tmnxVdoGrpMdaTxDataPktErrsHigh32  Counter32,
        tmnxVdoGrpMdaRtcpParseErrors      Counter32,
        tmnxVdoGrpMdaRtcpConfigErrors     Counter32,
        tmnxVdoGrpMdaRtcpIpcErrors        Counter32,
        tmnxVdoGrpMdaRtcpSgErrors         Counter32,
        tmnxVdoGrpMdaRtcpSubErrors        Counter32,
        tmnxVdoGrpMdaRtcpIntErrors        Counter32,
        tmnxVdoGrpMdaTxLostPackets        Counter32,
        tmnxVdoGrpMdaRequestedRtpPkts     Counter32,
        tmnxVdoGrpMdaHighPktPoolLimitHit  Counter32,
        tmnxVdoGrpMdaMallocFailures       Counter32,
        tmnxVdoGrpMdaDentDroppedPkts      Counter32,
        tmnxVdoGrpMdaBwPeak               Gauge32,
        tmnxVdoGrpMdaCurTotalRetBw        Gauge32,
        tmnxVdoGrpMdaPeakRetBw            Gauge32,
        tmnxVdoGrpMdaCurFccBw             Gauge32,
        tmnxVdoGrpMdaFccDropCntReq        Gauge32,
        tmnxVdoGrpMdaMcRtcp               Counter64,  
        tmnxVdoGrpMdaMcRtcpLow32          Counter32,  
        tmnxVdoGrpMdaMcRtcpHigh32         Counter32,  
        tmnxVdoGrpMdaMcRudp               Counter64,
        tmnxVdoGrpMdaMcRudpLow32          Counter32,
        tmnxVdoGrpMdaMcRudpHigh32         Counter32,
        tmnxVdoGrpMdaMcRetReqCrt          Counter64,
        tmnxVdoGrpMdaMcRetReqCrtLow32     Counter32,  
        tmnxVdoGrpMdaMcRetReqCrtHigh32    Counter32,
        tmnxVdoGrpMdaRetReqQnc            Counter64,
        tmnxVdoGrpMdaRetReqQncLow32       Counter32,
        tmnxVdoGrpMdaRetReqQncHigh32      Counter32,
        tmnxVdoGrpMdaPktsLostInSeq10      Counter32,
        tmnxVdoGrpMdaPktsLostInSeq20      Counter32,
        tmnxVdoGrpMdaPktsLostInSeq30      Counter32,
        tmnxVdoGrpMdaPktsLostInSeq40      Counter32,
        tmnxVdoGrpMdaPktsLostInSeqMore    Counter32
    }

tmnxVdoGrpMdaRowStatus                  OBJECT-TYPE
    SYNTAX         RowStatus
    MAX-ACCESS     read-create
    STATUS         current
    DESCRIPTION
        "The value of tmnxVdoGrpMdaRowStatus specifies the row status of this
         row entry. It is used for the association or removal of an MDA in the 
         Video ISA Group."
    ::= { tmnxVdoGrpMDAEntry 1 }

tmnxVdoGrpMdaAdminState                 OBJECT-TYPE
    SYNTAX         TmnxAdminState
    MAX-ACCESS     read-only
    STATUS         current
    DESCRIPTION
        "The value of tmnxVdoGrpMdaAdminState indicates the administrative 
         state of the video group on this MDA."
    ::= { tmnxVdoGrpMDAEntry 2 }

tmnxVdoGrpMdaOperState                  OBJECT-TYPE
    SYNTAX         TmnxOperState
    MAX-ACCESS     read-only
    STATUS         current
    DESCRIPTION
        "The value of tmnxVdoGrpMdaOperState indicates the current operational 
         state of the video group on this MDA."
    ::= { tmnxVdoGrpMDAEntry 3 }

tmnxVdoGrpMdaUsedMemory                 OBJECT-TYPE
    SYNTAX         Gauge32
    UNITS          "Bytes"
    MAX-ACCESS     read-only
    STATUS         current
    DESCRIPTION
        "The value of tmnxVdoGrpMdaUsedMemory indicates the amount of cache 
         being used by the video group for storing the video stream."
    ::= { tmnxVdoGrpMDAEntry 4 }

tmnxVdoGrpMdaAvailableMemory            OBJECT-TYPE
    SYNTAX         Gauge32
    UNITS          "Bytes"
    MAX-ACCESS     read-only
    STATUS         current
    DESCRIPTION
        "The value of tmnxVdoGrpMdaAvailableMemory indicates the amount of
         cache available on the MDA for storing the video stream."
    ::= { tmnxVdoGrpMDAEntry 5 }

tmnxVdoGrpMdaChannels                   OBJECT-TYPE
    SYNTAX         Gauge32
    MAX-ACCESS     read-only
    STATUS         current
    DESCRIPTION
        "The value of tmnxVdoGrpMdaChannels indicates the number of channels
         being served on this MDA."
    ::= { tmnxVdoGrpMDAEntry 6 }

tmnxVdoGrpMdaChannelAllocFails          OBJECT-TYPE
    SYNTAX         Counter32
    MAX-ACCESS     read-only
    STATUS         current
    DESCRIPTION
        "The value of tmnxVdoGrpMdaChannelAllocFails indicates the number of 
         failed channel allocations on this MDA."
    ::= { tmnxVdoGrpMDAEntry 7 }

tmnxVdoGrpMdaMaxBwExceeded              OBJECT-TYPE
    SYNTAX         Counter32
    MAX-ACCESS     read-only
    STATUS         current
    DESCRIPTION
        "The value of tmnxVdoGrpMdaMaxBwExceeded indicates the number of times
         maximum allowed bandwidth has been exceeded for each egress stream."
    ::= { tmnxVdoGrpMDAEntry 8 }

tmnxVdoGrpMdaBwInUse                    OBJECT-TYPE
    SYNTAX         Gauge32
    UNITS          "kbps"
    MAX-ACCESS     read-only
    STATUS         current
    DESCRIPTION
        "The value of tmnxVdoGrpMdaBwInUse indicates the total aggregate 
         bandwidth of the currently running egress streams."
    ::= { tmnxVdoGrpMDAEntry 9 }

tmnxVdoGrpMdaActiveRtcpSessions         OBJECT-TYPE
    SYNTAX         Gauge32
    MAX-ACCESS     read-only
    STATUS         current
    DESCRIPTION
        "The value of tmnxVdoGrpMdaActiveRtcpSessions indicates the number 
         of active Real Time Transport Control Protocol (RTCP) sessions on 
         this MDA."
    ::= { tmnxVdoGrpMDAEntry 10 }

tmnxVdoGrpMdaEgressStreamResets         OBJECT-TYPE
    SYNTAX         Counter32
    MAX-ACCESS     read-only
    STATUS         current
    DESCRIPTION
        "The value of tmnxVdoGrpMdaEgressStreamResets indicates the number of 
         egress stream resets on this MDA. An egress stream reset occurs when 
         there are no packets to transmit on the MDA."
    ::= { tmnxVdoGrpMDAEntry 11 }

tmnxVdoGrpMdaIngressStreamResets        OBJECT-TYPE
    SYNTAX         Counter32
    MAX-ACCESS     read-only
    STATUS         current
    DESCRIPTION
        "The value of tmnxVdoGrpMdaIngressStreamResets indicates the number of
         ingress stream resets on this MDA. An ingress stream reset occurs when 
         the ingress stream stopped coming in for more than one second."
    ::= { tmnxVdoGrpMDAEntry 12 }

tmnxVdoGrpMdaAdStreamResets             OBJECT-TYPE
    SYNTAX         Counter32
    MAX-ACCESS     read-only
    STATUS         current
    DESCRIPTION
        "The value of tmnxVdoGrpMdaAdStreamResets indicates the number of ad 
         stream resets on this MDA. An ad stream reset occurs when the ingress
         ad stream stops."
    ::= { tmnxVdoGrpMDAEntry 13 }

tmnxVdoGrpMdaAdStreamAborts             OBJECT-TYPE
    SYNTAX         Counter32
    MAX-ACCESS     read-only
    STATUS         current
    DESCRIPTION
        "The value of tmnxVdoGrpMdaAdStreamAborts indicates the number of ad 
         stream aborts on this MDA. An ad stream abort could happen when an 
         egress reset happens."
    ::= { tmnxVdoGrpMDAEntry 14 }

tmnxVdoGrpMdaSsrcCollisions             OBJECT-TYPE
    SYNTAX         Counter32
    MAX-ACCESS     read-only
    STATUS         current
    DESCRIPTION
        "The value of tmnxVdoGrpMdaSsrcCollisions indicates the number of 
         synchronization source (SSRC) id collisions on this MDA."
    ::= { tmnxVdoGrpMDAEntry 15 }

tmnxVdoGrpMdaRxDataPackets              OBJECT-TYPE
    SYNTAX         Counter64
    MAX-ACCESS     read-only
    STATUS         current
    DESCRIPTION
        "The value of tmnxVdoGrpMdaRxDataPackets indicates the number of data 
         packets received on this MDA."
    ::= { tmnxVdoGrpMDAEntry 16 }

tmnxVdoGrpMdaRxDataPacketsLow32 OBJECT-TYPE
    SYNTAX     Counter32
    MAX-ACCESS read-only
    STATUS     current
    DESCRIPTION
        "The value of tmnxVdoGrpMdaRxDataPacketsLow32 indicates the lower 32 
         bits of the value of tmnxVdoGrpMdaRxDataPackets."
    ::= { tmnxVdoGrpMDAEntry 17 }

tmnxVdoGrpMdaRxDataPacketsHigh32 OBJECT-TYPE
    SYNTAX     Counter32
    MAX-ACCESS read-only
    STATUS     current
    DESCRIPTION
        "The value of tmnxVdoGrpMdaRxDataPacketsHigh32 indicates the higher 32 
         bits of the value of tmnxVdoGrpMdaRxDataPackets."
    ::= { tmnxVdoGrpMDAEntry 18 }

tmnxVdoGrpMdaRxDataOctets               OBJECT-TYPE
    SYNTAX         Counter64
    MAX-ACCESS     read-only
    STATUS         current
    DESCRIPTION
        "The value of tmnxVdoGrpMdaRxDataOctets indicates the number of data 
         octets received on this MDA."
    ::= { tmnxVdoGrpMDAEntry 19 }

tmnxVdoGrpMdaRxDataOctetsLow32 OBJECT-TYPE
    SYNTAX     Counter32
    MAX-ACCESS read-only
    STATUS     current
    DESCRIPTION
        "The value of tmnxVdoGrpMdaRxDataOctetsLow32 indicates the lower 32 
         bits of the value of tmnxVdoGrpMdaRxDataOctets."
    ::= { tmnxVdoGrpMDAEntry 20 }

tmnxVdoGrpMdaRxDataOctetsHigh32 OBJECT-TYPE
    SYNTAX     Counter32
    MAX-ACCESS read-only
    STATUS     current
    DESCRIPTION
        "The value of tmnxVdoGrpMdaRxDataOctetsHigh32 indicates the higher 32 
         bits of the value of tmnxVdoGrpMdaRxDataOctets."
    ::= { tmnxVdoGrpMDAEntry 21 }

tmnxVdoGrpMdaRxDataPacketErrors         OBJECT-TYPE
    SYNTAX         Counter64
    MAX-ACCESS     read-only
    STATUS         current
    DESCRIPTION
        "The value of tmnxVdoGrpMdaRxDataPacketErrors indicates the number of 
         malformed or non-RTP (Real Time Transport Protocol) packets received 
         on this MDA."
    ::= { tmnxVdoGrpMDAEntry 22 }

tmnxVdoGrpMdaRxDataPktErrsLow32 OBJECT-TYPE
    SYNTAX     Counter32
    MAX-ACCESS read-only
    STATUS     current
    DESCRIPTION
        "The value of tmnxVdoGrpMdaRxDataPktErrsLow32 indicates the lower 32 
         bits of the value of tmnxVdoGrpMdaRxDataPacketErrors."
    ::= { tmnxVdoGrpMDAEntry 23 }

tmnxVdoGrpMdaRxDataPktErrsHigh32 OBJECT-TYPE
    SYNTAX     Counter32
    MAX-ACCESS read-only
    STATUS     current
    DESCRIPTION
        "The value of tmnxVdoGrpMdaRxDataPktErrsHigh32 indicates the higher 32 
         bits of the value of tmnxVdoGrpMdaRxDataPacketErrors."
    ::= { tmnxVdoGrpMDAEntry 24 }

tmnxVdoGrpMdaTxDataPackets              OBJECT-TYPE
    SYNTAX         Counter64
    MAX-ACCESS     read-only
    STATUS         current
    DESCRIPTION
        "The value of tmnxVdoGrpMdaTxDataPackets indicates the number of data 
         packets transmitted on this MDA."
    ::= { tmnxVdoGrpMDAEntry 25 }

tmnxVdoGrpMdaTxDataPacketsLow32 OBJECT-TYPE
    SYNTAX     Counter32
    MAX-ACCESS read-only
    STATUS     current
    DESCRIPTION
        "The value of tmnxVdoGrpMdaTxDataPacketsLow32 indicates the lower 32 
         bits of the value of tmnxVdoGrpMdaTxDataPackets."
    ::= { tmnxVdoGrpMDAEntry 26 }

tmnxVdoGrpMdaTxDataPacketsHigh32 OBJECT-TYPE
    SYNTAX     Counter32
    MAX-ACCESS read-only
    STATUS     current
    DESCRIPTION
        "The value of tmnxVdoGrpMdaTxDataPacketsHigh32 indicates the higher 32 
         bits of the value of tmnxVdoGrpMdaTxDataPackets."
    ::= { tmnxVdoGrpMDAEntry 27 }

tmnxVdoGrpMdaTxDataOctets               OBJECT-TYPE
    SYNTAX         Counter64
    MAX-ACCESS     read-only
    STATUS         current
    DESCRIPTION
        "The value of tmnxVdoGrpMdaTxDataOctets indicates the number of data 
         octets transmitted on this MDA."
    ::= { tmnxVdoGrpMDAEntry 28 }

tmnxVdoGrpMdaTxDataOctetsLow32 OBJECT-TYPE
    SYNTAX     Counter32
    MAX-ACCESS read-only
    STATUS     current
    DESCRIPTION
        "The value of tmnxVdoGrpMdaTxDataOctetsLow32 indicates the lower 32 
         bits of the value of tmnxVdoGrpMdaTxDataOctets."
    ::= { tmnxVdoGrpMDAEntry 29 }

tmnxVdoGrpMdaTxDataOctetsHigh32 OBJECT-TYPE
    SYNTAX     Counter32
    MAX-ACCESS read-only
    STATUS     current
    DESCRIPTION
        "The value of tmnxVdoGrpMdaTxDataOctetsHigh32 indicates the higher 32 
         bits of the value of tmnxVdoGrpMdaTxDataOctets."
    ::= { tmnxVdoGrpMDAEntry 30 }

tmnxVdoGrpMdaTxDataPacketErrors         OBJECT-TYPE
    SYNTAX         Counter64
    MAX-ACCESS     read-only
    STATUS         current
    DESCRIPTION
        "The value of tmnxVdoGrpMdaTxDataPacketErrors indicates the number of 
         failed data packets due to lack of resources to be transmitted on 
         this MDA."
    ::= { tmnxVdoGrpMDAEntry 31 }

tmnxVdoGrpMdaTxDataPktErrsLow32 OBJECT-TYPE
    SYNTAX     Counter32
    MAX-ACCESS read-only
    STATUS     current
    DESCRIPTION
        "The value of tmnxVdoGrpMdaTxDataPktErrsLow32 indicates the lower 32 
         bits of the value of tmnxVdoGrpMdaTxDataPacketErrors."
    ::= { tmnxVdoGrpMDAEntry 32 }

tmnxVdoGrpMdaTxDataPktErrsHigh32 OBJECT-TYPE
    SYNTAX     Counter32
    MAX-ACCESS read-only
    STATUS     current
    DESCRIPTION
        "The value of tmnxVdoGrpMdaTxDataPktErrsHigh32 indicates the higher 32 
         bits of the value of tmnxVdoGrpMdaTxDataPacketErrors."
    ::= { tmnxVdoGrpMDAEntry 33 }

tmnxVdoGrpMdaRtcpParseErrors         OBJECT-TYPE
    SYNTAX         Counter32
    MAX-ACCESS     read-only
    STATUS         current
    DESCRIPTION
        "The value of tmnxVdoGrpMdaRtcpParseErrors indicates the number of 
         Real-time Transport Control Protocol (RTCP) packet parsing errors on 
         this MDA."
    ::= { tmnxVdoGrpMDAEntry 34 }

tmnxVdoGrpMdaRtcpConfigErrors         OBJECT-TYPE
    SYNTAX         Counter32
    MAX-ACCESS     read-only
    STATUS         current
    DESCRIPTION
        "The value of tmnxVdoGrpMdaRtcpConfigErrors indicates the number of 
         Real-time Transport Control Protocol (RTCP) config errors on 
         this MDA. These errors occur when there is inconsistency between the 
         RTCP values and the configured values."
    ::= { tmnxVdoGrpMDAEntry 35 }

tmnxVdoGrpMdaRtcpIpcErrors         OBJECT-TYPE
    SYNTAX         Counter32
    MAX-ACCESS     read-only
    STATUS         current
    DESCRIPTION
        "The value of tmnxVdoGrpMdaRtcpIpcErrors indicates the number of 
         Real-time Transport Control Protocol (RTCP) inter-process communication
         message processing errors on this MDA."
    ::= { tmnxVdoGrpMDAEntry 36 }

tmnxVdoGrpMdaRtcpSgErrors         OBJECT-TYPE
    SYNTAX         Counter32
    MAX-ACCESS     read-only
    STATUS         current
    DESCRIPTION
        "The value of tmnxVdoGrpMdaRtcpSgErrors indicates the number of 
         Real-time Transport Control Protocol (RTCP) channel errors on 
         this MDA. These errors occue when a channel is not found for a given 
         interface to process RTCP packets."
    ::= { tmnxVdoGrpMDAEntry 37 }

tmnxVdoGrpMdaRtcpSubErrors         OBJECT-TYPE
    SYNTAX         Counter32
    MAX-ACCESS     read-only
    STATUS         current
    DESCRIPTION
        "The value of tmnxVdoGrpMdaRtcpSubErrors indicates the number of 
         Real-time Transport Control Protocol (RTCP) subscriber parameter errors 
         on this MDA. These errors occur when the subscriber calculations 
         exceed the maximum allowed bandwidth."
    ::= { tmnxVdoGrpMDAEntry 38 }

tmnxVdoGrpMdaRtcpIntErrors         OBJECT-TYPE
    SYNTAX         Counter32
    MAX-ACCESS     read-only
    STATUS         current
    DESCRIPTION
        "The value of tmnxVdoGrpMdaRtcpIntErrors indicates the number of 
         Real-time Transport Control Protocol (RTCP) interface related errors 
         on this MDA."
    ::= { tmnxVdoGrpMDAEntry 39 }

tmnxVdoGrpMdaTxLostPackets        OBJECT-TYPE
    SYNTAX         Counter32
    MAX-ACCESS     read-only
    STATUS         current
    DESCRIPTION
        "The value of tmnxVdoGrpMdaTxLostPackets indicates the number of 
         packets not found in the video MDA buffer for retransmission. When a 
         retransmission request arrives, packets are checked in the buffer and 
         if they are not found, the value of this object is incremented."
    ::= { tmnxVdoGrpMDAEntry 40 }

tmnxVdoGrpMdaRequestedRtpPkts    OBJECT-TYPE
    SYNTAX         Counter32
    MAX-ACCESS     read-only
    STATUS         current
    DESCRIPTION
        "The value of tmnxVdoGrpMdaRequestedRtpPkts indicates the number of 
         Real-time Transport Protocol (RTP) packets requested in the Real-time 
         Transport Control Protocol (RTCP) feedback (FB) messages received on 
         this MDA."
    ::= { tmnxVdoGrpMDAEntry 41 }

tmnxVdoGrpMdaHighPktPoolLimitHit    OBJECT-TYPE
    SYNTAX         Counter32
    MAX-ACCESS     read-only
    STATUS         current
    DESCRIPTION
        "The value of tmnxVdoGrpMdaHighPktPoolLimitHit indicates the number of 
         times the high packet pool limit has been hit. A high value of this 
         object indicates potential failure in ingress packet storage."
    ::= { tmnxVdoGrpMDAEntry 42 }

tmnxVdoGrpMdaMallocFailures    OBJECT-TYPE
    SYNTAX         Counter32
    MAX-ACCESS     read-only
    STATUS         current
    DESCRIPTION
        "The value of tmnxVdoGrpMdaMallocFailures indicates the number of 
         memory allocation failures on the management core of the video MDA."
    ::= { tmnxVdoGrpMDAEntry 43 }

tmnxVdoGrpMdaDentDroppedPkts    OBJECT-TYPE
    SYNTAX         Counter32
    MAX-ACCESS     read-only
    STATUS         current
    DESCRIPTION
        "The value of tmnxVdoGrpMdaDentDroppedPkts indicates the number of 
         packets dropped by the video MDA due to denting."
    ::= { tmnxVdoGrpMDAEntry 44 }

tmnxVdoGrpMdaBwPeak                 OBJECT-TYPE
    SYNTAX         Gauge32
    UNITS          "kbps"
    MAX-ACCESS     read-only
    STATUS         current
    DESCRIPTION
        "The value of tmnxVdoGrpMdaBwPeak indicates the maximum bandwidth
         of the currently running egress streams since the last clear event."
    ::= { tmnxVdoGrpMDAEntry 45 }

tmnxVdoGrpMdaCurTotalRetBw          OBJECT-TYPE
    SYNTAX         Gauge32
    UNITS          "kbps"
    MAX-ACCESS     read-only
    STATUS         current
    DESCRIPTION
        "The value of tmnxVdoGrpMdaCurTotalRetBw indicates the current total 
         Retransmission (RET) bandwidth in use."
    ::= { tmnxVdoGrpMDAEntry 46 }

tmnxVdoGrpMdaPeakRetBw                OBJECT-TYPE
    SYNTAX         Gauge32
    UNITS          "kbps"
    MAX-ACCESS     read-only
    STATUS         current
    DESCRIPTION
        "The value of tmnxVdoGrpMdaPeakRetBw indicates the maximum  
         Retransmission (RET) bandwidth used since the last clear event."
    ::= { tmnxVdoGrpMDAEntry 47 }

tmnxVdoGrpMdaCurFccBw                 OBJECT-TYPE
    SYNTAX         Gauge32
    UNITS          "kbps"
    MAX-ACCESS     read-only
    STATUS         current
    DESCRIPTION
        "The value of tmnxVdoGrpMdaCurFccBw indicates the current Fast Channel 
         Change (FCC) bandwidth in use."
    ::= { tmnxVdoGrpMDAEntry 48 }

tmnxVdoGrpMdaFccDropCntReq          OBJECT-TYPE
    SYNTAX         Gauge32
    MAX-ACCESS     read-only
    STATUS         current
    DESCRIPTION
        "The value of tmnxVdoGrpMdaCurFccBw indicates the drop count for the 
         Fast Channel Change (FCC) requests due to reserved Retransmission (RET) 
         bandwidth."
    ::= { tmnxVdoGrpMDAEntry 49 }    

tmnxVdoGrpMdaMcRtcp          OBJECT-TYPE
    SYNTAX         Counter64
    MAX-ACCESS     read-only
    STATUS         current
    DESCRIPTION
        "The value of tmnxVdoGrpMdaMcRtcp indicates the number of 
         multicast retransmissions done in response to Real Time Transport 
         Control Protocol (RTCP) requests."
    ::= { tmnxVdoGrpMDAEntry 50 }

tmnxVdoGrpMdaMcRtcpLow32 OBJECT-TYPE
    SYNTAX     Counter32
    MAX-ACCESS read-only
    STATUS     current
    DESCRIPTION
        "The value of tmnxVdoGrpMdaMcRtcpLow32 indicates the lower 32 
         bits of the value of tmnxVdoGrpMdaMcRtcp."
    ::= { tmnxVdoGrpMDAEntry 51 }

tmnxVdoGrpMdaMcRtcpHigh32 OBJECT-TYPE
    SYNTAX     Counter32
    MAX-ACCESS read-only
    STATUS     current
    DESCRIPTION
        "The value of tmnxVdoGrpMdaMcRtcpHigh32 indicates the higher 32 
         bits of the value of tmnxVdoGrpMdaMcRtcp."
    ::= { tmnxVdoGrpMDAEntry 52 }

tmnxVdoGrpMdaMcRudp          OBJECT-TYPE
    SYNTAX         Counter64
    MAX-ACCESS     read-only
    STATUS         current
    DESCRIPTION
        "The value of tmnxVdoGrpMdaMcRudp indicates the number of 
         multicast retransmissions done in response to Reliable User Datagram 
         Protocol (RUDP) requests."
    ::= { tmnxVdoGrpMDAEntry 53 }

tmnxVdoGrpMdaMcRudpLow32 OBJECT-TYPE
    SYNTAX     Counter32
    MAX-ACCESS read-only
    STATUS     current
    DESCRIPTION
        "The value of tmnxVdoGrpMdaMcRtcpLow32 indicates the lower 32 
         bits of the value of tmnxVdoGrpMdaMcRtcp."
    ::= { tmnxVdoGrpMDAEntry 54 }

tmnxVdoGrpMdaMcRudpHigh32 OBJECT-TYPE
    SYNTAX     Counter32
    MAX-ACCESS read-only
    STATUS     current
    DESCRIPTION
        "The value of tmnxVdoGrpMdaMcRudpHigh32 indicates the higher 32 
         bits of the value of tmnxVdoGrpMdaMcRudp."
    ::= { tmnxVdoGrpMDAEntry 55 }

tmnxVdoGrpMdaMcRetReqCrt          OBJECT-TYPE
    SYNTAX         Counter64
    MAX-ACCESS     read-only
    STATUS         current
    DESCRIPTION
        "The value of tmnxVdoGrpMdaMcRetReqCrt indicates the total number
         of mcast retransmission requests created in response to the unicast 
         retransmission requests."
    ::= { tmnxVdoGrpMDAEntry 56 }

tmnxVdoGrpMdaMcRetReqCrtLow32 OBJECT-TYPE
    SYNTAX     Counter32
    MAX-ACCESS read-only
    STATUS     current
    DESCRIPTION
        "The value of tmnxVdoGrpMdaMcRetReqCrtLow32 indicates the lower 32 
         bits of the value of tmnxVdoGrpMdaMcRetReqCrt."
    ::= { tmnxVdoGrpMDAEntry 57 }

tmnxVdoGrpMdaMcRetReqCrtHigh32 OBJECT-TYPE
    SYNTAX     Counter32
    MAX-ACCESS read-only
    STATUS     current
    DESCRIPTION
        "The value of tmnxVdoGrpMdaMcRetReqCrtHigh32 indicates the higher 32 
         bits of the value of tmnxVdoGrpMdaMcRetReqCrt."
    ::= { tmnxVdoGrpMDAEntry 58 }

tmnxVdoGrpMdaRetReqQnc          OBJECT-TYPE
    SYNTAX         Counter64
    MAX-ACCESS     read-only
    STATUS         current
    DESCRIPTION
        "The value of tmnxVdoGrpMdaRetReqQnc indicates the total 
         number of unicast retransmission requests quenched with the mulicast 
         retransmission."
    ::= { tmnxVdoGrpMDAEntry 59 }

tmnxVdoGrpMdaRetReqQncLow32 OBJECT-TYPE
    SYNTAX     Counter32
    MAX-ACCESS read-only
    STATUS     current
    DESCRIPTION
        "The value of tmnxVdoGrpMdaRetReqQncLow32 indicates the lower 32 
         bits of the value of tmnxVdoGrpMdaRetReqQnc."
    ::= { tmnxVdoGrpMDAEntry 60 }

tmnxVdoGrpMdaRetReqQncHigh32 OBJECT-TYPE
    SYNTAX     Counter32
    MAX-ACCESS read-only
    STATUS     current
    DESCRIPTION
        "The value of tmnxVdoGrpMdaRetReqQncHigh32 indicates the higher 32 
         bits of the value of tmnxVdoGrpMdaRetReqQnc."
    ::= { tmnxVdoGrpMDAEntry 61 }

tmnxVdoGrpMdaPktsLostInSeq10 OBJECT-TYPE
    SYNTAX     Counter32
    MAX-ACCESS read-only
    STATUS     current
    DESCRIPTION
        "The value of tmnxVdoGrpMdaPktsLostInSeq10 indicates the total number 
         of packets within sequences of 2 to 10 consecutive lost packets of the
         video group on this MDA."
    ::= { tmnxVdoGrpMDAEntry 62 }

tmnxVdoGrpMdaPktsLostInSeq20 OBJECT-TYPE
    SYNTAX     Counter32
    MAX-ACCESS read-only
    STATUS     current
    DESCRIPTION
        "The value of tmnxVdoGrpMdaPktsLostInSeq20 indicates the total number 
         of packets within sequences of 11 to 20 consecutive lost packets of the
         video group on this MDA."
    ::= { tmnxVdoGrpMDAEntry 63 }

tmnxVdoGrpMdaPktsLostInSeq30 OBJECT-TYPE
    SYNTAX     Counter32
    MAX-ACCESS read-only
    STATUS     current
    DESCRIPTION
        "The value of tmnxVdoGrpMdaPktsLostInSeq30 indicates the total number 
         of packets within sequences of 21 to 30 consecutive lost packets of the
         video group on this MDA."
    ::= { tmnxVdoGrpMDAEntry 64 }

tmnxVdoGrpMdaPktsLostInSeq40 OBJECT-TYPE
    SYNTAX     Counter32
    MAX-ACCESS read-only
    STATUS     current
    DESCRIPTION
        "The value of tmnxVdoGrpMdaPktsLostInSeq40 indicates the total number 
         of packets within sequences of 31 to 40 consecutive lost packets of the
         video group on this MDA."
    ::= { tmnxVdoGrpMDAEntry 65 }

tmnxVdoGrpMdaPktsLostInSeqMore OBJECT-TYPE
    SYNTAX     Counter32
    MAX-ACCESS read-only
    STATUS     current
    DESCRIPTION
        "The value of tmnxVdoGrpMdaPktsLostInSeqMore indicates the total number 
         of packets within sequences of 41 or more consecutive lost packets of 
         the video group on this MDA."
    ::= { tmnxVdoGrpMDAEntry 66 }

--
--      ADI Channel table
--

tmnxVdoAdiChlTableLastChanged OBJECT-TYPE
    SYNTAX      TimeStamp
    MAX-ACCESS  read-only
    STATUS      current
    DESCRIPTION
        "The value of tmnxVdoAdiChlTableLastChanged indicates the
         sysUpTime at the time of the last modification to
         tmnxVdoAdiChlTable by adding, deleting an entry or change
         to a writable object in the table.

         If no changes were made to the table since the last
         re-initialization of the local network management subsystem,
         then this object contains a zero value."
    ::= { tmnxVdoGlobalObjs 5 }

tmnxVdoAdiChlTable OBJECT-TYPE
    SYNTAX      SEQUENCE OF TmnxVdoAdiChlEntry
    MAX-ACCESS  not-accessible
    STATUS      current
    DESCRIPTION
        "The tmnxVdoAdiChlTable has an entry for each channel configured for the
         ADI (Ad Insertion) in the system. It lists the IP multicast groups and 
         corresponding IP multicast sources."
    ::= { tmnxVdoObjs 5 }

tmnxVdoAdiChlEntry OBJECT-TYPE
    SYNTAX      TmnxVdoAdiChlEntry
    MAX-ACCESS  not-accessible
    STATUS      current
    DESCRIPTION
        "Each row entry represents a source address from which receivers are 
         interested or not interested in receiving multicast traffic."
    INDEX      { svcId,
                 tmnxVdoIfName,
                 tmnxVdoAdiChlGrpAddrType,
                 tmnxVdoAdiChlGrpAddress,
                 tmnxVdoAdiChlSrcAddrType,
                 tmnxVdoAdiChlSrcAddress }
    ::= { tmnxVdoAdiChlTable 1 }

TmnxVdoAdiChlEntry ::= SEQUENCE {
    tmnxVdoAdiChlGrpAddrType   InetAddressType,
    tmnxVdoAdiChlGrpAddress    InetAddress,
    tmnxVdoAdiChlSrcAddrType   InetAddressType,
    tmnxVdoAdiChlSrcAddress    InetAddress,
    tmnxVdoAdiChlRowStatus     RowStatus, 
    tmnxVdoAdiChlName          TNamedItem, 
    tmnxVdoAdiChlDescription   TItemDescription,
    tmnxVdoAdiChlForwardScte35 TruthValue
}

tmnxVdoAdiChlGrpAddrType OBJECT-TYPE
    SYNTAX          InetAddressType
    MAX-ACCESS      not-accessible
    STATUS          current
    DESCRIPTION
        "The value of tmnxVdoAdiChlGrpAddrType indicates the type of
         address to be used for IP multicast group address."
    ::= { tmnxVdoAdiChlEntry 1 }

tmnxVdoAdiChlGrpAddress OBJECT-TYPE
    SYNTAX          InetAddress (SIZE(4|16))
    MAX-ACCESS      not-accessible
    STATUS          current
    DESCRIPTION
        "The value of tmnxVdoAdiChlGrpAddress indicates the IP multicast
         group address for which this entry contains information."
    ::= { tmnxVdoAdiChlEntry 2 }                

tmnxVdoAdiChlSrcAddrType OBJECT-TYPE
    SYNTAX          InetAddressType
    MAX-ACCESS      not-accessible
    STATUS          current
    DESCRIPTION
        "The value of tmnxVdoAdiChlSrcAddrType indicates the type of
         address to be used for source address."
    ::= { tmnxVdoAdiChlEntry 3 }

tmnxVdoAdiChlSrcAddress OBJECT-TYPE
    SYNTAX          InetAddress (SIZE(4|16))
    MAX-ACCESS      not-accessible
    STATUS          current
    DESCRIPTION
        "The value of tmnxVdoAdiChlSrcAddress indicates the source address
         for which this entry contains information."
    ::= { tmnxVdoAdiChlEntry 4 }

tmnxVdoAdiChlRowStatus OBJECT-TYPE
    SYNTAX          RowStatus
    MAX-ACCESS      read-create
    STATUS          current
    DESCRIPTION
        "The value of tmnxVdoAdiChlRowStatus specifies the row status of this
         row entry."
    ::= { tmnxVdoAdiChlEntry 5 }

tmnxVdoAdiChlName OBJECT-TYPE
    SYNTAX          TNamedItem (SIZE(1..30))
    MAX-ACCESS      read-create
    STATUS          current
    DESCRIPTION
        "The value of tmnxVdoAdiChlName specifies the name for this channel."
    DEFVAL { ''H }      -- the empty string
    ::= { tmnxVdoAdiChlEntry 6 }

tmnxVdoAdiChlDescription OBJECT-TYPE
    SYNTAX          TItemDescription
    MAX-ACCESS      read-create
    STATUS          current
    DESCRIPTION
        "The value of tmnxVdoAdiChlDescription specifies the user provided
         description string for this channel."
    DEFVAL { ''H }      -- the empty string
    ::= { tmnxVdoAdiChlEntry 7 }

tmnxVdoAdiChlForwardScte35 OBJECT-TYPE
    SYNTAX          TruthValue
    MAX-ACCESS      read-create
    STATUS          current
    DESCRIPTION
        "The value of tmnxVdoAdiChlForwardScte35 specifies whether the Society 
         of Cable Telecommunications Engineers 35 (scte35) cue avails in the 
         stream need to be forwarded or not. If the value of this object is 
         set to 'true', then scte35 messages will be forwarded in the 
         downstream."
    DEFVAL { true }
    ::= { tmnxVdoAdiChlEntry 8 }

--
--      ADI Zone Channel table
--

tmnxVdoAdiZoneChlTableLastChngd OBJECT-TYPE
    SYNTAX      TimeStamp
    MAX-ACCESS  read-only
    STATUS      current
    DESCRIPTION
        "The value of tmnxVdoAdiZoneChlTableLastChngd indicates the
         sysUpTime at the time of the last modification to
         tmnxVdoAdiZoneChlTable by adding, deleting an entry or change
         to a writable object in the table.

         If no changes were made to the table since the last
         re-initialization of the local network management subsystem,
         then this object contains a zero value."
    ::= { tmnxVdoGlobalObjs 6 }

tmnxVdoAdiZoneChlTable OBJECT-TYPE
    SYNTAX      SEQUENCE OF TmnxVdoAdiZoneChlEntry
    MAX-ACCESS  not-accessible
    STATUS      current
    DESCRIPTION
        "The tmnxVdoAdiZoneChlTable has an entry for each zone channel 
         configured for the ADI (Ad Insertion) in the system. It lists the IP 
         multicast groups and corresponding IP multicast sources."
    ::= { tmnxVdoObjs 6 }

tmnxVdoAdiZoneChlEntry OBJECT-TYPE
    SYNTAX      TmnxVdoAdiZoneChlEntry
    MAX-ACCESS  not-accessible
    STATUS      current
    DESCRIPTION
        "Each row entry represents a source address from which receivers are
         interested or not interested in receiving multicast traffic."
    INDEX      { svcId,
                 tmnxVdoIfName,
                 tmnxVdoAdiChlGrpAddrType,
                 tmnxVdoAdiChlGrpAddress,
                 tmnxVdoAdiChlSrcAddrType,
                 tmnxVdoAdiChlSrcAddress,
                 tmnxVdoAdiZoneChlGrpAddrType,
                 tmnxVdoAdiZoneChlGrpAddress,
                 tmnxVdoAdiZoneChlSrcAddrType,
                 tmnxVdoAdiZoneChlSrcAddress }
    ::= { tmnxVdoAdiZoneChlTable 1 }

TmnxVdoAdiZoneChlEntry ::= SEQUENCE {
    tmnxVdoAdiZoneChlGrpAddrType   InetAddressType,
    tmnxVdoAdiZoneChlGrpAddress    InetAddress,
    tmnxVdoAdiZoneChlSrcAddrType   InetAddressType,
    tmnxVdoAdiZoneChlSrcAddress    InetAddress,
    tmnxVdoAdiZoneChlRowStatus     RowStatus,
    tmnxVdoAdiZoneChlName          TNamedItem
}

tmnxVdoAdiZoneChlGrpAddrType OBJECT-TYPE
    SYNTAX          InetAddressType
    MAX-ACCESS      not-accessible
    STATUS          current
    DESCRIPTION
        "The value of tmnxVdoAdiZoneChlGrpAddrType indicates the type of
         address to be used for IP multicast group address."
    ::= { tmnxVdoAdiZoneChlEntry 1 }

tmnxVdoAdiZoneChlGrpAddress OBJECT-TYPE
    SYNTAX          InetAddress (SIZE(4|16))
    MAX-ACCESS      not-accessible
    STATUS          current
    DESCRIPTION
        "The value of tmnxVdoAdiZoneChlGrpAddress indicates the IP multicast
         group address for which this entry contains information."
    ::= { tmnxVdoAdiZoneChlEntry 2 }

tmnxVdoAdiZoneChlSrcAddrType OBJECT-TYPE
    SYNTAX          InetAddressType
    MAX-ACCESS      not-accessible
    STATUS          current
    DESCRIPTION
        "The value of tmnxVdoAdiZoneChlSrcAddrType indicates the type of
         address to be used for source address."
    ::= { tmnxVdoAdiZoneChlEntry 3 }

tmnxVdoAdiZoneChlSrcAddress OBJECT-TYPE
    SYNTAX          InetAddress (SIZE(4|16))
    MAX-ACCESS      not-accessible
    STATUS          current
    DESCRIPTION
        "The value of tmnxVdoAdiZoneChlSrcAddress indicates the source address
         for which this entry contains information."
    ::= { tmnxVdoAdiZoneChlEntry 4 }

tmnxVdoAdiZoneChlRowStatus OBJECT-TYPE
    SYNTAX          RowStatus
    MAX-ACCESS      read-create
    STATUS          current
    DESCRIPTION
        "The value of tmnxVdoAdiZoneChlRowStatus specifies the row status of 
         this row entry."
    ::= { tmnxVdoAdiZoneChlEntry 5 }

tmnxVdoAdiZoneChlName OBJECT-TYPE
    SYNTAX          TNamedItem (SIZE(1..30))
    MAX-ACCESS      read-create
    STATUS          current
    DESCRIPTION
        "The value of tmnxVdoAdiZoneChlName specifies the name for this zone 
         channel."
    DEFVAL { ''H }      -- the empty string
    ::= { tmnxVdoAdiZoneChlEntry 6 }

--
-- Video Source Group Statistics Table
--

tmnxVdoGrpSrcStatTable OBJECT-TYPE
    SYNTAX     SEQUENCE OF TmnxVdoGrpSrcStatEntry
    MAX-ACCESS not-accessible
    STATUS     current
    DESCRIPTION
        "tmnxVdoGrpSrcStatTable contains channel information and 
         statistics for the multicast groups."
    ::= { tmnxVdoObjs 7 }

tmnxVdoGrpSrcStatEntry OBJECT-TYPE
    SYNTAX     TmnxVdoGrpSrcStatEntry
    MAX-ACCESS not-accessible
    STATUS     current
    DESCRIPTION
        "An entry in the tmnxVdoGrpSrcStatTable. Each entry represents a 
         source address for the corresponding multicast group."
    INDEX      { 
                 svcId,
                 tmnxVdoIfName,
                 tmnxVdoGrpSrcGrpAddrType, 
                 tmnxVdoGrpSrcGroupAddress,
                 tmnxVdoGrpSrcSrcAddrType, 
                 tmnxVdoGrpSrcSourceAddress
               }
    ::= { tmnxVdoGrpSrcStatTable 1 }

TmnxVdoGrpSrcStatEntry ::= SEQUENCE {
    tmnxVdoGrpSrcGrpAddrType              InetAddressType,
    tmnxVdoGrpSrcGroupAddress             InetAddress,
    tmnxVdoGrpSrcSrcAddrType              InetAddressType,
    tmnxVdoGrpSrcSourceAddress            InetAddress,
    tmnxVdoGrpSrcStreamType               INTEGER,
    tmnxVdoGrpSrcVdoGrpId                 TmnxVdoGrpId,
    tmnxVdoGrpSrcAdminRTBufferSize        TmnxMcPathVdoBufferSize,
    tmnxVdoGrpSrcSSRCId                   Unsigned32,
    tmnxVdoGrpSrcUDPSrcPort               InetPortNumber,
    tmnxVdoGrpSrcUDPDestPort              InetPortNumber,
    tmnxVdoGrpSrcUptime                   Unsigned32,
    tmnxVdoGrpSrcAdminBW                  Unsigned32,
    tmnxVdoGrpSrcBufferSize               Gauge32,
    tmnxVdoGrpSrcRxBytes                  Counter64,
    tmnxVdoGrpSrcRxPackets                Counter64,
    tmnxVdoGrpSrcRxInvalidPackets         Counter64,
    tmnxVdoGrpSrcTxBytes                  Counter64,
    tmnxVdoGrpSrcTxPackets                Counter64,
    tmnxVdoGrpSrcTxFailedPackets          Counter64,
    tmnxVdoGrpSrcRTClientAdminState       TmnxAdminState,
    tmnxVdoGrpSrcRTClntRTSvrAddrType      InetAddressType,
    tmnxVdoGrpSrcRTClntRTSvrAddr          InetAddress,
    tmnxVdoGrpSrcRTClientRTSrvrPort       InetPortNumber,
    tmnxVdoGrpSrcRTClientRxReTxBytes      Counter64,
    tmnxVdoGrpSrcRTClientRxReTxPkts       Counter64,
    tmnxVdoGrpSrcRTClientTxRTReq          Counter32,
    tmnxVdoGrpSrcRTClientTxRTReqReTx      Counter32,
    tmnxVdoGrpSrcRTClientGapsDetectd      Counter32,
    tmnxVdoGrpSrcRTClientFailedReq        Counter32,
    tmnxVdoGrpSrcRTSrvrAdminState         TmnxAdminState,
    tmnxVdoGrpSrcRTSrvrRtpPktsReq         Counter32,
    tmnxVdoGrpSrcRTSrvrRxRTReq            Counter32,
    tmnxVdoGrpSrcRTSrvrRxFailedReq        Counter32,
    tmnxVdoGrpSrcRTSrvrTxRTReplies        Counter32,
    tmnxVdoGrpSrcRTSrvrTxBytes            Counter64,
    tmnxVdoGrpSrcRTSrvrTxPackets          Counter64,
    tmnxVdoGrpSrcFCCSrvrAdminState        TmnxAdminState,
    tmnxVdoGrpSrcFCCSrvrChnlType          TmnxMcPathVdoChlType,
    tmnxVdoGrpSrcFCCSrvrRxFCCReq          Counter32,
    tmnxVdoGrpSrcFCCSrvrRxFailedReq       Counter32,
    tmnxVdoGrpSrcFCCSrvrTxFCCReplies      Counter32,
    tmnxVdoGrpSrcFCCSrvrTxBytes           Counter64,
    tmnxVdoGrpSrcFCCSrvrTxPackets         Counter64,
    tmnxVdoGrpSrcADIAdminState            TmnxAdminState,
    tmnxVdoGrpSrcADICurrentState          INTEGER,
    tmnxVdoGrpSrcADIPATVersion            Unsigned32,          
    tmnxVdoGrpSrcADIPMTVersion            Unsigned32,
    tmnxVdoGrpSrcADIPATChanges            Counter32,
    tmnxVdoGrpSrcADIPMTChanges            Counter32,
    tmnxVdoGrpSrcADIRxPackets             Counter64,
    tmnxVdoGrpSrcADITxPackets             Counter64,
    tmnxVdoGrpSrcADIRxSCTE35Msgs          Counter32,
    tmnxVdoGrpSrcADIRxSCTE35MsgEnc        Counter32,
    tmnxVdoGrpSrcADIRxSCTE35MsgUnsup      Counter32,
    tmnxVdoGrpSrcADIRxSCTE35MsgDisc       Counter32,
    tmnxVdoGrpSrcADIUnsuppTSLenPkts       Counter32,
    tmnxVdoGrpSrcRTClientPort             Unsigned32,
    tmnxVdoGrpSrcDupSeqNumber             Counter32,
    tmnxVdoGrpSrcRTSTxMcRetPkts           Counter64,  
    tmnxVdoGrpSrcRTSTxMcRetPktsL32        Counter32,  
    tmnxVdoGrpSrcRTSTxMcRetPktsH32        Counter32,  
    tmnxVdoGrpSrcRTSTxMcRetBytes          Counter64,
    tmnxVdoGrpSrcRTSTxMcRetBytesL32       Counter32,
    tmnxVdoGrpSrcRTSTxMcRetBytesH32       Counter32,
    tmnxVdoGrpSrcRTSTxMcRetErrs           Counter64,   
    tmnxVdoGrpSrcRTSTxMcRetErrsL32        Counter32,   
    tmnxVdoGrpSrcRTSTxMcRetErrsH32        Counter32,
    tmnxVdoGrpSrcRTSRetReqQnc             Counter64,   
    tmnxVdoGrpSrcRTSRetReqQncL32          Counter32,   
    tmnxVdoGrpSrcRTSRetReqQncH32          Counter32,
    tmnxVdoGrpSrcRTSRetReqCrt             Counter64,  
    tmnxVdoGrpSrcRTSRetReqCrtL32          Counter32,  
    tmnxVdoGrpSrcRTSRetReqCrtH32          Counter32,
    tmnxVdoGrpSrcRxDupSsrcDrops           Counter32,
    tmnxVdoGrpSrcDupSsrc                  Counter32,
    tmnxVdoGrpSrcFccMinDuration           Unsigned32,
    tmnxVdoGrpSrcAudioReorder             Unsigned32,
    tmnxVdoGrpSrcRxBytesSaved             Counter64,
    tmnxVdoGrpSrcRxBytesSavedL32          Counter32,
    tmnxVdoGrpSrcRxBytesSavedH32          Counter32,
    tmnxVdoGrpSrcRxPacketsSaved           Counter64,
    tmnxVdoGrpSrcRxPacketsSavedL32        Counter32,
    tmnxVdoGrpSrcRxPacketsSavedH32        Counter32,
    tmnxVdoGrpSrcStatOperBW               Unsigned32,
    tmnxVdoGrpSrcRouterIfName             TNamedItemOrEmpty,
    tmnxVdoGrpSrcNumFccDentedPkts         Counter32
}

tmnxVdoGrpSrcGrpAddrType OBJECT-TYPE
    SYNTAX     InetAddressType
    MAX-ACCESS not-accessible
    STATUS     current
    DESCRIPTION
        "The value of tmnxVdoGrpSrcGrpAddrType indicates the type of 
         IP multicast group address represented by tmnxVdoGrpSrcGroupAddress."
    ::= { tmnxVdoGrpSrcStatEntry 1 }

tmnxVdoGrpSrcGroupAddress OBJECT-TYPE
    SYNTAX     InetAddress (SIZE (4|16))
    MAX-ACCESS not-accessible
    STATUS     current
    DESCRIPTION
        "The value of tmnxVdoGrpSrcGroupAddress indicates the IP multicast 
         group address for which this entry contains information."
    ::= { tmnxVdoGrpSrcStatEntry 2 }

tmnxVdoGrpSrcSrcAddrType OBJECT-TYPE
    SYNTAX     InetAddressType
    MAX-ACCESS not-accessible
    STATUS     current
    DESCRIPTION
        "The value of tmnxVdoGrpSrcSrcAddrType indicates the type of 
         IP multicast source address represented by 
         tmnxVdoGrpSrcSourceAddress."
    ::= { tmnxVdoGrpSrcStatEntry 3 }

tmnxVdoGrpSrcSourceAddress OBJECT-TYPE
    SYNTAX     InetAddress (SIZE (4|16))
    MAX-ACCESS not-accessible
    STATUS     current
    DESCRIPTION
        "The value of tmnxVdoGrpSrcSourceAddress indicates the IP multicast 
         source address for which this entry contains information."
    ::= { tmnxVdoGrpSrcStatEntry 4 }

tmnxVdoGrpSrcStreamType OBJECT-TYPE
    SYNTAX     INTEGER {
                   network (0),
                   zone (1)                 
               }
    MAX-ACCESS read-only
    STATUS     current
    DESCRIPTION
        "The value of tmnxVdoGrpSrcStreamType indicates the type of stream 
         being transmitted from the video ISA perspective. Network stream is 
         the stream ingressing the video ISA and being stored by it. Zone
         stream is the stream egressing the video ISA into which AD streams 
         will be inserted."
    ::= { tmnxVdoGrpSrcStatEntry 5 }

tmnxVdoGrpSrcVdoGrpId OBJECT-TYPE
    SYNTAX     TmnxVdoGrpId
    MAX-ACCESS read-only
    STATUS     current
    DESCRIPTION
        "The value of tmnxVdoGrpSrcVdoGrpId indicates the identifier of the 
         video group."
    ::= { tmnxVdoGrpSrcStatEntry 6 }

tmnxVdoGrpSrcAdminRTBufferSize OBJECT-TYPE
    SYNTAX     TmnxMcPathVdoBufferSize
    UNITS      "milliseconds"
    MAX-ACCESS read-only
    STATUS     current
    DESCRIPTION
        "The value of tmnxVdoGrpSrcAdminRTBufferSize indicates the number
         of milliseconds worth of channel packets to store for the
         Retransmission (RT) server."
    ::= { tmnxVdoGrpSrcStatEntry 7 }

tmnxVdoGrpSrcSSRCId OBJECT-TYPE
    SYNTAX     Unsigned32
    MAX-ACCESS read-only
    STATUS     current
    DESCRIPTION
        "The value of tmnxVdoGrpSrcSSRCId indicates the synchronization source 
         (SSRC) identifier carried in the Real-time Transport Protocol (RTP) 
         header to identify the source of a stream of RTP packets."
    ::= { tmnxVdoGrpSrcStatEntry 8 }

tmnxVdoGrpSrcUDPSrcPort OBJECT-TYPE
    SYNTAX     InetPortNumber
    MAX-ACCESS read-only
    STATUS     current
    DESCRIPTION
        "The value of tmnxVdoGrpSrcUDPSrcPort indicates the UDP source port 
         in the received RTP multicast stream."
    ::= { tmnxVdoGrpSrcStatEntry 9 }

tmnxVdoGrpSrcUDPDestPort OBJECT-TYPE
    SYNTAX     InetPortNumber
    MAX-ACCESS read-only
    STATUS     current
    DESCRIPTION
        "The value of tmnxVdoGrpSrcUDPDestPort indicates the UDP destination 
         port in the received RTP multicast stream."
    ::= { tmnxVdoGrpSrcStatEntry 10 }

tmnxVdoGrpSrcUptime OBJECT-TYPE
    SYNTAX     Unsigned32
    UNITS      "seconds"
    MAX-ACCESS read-only
    STATUS     current
    DESCRIPTION
        "The value of tmnxVdoGrpSrcUptime indicates the time since this 
         source group entry was created."
    ::= { tmnxVdoGrpSrcStatEntry 11 }

tmnxVdoGrpSrcAdminBW OBJECT-TYPE
    SYNTAX     Unsigned32
    UNITS      "kbps"
    MAX-ACCESS read-only
    STATUS     current
    DESCRIPTION
        "The value of tmnxVdoGrpSrcAdminBW indicates the administrative 
         bandwidth of the multicast group."
    ::= { tmnxVdoGrpSrcStatEntry 12 }

tmnxVdoGrpSrcBufferSize OBJECT-TYPE
    SYNTAX     Gauge32
    UNITS      "milliseconds"
    MAX-ACCESS read-only
    STATUS     current
    DESCRIPTION
        "The value of tmnxVdoGrpSrcBufferSize indicates the number of 
         milliseconds worth of channel packets stored by the Retransmission 
         (RT) server or Fast Channel Change (FCC) server on this channel."
    ::= { tmnxVdoGrpSrcStatEntry 13 }

tmnxVdoGrpSrcRxBytes OBJECT-TYPE
    SYNTAX     Counter64
    MAX-ACCESS read-only
    STATUS     current
    DESCRIPTION
        "The value of tmnxVdoGrpSrcRxBytes indicates the total number of 
         bytes received on this multicast channel."
    ::= { tmnxVdoGrpSrcStatEntry 14 }

tmnxVdoGrpSrcRxPackets OBJECT-TYPE
    SYNTAX     Counter64
    MAX-ACCESS read-only
    STATUS     current
    DESCRIPTION
        "The value of tmnxVdoGrpSrcRxPackets indicates the total number of 
         packets received on this multicast channel."
    ::= { tmnxVdoGrpSrcStatEntry 15 }

tmnxVdoGrpSrcRxInvalidPackets OBJECT-TYPE
    SYNTAX     Counter64
    MAX-ACCESS read-only
    STATUS     current
    DESCRIPTION
        "The value of tmnxVdoGrpSrcRxInvalidPackets indicates the total 
         number of invalid packets received on this multicast channel."
    ::= { tmnxVdoGrpSrcStatEntry 16 }

tmnxVdoGrpSrcTxBytes OBJECT-TYPE
    SYNTAX     Counter64
    MAX-ACCESS read-only
    STATUS     current
    DESCRIPTION
        "The value of tmnxVdoGrpSrcTxBytes indicates the total number of
         bytes transmitted on this multicast channel."
    ::= { tmnxVdoGrpSrcStatEntry 17 }

tmnxVdoGrpSrcTxPackets OBJECT-TYPE
    SYNTAX     Counter64
    MAX-ACCESS read-only
    STATUS     current
    DESCRIPTION
        "The value of tmnxVdoGrpSrcTxPackets indicates the total number of
         packets transmitted on this multicast channel."
    ::= { tmnxVdoGrpSrcStatEntry 18 }

tmnxVdoGrpSrcTxFailedPackets OBJECT-TYPE
    SYNTAX     Counter64
    MAX-ACCESS read-only
    STATUS     current
    DESCRIPTION
        "The value of tmnxVdoGrpSrcTxFailedPackets indicates the total 
         number of failures during the transmission of packets on this multicast 
         channel. Failure happens when the packet to be sent is not stored 
         in the video cache."
    ::= { tmnxVdoGrpSrcStatEntry 19 }

tmnxVdoGrpSrcRTClientAdminState OBJECT-TYPE
    SYNTAX     TmnxAdminState
    MAX-ACCESS read-only
    STATUS     current
    DESCRIPTION
        "The value of tmnxVdoGrpSrcRTClientAdminState indicates the 
         administrative state of the retransmission client."
    ::= { tmnxVdoGrpSrcStatEntry 20 }

tmnxVdoGrpSrcRTClntRTSvrAddrType OBJECT-TYPE
    SYNTAX     InetAddressType
    MAX-ACCESS read-only
    STATUS     current
    DESCRIPTION
        "The value of tmnxVdoGrpSrcRTClntRTSvrAddrType indicates the type of 
         address represented by tmnxVdoGrpSrcRTClntRTSvrAddr."
    ::= { tmnxVdoGrpSrcStatEntry 21 }

tmnxVdoGrpSrcRTClntRTSvrAddr OBJECT-TYPE
    SYNTAX     InetAddress (SIZE (4|16))
    MAX-ACCESS read-only
    STATUS     current
    DESCRIPTION
        "The value of tmnxVdoGrpSrcRTClntRTSvrAddr indicates the address of 
         the Retransmission (RT) server for this channel."
    ::= { tmnxVdoGrpSrcStatEntry 22 }

tmnxVdoGrpSrcRTClientRTSrvrPort OBJECT-TYPE
    SYNTAX     InetPortNumber
    MAX-ACCESS read-only
    STATUS     current
    DESCRIPTION
        "The value of tmnxVdoGrpSrcRTClientRTSrvrPort indicates the 
         Retransmission (RT) server port for this channel."
    ::= { tmnxVdoGrpSrcStatEntry 23 }

tmnxVdoGrpSrcRTClientRxReTxBytes OBJECT-TYPE
    SYNTAX     Counter64
    MAX-ACCESS read-only
    STATUS     current
    DESCRIPTION
        "The value of tmnxVdoGrpSrcRTClientRxReTxBytes indicates the total 
         number of retransmitted bytes received by the Retransmission (RT) 
         client."
    ::= { tmnxVdoGrpSrcStatEntry 24 }

tmnxVdoGrpSrcRTClientRxReTxPkts OBJECT-TYPE
    SYNTAX     Counter64
    MAX-ACCESS read-only
    STATUS     current
    DESCRIPTION
        "The value of tmnxVdoGrpSrcRTClientRxReTxPkts indicates the total 
         number of retransmitted packets received by the Retransmission (RT) 
         client."
    ::= { tmnxVdoGrpSrcStatEntry 25 }

tmnxVdoGrpSrcRTClientTxRTReq OBJECT-TYPE
    SYNTAX     Counter32
    MAX-ACCESS read-only
    STATUS     current
    DESCRIPTION
        "The value of tmnxVdoGrpSrcRTClientTxRTReq indicates the total number 
         of Retransmission (RT) requests sent by the RT client."
    ::= { tmnxVdoGrpSrcStatEntry 26 }

tmnxVdoGrpSrcRTClientTxRTReqReTx OBJECT-TYPE
    SYNTAX     Counter32
    MAX-ACCESS read-only
    STATUS     current
    DESCRIPTION
        "The value of tmnxVdoGrpSrcRTClientTxRTReqReTx indicates the total 
         number of repeat Retransmission (RT) requests attempted by the RT 
         client."
    ::= { tmnxVdoGrpSrcStatEntry 27 }

tmnxVdoGrpSrcRTClientGapsDetectd OBJECT-TYPE
    SYNTAX     Counter32
    MAX-ACCESS read-only
    STATUS     current
    DESCRIPTION
        "The value of tmnxVdoGrpSrcRTClientGapsDetectd indicates the total 
         number of gaps in the sequence numbers detected by the Retransmission 
         (RT) client."
    ::= { tmnxVdoGrpSrcStatEntry 28 }

tmnxVdoGrpSrcRTClientFailedReq OBJECT-TYPE
    SYNTAX     Counter32
    MAX-ACCESS read-only
    STATUS     current
    DESCRIPTION
        "The value of tmnxVdoGrpSrcRTClientFailedReq indicates the total 
         number of Retransmission (RT) requests that could not be generated by 
         the RT client due to gaps in the sequence numbers."
    ::= { tmnxVdoGrpSrcStatEntry 29 }

tmnxVdoGrpSrcRTSrvrAdminState OBJECT-TYPE
    SYNTAX     TmnxAdminState
    MAX-ACCESS read-only
    STATUS     current
    DESCRIPTION
        "The value of tmnxVdoGrpSrcRTSrvrAdminState indicates the 
         administrative state of the Retransmission (RT) server."
    ::= { tmnxVdoGrpSrcStatEntry 30 }

tmnxVdoGrpSrcRTSrvrRtpPktsReq OBJECT-TYPE
    SYNTAX     Counter32
    MAX-ACCESS read-only
    STATUS     current
    DESCRIPTION
        "The value of tmnxVdoGrpSrcRTSrvrRtpPktsReq indicates the totoal number 
         of Real-time Transport Protocol (RTP) packets requested in the 
         Real-time Transport Control Protocol (RTCP) feedback (FB) messages 
         received on this channel."
    ::= { tmnxVdoGrpSrcStatEntry 31 }

tmnxVdoGrpSrcRTSrvrRxRTReq OBJECT-TYPE
    SYNTAX     Counter32
    MAX-ACCESS read-only
    STATUS     current
    DESCRIPTION
        "The value of tmnxVdoGrpSrcRTSrvrRxRTReq indicates the total number 
         of RT requests received by the Retransmission (RT) server."
    ::= { tmnxVdoGrpSrcStatEntry 32 }

tmnxVdoGrpSrcRTSrvrRxFailedReq OBJECT-TYPE
    SYNTAX     Counter32
    MAX-ACCESS read-only
    STATUS     current
    DESCRIPTION
        "The value of tmnxVdoGrpSrcRTSrvrRxFailedReq indicates the total 
         number of failed requests at the Retransmission (RT) server due 
         to congestion or lack of resources."
    ::= { tmnxVdoGrpSrcStatEntry 33 }

tmnxVdoGrpSrcRTSrvrTxRTReplies OBJECT-TYPE
    SYNTAX     Counter32
    MAX-ACCESS read-only
    STATUS     current
    DESCRIPTION
        "The value of tmnxVdoGrpSrcRTSrvrTxRTReplies indicates the total 
         number of Retransmission (RT) replies sent by the RT server."
    ::= { tmnxVdoGrpSrcStatEntry 34 }

tmnxVdoGrpSrcRTSrvrTxBytes OBJECT-TYPE
    SYNTAX     Counter64
    MAX-ACCESS read-only
    STATUS     current
    DESCRIPTION
        "The value of tmnxVdoGrpSrcRTSrvrTxBytes indicates the total 
         number of bytes sent by the Retransmission (RT) server."
    ::= { tmnxVdoGrpSrcStatEntry 35 }

tmnxVdoGrpSrcRTSrvrTxPackets OBJECT-TYPE
    SYNTAX     Counter64
    MAX-ACCESS read-only
    STATUS     current
    DESCRIPTION
        "The value of tmnxVdoGrpSrcRTSrvrTxPackets indicates the total 
         number of packets sent by the Retransmission (RT) server."
    ::= { tmnxVdoGrpSrcStatEntry 36 }

tmnxVdoGrpSrcFCCSrvrAdminState OBJECT-TYPE
    SYNTAX     TmnxAdminState
    MAX-ACCESS read-only
    STATUS     current
    DESCRIPTION
        "The value of tmnxVdoGrpSrcFCCSrvrAdminState indicates whether the 
         Fast Channel Change (FCC) server is enabled on this channel."
    ::= { tmnxVdoGrpSrcStatEntry 37 }

tmnxVdoGrpSrcFCCSrvrChnlType OBJECT-TYPE
    SYNTAX     TmnxMcPathVdoChlType
    MAX-ACCESS read-only
    STATUS     current
    DESCRIPTION
        "The value of tmnxVdoGrpSrcFCCSrvrChnlType indicates the type of 
         channel served by the Fast Channel Change (FCC) server."
    ::= { tmnxVdoGrpSrcStatEntry 38 }

tmnxVdoGrpSrcFCCSrvrRxFCCReq OBJECT-TYPE
    SYNTAX     Counter32
    MAX-ACCESS read-only
    STATUS     current
    DESCRIPTION
        "The value of tmnxVdoGrpSrcFCCSrvrRxFCCReq indicates the total number 
         of Fast Channel Change (FCC) requests received by the FCC server."
    ::= { tmnxVdoGrpSrcStatEntry 39 }

tmnxVdoGrpSrcFCCSrvrRxFailedReq OBJECT-TYPE
    SYNTAX     Counter32
    MAX-ACCESS read-only
    STATUS     current
    DESCRIPTION
        "The value of tmnxVdoGrpSrcFCCSrvrRxFailedReq indicates the total 
         number of failed requests at the Fast Channel Change (FCC) server."
    ::= { tmnxVdoGrpSrcStatEntry 40 }

tmnxVdoGrpSrcFCCSrvrTxFCCReplies OBJECT-TYPE
    SYNTAX     Counter32
    MAX-ACCESS read-only
    STATUS     current
    DESCRIPTION
        "The value of tmnxVdoGrpSrcFCCSrvrTxFCCReplies indicates the total 
         number of Fast Channel Change (FCC) replies sent by the FCC server."
    ::= { tmnxVdoGrpSrcStatEntry 41 }

tmnxVdoGrpSrcFCCSrvrTxBytes OBJECT-TYPE
    SYNTAX     Counter64
    MAX-ACCESS read-only
    STATUS     current
    DESCRIPTION
        "The value of tmnxVdoGrpSrcFCCSrvrTxBytes indicates the total 
         number of bytes sent by the Fast Channel Change (FCC) server."
    ::= { tmnxVdoGrpSrcStatEntry 42 }

tmnxVdoGrpSrcFCCSrvrTxPackets OBJECT-TYPE
    SYNTAX     Counter64
    MAX-ACCESS read-only
    STATUS     current
    DESCRIPTION
        "The value of tmnxVdoGrpSrcFCCSrvrTxPackets indicates the total 
         number of packets sent by the Fast Channel Change (FCC) server."
    ::= { tmnxVdoGrpSrcStatEntry 43 }

tmnxVdoGrpSrcADIAdminState OBJECT-TYPE
    SYNTAX     TmnxAdminState
    MAX-ACCESS read-only
    STATUS     current
    DESCRIPTION
        "The value of tmnxVdoGrpSrcADIAdminState indicates whether Ad Insertion
         is enabled on the video ISA."
    ::= { tmnxVdoGrpSrcStatEntry 44 }

tmnxVdoGrpSrcADICurrentState OBJECT-TYPE
    SYNTAX     INTEGER {
                   network (0),
                   ad (1)
               }
    MAX-ACCESS read-only
    STATUS     current
    DESCRIPTION
        "The value of tmnxVdoGrpSrcADICurrentState indicates whether the video 
         ISA is transmitting network stream or ads."
    ::= { tmnxVdoGrpSrcStatEntry 45 }

tmnxVdoGrpSrcADIPATVersion OBJECT-TYPE
    SYNTAX     Unsigned32
    MAX-ACCESS read-only
    STATUS     current
    DESCRIPTION
        "The value of tmnxVdoGrpSrcADIPATVersion indicates the version of the 
         Program Association Table (PAT)."
    ::= { tmnxVdoGrpSrcStatEntry 46 }

tmnxVdoGrpSrcADIPMTVersion OBJECT-TYPE
    SYNTAX     Unsigned32
    MAX-ACCESS read-only
    STATUS     current
    DESCRIPTION
        "The value of tmnxVdoGrpSrcADIPMTVersion indicates the version of the 
         Program Map Table (PMT)."
    ::= { tmnxVdoGrpSrcStatEntry 47 }

tmnxVdoGrpSrcADIPATChanges OBJECT-TYPE
    SYNTAX     Counter32
    MAX-ACCESS read-only
    STATUS     current
    DESCRIPTION
        "The value of tmnxVdoGrpSrcADIPATChanges indicates the total number 
         of Program Association Table (PAT) version changes."
    ::= { tmnxVdoGrpSrcStatEntry 48 }

tmnxVdoGrpSrcADIPMTChanges OBJECT-TYPE
    SYNTAX     Counter32
    MAX-ACCESS read-only
    STATUS     current
    DESCRIPTION
        "The value of tmnxVdoGrpSrcADIPMTChanges indicates the total number 
         of Program Map Table (PMT) version changes."
    ::= { tmnxVdoGrpSrcStatEntry 49 }

tmnxVdoGrpSrcADIRxPackets OBJECT-TYPE
    SYNTAX     Counter64
    MAX-ACCESS read-only
    STATUS     current
    DESCRIPTION
        "The value of tmnxVdoGrpSrcADIRxPackets indicates the total number 
         of Ad Insert (ADI) packets received by the video ISA."
    ::= { tmnxVdoGrpSrcStatEntry 50 }

tmnxVdoGrpSrcADITxPackets OBJECT-TYPE
    SYNTAX     Counter64
    MAX-ACCESS read-only
    STATUS     current
    DESCRIPTION
        "The value of tmnxVdoGrpSrcADITxPackets indicates the total number 
         of Ad Insert (ADI) packets sent by the video ISA."
    ::= { tmnxVdoGrpSrcStatEntry 51 }

tmnxVdoGrpSrcADIRxSCTE35Msgs OBJECT-TYPE
    SYNTAX     Counter32
    MAX-ACCESS read-only
    STATUS     current
    DESCRIPTION
        "The value of tmnxVdoGrpSrcADIRxSCTE35Msgs indicates the total number 
         of Society of Cable Telecommunications Engineers (SCTE-35) messages 
         received by the video ISA."
    ::= { tmnxVdoGrpSrcStatEntry 52 }

tmnxVdoGrpSrcADIRxSCTE35MsgEnc OBJECT-TYPE
    SYNTAX     Counter32
    MAX-ACCESS read-only
    STATUS     current
    DESCRIPTION
        "The value of tmnxVdoGrpSrcADIRxSCTE35MsgEnc indicates the total number 
         of encrypted Society of Cable Telecommunications Engineers (SCTE-35) 
         messages received by the video ISA."
    ::= { tmnxVdoGrpSrcStatEntry 53 }

tmnxVdoGrpSrcADIRxSCTE35MsgUnsup OBJECT-TYPE
    SYNTAX     Counter32
    MAX-ACCESS read-only
    STATUS     current
    DESCRIPTION
        "The value of tmnxVdoGrpSrcADIRxSCTE35MsgUnsup indicates the total 
         number of unsupported Society of Cable Telecommunications Engineers 
         (SCTE-35) messages received by the video ISA."
    ::= { tmnxVdoGrpSrcStatEntry 54 }

tmnxVdoGrpSrcADIRxSCTE35MsgDisc OBJECT-TYPE
    SYNTAX     Counter32
    MAX-ACCESS read-only
    STATUS     current
    DESCRIPTION
        "The value of tmnxVdoGrpSrcADIRxSCTE35MsgDisc indicates the total number 
         of Society of Cable Telecommunications Engineers (SCTE-35) messages 
         received by the video ISA and discarded. SCTE-35 messages with 
         unsupported commands and encrypted SCTE-35 messages are 
         discarded."
    ::= { tmnxVdoGrpSrcStatEntry 55 }

tmnxVdoGrpSrcADIUnsuppTSLenPkts OBJECT-TYPE
    SYNTAX     Counter32
    MAX-ACCESS read-only
    STATUS     current
    DESCRIPTION
        "The value of tmnxVdoGrpSrcADIUnsuppTSLenPkts indicates the total number
         of data packets received whose size is not equal to 188 bytes. The 
         value of this object is valid only when the corresponding 
         tmnxVdoGrpADIServerState value is set to 'true'."
    ::= { tmnxVdoGrpSrcStatEntry 56 }

tmnxVdoGrpSrcRTClientPort OBJECT-TYPE
    SYNTAX     Unsigned32 (6000..7000)
    MAX-ACCESS read-only
    STATUS     current
    DESCRIPTION
        "The value of tmnxVdoGrpSrcRTClientPort indicates the local port 
         on which the Retransmission (RT) requests are received."
    ::= { tmnxVdoGrpSrcStatEntry 57 }

tmnxVdoGrpSrcDupSeqNumber OBJECT-TYPE
    SYNTAX     Counter32
    MAX-ACCESS read-only
    STATUS     current
    DESCRIPTION
        "The value of tmnxVdoGrpSrcDupSeqNumber indicates the total number of
         Real-time Transport Protocol (RTP) packets detected with a duplicate 
         sequence number."
    ::= { tmnxVdoGrpSrcStatEntry 58 }

tmnxVdoGrpSrcRTSTxMcRetPkts OBJECT-TYPE
    SYNTAX     Counter64
    MAX-ACCESS read-only
    STATUS     current
    DESCRIPTION
        "The value of tmnxVdoGrpSrcRTSTxMcRetPkts indicates the total number 
         of multicast packets sent in response to retransmission requests."
    ::= { tmnxVdoGrpSrcStatEntry 59 }

tmnxVdoGrpSrcRTSTxMcRetPktsL32 OBJECT-TYPE
    SYNTAX     Counter32
    MAX-ACCESS read-only
    STATUS     current
    DESCRIPTION
        "The value of tmnxVdoGrpSrcRTSTxMcRetPktsL32 indicates the lower 32 
         bits of the value of tmnxVdoGrpSrcRTSTxMcRetPkts."
    ::= { tmnxVdoGrpSrcStatEntry 60 }

tmnxVdoGrpSrcRTSTxMcRetPktsH32 OBJECT-TYPE
    SYNTAX     Counter32
    MAX-ACCESS read-only
    STATUS     current
    DESCRIPTION
        "The value of tmnxVdoGrpSrcRTSTxMcRetPktsH32 indicates the higher 32 
         bits of the value of tmnxVdoGrpSrcRTSTxMcRetPkts."
    ::= { tmnxVdoGrpSrcStatEntry 61 }

tmnxVdoGrpSrcRTSTxMcRetBytes OBJECT-TYPE
    SYNTAX     Counter64
    MAX-ACCESS read-only
    STATUS     current
    DESCRIPTION
        "The value of tmnxVdoGrpSrcRTSTxMcRetBytes indicates the total number 
         of multicast bytes sent in response to retransmission requests."
    ::= { tmnxVdoGrpSrcStatEntry 62 }

tmnxVdoGrpSrcRTSTxMcRetBytesL32 OBJECT-TYPE
    SYNTAX     Counter32
    MAX-ACCESS read-only
    STATUS     current
    DESCRIPTION
        "The value of tmnxVdoGrpSrcRTSTxMcRetBytesL32 indicates the lower 32 
         bits of the value of tmnxVdoGrpSrcRTSTxMcRetBytes."
    ::= { tmnxVdoGrpSrcStatEntry 63 }

tmnxVdoGrpSrcRTSTxMcRetBytesH32 OBJECT-TYPE
    SYNTAX     Counter32
    MAX-ACCESS read-only
    STATUS     current
    DESCRIPTION
        "The value of tmnxVdoGrpSrcRTSTxMcRetBytesH32 indicates the higher 32 
         bits of the value of tmnxVdoGrpSrcRTSTxMcRetBytes."
    ::= { tmnxVdoGrpSrcStatEntry 64 }

tmnxVdoGrpSrcRTSTxMcRetErrs OBJECT-TYPE
    SYNTAX     Counter64
    MAX-ACCESS read-only
    STATUS     current
    DESCRIPTION
        "The value of tmnxVdoGrpSrcRTSTxMcRetErrs indicates the total number
         of errors occured while doing  multicast retransmission in response to 
         requests."
    ::= { tmnxVdoGrpSrcStatEntry 65 }

tmnxVdoGrpSrcRTSTxMcRetErrsL32 OBJECT-TYPE
    SYNTAX     Counter32
    MAX-ACCESS read-only
    STATUS     current
    DESCRIPTION
        "The value of tmnxVdoGrpSrcRTSTxMcRetErrsL32 indicates the lower 32 
         bits of the value of tmnxVdoGrpSrcRTSTxMcRetErrs."
    ::= { tmnxVdoGrpSrcStatEntry 66 }

tmnxVdoGrpSrcRTSTxMcRetErrsH32 OBJECT-TYPE
    SYNTAX     Counter32
    MAX-ACCESS read-only
    STATUS     current
    DESCRIPTION
        "The value of tmnxVdoGrpSrcRTSTxMcRetErrsH32 indicates the higher 32 
         bits of the value of tmnxVdoGrpSrcRTSTxMcRetErrs."
    ::= { tmnxVdoGrpSrcStatEntry 67 }


tmnxVdoGrpSrcRTSRetReqQnc OBJECT-TYPE
    SYNTAX     Counter64
    MAX-ACCESS read-only
    STATUS     current
    DESCRIPTION
        "The value of tmnxVdoGrpSrcRTSRetReqQnc indicates the total 
         number of unicast retransmission requests quenced by carrying out  
         multicast response requests."
    ::= { tmnxVdoGrpSrcStatEntry 68 }

tmnxVdoGrpSrcRTSRetReqQncL32 OBJECT-TYPE
    SYNTAX     Counter32
    MAX-ACCESS read-only
    STATUS     current
    DESCRIPTION
        "The value of tmnxVdoGrpSrcRTSRetReqQncL32 indicates the lower 32 
         bits of the value of tmnxVdoGrpSrcRTSRetReqQnc."
    ::= { tmnxVdoGrpSrcStatEntry 69 }

tmnxVdoGrpSrcRTSRetReqQncH32 OBJECT-TYPE
    SYNTAX     Counter32
    MAX-ACCESS read-only
    STATUS     current
    DESCRIPTION
        "The value of tmnxVdoGrpSrcRTSRetReqQncH32 indicates the higher 32 
         bits of the value of tmnxVdoGrpSrcRTSRetReqQnc."
    ::= { tmnxVdoGrpSrcStatEntry 70 }

tmnxVdoGrpSrcRTSRetReqCrt OBJECT-TYPE
    SYNTAX     Counter64
    MAX-ACCESS read-only
    STATUS     current
    DESCRIPTION
        "The value of tmnxVdoGrpSrcRTSRetReqCrt indicates the total 
         number of multicast retransmission requests created in response to the 
         unicast retransmission."
    ::= { tmnxVdoGrpSrcStatEntry 71 }

tmnxVdoGrpSrcRTSRetReqCrtL32 OBJECT-TYPE
    SYNTAX     Counter32
    MAX-ACCESS read-only
    STATUS     current
    DESCRIPTION
        "The value of tmnxVdoGrpSrcRTSRetReqCrtL32 indicates the lower 32 
         bits of the value of tmnxVdoGrpSrcRTSRetReqCrt."
    ::= { tmnxVdoGrpSrcStatEntry 72 }

tmnxVdoGrpSrcRTSRetReqCrtH32 OBJECT-TYPE
    SYNTAX     Counter32
    MAX-ACCESS read-only
    STATUS     current
    DESCRIPTION
        "The value of tmnxVdoGrpSrcRTSRetReqCrtH32 indicates the higher 32 
         bits of the value of tmnxVdoGrpSrcRTSRetReqCrt."
    ::= { tmnxVdoGrpSrcStatEntry 73 }

tmnxVdoGrpSrcRxDupSsrcDrops OBJECT-TYPE
    SYNTAX     Counter32
    MAX-ACCESS read-only
    STATUS     current
    DESCRIPTION
        "The value of tmnxVdoGrpSrcRxDupSsrcDrops indicates the number of
         receive-packets dropped with a duplicate synchronization source (SSRC) 
         identifier."
    ::= { tmnxVdoGrpSrcStatEntry 74 }

tmnxVdoGrpSrcDupSsrc OBJECT-TYPE
    SYNTAX     Counter32
    MAX-ACCESS read-only
    STATUS     current
    DESCRIPTION
        "The value of tmnxVdoGrpSrcDupSsrc indicates the number of packets
         detected with a duplicate synchronization source (SSRC) identifier."
    ::= { tmnxVdoGrpSrcStatEntry 75 }

tmnxVdoGrpSrcFccMinDuration OBJECT-TYPE
    SYNTAX     Unsigned32 (1..100000)
    UNITS      "milliseconds"
    MAX-ACCESS read-only
    STATUS     current
    DESCRIPTION
        "The value of tmnxVdoGrpSrcFccMinDuration indicates the minimum FCC 
         duration in msecs for FCC requests for this channel."
    ::= { tmnxVdoGrpSrcStatEntry 76 }

tmnxVdoGrpSrcAudioReorder OBJECT-TYPE
    SYNTAX     Unsigned32 (1..100000)
    UNITS      "milliseconds"
    MAX-ACCESS read-only
    STATUS     current
    DESCRIPTION
        "The value of tmnxVdoGrpSrcAudioReorder indicates in msecs how much 
         earlier the audio frames are sent during an FCC burst to achieve a 
         good audio fast-channel-change experience."
    ::= { tmnxVdoGrpSrcStatEntry 77 }

tmnxVdoGrpSrcRxBytesSaved OBJECT-TYPE
    SYNTAX     Counter64
    MAX-ACCESS read-only
    STATUS     current
    DESCRIPTION
        "The value of tmnxVdoGrpSrcRxBytesSaved indicates the total number of 
         received bytes that are saved on this multicast channel."
    ::= { tmnxVdoGrpSrcStatEntry 78 }

tmnxVdoGrpSrcRxBytesSavedL32 OBJECT-TYPE
    SYNTAX     Counter32
    MAX-ACCESS read-only
    STATUS     current
    DESCRIPTION
        "The value of tmnxVdoGrpSrcRxBytesSavedL32 indicates the lower 32 bits
         of the value of tmnxVdoGrpSrcRxBytesSaved."
    ::= { tmnxVdoGrpSrcStatEntry 79 }

tmnxVdoGrpSrcRxBytesSavedH32 OBJECT-TYPE
    SYNTAX     Counter32
    MAX-ACCESS read-only
    STATUS     current
    DESCRIPTION
        "The value of tmnxVdoGrpSrcRxBytesSavedH32 indicates the higher 32 bits
         of the value of tmnxVdoGrpSrcRxBytesSaved."
    ::= { tmnxVdoGrpSrcStatEntry 80 }

tmnxVdoGrpSrcRxPacketsSaved OBJECT-TYPE
    SYNTAX     Counter64
    MAX-ACCESS read-only
    STATUS     current
    DESCRIPTION
        "The value of tmnxVdoGrpSrcRxPacketsSaved indicates the total number of 
         received packets that are saved on this multicast channel."
    ::= { tmnxVdoGrpSrcStatEntry 81 }

tmnxVdoGrpSrcRxPacketsSavedL32 OBJECT-TYPE
    SYNTAX     Counter32
    MAX-ACCESS read-only
    STATUS     current
    DESCRIPTION
        "The value of tmnxVdoGrpSrcRxPacketsSavedL32 indicates the lower 32 bits
         of the value of tmnxVdoGrpSrcRxPacketsSaved."
    ::= { tmnxVdoGrpSrcStatEntry 82 }

tmnxVdoGrpSrcRxPacketsSavedH32 OBJECT-TYPE
    SYNTAX     Counter32
    MAX-ACCESS read-only
    STATUS     current
    DESCRIPTION
        "The value of tmnxVdoGrpSrcRxPacketsSavedH32 indicates the higher 32
         bits of the value of tmnxVdoGrpSrcRxPacketsSaved."
    ::= { tmnxVdoGrpSrcStatEntry 83 }

tmnxVdoGrpSrcStatOperBW OBJECT-TYPE
    SYNTAX     Unsigned32
    UNITS      "kbps"
    MAX-ACCESS read-only
    STATUS     current
    DESCRIPTION
        "The value of tmnxVdoGrpSrcStatOperBW indicates the most recently
         computed bandwidth of the video stream averaged over the last one 
         second."
    ::= { tmnxVdoGrpSrcStatEntry 84 }

tmnxVdoGrpSrcRouterIfName OBJECT-TYPE
    SYNTAX     TNamedItemOrEmpty
    MAX-ACCESS read-only
    STATUS     current
    DESCRIPTION
        "The value of tmnxVdoGrpSrcRouterIfName indicates the ingress interface 
         name for this video channel."
    ::= { tmnxVdoGrpSrcStatEntry 85 }

tmnxVdoGrpSrcNumFccDentedPkts OBJECT-TYPE
    SYNTAX     Counter32
    MAX-ACCESS read-only
    STATUS     current
    DESCRIPTION
        "The value of tmnxVdoGrpSrcNumFccDentedPkts indicates the number of 
         packets in the unicast FCC stream that were dropped due to denting."
    ::= { tmnxVdoGrpSrcStatEntry 86 }

--
-- Video Source Group Statistics SNMPv1 Table
--

tmnxVdoSGStatV1Table OBJECT-TYPE
    SYNTAX     SEQUENCE OF TmnxVdoSGStatV1Entry
    MAX-ACCESS not-accessible
    STATUS     current
    DESCRIPTION
        "The tmnxVdoSGStatV1Table provides an extension of the
         tmnxVdoGrpSrcStatTable and contains channel statistics for the
         multicast groups."
    ::= { tmnxVdoObjs 8 }

tmnxVdoSGStatV1Entry OBJECT-TYPE
    SYNTAX     TmnxVdoSGStatV1Entry
    MAX-ACCESS not-accessible
    STATUS     current
    DESCRIPTION
        "An entry in the tmnxVdoSGStatV1Table containing channel statistics.

         The counters in this table are defined as 32-bit entries which hold
         the values of 64-bit entries in tmnxVdoGrpSrcStatTable."
    AUGMENTS    {  tmnxVdoGrpSrcStatEntry  }
    ::= { tmnxVdoSGStatV1Table 1 }

TmnxVdoSGStatV1Entry ::= SEQUENCE {
    tmnxVdoSGV1RxBytesLow32               Counter32,
    tmnxVdoSGV1RxBytesHigh32              Counter32,
    tmnxVdoSGV1RxPacketsLow32             Counter32,
    tmnxVdoSGV1RxPacketsHigh32            Counter32,
    tmnxVdoSGV1RxInvalidPacketsLow32      Counter32,
    tmnxVdoSGV1RxInvalidPacketsHgh32      Counter32,
    tmnxVdoSGV1TxBytesLow32               Counter32,
    tmnxVdoSGV1TxBytesHigh32              Counter32,
    tmnxVdoSGV1TxPacketsLow32             Counter32,
    tmnxVdoSGV1TxPacketsHigh32            Counter32,
    tmnxVdoSGV1TxFailedPacketsLow32       Counter32,
    tmnxVdoSGV1TxFailedPacketsHigh32      Counter32,
    tmnxVdoSGV1RTClntRxReTxBytsLow32      Counter32,
    tmnxVdoSGV1RTClntRxReTxBytsHgh32      Counter32,
    tmnxVdoSGV1RTClntRxReTxPktsLow32      Counter32,
    tmnxVdoSGV1RTClntRxReTxPktsHgh32      Counter32,
    tmnxVdoSGV1RTSrvrTxBytesLow32         Counter32,
    tmnxVdoSGV1RTSrvrTxBytesHigh32        Counter32,
    tmnxVdoSGV1RTSrvrTxPacketsLow32       Counter32,
    tmnxVdoSGV1RTSrvrTxPacketsHigh32      Counter32,
    tmnxVdoSGV1FCCSrvrTxBytesLow32        Counter32,
    tmnxVdoSGV1FCCSrvrTxBytesHigh32       Counter32,
    tmnxVdoSGV1FCCSrvrTxPacketsLow32      Counter32,
    tmnxVdoSGV1FCCSrvrTxPacketsHgh32      Counter32,
    tmnxVdoSGV1ADIRxPacketsLow32          Counter32,
    tmnxVdoSGV1ADIRxPacketsHigh32         Counter32,
    tmnxVdoSGV1ADITxPacketsLow32          Counter32,
    tmnxVdoSGV1ADITxPacketsHigh32         Counter32
}

tmnxVdoSGV1RxBytesLow32 OBJECT-TYPE
    SYNTAX     Counter32
    MAX-ACCESS read-only
    STATUS     current
    DESCRIPTION
        "The value of tmnxVdoSGV1RxBytesLow32 indicates the lower 32 bits
         of the value of tmnxVdoGrpSrcRxBytes."
    ::= { tmnxVdoSGStatV1Entry 1 }

tmnxVdoSGV1RxBytesHigh32 OBJECT-TYPE
    SYNTAX     Counter32
    MAX-ACCESS read-only
    STATUS     current
    DESCRIPTION
        "The value of tmnxVdoSGV1RxBytesHigh32 indicates the higher 32 bits
         of the value of tmnxVdoGrpSrcRxBytes."
    ::= { tmnxVdoSGStatV1Entry 2 }

tmnxVdoSGV1RxPacketsLow32 OBJECT-TYPE
    SYNTAX     Counter32
    MAX-ACCESS read-only
    STATUS     current
    DESCRIPTION
        "The value of tmnxVdoSGV1RxPacketsLow32 indicates the lower 32 bits
         of the value of tmnxVdoGrpSrcRxPackets."
    ::= { tmnxVdoSGStatV1Entry 3 }

tmnxVdoSGV1RxPacketsHigh32 OBJECT-TYPE
    SYNTAX     Counter32
    MAX-ACCESS read-only
    STATUS     current
    DESCRIPTION
        "The value of tmnxVdoSGV1RxPacketsHigh32 indicates the higher 32 bits
         of the value of tmnxVdoGrpSrcRxPackets."
    ::= { tmnxVdoSGStatV1Entry 4 }

tmnxVdoSGV1RxInvalidPacketsLow32 OBJECT-TYPE
    SYNTAX     Counter32
    MAX-ACCESS read-only
    STATUS     current
    DESCRIPTION
        "The value of tmnxVdoSGV1RxInvalidPacketsLow32 indicates the lower
         32 bits of the value of tmnxVdoGrpSrcRxInvalidPackets."
    ::= { tmnxVdoSGStatV1Entry 5 }

tmnxVdoSGV1RxInvalidPacketsHgh32 OBJECT-TYPE
    SYNTAX     Counter32
    MAX-ACCESS read-only
    STATUS     current
    DESCRIPTION
        "The value of tmnxVdoSGV1RxInvalidPacketsHgh32 indicates the higher
         32 bits of the value of tmnxVdoGrpSrcRxInvalidPackets."
    ::= { tmnxVdoSGStatV1Entry 6 }

tmnxVdoSGV1TxBytesLow32 OBJECT-TYPE
    SYNTAX     Counter32
    MAX-ACCESS read-only
    STATUS     current
    DESCRIPTION
        "The value of tmnxVdoSGV1TxBytesLow32 indicates the lower 32 bits
         of the value of tmnxVdoGrpSrcTxBytes."
    ::= { tmnxVdoSGStatV1Entry 7 }

tmnxVdoSGV1TxBytesHigh32 OBJECT-TYPE
    SYNTAX     Counter32
    MAX-ACCESS read-only
    STATUS     current
    DESCRIPTION
        "The value of tmnxVdoSGV1TxBytesHigh32 indicates the higher 32 bits
         of the value of tmnxVdoGrpSrcTxBytes."
    ::= { tmnxVdoSGStatV1Entry 8 }

tmnxVdoSGV1TxPacketsLow32 OBJECT-TYPE
    SYNTAX     Counter32
    MAX-ACCESS read-only
    STATUS     current
    DESCRIPTION
        "The value of tmnxVdoSGV1TxPacketsLow32 indicates the lower 32 bits
         of the value of tmnxVdoGrpSrcTxPackets."
    ::= { tmnxVdoSGStatV1Entry 9 }

tmnxVdoSGV1TxPacketsHigh32 OBJECT-TYPE
    SYNTAX     Counter32
    MAX-ACCESS read-only
    STATUS     current
    DESCRIPTION
        "The value of tmnxVdoSGV1TxPacketsHigh32 indicates the higher 32 bits
         of the value of tmnxVdoGrpSrcTxPackets."
    ::= { tmnxVdoSGStatV1Entry 10 }

tmnxVdoSGV1TxFailedPacketsLow32 OBJECT-TYPE
    SYNTAX     Counter32
    MAX-ACCESS read-only
    STATUS     current
    DESCRIPTION
        "The value of tmnxVdoSGV1TxFailedPacketsLow32 indicates the lower
         32 bits of the value of tmnxVdoGrpSrcTxFailedPackets."
    ::= { tmnxVdoSGStatV1Entry 11 }

tmnxVdoSGV1TxFailedPacketsHigh32 OBJECT-TYPE
    SYNTAX     Counter32
    MAX-ACCESS read-only
    STATUS     current
    DESCRIPTION
        "The value of tmnxVdoSGV1TxFailedPacketsHigh32 indicates the higher
         32 bits of the value of tmnxVdoGrpSrcTxFailedPackets."
    ::= { tmnxVdoSGStatV1Entry 12 }

tmnxVdoSGV1RTClntRxReTxBytsLow32 OBJECT-TYPE
    SYNTAX     Counter32
    MAX-ACCESS read-only
    STATUS     current
    DESCRIPTION
        "The value of tmnxVdoSGV1RTClntRxReTxBytsLow32 indicates the lower
         32 bits of the value of tmnxVdoGrpSrcRTClientRxReTxBytes."
    ::= { tmnxVdoSGStatV1Entry 13 }

tmnxVdoSGV1RTClntRxReTxBytsHgh32 OBJECT-TYPE
    SYNTAX     Counter32
    MAX-ACCESS read-only
    STATUS     current
    DESCRIPTION
        "The value of tmnxVdoSGV1RTClntRxReTxBytsHgh32 indicates the higher
         32 bits of the value of tmnxVdoGrpSrcRTClientRxReTxBytes."
    ::= { tmnxVdoSGStatV1Entry 14 }

tmnxVdoSGV1RTClntRxReTxPktsLow32 OBJECT-TYPE
    SYNTAX     Counter32
    MAX-ACCESS read-only
    STATUS     current
    DESCRIPTION
        "The value of tmnxVdoSGV1RTClntRxReTxPktsLow32 indicates the lower
         32 bits of the value of tmnxVdoGrpSrcRTClientRxReTxPkts."
    ::= { tmnxVdoSGStatV1Entry 15 }

tmnxVdoSGV1RTClntRxReTxPktsHgh32 OBJECT-TYPE
    SYNTAX     Counter32
    MAX-ACCESS read-only
    STATUS     current
    DESCRIPTION
        "The value of tmnxVdoSGV1RTClntRxReTxPktsHgh32 indicates the higher
         32 bits of the value of tmnxVdoGrpSrcRTClientRxReTxPkts."
    ::= { tmnxVdoSGStatV1Entry 16 }

tmnxVdoSGV1RTSrvrTxBytesLow32 OBJECT-TYPE
    SYNTAX     Counter32
    MAX-ACCESS read-only
    STATUS     current
    DESCRIPTION
        "The value of tmnxVdoSGV1RTSrvrTxBytesLow32 indicates the lower 32 bits
         of the value of tmnxVdoGrpSrcRTSrvrTxBytes."
    ::= { tmnxVdoSGStatV1Entry 17 }

tmnxVdoSGV1RTSrvrTxBytesHigh32 OBJECT-TYPE
    SYNTAX     Counter32
    MAX-ACCESS read-only
    STATUS     current
    DESCRIPTION
        "The value of tmnxVdoSGV1RTSrvrTxBytesHigh32 indicates the higher
         32 bits of the value of tmnxVdoGrpSrcRTSrvrTxBytes."
    ::= { tmnxVdoSGStatV1Entry 18 }

tmnxVdoSGV1RTSrvrTxPacketsLow32 OBJECT-TYPE
    SYNTAX     Counter32
    MAX-ACCESS read-only
    STATUS     current
    DESCRIPTION
        "The value of tmnxVdoSGV1RTSrvrTxPacketsLow32 indicates the lower
         32 bits of the value of tmnxVdoGrpSrcRTSrvrTxPackets."
    ::= { tmnxVdoSGStatV1Entry 19 }

tmnxVdoSGV1RTSrvrTxPacketsHigh32 OBJECT-TYPE
    SYNTAX     Counter32
    MAX-ACCESS read-only
    STATUS     current
    DESCRIPTION
        "The value of tmnxVdoSGV1RTSrvrTxPacketsHigh32 indicates the higher
         32 bits of the value of tmnxVdoGrpSrcRTSrvrTxPackets."
    ::= { tmnxVdoSGStatV1Entry 20 }

tmnxVdoSGV1FCCSrvrTxBytesLow32 OBJECT-TYPE
    SYNTAX     Counter32
    MAX-ACCESS read-only
    STATUS     current
    DESCRIPTION
        "The value of tmnxVdoSGV1FCCSrvrTxBytesLow32 indicates the lower
         32 bits of the value of tmnxVdoGrpSrcFCCSrvrTxBytes."
    ::= { tmnxVdoSGStatV1Entry 21 }

tmnxVdoSGV1FCCSrvrTxBytesHigh32 OBJECT-TYPE
    SYNTAX     Counter32
    MAX-ACCESS read-only
    STATUS     current
    DESCRIPTION
        "The value of tmnxVdoSGV1FCCSrvrTxBytesHigh32 indicates the higher
         32 bits of the value of tmnxVdoGrpSrcFCCSrvrTxBytes."
    ::= { tmnxVdoSGStatV1Entry 22 }

tmnxVdoSGV1FCCSrvrTxPacketsLow32 OBJECT-TYPE
    SYNTAX     Counter32
    MAX-ACCESS read-only
    STATUS     current
    DESCRIPTION
        "The value of tmnxVdoSGV1FCCSrvrTxPacketsLow32 indicates the lower
         32 bits of the value of tmnxVdoGrpSrcFCCSrvrTxPackets."
    ::= { tmnxVdoSGStatV1Entry 23 }

tmnxVdoSGV1FCCSrvrTxPacketsHgh32 OBJECT-TYPE
    SYNTAX     Counter32
    MAX-ACCESS read-only
    STATUS     current
    DESCRIPTION
        "The value of tmnxVdoSGV1FCCSrvrTxPacketsHgh32 indicates the higher
         32 bits of the value of tmnxVdoGrpSrcFCCSrvrTxPackets."
    ::= { tmnxVdoSGStatV1Entry 24 }

tmnxVdoSGV1ADIRxPacketsLow32 OBJECT-TYPE
    SYNTAX     Counter32
    MAX-ACCESS read-only
    STATUS     current
    DESCRIPTION
        "The value of tmnxVdoSGV1ADIRxPacketsLow32 indicates the lower 32 bits
         of the value of tmnxVdoGrpSrcADIRxPackets."
    ::= { tmnxVdoSGStatV1Entry 25 }

tmnxVdoSGV1ADIRxPacketsHigh32 OBJECT-TYPE
    SYNTAX     Counter32
    MAX-ACCESS read-only
    STATUS     current
    DESCRIPTION
        "The value of tmnxVdoSGV1ADIRxPacketsHigh32 indicates the higher
         32 bits of the value of tmnxVdoGrpSrcADIRxPackets."
    ::= { tmnxVdoSGStatV1Entry 26 }

tmnxVdoSGV1ADITxPacketsLow32 OBJECT-TYPE
    SYNTAX     Counter32
    MAX-ACCESS read-only
    STATUS     current
    DESCRIPTION
        "The value of tmnxVdoSGV1ADITxPacketsLow32 indicates the lower 32 bits
         of the value of tmnxVdoGrpSrcADITxPackets."
    ::= { tmnxVdoSGStatV1Entry 27 }

tmnxVdoSGV1ADITxPacketsHigh32 OBJECT-TYPE
    SYNTAX     Counter32
    MAX-ACCESS read-only
    STATUS     current
    DESCRIPTION
        "The value of tmnxVdoSGV1ADITxPacketsHigh32 indicates the higher
         32 bits of the value of tmnxVdoGrpSrcADITxPackets."
    ::= { tmnxVdoSGStatV1Entry 28 }

--
-- Video Session Table
--

tmnxVdoSessionTable OBJECT-TYPE
    SYNTAX     SEQUENCE OF TmnxVdoSessionEntry
    MAX-ACCESS not-accessible
    STATUS     current
    DESCRIPTION
        "tmnxVdoSessionTable contains information and statistics for each 
         session."
    ::= { tmnxVdoObjs 9 }

tmnxVdoSessionEntry OBJECT-TYPE
    SYNTAX     TmnxVdoSessionEntry
    MAX-ACCESS not-accessible
    STATUS     current
    DESCRIPTION
        "An entry in the tmnxVdoSessionTable. Each entry represents the source 
         address for the session."
    INDEX      { 
                 svcId,
                 tmnxVdoIfName,
                 tmnxVdoSessionSourceAddrType,
                 tmnxVdoSessionSourceAddr,
                 tmnxVdoSessionSourcePort
               }
    ::= { tmnxVdoSessionTable 1 }

TmnxVdoSessionEntry ::= SEQUENCE {
    tmnxVdoSessionSourceAddrType          InetAddressType,
    tmnxVdoSessionSourceAddr              InetAddress,
    tmnxVdoSessionSourcePort              InetPortNumber,
    tmnxVdoSessionSSRCId                  Counter32,
    tmnxVdoSessionUpTime                  Unsigned32,
    tmnxVdoSessionExpireTime              Unsigned32,
    tmnxVdoSessionCName                   TNamedItem,
    tmnxVdoSessionDestAddrType            InetAddressType,
    tmnxVdoSessionDestAddr                InetAddress,
    tmnxVdoSessionRxFCCRequests           Counter32,
    tmnxVdoSessionTxFCCReplies            Counter32,
    tmnxVdoSessionTxFCCPackets            Counter32,
    tmnxVdoSessionTxFCCOctets             Counter32,
    tmnxVdoSessionTxFCCFailedPackets      Counter32,    
    tmnxVdoSessionRxRTRequests            Counter32,
    tmnxVdoSessionTxRTReplies             Counter32,
    tmnxVdoSessionTxRTPackets             Counter32,
    tmnxVdoSessionTxRTOctets              Counter32,
    tmnxVdoSessionTxRTFailedPackets       Counter32,
    tmnxVdoSessionRequestedRtpPkts        Counter32,
    tmnxVdoSessionRTReqQuenched           Counter32,
    tmnxVdoSessionRTMcastReqCreated       Counter32,
    tmnxVdoSessionPktsLostInSeq10         Counter32,
    tmnxVdoSessionPktsLostInSeq20         Counter32,
    tmnxVdoSessionPktsLostInSeq30         Counter32,
    tmnxVdoSessionPktsLostInSeq40         Counter32,
    tmnxVdoSessionPktsLostInSeqMore       Counter32
}

tmnxVdoSessionSourceAddrType OBJECT-TYPE
    SYNTAX     InetAddressType
    MAX-ACCESS not-accessible
    STATUS     current
    DESCRIPTION
        "The value of tmnxVdoSessionSourceAddrType indicates the type of 
         address represented by tmnxVdoSessionSourceAddr."
    ::= { tmnxVdoSessionEntry 1 }

tmnxVdoSessionSourceAddr OBJECT-TYPE
    SYNTAX     InetAddress (SIZE (4|16))
    MAX-ACCESS not-accessible
    STATUS     current
    DESCRIPTION
        "The value of tmnxVdoSessionSourceAddr indicates the address of the 
         Fast Channel Change (FCC) server or Retransmission (RT) server."
    ::= { tmnxVdoSessionEntry 2 }

tmnxVdoSessionSourcePort OBJECT-TYPE
    SYNTAX     InetPortNumber
    MAX-ACCESS not-accessible
    STATUS     current
    DESCRIPTION
        "The value of tmnxVdoSessionSourcePort indicates the server port on 
         which the Fast Channel Change or Retransmission services are being 
         provided."
    ::= { tmnxVdoSessionEntry 3 }

tmnxVdoSessionSSRCId OBJECT-TYPE
    SYNTAX     Counter32
    MAX-ACCESS read-only
    STATUS     current
    DESCRIPTION
        "The value of tmnxVdoSessionSSRCId indicates the synchronization 
         source (SSRC) identifier of the server."
    ::= { tmnxVdoSessionEntry 4 }

tmnxVdoSessionUpTime OBJECT-TYPE
    SYNTAX     Unsigned32
    UNITS      "seconds"
    MAX-ACCESS read-only
    STATUS     current
    DESCRIPTION
        "The value of tmnxVdoSessionUpTime indicates how long it has been 
         since the session was established."
    ::= { tmnxVdoSessionEntry 5 }

tmnxVdoSessionExpireTime OBJECT-TYPE
    SYNTAX     Unsigned32
    UNITS      "seconds"
    MAX-ACCESS read-only
    STATUS     current
    DESCRIPTION
        "The value of tmnxVdoSessionExpireTime indicates the expiry time of 
         this session. The value of this object ticks backwards and indicates 
         the remaining time that the row may exist before it is aged out." 
    ::= { tmnxVdoSessionEntry 6 }

tmnxVdoSessionCName OBJECT-TYPE
    SYNTAX     TNamedItem
    MAX-ACCESS read-only
    STATUS     current
    DESCRIPTION
        "The value of tmnxVdoSessionCName indicates the canonical name of 
         the server."
    ::= { tmnxVdoSessionEntry 7 }

tmnxVdoSessionDestAddrType OBJECT-TYPE
    SYNTAX     InetAddressType
    MAX-ACCESS read-only
    STATUS     current
    DESCRIPTION
        "The value of tmnxVdoSessionDestAddrType indicates the type of address 
         represented by tmnxVdoSessionDestAddr."
    ::= { tmnxVdoSessionEntry 8 }

tmnxVdoSessionDestAddr OBJECT-TYPE
    SYNTAX     InetAddress (SIZE (4|16))
    MAX-ACCESS read-only
    STATUS     current
    DESCRIPTION
        "The value of tmnxVdoSessionDestAddr indicates the address of the 
         destionation in this session."
    ::= { tmnxVdoSessionEntry 9 }

tmnxVdoSessionRxFCCRequests OBJECT-TYPE
    SYNTAX     Counter32
    MAX-ACCESS read-only
    STATUS     current
    DESCRIPTION
        "The value of tmnxVdoSessionRxFCCRequests indicates the total number 
         of Fast Channel Change (FCC) requests received by the server."
    ::= { tmnxVdoSessionEntry 10 }

tmnxVdoSessionTxFCCReplies OBJECT-TYPE
    SYNTAX     Counter32
    MAX-ACCESS read-only
    STATUS     current
    DESCRIPTION
        "The value of tmnxVdoSessionTxFCCReplies indicates the total number 
         of Fast Channel Change (FCC) replies sent by the server."
    ::= { tmnxVdoSessionEntry 11 }

tmnxVdoSessionTxFCCPackets OBJECT-TYPE
    SYNTAX     Counter32
    MAX-ACCESS read-only
    STATUS     current
    DESCRIPTION
        "The value of tmnxVdoSessionTxFCCPackets indicates the total number 
         of Fast Channel Change (FCC) packets sent by the server."
    ::= { tmnxVdoSessionEntry 12 }

tmnxVdoSessionTxFCCOctets OBJECT-TYPE
    SYNTAX     Counter32
    MAX-ACCESS read-only
    STATUS     current
    DESCRIPTION
        "The value of tmnxVdoSessionTxFCCOctets indicates the total number 
         of Fast Channel Change (FCC) octets sent by the server."
    ::= { tmnxVdoSessionEntry 13 }

tmnxVdoSessionTxFCCFailedPackets OBJECT-TYPE
    SYNTAX     Counter32
    MAX-ACCESS read-only
    STATUS     current
    DESCRIPTION
        "The value of tmnxVdoSessionTxFCCFailedPackets indicates the total 
         number of failures during the transmission of Fast Channel Change (FCC) 
         packets. Failure happens when the packet to be sent is not stored 
         in the video cache."
    ::= { tmnxVdoSessionEntry 14 }

tmnxVdoSessionRxRTRequests OBJECT-TYPE
    SYNTAX     Counter32
    MAX-ACCESS read-only
    STATUS     current
    DESCRIPTION
        "The value of tmnxVdoSessionRxRTRequests indicates the total number 
         of Retransmission (RT) requests received by the server."
    ::= { tmnxVdoSessionEntry 15 }

tmnxVdoSessionTxRTReplies OBJECT-TYPE
    SYNTAX     Counter32
    MAX-ACCESS read-only
    STATUS     current
    DESCRIPTION
        "The value of tmnxVdoSessionTxRTReplies indicates the total number 
         of Retransmission (RT) replies sent by the server."
    ::= { tmnxVdoSessionEntry 16 }

tmnxVdoSessionTxRTPackets OBJECT-TYPE
    SYNTAX     Counter32
    MAX-ACCESS read-only
    STATUS     current
    DESCRIPTION
        "The value of tmnxVdoSessionTxRTPackets indicates the total number 
         of Retransmission (RT) packets sent by the server."
    ::= { tmnxVdoSessionEntry 17 }

tmnxVdoSessionTxRTOctets OBJECT-TYPE
    SYNTAX     Counter32
    MAX-ACCESS read-only
    STATUS     current
    DESCRIPTION
        "The value of tmnxVdoSessionTxRTOctets indicates the total number 
         of Retransmission (RT) octets sent by the server."
    ::= { tmnxVdoSessionEntry 18 }

tmnxVdoSessionTxRTFailedPackets OBJECT-TYPE
    SYNTAX     Counter32
    MAX-ACCESS read-only
    STATUS     current
    DESCRIPTION
        "The value of tmnxVdoSessionTxRTFailedPackets indicates the total 
         number of failures during the transmission of Retransmission (RT) 
         packets. Failure happens when the packet to be sent is not stored 
         in the video cache."
    ::= { tmnxVdoSessionEntry 19 }

tmnxVdoSessionRequestedRtpPkts OBJECT-TYPE
    SYNTAX     Counter32
    MAX-ACCESS read-only
    STATUS     current
    DESCRIPTION
        "The value of tmnxVdoSessionRequestedRtpPkts indicates the number of 
         Real-time Transport Protocol (RTP) packets requested in the Real-time 
         Transport Control Protocol (RTCP) feedback (FB) messages received in 
         this session."
    ::= { tmnxVdoSessionEntry 20 }

tmnxVdoSessionRTReqQuenched OBJECT-TYPE
    SYNTAX     Counter32
    MAX-ACCESS read-only
    STATUS     current
    DESCRIPTION
        "The value of tmnxVdoSessionRTReqQuenched indicates the number of 
         unicast retransmission requests quenched with multicast retransmission 
         in this session."
    ::= { tmnxVdoSessionEntry 21 }

tmnxVdoSessionRTMcastReqCreated OBJECT-TYPE
    SYNTAX     Counter32
    MAX-ACCESS read-only
    STATUS     current
    DESCRIPTION
        "The value of tmnxVdoSessionRTMcastReqCreated indicates the number of 
        multicast retransmission requests created in response to unicast 
        retransmission requests in this session."
    ::= { tmnxVdoSessionEntry 22 }

tmnxVdoSessionPktsLostInSeq10 OBJECT-TYPE
    SYNTAX     Counter32
    MAX-ACCESS read-only
    STATUS     current
    DESCRIPTION
        "The value of tmnxVdoSessionPktsLostInSeq10 indicates the total number 
         of packets within sequences of 2 to 10 consecutive lost packets in 
         this session."
    ::= { tmnxVdoSessionEntry 23 }

tmnxVdoSessionPktsLostInSeq20 OBJECT-TYPE
    SYNTAX     Counter32
    MAX-ACCESS read-only
    STATUS     current
    DESCRIPTION
        "The value of tmnxVdoSessionPktsLostInSeq20 indicates the total number 
         of packets within sequences of 11 to 20 consecutive lost packets in 
         this session."
    ::= { tmnxVdoSessionEntry 24 }

tmnxVdoSessionPktsLostInSeq30 OBJECT-TYPE
    SYNTAX     Counter32
    MAX-ACCESS read-only
    STATUS     current
    DESCRIPTION
        "The value of tmnxVdoSessionPktsLostInSeq30 indicates the total number 
         of packets within sequences of 21 to 30 consecutive lost packets in 
         this session."
    ::= { tmnxVdoSessionEntry 25 }

tmnxVdoSessionPktsLostInSeq40 OBJECT-TYPE
    SYNTAX     Counter32
    MAX-ACCESS read-only
    STATUS     current
    DESCRIPTION
        "The value of tmnxVdoSessionPktsLostInSeq40 indicates the total number 
         of packets within sequences of 31 to 40 consecutive lost packets in 
         this session."
    ::= { tmnxVdoSessionEntry 26 }

tmnxVdoSessionPktsLostInSeqMore OBJECT-TYPE
    SYNTAX     Counter32
    MAX-ACCESS read-only
    STATUS     current
    DESCRIPTION
        "The value of tmnxVdoSessionPktsLostInSeqMore indicates the total number 
         of packets within sequences of 41 or more consecutive lost packets in 
         this session."
    ::= { tmnxVdoSessionEntry 27 }

--
-- Video Interface Address Statistics Table (Lower 32 bits)
--

tmnxVdoIfStatTable OBJECT-TYPE
    SYNTAX     SEQUENCE OF TmnxVdoIfStatEntry
    MAX-ACCESS not-accessible
    STATUS     current
    DESCRIPTION
        "tmnxVdoIfStatTable contains information and statistics for each 
         video interface configured in the system."
    ::= { tmnxVdoObjs 10 }

tmnxVdoIfStatEntry OBJECT-TYPE
    SYNTAX     TmnxVdoIfStatEntry
    MAX-ACCESS not-accessible
    STATUS     current
    DESCRIPTION
        "An entry in the tmnxVdoIfStatTable. Each row entry represents an 
         IP address assigned to a video interface."
    AUGMENTS { tmnxVdoIfAddrEntry }
    ::= { tmnxVdoIfStatTable 1 }

TmnxVdoIfStatEntry ::= SEQUENCE {
    tmnxVdoIfStatHdRTServerState          TruthValue,
    tmnxVdoIfStatSdRTServerState          TruthValue,
    tmnxVdoIfStatPipRTServerState         TruthValue,
    tmnxVdoIfStatRTSvrSdRtpPktsReq        Counter64,
    tmnxVdoIfStatRTSvrHdRtpPktsReq        Counter64,
    tmnxVdoIfStatRTSvrPipRtpPktsReq       Counter64,
    tmnxVdoIfStatRTSvrRxSdRTReq           Counter64,
    tmnxVdoIfStatRTSvrRxSdFailedReq       Counter64,
    tmnxVdoIfStatRTSvrRxHdRTReq           Counter64,
    tmnxVdoIfStatRTSvrRxHdFailedReq       Counter64,
    tmnxVdoIfStatRTSvrRxPipRTReq          Counter64,
    tmnxVdoIfStatRTSvrRxPipFailedReq      Counter64,
    tmnxVdoIfStatRTSvrTxSdRTReplies       Counter64,
    tmnxVdoIfStatRTSvrTxSdBytes           Counter64,
    tmnxVdoIfStatRTSvrTxSdPackets         Counter64,
    tmnxVdoIfStatRTSvrTxHdRTReplies       Counter64,
    tmnxVdoIfStatRTSvrTxHdBytes           Counter64,
    tmnxVdoIfStatRTSvrTxHdPackets         Counter64,
    tmnxVdoIfStatRTSvrTxPipRTReplies      Counter64,
    tmnxVdoIfStatRTSvrTxPipBytes          Counter64,
    tmnxVdoIfStatRTSvrTxPipPackets        Counter64,
    tmnxVdoIfStatHdFCCServerMode          TmnxVdoFccServerMode,
    tmnxVdoIfStatSdFCCServerMode          TmnxVdoFccServerMode,
    tmnxVdoIfStatPipFCCServerMode         TmnxVdoFccServerMode,
    tmnxVdoIfStatFCCSrRxSdFCCReq          Counter64,
    tmnxVdoIfStatFCCSrRxSdFailedReq       Counter64,
    tmnxVdoIfStatFCCSrRxHdFCCReq          Counter64,
    tmnxVdoIfStatFCCSrRxHdFailedReq       Counter64,
    tmnxVdoIfStatFCCSrRxPipFCCReq         Counter64,
    tmnxVdoIfStatFCCSrRxPipFailedReq      Counter64,
    tmnxVdoIfStatFCCSrTxSdFCCReplies      Counter64,
    tmnxVdoIfStatFCCSrTxSdBytes           Counter64,
    tmnxVdoIfStatFCCSrTxSdPackets         Counter64,
    tmnxVdoIfStatFCCSrTxHdFCCReplies      Counter64,
    tmnxVdoIfStatFCCSrTxHdBytes           Counter64,
    tmnxVdoIfStatFCCSrTxHdPackets         Counter64,
    tmnxVdoIfStatFCCSrTxPipFCCRplies      Counter64,
    tmnxVdoIfStatFCCSrTxPipBytes          Counter64,
    tmnxVdoIfStatFCCSrTxPipPackets        Counter64,
    tmnxVdoIfStatTxFailedPackets          Counter64,    
    tmnxVdoIfScte30TcpSessions            Counter32,
    tmnxVdoIfScte30InitSessions           Counter32,
    tmnxVdoIfStatRTSSdMcRdPktsReq         Counter64,
    tmnxVdoIfStatRTSSdMcRdPktsReqL32      Counter32,
    tmnxVdoIfStatRTSSdMcRdPktsReqH32      Counter32,
    tmnxVdoIfStatRTSHDMcRdPktsReq         Counter64,
    tmnxVdoIfStatRTSHDMcRdPktsReqL32      Counter32,
    tmnxVdoIfStatRTSHDMcRdPktsReqH32      Counter32,
    tmnxVdoIfStatRTSPipMcRdPktReq         Counter64,
    tmnxVdoIfStatRTSPipMcRdPktReqL32      Counter32,
    tmnxVdoIfStatRTSPipMcRdPktReqH32      Counter32,
    tmnxVdoIfStatSDPktLostInSeq10         Counter32,
    tmnxVdoIfStatSDPktLostInSeq20         Counter32,
    tmnxVdoIfStatSDPktLostInSeq30         Counter32,
    tmnxVdoIfStatSDPktLostInSeq40         Counter32,
    tmnxVdoIfStatSDPktLostInSeqMore       Counter32,
    tmnxVdoIfStatHDPktLostInSeq10         Counter32,
    tmnxVdoIfStatHDPktLostInSeq20         Counter32,
    tmnxVdoIfStatHDPktLostInSeq30         Counter32,
    tmnxVdoIfStatHDPktLostInSeq40         Counter32,
    tmnxVdoIfStatHDPktLostInSeqMore       Counter32,
    tmnxVdoIfStatPipPktLostInSeq10        Counter32,
    tmnxVdoIfStatPipPktLostInSeq20        Counter32,
    tmnxVdoIfStatPipPktLostInSeq30        Counter32,
    tmnxVdoIfStatPipPktLostInSeq40        Counter32,
    tmnxVdoIfStatPipPktLostInSeqMore      Counter32
}

tmnxVdoIfStatHdRTServerState OBJECT-TYPE
    SYNTAX     TruthValue
    MAX-ACCESS read-only
    STATUS     current
    DESCRIPTION
        "The value of tmnxVdoIfStatHdRTServerState indicates whether the 
         High Definition (HD) retransmission server is enabled on 
         this interface."
    ::= { tmnxVdoIfStatEntry 1 }

tmnxVdoIfStatSdRTServerState OBJECT-TYPE
    SYNTAX     TruthValue
    MAX-ACCESS read-only
    STATUS     current
    DESCRIPTION
        "The value of tmnxVdoIfStatSdRTServerState indicates whether the 
         Standard Definition (SD) retransmission server is enabled on 
         this interface."
    ::= { tmnxVdoIfStatEntry 2 }

tmnxVdoIfStatPipRTServerState OBJECT-TYPE
    SYNTAX     TruthValue
    MAX-ACCESS read-only
    STATUS     current
    DESCRIPTION
        "The value of tmnxVdoIfStatPipRTServerState indicates whether the 
         Picture-in-Picture (PIP) retransmission server is enabled on 
         this interface."
    ::= { tmnxVdoIfStatEntry 3 }

tmnxVdoIfStatRTSvrSdRtpPktsReq OBJECT-TYPE
    SYNTAX     Counter64
    MAX-ACCESS read-only
    STATUS     current
    DESCRIPTION
        "The value of tmnxVdoIfStatRTSvrSdRtpPktsReq indicates the total number 
         of Standard Definition (SD) channel Real-time Transport Protocol (RTP) 
         packets requested in the Real-time Transport Control Protocol (RTCP) 
         feedback (FB) messages received on this interface."
    ::= { tmnxVdoIfStatEntry 4 }

tmnxVdoIfStatRTSvrHdRtpPktsReq OBJECT-TYPE
    SYNTAX     Counter64
    MAX-ACCESS read-only
    STATUS     current
    DESCRIPTION
        "The value of tmnxVdoIfStatRTSvrHdRtpPktsReq indicates the total number 
         of High Definition (HD) channel Real-time Transport Protocol (RTP) 
         packets requested in the Real-time Transport Control Protocol (RTCP) 
         feedback (FB) messages received on this interface."
    ::= { tmnxVdoIfStatEntry 5 }

tmnxVdoIfStatRTSvrPipRtpPktsReq OBJECT-TYPE
    SYNTAX     Counter64
    MAX-ACCESS read-only
    STATUS     current
    DESCRIPTION
        "The value of tmnxVdoIfStatRTSvrPipRtpPktsReq indicates the total number 
         of Picture-In-Picture (PIP) channel Real-time Transport Protocol (RTP) 
         packets requested in the Real-time Transport Control Protocol (RTCP) 
         feedback (FB) messages received on this interface."
    ::= { tmnxVdoIfStatEntry 6 }

tmnxVdoIfStatRTSvrRxSdRTReq OBJECT-TYPE
    SYNTAX     Counter64
    MAX-ACCESS read-only
    STATUS     current
    DESCRIPTION
        "The value of tmnxVdoIfStatRTSvrRxSdRTReq indicates the total number 
         of Retransmission (RT) requests received from Standard Definition 
         (SD) channels on this interface."
    ::= { tmnxVdoIfStatEntry 7 }

tmnxVdoIfStatRTSvrRxSdFailedReq OBJECT-TYPE
    SYNTAX     Counter64
    MAX-ACCESS read-only
    STATUS     current
    DESCRIPTION
        "The value of tmnxVdoIfStatRTSvrRxSdFailedReq indicates the total 
         number of failed Retransmission (RT) requests received from Standard 
         Definition (SD) channels on this interface."
    ::= { tmnxVdoIfStatEntry 8 }

tmnxVdoIfStatRTSvrRxHdRTReq OBJECT-TYPE
    SYNTAX     Counter64
    MAX-ACCESS read-only
    STATUS     current
    DESCRIPTION
        "The value of tmnxVdoIfStatRTSvrRxHdRTReq indicates the total number 
         of Retransmission (RT) requests received from High Definition (HD) 
         channels on this interface."
    ::= { tmnxVdoIfStatEntry 9 }

tmnxVdoIfStatRTSvrRxHdFailedReq OBJECT-TYPE
    SYNTAX     Counter64
    MAX-ACCESS read-only
    STATUS     current
    DESCRIPTION
        "The value of tmnxVdoIfStatRTSvrRxHdFailedReq indicates the total 
         number of failed Retransmission (RT) requests received from High 
         Definition (HD) channels on this interface."
    ::= { tmnxVdoIfStatEntry 10 }

tmnxVdoIfStatRTSvrRxPipRTReq OBJECT-TYPE
    SYNTAX     Counter64
    MAX-ACCESS read-only
    STATUS     current
    DESCRIPTION
        "The value of tmnxVdoIfStatRTSvrRxPipRTReq indicates the total number 
         of Retransmission (RT) requests received from Picture-In-Picture 
         (PIP) channels on this interface."
    ::= { tmnxVdoIfStatEntry 11 }

tmnxVdoIfStatRTSvrRxPipFailedReq OBJECT-TYPE
    SYNTAX     Counter64
    MAX-ACCESS read-only
    STATUS     current
    DESCRIPTION
        "The value of tmnxVdoIfStatRTSvrRxPipFailedReq indicates the total 
         number of failed Retransmission (RT) requests received from 
         Picture-In-Picture (PIP) channels on this interface."
    ::= { tmnxVdoIfStatEntry 12 }

tmnxVdoIfStatRTSvrTxSdRTReplies OBJECT-TYPE
    SYNTAX     Counter64
    MAX-ACCESS read-only
    STATUS     current
    DESCRIPTION
        "The value of tmnxVdoIfStatRTSvrTxSdRTReplies indicates the total 
         number of Standard Definition (SD) channel Retransmission (RT) 
         replies sent from this interface."
    ::= { tmnxVdoIfStatEntry 13 }

tmnxVdoIfStatRTSvrTxSdBytes OBJECT-TYPE
    SYNTAX     Counter64
    MAX-ACCESS read-only
    STATUS     current
    DESCRIPTION
        "The value of tmnxVdoIfStatRTSvrTxSdBytes indicates the total 
         number of Standard Definition (SD) channel bytes sent from this 
         interface."
    ::= { tmnxVdoIfStatEntry 14 }

tmnxVdoIfStatRTSvrTxSdPackets OBJECT-TYPE
    SYNTAX     Counter64
    MAX-ACCESS read-only
    STATUS     current
    DESCRIPTION
        "The value of tmnxVdoIfStatRTSvrTxSdPackets indicates the total 
         number of Standard Definition (SD) channel packets sent from this 
         interface."
    ::= { tmnxVdoIfStatEntry 15 }

tmnxVdoIfStatRTSvrTxHdRTReplies OBJECT-TYPE
    SYNTAX     Counter64
    MAX-ACCESS read-only
    STATUS     current
    DESCRIPTION
        "The value of tmnxVdoIfStatRTSvrTxHdRTReplies indicates the total 
         number of High Definition (HD) channel Retransmission (RT) replies 
         sent from this interface."
    ::= { tmnxVdoIfStatEntry 16 }

tmnxVdoIfStatRTSvrTxHdBytes OBJECT-TYPE
    SYNTAX     Counter64
    MAX-ACCESS read-only
    STATUS     current
    DESCRIPTION
        "The value of tmnxVdoIfStatRTSvrTxHdBytes indicates the total 
         number of High Definition (HD) channel bytes sent from this 
         interface."
    ::= { tmnxVdoIfStatEntry 17 }

tmnxVdoIfStatRTSvrTxHdPackets OBJECT-TYPE
    SYNTAX     Counter64
    MAX-ACCESS read-only
    STATUS     current
    DESCRIPTION
        "The value of tmnxVdoIfStatRTSvrTxHdPackets indicates the total 
         number of High Definition (HD) channel packets sent from this 
         interface."
    ::= { tmnxVdoIfStatEntry 18 }

tmnxVdoIfStatRTSvrTxPipRTReplies OBJECT-TYPE
    SYNTAX     Counter64
    MAX-ACCESS read-only
    STATUS     current
    DESCRIPTION
        "The value of tmnxVdoIfStatRTSvrTxPipRTReplies indicates the total 
         number of Picture-In-Picture (PIP) channel Retransmission (RT) 
         replies sent from this interface."
    ::= { tmnxVdoIfStatEntry 19 }

tmnxVdoIfStatRTSvrTxPipBytes OBJECT-TYPE
    SYNTAX     Counter64
    MAX-ACCESS read-only
    STATUS     current
    DESCRIPTION
        "The value of tmnxVdoIfStatRTSvrTxPipBytes indicates the total 
         number of Picture-In-Picture (PIP) channel bytes sent from this 
         interface."
    ::= { tmnxVdoIfStatEntry 20 }

tmnxVdoIfStatRTSvrTxPipPackets OBJECT-TYPE
    SYNTAX     Counter64
    MAX-ACCESS read-only
    STATUS     current
    DESCRIPTION
        "The value of tmnxVdoIfStatRTSvrTxPipPackets indicates the total 
         number of Picture-In-Picture (PIP) channel packets sent from this 
         interface."
    ::= { tmnxVdoIfStatEntry 21 }

tmnxVdoIfStatHdFCCServerMode OBJECT-TYPE
    SYNTAX     TmnxVdoFccServerMode
    MAX-ACCESS read-only
    STATUS     current
    DESCRIPTION
        "The value of tmnxVdoIfStatHdFCCServerMode indicates the mode of the
         High Definition (HD) Fast Channel Change (FCC) server on this 
         interface."
    ::= { tmnxVdoIfStatEntry 22 }

tmnxVdoIfStatSdFCCServerMode OBJECT-TYPE
    SYNTAX     TmnxVdoFccServerMode
    MAX-ACCESS read-only
    STATUS     current
    DESCRIPTION
        "The value of tmnxVdoIfStatSdFCCServerMode indicates the mode of the
         Standard Definition (SD) Fast Channel Change (FCC) server on this 
         interface."
    ::= { tmnxVdoIfStatEntry 23 }

tmnxVdoIfStatPipFCCServerMode OBJECT-TYPE
    SYNTAX     TmnxVdoFccServerMode
    MAX-ACCESS read-only
    STATUS     current
    DESCRIPTION
        "The value of tmnxVdoIfStatPipFCCServerMode indicates the mode of the
         Picture-in-Picture (PIP) Fast Channel Change (FCC) server on this 
         interface."
    ::= { tmnxVdoIfStatEntry 24 }

tmnxVdoIfStatFCCSrRxSdFCCReq OBJECT-TYPE
    SYNTAX     Counter64
    MAX-ACCESS read-only
    STATUS     current
    DESCRIPTION
        "The value of tmnxVdoIfStatFCCSrRxSdFCCReq indicates the total number 
         of Fast Channel Change (FCC) requests received from Standard 
         Definition (SD) channels on this interface."
    ::= { tmnxVdoIfStatEntry 25 }

tmnxVdoIfStatFCCSrRxSdFailedReq OBJECT-TYPE
    SYNTAX     Counter64
    MAX-ACCESS read-only
    STATUS     current
    DESCRIPTION
        "The value of tmnxVdoIfStatFCCSrRxSdFailedReq indicates the total 
         number of failed Fast Channel Change (FCC) requests received from 
         Standard Definition (SD) channels on this interface."
    ::= { tmnxVdoIfStatEntry 26 }

tmnxVdoIfStatFCCSrRxHdFCCReq OBJECT-TYPE
    SYNTAX     Counter64
    MAX-ACCESS read-only
    STATUS     current
    DESCRIPTION
        "The value of tmnxVdoIfStatFCCSrRxHdFCCReq indicates the total number 
         of Fast Channel Change (FCC) requests received from High Definition 
         (HD) channels on this interface."
    ::= { tmnxVdoIfStatEntry 27 }

tmnxVdoIfStatFCCSrRxHdFailedReq OBJECT-TYPE
    SYNTAX     Counter64
    MAX-ACCESS read-only
    STATUS     current
    DESCRIPTION
        "The value of tmnxVdoIfStatFCCSrRxHdFailedReq indicates the total 
         number of failed Fast Channel Change (FCC) requests received from 
         High Definition (HD) channels on this interface."
    ::= { tmnxVdoIfStatEntry 28 }

tmnxVdoIfStatFCCSrRxPipFCCReq OBJECT-TYPE
    SYNTAX     Counter64
    MAX-ACCESS read-only
    STATUS     current
    DESCRIPTION
        "The value of tmnxVdoIfStatFCCSrRxPipFCCReq indicates the total number 
         of Fast Channel Change (FCC) requests received from Picture-In-Picture
         (PIP) channels on this interface."
    ::= { tmnxVdoIfStatEntry 29 }

tmnxVdoIfStatFCCSrRxPipFailedReq OBJECT-TYPE
    SYNTAX     Counter64
    MAX-ACCESS read-only
    STATUS     current
    DESCRIPTION
        "The value of tmnxVdoIfStatFCCSrRxPipFailedReq indicates the total 
         number of failed Fast Channel Change (FCC) requests received from 
         Picture-In-Picture (PIP) channels on this interface."
    ::= { tmnxVdoIfStatEntry 30 }

tmnxVdoIfStatFCCSrTxSdFCCReplies OBJECT-TYPE
    SYNTAX     Counter64
    MAX-ACCESS read-only
    STATUS     current
    DESCRIPTION
        "The value of tmnxVdoIfStatFCCSrTxSdFCCReplies indicates the total 
         number of Standard Definition (SD) channel Fast Channel Change (FCC) 
         replies sent from this interface."
    ::= { tmnxVdoIfStatEntry 31 }

tmnxVdoIfStatFCCSrTxSdBytes OBJECT-TYPE
    SYNTAX     Counter64
    MAX-ACCESS read-only
    STATUS     current
    DESCRIPTION
        "The value of tmnxVdoIfStatFCCSrTxSdBytes indicates the total 
         number of Standard Definition (SD) channel bytes sent from this 
         interface."
    ::= { tmnxVdoIfStatEntry 32 }

tmnxVdoIfStatFCCSrTxSdPackets OBJECT-TYPE
    SYNTAX     Counter64
    MAX-ACCESS read-only
    STATUS     current
    DESCRIPTION
        "The value of tmnxVdoIfStatFCCSrTxSdPackets indicates the total 
         number of Standard Definition (SD) channel packets sent from this 
         interface."
    ::= { tmnxVdoIfStatEntry 33 }

tmnxVdoIfStatFCCSrTxHdFCCReplies OBJECT-TYPE
    SYNTAX     Counter64
    MAX-ACCESS read-only
    STATUS     current
    DESCRIPTION
        "The value of tmnxVdoIfStatFCCSrTxHdFCCReplies indicates the total 
         number of High Definition (HD) channel Fast Channel Change (FCC) 
         replies sent from this interface."
    ::= { tmnxVdoIfStatEntry 34 }

tmnxVdoIfStatFCCSrTxHdBytes OBJECT-TYPE
    SYNTAX     Counter64
    MAX-ACCESS read-only
    STATUS     current
    DESCRIPTION
        "The value of tmnxVdoIfStatFCCSrTxHdBytes indicates the total 
         number of High Definition (HD) channel bytes sent from this 
         interface."
    ::= { tmnxVdoIfStatEntry 35 }

tmnxVdoIfStatFCCSrTxHdPackets OBJECT-TYPE
    SYNTAX     Counter64
    MAX-ACCESS read-only
    STATUS     current
    DESCRIPTION
        "The value of tmnxVdoIfStatFCCSrTxHdPackets indicates the total 
         number of High Definition (HD) channel packets sent from this 
         interface."
    ::= { tmnxVdoIfStatEntry 36 }

tmnxVdoIfStatFCCSrTxPipFCCRplies OBJECT-TYPE
    SYNTAX     Counter64
    MAX-ACCESS read-only
    STATUS     current
    DESCRIPTION
        "The value of tmnxVdoIfStatFCCSrTxPipFCCRplies indicates the total 
         number of Picture-In-Picture (PIP) channel Fast Channel Change (FCC) 
         replies sent from this interface."
    ::= { tmnxVdoIfStatEntry 37 }

tmnxVdoIfStatFCCSrTxPipBytes OBJECT-TYPE
    SYNTAX     Counter64
    MAX-ACCESS read-only
    STATUS     current
    DESCRIPTION
        "The value of tmnxVdoIfStatFCCSrTxPipBytes indicates the total 
         number of Picture-In-Picture (PIP) channel bytes sent from this 
         interface."
    ::= { tmnxVdoIfStatEntry 38 }

tmnxVdoIfStatFCCSrTxPipPackets OBJECT-TYPE
    SYNTAX     Counter64
    MAX-ACCESS read-only
    STATUS     current
    DESCRIPTION
        "The value of tmnxVdoIfStatFCCSrTxPipPackets indicates the total 
         number of Picture-In-Picture (PIP) channel packets sent from this 
         interface."
    ::= { tmnxVdoIfStatEntry 39 }

tmnxVdoIfStatTxFailedPackets OBJECT-TYPE
    SYNTAX     Counter64
    MAX-ACCESS read-only
    STATUS     current
    DESCRIPTION
        "The value of tmnxVdoIfStatTxFailedPackets indicates the total 
         number of failures during the transmission of packets from this video 
         interface. Failure happens when the packet to be sent is not stored 
         in the video cache."
    ::= { tmnxVdoIfStatEntry 40 }

tmnxVdoIfScte30TcpSessions OBJECT-TYPE
    SYNTAX     Counter32
    MAX-ACCESS read-only
    STATUS     current
    DESCRIPTION
        "The value of tmnxVdoIfScte30TcpSessions indicates the total number 
         of scte30 tcp sessions with the Ad Insert (ADI) servers for this 
         interface."
    ::= { tmnxVdoIfStatEntry 41 }

tmnxVdoIfScte30InitSessions OBJECT-TYPE
    SYNTAX     Counter32
    MAX-ACCESS read-only
    STATUS     current
    DESCRIPTION
        "The value of tmnxVdoIfScte30InitSessions indicates the total number 
         of scte30 init sessions with the Ad Insert (ADI) servers for this 
         interface."
    ::= { tmnxVdoIfStatEntry 42 }

tmnxVdoIfStatRTSSdMcRdPktsReq OBJECT-TYPE
    SYNTAX     Counter64
    MAX-ACCESS read-only
    STATUS     current
    DESCRIPTION
        "The value of tmnxVdoIfStatRTSSdMcRdPktsReq indicates the total 
         number of multicast retransmission requests created for Standard 
         Definition (SD) channels on this interface."
    ::= { tmnxVdoIfStatEntry 43 }

tmnxVdoIfStatRTSSdMcRdPktsReqL32 OBJECT-TYPE
    SYNTAX     Counter32
    MAX-ACCESS read-only
    STATUS     current
    DESCRIPTION
        "The value of tmnxVdoIfStatRTSSdMcRdPktsReqL32 indicates the lower 32 
         bits of the value of tmnxVdoIfStatRTSSdMcRdPktsReq."
    ::= { tmnxVdoIfStatEntry 44 }

tmnxVdoIfStatRTSSdMcRdPktsReqH32 OBJECT-TYPE
    SYNTAX     Counter32
    MAX-ACCESS read-only
    STATUS     current
    DESCRIPTION
        "The value of tmnxVdoIfStatRTSSdMcRdPktsReqH32 indicates the higher 32 
         bits of the value of tmnxVdoIfStatRTSSdMcRdPktsReq."
    ::= { tmnxVdoIfStatEntry 45 }

tmnxVdoIfStatRTSHDMcRdPktsReq OBJECT-TYPE
   SYNTAX     Counter64
   MAX-ACCESS read-only
   STATUS     current
   DESCRIPTION
       "The value of tmnxVdoIfStatRTSHDMcRdPktsReq indicates the total 
        number of multicast retransmission requests created for High Definition 
         (HD) channels on this interface."
   ::= { tmnxVdoIfStatEntry 46 }

tmnxVdoIfStatRTSHDMcRdPktsReqL32 OBJECT-TYPE
    SYNTAX     Counter32
    MAX-ACCESS read-only
    STATUS     current
    DESCRIPTION
        "The value of tmnxVdoIfStatRTSHDMcRdPktsReqL32 indicates the lower 32 
         bits of the value of tmnxVdoIfStatRTSHDMcRdPktsReq."
    ::= { tmnxVdoIfStatEntry 47 }

tmnxVdoIfStatRTSHDMcRdPktsReqH32 OBJECT-TYPE
    SYNTAX     Counter32
    MAX-ACCESS read-only
    STATUS     current
    DESCRIPTION
        "The value of tmnxVdoIfStatRTSHDMcRdPktsReqH32 indicates the higher 32 
         bits of the value of tmnxVdoIfStatRTSHDMcRdPktsReq."
    ::= { tmnxVdoIfStatEntry 48 }

tmnxVdoIfStatRTSPipMcRdPktReq OBJECT-TYPE
   SYNTAX     Counter64
   MAX-ACCESS read-only
   STATUS     current
   DESCRIPTION
       "The value of tmnxVdoIfStatRTSPipMcRdPktReq indicates the total 
        number of multicast retransmission requests created for 
        Picture-In-Picture (PIP) channels on this interface."
   ::= { tmnxVdoIfStatEntry 49 }

tmnxVdoIfStatRTSPipMcRdPktReqL32 OBJECT-TYPE
    SYNTAX     Counter32
    MAX-ACCESS read-only
    STATUS     current
    DESCRIPTION
        "The value of tmnxVdoIfStatRTSPipMcRdPktReqL32 indicates the lower 32 
         bits of the value of tmnxVdoIfStatRTSPipMcRdPktReq."
    ::= { tmnxVdoIfStatEntry 50 }

tmnxVdoIfStatRTSPipMcRdPktReqH32 OBJECT-TYPE
    SYNTAX     Counter32
    MAX-ACCESS read-only
    STATUS     current
    DESCRIPTION
        "The value of tmnxVdoIfStatRTSPipMcRdPktReqH32 indicates the higher 32 
         bits of the value of tmnxVdoIfStatRTSPipMcRdPktReq."
    ::= { tmnxVdoIfStatEntry 51 }

tmnxVdoIfStatSDPktLostInSeq10 OBJECT-TYPE
    SYNTAX     Counter32
    MAX-ACCESS read-only
    STATUS     current
    DESCRIPTION
        "The value of tmnxVdoIfStatSDPktLostInSeq10 indicates the total number 
         of packets within sequences of 2 to 10 consecutive lost packets for 
         Standard Definition (SD) channels on this video interface."
    ::= { tmnxVdoIfStatEntry 52 }

tmnxVdoIfStatSDPktLostInSeq20 OBJECT-TYPE
    SYNTAX     Counter32
    MAX-ACCESS read-only
    STATUS     current
    DESCRIPTION
        "The value of tmnxVdoIfStatSDPktLostInSeq20 indicates the total number 
         of packets within sequences of 11 to 20 consecutive lost packets for 
         Standard Definition (SD) channels on this video interface."
    ::= { tmnxVdoIfStatEntry 53 }

tmnxVdoIfStatSDPktLostInSeq30 OBJECT-TYPE
    SYNTAX     Counter32
    MAX-ACCESS read-only
    STATUS     current
    DESCRIPTION
        "The value of tmnxVdoIfStatSDPktLostInSeq30 indicates the total number 
         of packets within sequences of 21 to 30 consecutive lost packets for 
         Standard Definition (SD) channels on this video interface."
    ::= { tmnxVdoIfStatEntry 54 }

tmnxVdoIfStatSDPktLostInSeq40 OBJECT-TYPE
    SYNTAX     Counter32
    MAX-ACCESS read-only
    STATUS     current
    DESCRIPTION
        "The value of tmnxVdoIfStatSDPktLostInSeq40 indicates the total number 
         of packets within sequences of 31 to 40 consecutive lost packets for 
         Standard Definition (SD) channels on this video interface."
    ::= { tmnxVdoIfStatEntry 55 }

tmnxVdoIfStatSDPktLostInSeqMore OBJECT-TYPE
    SYNTAX     Counter32
    MAX-ACCESS read-only
    STATUS     current
    DESCRIPTION
        "The value of tmnxVdoIfStatSDPktLostInSeqMore indicates the total number 
         of packets within sequences of 41 or more consecutive lost packets for 
         Standard Definition (SD) channels on this video interface."
    ::= { tmnxVdoIfStatEntry 56 }

tmnxVdoIfStatHDPktLostInSeq10 OBJECT-TYPE
    SYNTAX     Counter32
    MAX-ACCESS read-only
    STATUS     current
    DESCRIPTION
        "The value of tmnxVdoIfStatHDPktLostInSeq10 indicates the total number 
         of packets within sequences of 2 to 10 consecutive lost packets for 
         High Definition (HD) channels on this video interface."
    ::= { tmnxVdoIfStatEntry 57 }

tmnxVdoIfStatHDPktLostInSeq20 OBJECT-TYPE
    SYNTAX     Counter32
    MAX-ACCESS read-only
    STATUS     current
    DESCRIPTION
        "The value of tmnxVdoIfStatHDPktLostInSeq20 indicates the total number 
         of packets within sequences of 11 to 20 consecutive lost packets for 
         High Definition (HD) channels on this video interface."
    ::= { tmnxVdoIfStatEntry 58 }

tmnxVdoIfStatHDPktLostInSeq30 OBJECT-TYPE
    SYNTAX     Counter32
    MAX-ACCESS read-only
    STATUS     current
    DESCRIPTION
        "The value of tmnxVdoIfStatHDPktLostInSeq30 indicates the total number 
         of packets within sequences of 21 to 30 consecutive lost packets for 
         High Definition (HD) channels on this video interface."
    ::= { tmnxVdoIfStatEntry 59 }

tmnxVdoIfStatHDPktLostInSeq40 OBJECT-TYPE
    SYNTAX     Counter32
    MAX-ACCESS read-only
    STATUS     current
    DESCRIPTION
        "The value of tmnxVdoIfStatHDPktLostInSeq40 indicates the total number 
         of packets within sequences of 31 to 40 consecutive lost packets for 
         High Definition (HD) channels on this video interface."
    ::= { tmnxVdoIfStatEntry 60 }

tmnxVdoIfStatHDPktLostInSeqMore OBJECT-TYPE
    SYNTAX     Counter32
    MAX-ACCESS read-only
    STATUS     current
    DESCRIPTION
        "The value of tmnxVdoIfStatHDPktLostInSeqMore indicates the total number 
         of packets within sequences of 41 or more consecutive lost packets for 
         High Definition (HD)  channels on this video interface."
    ::= { tmnxVdoIfStatEntry 61 }

tmnxVdoIfStatPipPktLostInSeq10 OBJECT-TYPE
    SYNTAX     Counter32
    MAX-ACCESS read-only
    STATUS     current
    DESCRIPTION
        "The value of tmnxVdoIfStatPipPktLostInSeq10 indicates the total number 
         of packets within sequences of 2 to 10 consecutive lost packets for 
         Picture-In-Picture (PIP) channels on this video interface."
    ::= { tmnxVdoIfStatEntry 62 }

tmnxVdoIfStatPipPktLostInSeq20 OBJECT-TYPE
    SYNTAX     Counter32
    MAX-ACCESS read-only
    STATUS     current
    DESCRIPTION
        "The value of tmnxVdoIfStatPipPktLostInSeq20 indicates the total number 
         of packets within sequences of 11 to 20 consecutive lost packets for 
         Picture-In-Picture (PIP) channels on this video interface."
    ::= { tmnxVdoIfStatEntry 63 }

tmnxVdoIfStatPipPktLostInSeq30 OBJECT-TYPE
    SYNTAX     Counter32
    MAX-ACCESS read-only
    STATUS     current
    DESCRIPTION
        "The value of tmnxVdoIfStatPipPktLostInSeq30 indicates the total number 
         of packets within sequences of 21 to 30 consecutive lost packets for 
         Picture-In-Picture (PIP) channels on this video interface."
    ::= { tmnxVdoIfStatEntry 64 }

tmnxVdoIfStatPipPktLostInSeq40 OBJECT-TYPE
    SYNTAX     Counter32
    MAX-ACCESS read-only
    STATUS     current
    DESCRIPTION
        "The value of tmnxVdoIfStatPipPktLostInSeq40 indicates the total number 
         of packets within sequences of 31 to 40 consecutive lost packets for 
         Picture-In-Picture (PIP) channels on this video interface."
    ::= { tmnxVdoIfStatEntry 65 }

tmnxVdoIfStatPipPktLostInSeqMore OBJECT-TYPE
    SYNTAX     Counter32
    MAX-ACCESS read-only
    STATUS     current
    DESCRIPTION
        "The value of tmnxVdoIfStatPipPktLostInSeqMore indicates the total number 
         of packets within sequences of 41 or more consecutive lost packets for 
         Picture-In-Picture (PIP)  channels on this video interface."
    ::= { tmnxVdoIfStatEntry 66 }

--
-- Video Interface Address Statistics Table (Higher 32 bits)
--

tmnxVdoIfStLowTable OBJECT-TYPE
    SYNTAX     SEQUENCE OF TmnxVdoIfStLowEntry
    MAX-ACCESS not-accessible
    STATUS     current
    DESCRIPTION
        "The tmnxVdoIfStLowTable contains information and statistics for each
         video interface configured in the system."
    ::= { tmnxVdoObjs 11 }

tmnxVdoIfStLowEntry OBJECT-TYPE
    SYNTAX     TmnxVdoIfStLowEntry
    MAX-ACCESS not-accessible
    STATUS     current
    DESCRIPTION
    "An entry in the tmnxVdoIfStLowTable containing video interface
     statistics.

     The counters in this table are defined as 32-bit entries which hold
     the lower 32 bits of the 64-bit counter values in tmnxVdoIfStatTable."
    AUGMENTS { tmnxVdoIfAddrEntry }
    ::= { tmnxVdoIfStLowTable 1 }

TmnxVdoIfStLowEntry ::= SEQUENCE {
    tmnxVdoIfStLowRTSvrSdRtpPktsReq        Counter32,
    tmnxVdoIfStLowRTSvrHdRtpPktsReq        Counter32,
    tmnxVdoIfStLowRTSvrPipRtpPktsReq       Counter32,
    tmnxVdoIfStLowRTSvrRxSdRTReq           Counter32,
    tmnxVdoIfStLowRTSvrRxSdFailedReq       Counter32,
    tmnxVdoIfStLowRTSvrRxHdRTReq           Counter32,
    tmnxVdoIfStLowRTSvrRxHdFailedReq       Counter32,
    tmnxVdoIfStLowRTSvrRxPipRTReq          Counter32,
    tmnxVdoIfStLowRTSvrRxPipFailedRq       Counter32,
    tmnxVdoIfStLowRTSvrTxSdRTReplies       Counter32,
    tmnxVdoIfStLowRTSvrTxSdBytes           Counter32,
    tmnxVdoIfStLowRTSvrTxSdPackets         Counter32,
    tmnxVdoIfStLowRTSvrTxHdRTReplies       Counter32,
    tmnxVdoIfStLowRTSvrTxHdBytes           Counter32,
    tmnxVdoIfStLowRTSvrTxHdPackets         Counter32,
    tmnxVdoIfStLowRTSvrTxPipRTReplis       Counter32,
    tmnxVdoIfStLowRTSvrTxPipBytes          Counter32,
    tmnxVdoIfStLowRTSvrTxPipPackets        Counter32,
    tmnxVdoIfStLowFCCSrRxSdFCCReq          Counter32,
    tmnxVdoIfStLowFCCSrRxSdFailedReq       Counter32,
    tmnxVdoIfStLowFCCSrRxHdFCCReq          Counter32,
    tmnxVdoIfStLowFCCSrRxHdFailedReq       Counter32,
    tmnxVdoIfStLowFCCSrRxPipFCCReq         Counter32,
    tmnxVdoIfStLowFCCSrRxPipFailedRq       Counter32,
    tmnxVdoIfStLowFCCSrTxSdFCCReplis       Counter32,
    tmnxVdoIfStLowFCCSrTxSdBytes           Counter32,
    tmnxVdoIfStLowFCCSrTxSdPackets         Counter32,
    tmnxVdoIfStLowFCCSrTxHdFCCReplis       Counter32,
    tmnxVdoIfStLowFCCSrTxHdBytes           Counter32,
    tmnxVdoIfStLowFCCSrTxHdPackets         Counter32,
    tmnxVdoIfStLowFCCSrTxPipFCCRplis       Counter32,
    tmnxVdoIfStLowFCCSrTxPipBytes          Counter32,
    tmnxVdoIfStLowFCCSrTxPipPackets        Counter32,
    tmnxVdoIfStLowTxFailedPackets          Counter32
}

tmnxVdoIfStLowRTSvrSdRtpPktsReq OBJECT-TYPE
    SYNTAX     Counter32
    MAX-ACCESS read-only
    STATUS     current
    DESCRIPTION
        "The value of tmnxVdoIfStLowRTSvrSdRtpPktsReq indicates the lower
         32 bits of the value of tmnxVdoIfStatRTSvrSdRtpPktsReq."
    ::= { tmnxVdoIfStLowEntry 1 }

tmnxVdoIfStLowRTSvrHdRtpPktsReq OBJECT-TYPE
    SYNTAX     Counter32
    MAX-ACCESS read-only
    STATUS     current
    DESCRIPTION
        "The value of tmnxVdoIfStLowRTSvrHdRtpPktsReq indicates the lower
         32 bits of the value of tmnxVdoIfStatRTSvrHdRtpPktsReq."
    ::= { tmnxVdoIfStLowEntry 2 }

tmnxVdoIfStLowRTSvrPipRtpPktsReq OBJECT-TYPE
    SYNTAX     Counter32
    MAX-ACCESS read-only
    STATUS     current
    DESCRIPTION
        "The value of tmnxVdoIfStLowRTSvrPipRtpPktsReq indicates the lower
         32 bits of the value of tmnxVdoIfStatRTSvrPipRtpPktsReq."
    ::= { tmnxVdoIfStLowEntry 3 }

tmnxVdoIfStLowRTSvrRxSdRTReq OBJECT-TYPE
    SYNTAX     Counter32
    MAX-ACCESS read-only
    STATUS     current
    DESCRIPTION
        "The value of tmnxVdoIfStLowRTSvrRxSdRTReq indicates the lower 32 bits
         of the value of tmnxVdoIfStatRTSvrRxSdRTReq."
    ::= { tmnxVdoIfStLowEntry 4 }

tmnxVdoIfStLowRTSvrRxSdFailedReq OBJECT-TYPE
    SYNTAX     Counter32
    MAX-ACCESS read-only
    STATUS     current
    DESCRIPTION
        "The value of tmnxVdoIfStLowRTSvrRxSdFailedReq indicates the lower
         32 bits of the value of tmnxVdoIfStatRTSvrRxSdFailedReq."
    ::= { tmnxVdoIfStLowEntry 5 }

tmnxVdoIfStLowRTSvrRxHdRTReq OBJECT-TYPE
    SYNTAX     Counter32
    MAX-ACCESS read-only
    STATUS     current
    DESCRIPTION
        "The value of tmnxVdoIfStLowRTSvrRxHdRTReq indicates the lower 32 bits
         of the value of tmnxVdoIfStatRTSvrRxHdRTReq."
    ::= { tmnxVdoIfStLowEntry 6 }

tmnxVdoIfStLowRTSvrRxHdFailedReq OBJECT-TYPE
    SYNTAX     Counter32
    MAX-ACCESS read-only
    STATUS     current
    DESCRIPTION
        "The value of tmnxVdoIfStLowRTSvrRxHdFailedReq indicates the lower
         32 bits of the value of tmnxVdoIfStatRTSvrRxHdFailedReq."
    ::= { tmnxVdoIfStLowEntry 7 }

tmnxVdoIfStLowRTSvrRxPipRTReq OBJECT-TYPE
    SYNTAX     Counter32
    MAX-ACCESS read-only
    STATUS     current
    DESCRIPTION
        "The value of tmnxVdoIfStLowRTSvrRxPipRTReq indicates the lower 32 bits
         of the value of tmnxVdoIfStatRTSvrRxPipRTReq."
    ::= { tmnxVdoIfStLowEntry 8 }

tmnxVdoIfStLowRTSvrRxPipFailedRq OBJECT-TYPE
    SYNTAX     Counter32
    MAX-ACCESS read-only
    STATUS     current
    DESCRIPTION
        "The value of tmnxVdoIfStLowRTSvrRxPipFailedRq indicates the lower
         32 bits of the value of tmnxVdoIfStatRTSvrRxPipFailedReq."
    ::= { tmnxVdoIfStLowEntry 9 }

tmnxVdoIfStLowRTSvrTxSdRTReplies OBJECT-TYPE
    SYNTAX     Counter32
    MAX-ACCESS read-only
    STATUS     current
    DESCRIPTION
        "The value of tmnxVdoIfStLowRTSvrTxSdRTReplies indicates the lower
         32 bits of the value of tmnxVdoIfStatRTSvrTxSdRTReplies."
    ::= { tmnxVdoIfStLowEntry 10 }

tmnxVdoIfStLowRTSvrTxSdBytes OBJECT-TYPE
    SYNTAX     Counter32
    MAX-ACCESS read-only
    STATUS     current
    DESCRIPTION
        "The value of tmnxVdoIfStLowRTSvrTxSdBytes indicates the lower 32 bits
         of the value of tmnxVdoIfStatRTSvrTxSdBytes."
    ::= { tmnxVdoIfStLowEntry 11 }

tmnxVdoIfStLowRTSvrTxSdPackets OBJECT-TYPE
    SYNTAX     Counter32
    MAX-ACCESS read-only
    STATUS     current
    DESCRIPTION
        "The value of tmnxVdoIfStLowRTSvrTxSdPackets indicates the lower
         32 bits of the value of tmnxVdoIfStatRTSvrTxSdPackets."
    ::= { tmnxVdoIfStLowEntry 12 }

tmnxVdoIfStLowRTSvrTxHdRTReplies OBJECT-TYPE
    SYNTAX     Counter32
    MAX-ACCESS read-only
    STATUS     current
    DESCRIPTION
        "The value of tmnxVdoIfStLowRTSvrTxHdRTReplies indicates the lower
         32 bits of the value of tmnxVdoIfStatRTSvrTxHdRTReplies."
    ::= { tmnxVdoIfStLowEntry 13 }

tmnxVdoIfStLowRTSvrTxHdBytes OBJECT-TYPE
    SYNTAX     Counter32
    MAX-ACCESS read-only
    STATUS     current
    DESCRIPTION
        "The value of tmnxVdoIfStLowRTSvrTxHdBytes indicates the lower 32 bits
         of the value of tmnxVdoIfStatRTSvrTxHdBytes."
    ::= { tmnxVdoIfStLowEntry 14 }

tmnxVdoIfStLowRTSvrTxHdPackets OBJECT-TYPE
    SYNTAX     Counter32
    MAX-ACCESS read-only
    STATUS     current
    DESCRIPTION
        "The value of tmnxVdoIfStLowRTSvrTxHdPackets indicates the lower
         32 bits of the value of tmnxVdoIfStatRTSvrTxHdPackets."
    ::= { tmnxVdoIfStLowEntry 15 }

tmnxVdoIfStLowRTSvrTxPipRTReplis OBJECT-TYPE
    SYNTAX     Counter32
    MAX-ACCESS read-only
    STATUS     current
    DESCRIPTION
        "The value of tmnxVdoIfStLowRTSvrTxPipRTReplis indicates the lower
         32 bits of the value of tmnxVdoIfStatRTSvrTxPipRTReplies."
    ::= { tmnxVdoIfStLowEntry 16 }

tmnxVdoIfStLowRTSvrTxPipBytes OBJECT-TYPE
    SYNTAX     Counter32
    MAX-ACCESS read-only
    STATUS     current
    DESCRIPTION
        "The value of tmnxVdoIfStLowRTSvrTxPipBytes indicates the lower 32 bits
         of the value of tmnxVdoIfStatRTSvrTxPipBytes."
    ::= { tmnxVdoIfStLowEntry 17 }

tmnxVdoIfStLowRTSvrTxPipPackets OBJECT-TYPE
    SYNTAX     Counter32
    MAX-ACCESS read-only
    STATUS     current
    DESCRIPTION
        "The value of tmnxVdoIfStLowRTSvrTxPipPackets indicates the lower
         32 bits of the value of tmnxVdoIfStatRTSvrTxPipPackets."
    ::= { tmnxVdoIfStLowEntry 18 }

tmnxVdoIfStLowFCCSrRxSdFCCReq OBJECT-TYPE
    SYNTAX     Counter32
    MAX-ACCESS read-only
    STATUS     current
    DESCRIPTION
        "The value of tmnxVdoIfStLowFCCSrRxSdFCCReq indicates the lower 32 bits
         of the value of tmnxVdoIfStatFCCSrRxSdFCCReq."
    ::= { tmnxVdoIfStLowEntry 19 }

tmnxVdoIfStLowFCCSrRxSdFailedReq OBJECT-TYPE
    SYNTAX     Counter32
    MAX-ACCESS read-only
    STATUS     current
    DESCRIPTION
        "The value of tmnxVdoIfStLowFCCSrRxSdFailedReq indicates the lower
         32 bits of the value of tmnxVdoIfStatFCCSrRxSdFailedReq."
    ::= { tmnxVdoIfStLowEntry 20 }

tmnxVdoIfStLowFCCSrRxHdFCCReq OBJECT-TYPE
    SYNTAX     Counter32
    MAX-ACCESS read-only
    STATUS     current
    DESCRIPTION
        "The value of tmnxVdoIfStLowFCCSrRxHdFCCReq indicates the lower 32 bits
         of the value of tmnxVdoIfStatFCCSrRxHdFCCReq."
    ::= { tmnxVdoIfStLowEntry 21 }

tmnxVdoIfStLowFCCSrRxHdFailedReq OBJECT-TYPE
    SYNTAX     Counter32
    MAX-ACCESS read-only
    STATUS     current
    DESCRIPTION
        "The value of tmnxVdoIfStLowFCCSrRxHdFailedReq indicates the lower
         32 bits of the value of tmnxVdoIfStatFCCSrRxHdFailedReq."
    ::= { tmnxVdoIfStLowEntry 22 }

tmnxVdoIfStLowFCCSrRxPipFCCReq OBJECT-TYPE
    SYNTAX     Counter32
    MAX-ACCESS read-only
    STATUS     current
    DESCRIPTION
        "The value of tmnxVdoIfStLowFCCSrRxPipFCCReq indicates the lower
         32 bits of the value of tmnxVdoIfStatFCCSrRxPipFCCReq."
    ::= { tmnxVdoIfStLowEntry 23 }

tmnxVdoIfStLowFCCSrRxPipFailedRq OBJECT-TYPE
    SYNTAX     Counter32
    MAX-ACCESS read-only
    STATUS     current
    DESCRIPTION
        "The value of tmnxVdoIfStLowFCCSrRxPipFailedRq indicates the lower
         32 bits of the value of tmnxVdoIfStatFCCSrRxPipFailedReq."
    ::= { tmnxVdoIfStLowEntry 24 }

tmnxVdoIfStLowFCCSrTxSdFCCReplis OBJECT-TYPE
    SYNTAX     Counter32
    MAX-ACCESS read-only
    STATUS     current
    DESCRIPTION
        "The value of tmnxVdoIfStLowFCCSrTxSdFCCReplis indicates the lower
         32 bits of the value of tmnxVdoIfStatFCCSrTxSdFCCReplies."
    ::= { tmnxVdoIfStLowEntry 25 }

tmnxVdoIfStLowFCCSrTxSdBytes OBJECT-TYPE
    SYNTAX     Counter32
    MAX-ACCESS read-only
    STATUS     current
    DESCRIPTION
        "The value of tmnxVdoIfStLowFCCSrTxSdBytes indicates the lower 32 bits
         of the value of tmnxVdoIfStatFCCSrTxSdBytes."
    ::= { tmnxVdoIfStLowEntry 26 }

tmnxVdoIfStLowFCCSrTxSdPackets OBJECT-TYPE
    SYNTAX     Counter32
    MAX-ACCESS read-only
    STATUS     current
    DESCRIPTION
        "The value of tmnxVdoIfStLowFCCSrTxSdPackets indicates the lower
         32 bits of the value of tmnxVdoIfStatFCCSrTxSdPackets."
    ::= { tmnxVdoIfStLowEntry 27 }

tmnxVdoIfStLowFCCSrTxHdFCCReplis OBJECT-TYPE
    SYNTAX     Counter32
    MAX-ACCESS read-only
    STATUS     current
    DESCRIPTION
        "The value of tmnxVdoIfStLowFCCSrTxHdFCCReplis indicates the lower
         32 bits of the value of tmnxVdoIfStatFCCSrTxHdFCCReplies."
    ::= { tmnxVdoIfStLowEntry 28 }

tmnxVdoIfStLowFCCSrTxHdBytes OBJECT-TYPE
    SYNTAX     Counter32
    MAX-ACCESS read-only
    STATUS     current
    DESCRIPTION
        "The value of tmnxVdoIfStLowFCCSrTxHdBytes indicates the lower 32 bits
         of the value of tmnxVdoIfStatFCCSrTxHdBytes."
    ::= { tmnxVdoIfStLowEntry 29 }

tmnxVdoIfStLowFCCSrTxHdPackets OBJECT-TYPE
    SYNTAX     Counter32
    MAX-ACCESS read-only
    STATUS     current
    DESCRIPTION
        "The value of tmnxVdoIfStLowFCCSrTxHdPackets indicates the lower
         32 bits of the value of tmnxVdoIfStatFCCSrTxHdPackets."
    ::= { tmnxVdoIfStLowEntry 30 }

tmnxVdoIfStLowFCCSrTxPipFCCRplis OBJECT-TYPE
    SYNTAX     Counter32
    MAX-ACCESS read-only
    STATUS     current
    DESCRIPTION
        "The value of tmnxVdoIfStLowFCCSrTxPipFCCRplis indicates the lower
         32 bits of the value of tmnxVdoIfStatFCCSrTxPipFCCRplies."
    ::= { tmnxVdoIfStLowEntry 31 }

tmnxVdoIfStLowFCCSrTxPipBytes OBJECT-TYPE
    SYNTAX     Counter32
    MAX-ACCESS read-only
    STATUS     current
    DESCRIPTION
        "The value of tmnxVdoIfStLowFCCSrTxPipBytes indicates the lower 32 bits
         of the value of tmnxVdoIfStatFCCSrTxPipBytes."
    ::= { tmnxVdoIfStLowEntry 32 }

tmnxVdoIfStLowFCCSrTxPipPackets OBJECT-TYPE
    SYNTAX     Counter32
    MAX-ACCESS read-only
    STATUS     current
    DESCRIPTION
        "The value of tmnxVdoIfStLowFCCSrTxPipPackets indicates the lower
         32 bits of the value of tmnxVdoIfStatFCCSrTxPipPackets."
    ::= { tmnxVdoIfStLowEntry 33 }

tmnxVdoIfStLowTxFailedPackets OBJECT-TYPE
    SYNTAX     Counter32
    MAX-ACCESS read-only
    STATUS     current
    DESCRIPTION
        "The value of tmnxVdoIfStLowTxFailedPackets indicates the lower 32 bits
         of the value of tmnxVdoIfStatTxFailedPackets."
    ::= { tmnxVdoIfStLowEntry 34 }

--
-- Video Interface Address Statistics Table
--

tmnxVdoIfStHghTable OBJECT-TYPE
    SYNTAX     SEQUENCE OF TmnxVdoIfStHghEntry
    MAX-ACCESS not-accessible
    STATUS     current
    DESCRIPTION
        "The tmnxVdoIfStLowTable contains information and statistics for each
         video interface configured in the system."
    ::= { tmnxVdoObjs 12 }

tmnxVdoIfStHghEntry OBJECT-TYPE
    SYNTAX     TmnxVdoIfStHghEntry
    MAX-ACCESS not-accessible
    STATUS     current
    DESCRIPTION
        "An entry in the tmnxVdoIfStLowTable containing video interface
         statistics.

         The counters in this table are defined as 32-bit entries which hold
         the higher 32 bits of the 64-bit counter values in tmnxVdoIfStatTable."
    AUGMENTS { tmnxVdoIfAddrEntry }
    ::= { tmnxVdoIfStHghTable 1 }

TmnxVdoIfStHghEntry ::= SEQUENCE {
    tmnxVdoIfStHghRTSvrSdRtpPktsReq        Counter32,
    tmnxVdoIfStHghRTSvrHdRtpPktsReq        Counter32,
    tmnxVdoIfStHghRTSvrPipRtpPktsReq       Counter32,
    tmnxVdoIfStHghRTSvrRxSdRTReq           Counter32,
    tmnxVdoIfStHghRTSvrRxSdFailedReq       Counter32,
    tmnxVdoIfStHghRTSvrRxHdRTReq           Counter32,
    tmnxVdoIfStHghRTSvrRxHdFailedReq       Counter32,
    tmnxVdoIfStHghRTSvrRxPipRTReq          Counter32,
    tmnxVdoIfStHghRTSvrRxPipFailedRq       Counter32,
    tmnxVdoIfStHghRTSvrTxSdRTReplies       Counter32,
    tmnxVdoIfStHghRTSvrTxSdBytes           Counter32,
    tmnxVdoIfStHghRTSvrTxSdPackets         Counter32,
    tmnxVdoIfStHghRTSvrTxHdRTReplies       Counter32,
    tmnxVdoIfStHghRTSvrTxHdBytes           Counter32,
    tmnxVdoIfStHghRTSvrTxHdPackets         Counter32,
    tmnxVdoIfStHghRTSvrTxPipRTReplis       Counter32,
    tmnxVdoIfStHghRTSvrTxPipBytes          Counter32,
    tmnxVdoIfStHghRTSvrTxPipPackets        Counter32,
    tmnxVdoIfStHghFCCSrRxSdFCCReq          Counter32,
    tmnxVdoIfStHghFCCSrRxSdFailedReq       Counter32,
    tmnxVdoIfStHghFCCSrRxHdFCCReq          Counter32,
    tmnxVdoIfStHghFCCSrRxHdFailedReq       Counter32,
    tmnxVdoIfStHghFCCSrRxPipFCCReq         Counter32,
    tmnxVdoIfStHghFCCSrRxPipFailedRq       Counter32,
    tmnxVdoIfStHghFCCSrTxSdFCCReplis       Counter32,
    tmnxVdoIfStHghFCCSrTxSdBytes           Counter32,
    tmnxVdoIfStHghFCCSrTxSdPackets         Counter32,
    tmnxVdoIfStHghFCCSrTxHdFCCReplis       Counter32,
    tmnxVdoIfStHghFCCSrTxHdBytes           Counter32,
    tmnxVdoIfStHghFCCSrTxHdPackets         Counter32,
    tmnxVdoIfStHghFCCSrTxPipFCCRplis       Counter32,
    tmnxVdoIfStHghFCCSrTxPipBytes          Counter32,
    tmnxVdoIfStHghFCCSrTxPipPackets        Counter32,
    tmnxVdoIfStHghTxFailedPackets          Counter32
}

tmnxVdoIfStHghRTSvrSdRtpPktsReq OBJECT-TYPE
    SYNTAX     Counter32
    MAX-ACCESS read-only
    STATUS     current
    DESCRIPTION
        "The value of tmnxVdoIfStHghRTSvrSdRtpPktsReq indicates the higher
         32 bits of the value of tmnxVdoIfStatRTSvrSdRtpPktsReq."
    ::= { tmnxVdoIfStHghEntry 1 }

tmnxVdoIfStHghRTSvrHdRtpPktsReq OBJECT-TYPE
    SYNTAX     Counter32
    MAX-ACCESS read-only
    STATUS     current
    DESCRIPTION
        "The value of tmnxVdoIfStHghRTSvrHdRtpPktsReq indicates the higher
         32 bits of the value of tmnxVdoIfStatRTSvrHdRtpPktsReq."
    ::= { tmnxVdoIfStHghEntry 2 }

tmnxVdoIfStHghRTSvrPipRtpPktsReq OBJECT-TYPE
    SYNTAX     Counter32
    MAX-ACCESS read-only
    STATUS     current
    DESCRIPTION
        "The value of tmnxVdoIfStHghRTSvrPipRtpPktsReq indicates the higher
         32 bits of the value of tmnxVdoIfStatRTSvrPipRtpPktsReq."
    ::= { tmnxVdoIfStHghEntry 3 }

tmnxVdoIfStHghRTSvrRxSdRTReq OBJECT-TYPE
    SYNTAX     Counter32
    MAX-ACCESS read-only
    STATUS     current
    DESCRIPTION
        "The value of tmnxVdoIfStHghRTSvrRxSdRTReq indicates the higher 32 bits
         of the value of tmnxVdoIfStatRTSvrRxSdRTReq."
    ::= { tmnxVdoIfStHghEntry 4 }

tmnxVdoIfStHghRTSvrRxSdFailedReq OBJECT-TYPE
    SYNTAX     Counter32
    MAX-ACCESS read-only
    STATUS     current
    DESCRIPTION
        "The value of tmnxVdoIfStHghRTSvrRxSdFailedReq indicates the higher
         32 bits of the value of tmnxVdoIfStatRTSvrRxSdFailedReq."
    ::= { tmnxVdoIfStHghEntry 5 }

tmnxVdoIfStHghRTSvrRxHdRTReq OBJECT-TYPE
    SYNTAX     Counter32
    MAX-ACCESS read-only
    STATUS     current
    DESCRIPTION
        "The value of tmnxVdoIfStHghRTSvrRxHdRTReq indicates the higher 32 bits
         of the value of tmnxVdoIfStatRTSvrRxHdRTReq."
    ::= { tmnxVdoIfStHghEntry 6 }

tmnxVdoIfStHghRTSvrRxHdFailedReq OBJECT-TYPE
    SYNTAX     Counter32
    MAX-ACCESS read-only
    STATUS     current
    DESCRIPTION
        "The value of tmnxVdoIfStHghRTSvrRxHdFailedReq indicates the higher
         32 bits of the value of tmnxVdoIfStatRTSvrRxHdFailedReq."
    ::= { tmnxVdoIfStHghEntry 7 }

tmnxVdoIfStHghRTSvrRxPipRTReq OBJECT-TYPE
    SYNTAX     Counter32
    MAX-ACCESS read-only
    STATUS     current
    DESCRIPTION
        "The value of tmnxVdoIfStHghRTSvrRxPipRTReq indicates the higher
         32 bits of the value of tmnxVdoIfStatRTSvrRxPipRTReq."
    ::= { tmnxVdoIfStHghEntry 8 }

tmnxVdoIfStHghRTSvrRxPipFailedRq OBJECT-TYPE
    SYNTAX     Counter32
    MAX-ACCESS read-only
    STATUS     current
    DESCRIPTION
        "The value of tmnxVdoIfStHghRTSvrRxPipFailedRq indicates the higher
         32 bits of the value of tmnxVdoIfStatRTSvrRxPipFailedReq."
    ::= { tmnxVdoIfStHghEntry 9 }

tmnxVdoIfStHghRTSvrTxSdRTReplies OBJECT-TYPE
    SYNTAX     Counter32
    MAX-ACCESS read-only
    STATUS     current
    DESCRIPTION
        "The value of tmnxVdoIfStHghRTSvrTxSdRTReplies indicates the higher
         32 bits of the value of tmnxVdoIfStatRTSvrTxSdRTReplies."
    ::= { tmnxVdoIfStHghEntry 10 }

tmnxVdoIfStHghRTSvrTxSdBytes OBJECT-TYPE
    SYNTAX     Counter32
    MAX-ACCESS read-only
    STATUS     current
    DESCRIPTION
        "The value of tmnxVdoIfStHghRTSvrTxSdBytes indicates the higher 32 bits
         of the value of tmnxVdoIfStatRTSvrTxSdBytes."
    ::= { tmnxVdoIfStHghEntry 11 }

tmnxVdoIfStHghRTSvrTxSdPackets OBJECT-TYPE
    SYNTAX     Counter32
    MAX-ACCESS read-only
    STATUS     current
    DESCRIPTION
        "The value of tmnxVdoIfStHghRTSvrTxSdPackets indicates the higher
         32 bits of the value of tmnxVdoIfStatRTSvrTxSdPackets."
    ::= { tmnxVdoIfStHghEntry 12 }

tmnxVdoIfStHghRTSvrTxHdRTReplies OBJECT-TYPE
    SYNTAX     Counter32
    MAX-ACCESS read-only
    STATUS     current
    DESCRIPTION
        "The value of tmnxVdoIfStHghRTSvrTxHdRTReplies indicates the higher
         32 bits of the value of tmnxVdoIfStatRTSvrTxHdRTReplies."
    ::= { tmnxVdoIfStHghEntry 13 }

tmnxVdoIfStHghRTSvrTxHdBytes OBJECT-TYPE
    SYNTAX     Counter32
    MAX-ACCESS read-only
    STATUS     current
    DESCRIPTION
        "The value of tmnxVdoIfStHghRTSvrTxHdBytes indicates the higher 32 bits
         of the value of tmnxVdoIfStatRTSvrTxHdBytes."
    ::= { tmnxVdoIfStHghEntry 14 }

tmnxVdoIfStHghRTSvrTxHdPackets OBJECT-TYPE
    SYNTAX     Counter32
    MAX-ACCESS read-only
    STATUS     current
    DESCRIPTION
        "The value of tmnxVdoIfStHghRTSvrTxHdPackets indicates the higher
         32 bits of the value of tmnxVdoIfStatRTSvrTxHdPackets."
    ::= { tmnxVdoIfStHghEntry 15 }

tmnxVdoIfStHghRTSvrTxPipRTReplis OBJECT-TYPE
    SYNTAX     Counter32
    MAX-ACCESS read-only
    STATUS     current
    DESCRIPTION
        "The value of tmnxVdoIfStHghRTSvrTxPipRTReplis indicates the higher
         32 bits of the value of tmnxVdoIfStatRTSvrTxPipRTReplies."
    ::= { tmnxVdoIfStHghEntry 16 }

tmnxVdoIfStHghRTSvrTxPipBytes OBJECT-TYPE
    SYNTAX     Counter32
    MAX-ACCESS read-only
    STATUS     current
    DESCRIPTION
        "The value of tmnxVdoIfStHghRTSvrTxPipBytes indicates the higher
         32 bits of the value of tmnxVdoIfStatRTSvrTxPipBytes."
    ::= { tmnxVdoIfStHghEntry 17 }

tmnxVdoIfStHghRTSvrTxPipPackets OBJECT-TYPE
    SYNTAX     Counter32
    MAX-ACCESS read-only
    STATUS     current
    DESCRIPTION
        "The value of tmnxVdoIfStHghRTSvrTxPipPackets indicates the higher
         32 bits of the value of tmnxVdoIfStatRTSvrTxPipPackets."
    ::= { tmnxVdoIfStHghEntry 18 }

tmnxVdoIfStHghFCCSrRxSdFCCReq OBJECT-TYPE
    SYNTAX     Counter32
    MAX-ACCESS read-only
    STATUS     current
    DESCRIPTION
        "The value of tmnxVdoIfStHghFCCSrRxSdFCCReq indicates the higher
         32 bits of the value of tmnxVdoIfStatFCCSrRxSdFCCReq."
    ::= { tmnxVdoIfStHghEntry 19 }

tmnxVdoIfStHghFCCSrRxSdFailedReq OBJECT-TYPE
    SYNTAX     Counter32
    MAX-ACCESS read-only
    STATUS     current
    DESCRIPTION
        "The value of tmnxVdoIfStHghFCCSrRxSdFailedReq indicates the higher
         32 bits of the value of tmnxVdoIfStatFCCSrRxSdFailedReq."
    ::= { tmnxVdoIfStHghEntry 20 }

tmnxVdoIfStHghFCCSrRxHdFCCReq OBJECT-TYPE
    SYNTAX     Counter32
    MAX-ACCESS read-only
    STATUS     current
    DESCRIPTION
        "The value of tmnxVdoIfStHghFCCSrRxHdFCCReq indicates the higher
         32 bits of the value of tmnxVdoIfStatFCCSrRxHdFCCReq."
    ::= { tmnxVdoIfStHghEntry 21 }

tmnxVdoIfStHghFCCSrRxHdFailedReq OBJECT-TYPE
    SYNTAX     Counter32
    MAX-ACCESS read-only
    STATUS     current
    DESCRIPTION
        "The value of tmnxVdoIfStHghFCCSrRxHdFailedReq indicates the higher
         32 bits of the value of tmnxVdoIfStatFCCSrRxHdFailedReq."
    ::= { tmnxVdoIfStHghEntry 22 }

tmnxVdoIfStHghFCCSrRxPipFCCReq OBJECT-TYPE
    SYNTAX     Counter32
    MAX-ACCESS read-only
    STATUS     current
    DESCRIPTION
        "The value of tmnxVdoIfStHghFCCSrRxPipFCCReq indicates the higher
         32 bits of the value of tmnxVdoIfStatFCCSrRxPipFCCReq."
    ::= { tmnxVdoIfStHghEntry 23 }

tmnxVdoIfStHghFCCSrRxPipFailedRq OBJECT-TYPE
    SYNTAX     Counter32
    MAX-ACCESS read-only
    STATUS     current
    DESCRIPTION
        "The value of tmnxVdoIfStHghFCCSrRxPipFailedRq indicates the higher
         32 bits of the value of tmnxVdoIfStatFCCSrRxPipFailedReq."
    ::= { tmnxVdoIfStHghEntry 24 }

tmnxVdoIfStHghFCCSrTxSdFCCReplis OBJECT-TYPE
    SYNTAX     Counter32
    MAX-ACCESS read-only
    STATUS     current
    DESCRIPTION
        "The value of tmnxVdoIfStHghFCCSrTxSdFCCReplis indicates the higher
         32 bits of the value of tmnxVdoIfStatFCCSrTxSdFCCReplies."
    ::= { tmnxVdoIfStHghEntry 25 }

tmnxVdoIfStHghFCCSrTxSdBytes OBJECT-TYPE
    SYNTAX     Counter32
    MAX-ACCESS read-only
    STATUS     current
    DESCRIPTION
        "The value of tmnxVdoIfStHghFCCSrTxSdBytes indicates the higher 32 bits
         of the value of tmnxVdoIfStatFCCSrTxSdBytes."
    ::= { tmnxVdoIfStHghEntry 26 }

tmnxVdoIfStHghFCCSrTxSdPackets OBJECT-TYPE
    SYNTAX     Counter32
    MAX-ACCESS read-only
    STATUS     current
    DESCRIPTION
        "The value of tmnxVdoIfStHghFCCSrTxSdPackets indicates the higher
         32 bits of the value of tmnxVdoIfStatFCCSrTxSdPackets."
    ::= { tmnxVdoIfStHghEntry 27 }

tmnxVdoIfStHghFCCSrTxHdFCCReplis OBJECT-TYPE
    SYNTAX     Counter32
    MAX-ACCESS read-only
    STATUS     current
    DESCRIPTION
        "The value of tmnxVdoIfStHghFCCSrTxHdFCCReplis indicates the higher
         32 bits of the value of tmnxVdoIfStatFCCSrTxHdFCCReplies."
    ::= { tmnxVdoIfStHghEntry 28 }

tmnxVdoIfStHghFCCSrTxHdBytes OBJECT-TYPE
    SYNTAX     Counter32
    MAX-ACCESS read-only
    STATUS     current
    DESCRIPTION
        "The value of tmnxVdoIfStHghFCCSrTxHdBytes indicates the higher 32 bits
         of the value of tmnxVdoIfStatFCCSrTxHdBytes."
    ::= { tmnxVdoIfStHghEntry 29 }

tmnxVdoIfStHghFCCSrTxHdPackets OBJECT-TYPE
    SYNTAX     Counter32
    MAX-ACCESS read-only
    STATUS     current
    DESCRIPTION
        "The value of tmnxVdoIfStHghFCCSrTxHdPackets indicates the higher
         32 bits of the value of tmnxVdoIfStatFCCSrTxHdPackets."
    ::= { tmnxVdoIfStHghEntry 30 }

tmnxVdoIfStHghFCCSrTxPipFCCRplis OBJECT-TYPE
    SYNTAX     Counter32
    MAX-ACCESS read-only
    STATUS     current
    DESCRIPTION
        "The value of tmnxVdoIfStHghFCCSrTxPipFCCRplis indicates the higher
         32 bits of the value of tmnxVdoIfStatFCCSrTxPipFCCRplies."
    ::= { tmnxVdoIfStHghEntry 31 }

tmnxVdoIfStHghFCCSrTxPipBytes OBJECT-TYPE
    SYNTAX     Counter32
    MAX-ACCESS read-only
    STATUS     current
    DESCRIPTION
        "The value of tmnxVdoIfStHghFCCSrTxPipBytes indicates the higher
         32 bits of the value of tmnxVdoIfStatFCCSrTxPipBytes."
    ::= { tmnxVdoIfStHghEntry 32 }

tmnxVdoIfStHghFCCSrTxPipPackets OBJECT-TYPE
    SYNTAX     Counter32
    MAX-ACCESS read-only
    STATUS     current
    DESCRIPTION
        "The value of tmnxVdoIfStHghFCCSrTxPipPackets indicates the higher
         32 bits of the value of tmnxVdoIfStatFCCSrTxPipPackets."
    ::= { tmnxVdoIfStHghEntry 33 }

tmnxVdoIfStHghTxFailedPackets OBJECT-TYPE
    SYNTAX     Counter32
    MAX-ACCESS read-only
    STATUS     current
    DESCRIPTION
        "The value of tmnxVdoIfStHghTxFailedPackets indicates the higher
         32 bits of the value of tmnxVdoIfStatTxFailedPackets."
    ::= { tmnxVdoIfStHghEntry 34 }

--
-- Video Program Identifier Table
--

tmnxVdoPIDTable OBJECT-TYPE
    SYNTAX     SEQUENCE OF TmnxVdoPIDEntry
    MAX-ACCESS not-accessible
    STATUS     current
    DESCRIPTION
        "tmnxVdoPIDTable contains information about the data in the 
         Transport Stream."
    ::= { tmnxVdoObjs 13 }

tmnxVdoPIDEntry OBJECT-TYPE
    SYNTAX     TmnxVdoPIDEntry
    MAX-ACCESS not-accessible
    STATUS     current
    DESCRIPTION
        "An entry in the tmnxVdoPIDTable. Each row entry represents a 
         packet identifier used to identify the type of data stored in the 
         packet payload."
    INDEX      { 
                 svcId,
                 tmnxVdoIfName,
                 tmnxVdoGrpSrcGrpAddrType, 
                 tmnxVdoGrpSrcGroupAddress,
                 tmnxVdoGrpSrcSrcAddrType, 
                 tmnxVdoGrpSrcSourceAddress,
                 tmnxVdoPID
               }
    ::= { tmnxVdoPIDTable 1 }

TmnxVdoPIDEntry ::= SEQUENCE {
    tmnxVdoPID                         Unsigned32,
    tmnxVdoPIDType                     TmnxVdoPIDType,
    tmnxVdoPIDMpegStreamType           Unsigned32,
    tmnxVdoPIDLanguage                 TNamedItem,
    tmnxVdoPIDCcErrSecs                Unsigned32,
    tmnxVdoPIDTeiErrSecs               Unsigned32,
    tmnxVdoPIDAbsentErrSecs            Unsigned32,
    tmnxVdoPIDBitrate                  Unsigned32,
    tmnxVdoPIDIsPCR                    TruthValue
}

tmnxVdoPID OBJECT-TYPE
    SYNTAX     Unsigned32 (0..8191)
    MAX-ACCESS not-accessible
    STATUS     current
    DESCRIPTION
        "The value of tmnxVdoPID indicates the 13-bit packet identifier 
         used to identify the type of data stored in the packet payload."
    ::= { tmnxVdoPIDEntry 1 }

tmnxVdoPIDType OBJECT-TYPE
    SYNTAX     TmnxVdoPIDType
    MAX-ACCESS read-only
    STATUS     current
    DESCRIPTION
        "The value of tmnxVdoPIDType indicates the type of the packet 
         identifier."
    ::= { tmnxVdoPIDEntry 2 }

tmnxVdoPIDMpegStreamType OBJECT-TYPE
    SYNTAX     Unsigned32
    MAX-ACCESS read-only
    STATUS     current
    DESCRIPTION
        "The value of tmnxVdoPIDMpegStreamType indicates the type of MPEG  
         stream."
    ::= { tmnxVdoPIDEntry 3 }

tmnxVdoPIDLanguage OBJECT-TYPE
    SYNTAX     TNamedItem
    MAX-ACCESS read-only
    STATUS     current
    DESCRIPTION
        "The value of tmnxVdoPIDLanguage indicates the language of the 
         MPEG stream."
    ::= { tmnxVdoPIDEntry 4 }

tmnxVdoPIDCcErrSecs OBJECT-TYPE
    SYNTAX      Unsigned32
    UNITS       "seconds"
    MAX-ACCESS  read-only
    STATUS      current
    DESCRIPTION
        "The value of tmnxVdoPIDCcErrSecs indicates the total number of 
         continuity counter error seconds for the MPEG stream."
    ::= { tmnxVdoPIDEntry 5 }

tmnxVdoPIDTeiErrSecs OBJECT-TYPE
    SYNTAX      Unsigned32
    UNITS       "seconds"
    MAX-ACCESS  read-only
    STATUS      current
    DESCRIPTION
        "The value of tmnxVdoPIDTeiErrSecs indicates the total number of TEI
        (Transport Error Indicator) error seconds for the MPEG stream."
    ::= { tmnxVdoPIDEntry 6 }

tmnxVdoPIDAbsentErrSecs OBJECT-TYPE
    SYNTAX      Unsigned32
    MAX-ACCESS  read-only
    STATUS      current
    DESCRIPTION
        "The value of tmnxVdoPIDAbsentErrSecs indicates the total number of 
         video or non-video PID (Program Identifier) absent error seconds for 
         the MPEG stream based on the PID type. This object has seperate 
         instances for each PID type within a video stream based on bundle,
         channel and source-override configurations. So for example if we 
         have a bundle configured, we can count the absent errors on two 
         different PID streams - video and non-video - of the bundle. In 
         this case 'TIMETRA-MCAST-PATH-MGMT-MIB:: tmnxMcPathBdlVdoVidPIDAbsent' 
         sets the time duration in milli-seconds, after every lapse of which the 
         video PID instance of tmnxVdoPIDAbsentErrSecs updates itself to reflect 
         the latest absent error count for the video PIDs for the bundle. 
         Similarly we have   
         'TIMETRA-MCAST-PATH-MGMT-MIB:: tmnxMcPathBdlVdoNonVidPIDAbsent' which 
         sets the time duration in milli-seconds, after every lapse of which the 
         non-video PID instance of tmnxVdoPIDAbsentErrSecs updates itself to 
         reflect the latest absent error count for non-video PIDs in the bundle. 
         The above explanation can be extended to apply to channel and 
         source-override video stream. Consequently we have 
         'TIMETRA-MCAST-PATH-MGMT-MIB:: tmnxMcPathBdlChlVdoVidPIDAbs' and
         'TIMETRA-MCAST-PATH-MGMT-MIB:: tmnxMcPathBdlChlVdoNonVidPIDAbs' which 
         set the time duration in milli-seconds after every lapse of which the 
         video and non-video PID instances of tmnxVdoPIDAbsentErrSecs for 
         channel update themselves to reflect their respective latest absent 
         error counts. In case of source-override configuration we have 
         'TIMETRA-MCAST-PATH-MGMT-MIB:: tmnxMcPathChlSrcVdoVidPIDAbs' and
         'TIMETRA-MCAST-PATH-MGMT-MIB:: tmnxMcPathChlSrcVdoNonVidPIDAbs' which 
         set the time duration in milli-seconds, after every lapse of which 
         its video and non-video PID instances of tmnxVdoPIDAbsentErrSecs for 
         source-override update themselves to reflect their latest absent error 
         counts."
    ::= { tmnxVdoPIDEntry 7 }

tmnxVdoPIDBitrate OBJECT-TYPE
    SYNTAX      Unsigned32
    UNITS       "kbps"
    MAX-ACCESS  read-only
    STATUS      current
    DESCRIPTION
        "The value of tmnxVdoPIDBitrate indicates the bitrate of the stream."
    ::= { tmnxVdoPIDEntry 8 }

tmnxVdoPIDIsPCR OBJECT-TYPE
    SYNTAX      TruthValue
    MAX-ACCESS  read-only
    STATUS      current
    DESCRIPTION
        "The value of tmnxVdoPIDIsPCR indicates whether or not this is a 
         Program Clock Reference(PCR) PID."
    ::= { tmnxVdoPIDEntry 9 }

--
--  Video Interface SCTE 30 Ad Server Table
--

tmnxVdoIfScte30AdSrvrTblLstChngd OBJECT-TYPE
    SYNTAX      TimeStamp
    MAX-ACCESS  read-only
    STATUS      current
    DESCRIPTION
        "The value of tmnxVdoIfScte30AdSrvrTblLstChngd indicates the sysUpTime 
         at the time of the last modification to tmnxVdoIfScte30AdSrvrTable by 
         adding, deleting an entry or change to a writable object in the table.

         If no changes were made to the table since the last re-initialization 
         of the local network management subsystem, then this object contains 
         a zero value."
    ::= { tmnxVdoGlobalObjs 7 }

tmnxVdoIfScte30AdSrvrTable  OBJECT-TYPE
    SYNTAX      SEQUENCE OF TmnxVdoIfScte30AdSrvrEntry
    MAX-ACCESS  not-accessible
    STATUS      current
    DESCRIPTION
        "The tmnxVdoIfScte30AdSrvrTable has an entry for each ad server IP 
         address configured for the video interface in the system."
    ::= { tmnxVdoObjs 14 }

tmnxVdoIfScte30AdSrvrEntry  OBJECT-TYPE
    SYNTAX      TmnxVdoIfScte30AdSrvrEntry
    MAX-ACCESS  not-accessible
    STATUS      current
    DESCRIPTION
        "Each row entry represents an ad server IP address configured for the 
         video interface in the system. Entries can be created and deleted by 
         the user."
    INDEX { svcId,
            tmnxVdoIfName,
            tmnxVdoIfScte30AdSrvrAddrType,
            tmnxVdoIfScte30AdSrvrAddr
    }
    ::= { tmnxVdoIfScte30AdSrvrTable 1 }

TmnxVdoIfScte30AdSrvrEntry ::= SEQUENCE {
        tmnxVdoIfScte30AdSrvrAddrType     InetAddressType,
        tmnxVdoIfScte30AdSrvrAddr         InetAddress,
        tmnxVdoIfScte30AdSrvrRowStatus    RowStatus
    }

tmnxVdoIfScte30AdSrvrAddrType  OBJECT-TYPE
    SYNTAX      InetAddressType
    MAX-ACCESS  not-accessible
    STATUS      current
    DESCRIPTION
        "The value of tmnxVdoIfScte30AdSrvrAddrType specifies the type of 
         address represented by tmnxVdoIfScte30AdSrvrAddr."
    ::= { tmnxVdoIfScte30AdSrvrEntry 1 }

tmnxVdoIfScte30AdSrvrAddr  OBJECT-TYPE
    SYNTAX      InetAddress (SIZE(4|16))
    MAX-ACCESS  not-accessible
    STATUS      current
    DESCRIPTION
        "The value of tmnxVdoIfScte30AdSrvrAddr specifies the IP address of
         the ad server."
    ::= { tmnxVdoIfScte30AdSrvrEntry 2 }

tmnxVdoIfScte30AdSrvrRowStatus  OBJECT-TYPE
    SYNTAX      RowStatus
    MAX-ACCESS  read-create
    STATUS      current
    DESCRIPTION
        "The value of tmnxVdoIfScte30AdSrvrRowStatus specifies the row status of
         this row. The row status is used for creation, deletion or control
         of tmnxVdoIfScte30AdSrvrTable entries."
    ::= { tmnxVdoIfScte30AdSrvrEntry 3 }

--
-- Video Source Group ADI Statistics Table
--

tmnxVdoSGAdiStatTable OBJECT-TYPE
    SYNTAX     SEQUENCE OF TmnxVdoSGAdiStatEntry
    MAX-ACCESS not-accessible
    STATUS     current
    DESCRIPTION
        "The tmnxVdoSGAdiStatTable has an entry for each Ad Insert (ADI) server 
         on the channel. This table contains ad server information and 
         statistics."
    ::= { tmnxVdoObjs 15 }

tmnxVdoSGAdiStatEntry OBJECT-TYPE
    SYNTAX     TmnxVdoSGAdiStatEntry
    MAX-ACCESS not-accessible
    STATUS     current
    DESCRIPTION
        "An entry in the tmnxVdoSGAdiStatTable. Each entry represents a 
         Ad Insert (ADI) server for the corresponding multicast group."
    INDEX      { 
                 svcId,
                 tmnxVdoIfName,
                 tmnxVdoGrpSrcGrpAddrType, 
                 tmnxVdoGrpSrcGroupAddress,
                 tmnxVdoGrpSrcSrcAddrType, 
                 tmnxVdoGrpSrcSourceAddress,
                 tmnxVdoSGAdiServerAddrType,
                 tmnxVdoSGAdiServerAddr
               }
    ::= { tmnxVdoSGAdiStatTable 1 }

TmnxVdoSGAdiStatEntry ::= SEQUENCE {
    tmnxVdoSGAdiServerAddrType        InetAddressType,
    tmnxVdoSGAdiServerAddr            InetAddress,
    tmnxVdoSGAdiServerUptime          Unsigned32,
    tmnxVdoSGAdiInitReq               Counter32,
    tmnxVdoSGAdiSucInitResp           Counter32,
    tmnxVdoSGAdiUnsucInitResp         Counter32,
    tmnxVdoSGAdiAliveReq              Counter32,
    tmnxVdoSGAdiSucAliveResp          Counter32,
    tmnxVdoSGAdiUnSucAliveResp        Counter32,
    tmnxVdoSGAdiCueReq                Counter32,
    tmnxVdoSGAdiSucCueResp            Counter32,
    tmnxVdoSGAdiUnsucCueResp          Counter32,
    tmnxVdoSGAdiAbortReq              Counter32,
    tmnxVdoSGAdiSucAbortResp          Counter32,
    tmnxVdoSGAdiUnsucAbortResp        Counter32,
    tmnxVdoSGAdiUnknownSCTE30Req      Counter32,
    tmnxVdoSGAdiSpliceReq             Counter32,
    tmnxVdoSGAdiSucSpliceResp         Counter32,
    tmnxVdoSGAdiUnsucSpliceResp       Counter32,
    tmnxVdoSGAdiSucSpliceInCompResp   Counter32,
    tmnxVdoSGAdiSucSpliceOutCompResp  Counter32,
    tmnxVdoSGAdiUnsucSpliceOutComRes  Counter32,
    tmnxVdoSGAdiMinPort               Counter32,
    tmnxVdoSGAdiMaxPort               Counter32,
    tmnxVdoSGAdiChlName               TNamedItem
}

tmnxVdoSGAdiServerAddrType OBJECT-TYPE
    SYNTAX     InetAddressType
    MAX-ACCESS not-accessible
    STATUS     current
    DESCRIPTION
        "The value of tmnxVdoSGAdiServerAddrType indicates the type of 
         Ad Insert (ADI) server address represented by tmnxVdoSGAdiServerAddr."
    ::= { tmnxVdoSGAdiStatEntry 1 }

tmnxVdoSGAdiServerAddr OBJECT-TYPE
    SYNTAX     InetAddress (SIZE (4|16))
    MAX-ACCESS not-accessible
    STATUS     current
    DESCRIPTION
         "The value of tmnxVdoSGAdiServerAddr indicates the address of Ad 
          Insert (ADI) server on this channel."
    ::= { tmnxVdoSGAdiStatEntry 2 }

tmnxVdoSGAdiServerUptime OBJECT-TYPE
    SYNTAX     Unsigned32
    UNITS      "seconds"
    MAX-ACCESS read-only
    STATUS     current
    DESCRIPTION
        "The value of tmnxVdoSGAdiServerUptime indicates the time in seconds 
         since the connection with Ad Insert (ADI) server was established."
    ::= { tmnxVdoSGAdiStatEntry 3 }
    
tmnxVdoSGAdiInitReq OBJECT-TYPE
    SYNTAX     Counter32
    MAX-ACCESS read-only
    STATUS     current
    DESCRIPTION
        "The value of tmnxVdoSGAdiInitReq indicates the total number of init 
         requests received from the Ad Insert (ADI) server."
    ::= { tmnxVdoSGAdiStatEntry 4 }

tmnxVdoSGAdiSucInitResp OBJECT-TYPE
    SYNTAX     Counter32
    MAX-ACCESS read-only
    STATUS     current
    DESCRIPTION
        "The value of tmnxVdoSGAdiSucInitResp indicates the total number of 
         successful init responses sent to the Ad Insert (ADI) server."
    ::= { tmnxVdoSGAdiStatEntry 5 }

tmnxVdoSGAdiUnsucInitResp OBJECT-TYPE
    SYNTAX     Counter32
    MAX-ACCESS read-only
    STATUS     current
    DESCRIPTION
        "The value of tmnxVdoSGAdiUnsucInitResp indicates the total number of 
         unsuccessful init responses sent to the Ad Insert (ADI) server."
    ::= { tmnxVdoSGAdiStatEntry 6 }

tmnxVdoSGAdiAliveReq OBJECT-TYPE
    SYNTAX     Counter32
    MAX-ACCESS read-only
    STATUS     current
    DESCRIPTION
        "The value of tmnxVdoSGAdiAliveReq indicates the total number of alive 
         messages received from the Ad Insert (ADI) server."
    ::= { tmnxVdoSGAdiStatEntry 7 }

tmnxVdoSGAdiSucAliveResp OBJECT-TYPE
    SYNTAX     Counter32
    MAX-ACCESS read-only
    STATUS     current
    DESCRIPTION
        "The value of tmnxVdoSGAdiSucAliveResp indicates the total number of 
         successful alive messages sent to the Ad Insert (ADI) server."
    ::= { tmnxVdoSGAdiStatEntry 8 }

tmnxVdoSGAdiUnSucAliveResp OBJECT-TYPE
    SYNTAX     Counter32
    MAX-ACCESS read-only
    STATUS     current
    DESCRIPTION
        "The value of tmnxVdoSGAdiUnSucAliveResp indicates the total number of 
         unsuccessful alive messages sent to the Ad Insert (ADI) server."
    ::= { tmnxVdoSGAdiStatEntry 9 }

tmnxVdoSGAdiCueReq OBJECT-TYPE
    SYNTAX     Counter32
    MAX-ACCESS read-only
    STATUS     current
    DESCRIPTION
        "The value of tmnxVdoSGAdiCueReq indicates the total number of 
         total number of cue requests sent to the Ad Insert (ADI) server."
    ::= { tmnxVdoSGAdiStatEntry 10 }

tmnxVdoSGAdiSucCueResp OBJECT-TYPE
    SYNTAX     Counter32
    MAX-ACCESS read-only
    STATUS     current
    DESCRIPTION
        "The value of tmnxVdoSGAdiSucCueResp indicates the total number of 
         successful cue responses received from the Ad Insert (ADI) server."
    ::= { tmnxVdoSGAdiStatEntry 11 }

tmnxVdoSGAdiUnsucCueResp OBJECT-TYPE
    SYNTAX     Counter32
    MAX-ACCESS read-only
    STATUS     current
    DESCRIPTION
        "The value of tmnxVdoSGAdiUnsucCueResp indicates the total number of 
         unsuccessful cue responses received from the Ad Insert (ADI) server."
    ::= { tmnxVdoSGAdiStatEntry 12 }

tmnxVdoSGAdiAbortReq OBJECT-TYPE
    SYNTAX     Counter32
    MAX-ACCESS read-only
    STATUS     current
    DESCRIPTION
        "The value of tmnxVdoSGAdiAbortReq indicates the total number of abort 
         requests received from the Ad Insert (ADI) server."
    ::= { tmnxVdoSGAdiStatEntry 13 }

tmnxVdoSGAdiSucAbortResp OBJECT-TYPE
    SYNTAX     Counter32
    MAX-ACCESS read-only
    STATUS     current
    DESCRIPTION
        "The value of tmnxVdoSGAdiSucAbortResp indicates the total number of 
         successful abort responses sent to the Ad Insert (ADI) server. "
    ::= { tmnxVdoSGAdiStatEntry 14 }

tmnxVdoSGAdiUnsucAbortResp OBJECT-TYPE
    SYNTAX     Counter32
    MAX-ACCESS read-only
    STATUS     current
    DESCRIPTION
        "The value of tmnxVdoSGAdiUnsucAbortResp indicates the total number of 
         unsuccessful abort responses sent to the Ad Insert (ADI) server."
    ::= { tmnxVdoSGAdiStatEntry 15 }

tmnxVdoSGAdiUnknownSCTE30Req OBJECT-TYPE
    SYNTAX     Counter32
    MAX-ACCESS read-only
    STATUS     current
    DESCRIPTION
        "The value of tmnxVdoSGAdiUnknownSCTE30Req indicates the total number of 
         invalid Society of Cable Telecommunications Engineers 30 (SCTE-30) 
         requests received from the Ad Insert (ADI) server."
    ::= { tmnxVdoSGAdiStatEntry 16 }

tmnxVdoSGAdiSpliceReq OBJECT-TYPE
    SYNTAX     Counter32
    MAX-ACCESS read-only
    STATUS     current
    DESCRIPTION
        "The value of tmnxVdoSGAdiSpliceReq indicates the total number of splice 
         requests received from the Ad Insert (ADI) server."
    ::= { tmnxVdoSGAdiStatEntry 17 }

tmnxVdoSGAdiSucSpliceResp OBJECT-TYPE
    SYNTAX     Counter32
    MAX-ACCESS read-only
    STATUS     current
    DESCRIPTION
        "The value of tmnxVdoSGAdiSucSpliceResp indicates the total number of 
         successful splice responses sent to the Ad Insert (ADI) server."
    ::= { tmnxVdoSGAdiStatEntry 18 }

tmnxVdoSGAdiUnsucSpliceResp OBJECT-TYPE
    SYNTAX     Counter32
    MAX-ACCESS read-only
    STATUS     current
    DESCRIPTION
        "The value of tmnxVdoSGAdiUnsucSpliceResp indicates the total number of 
         unsuccessful splice responses sent to the Ad Insert (ADI) server."
    ::= { tmnxVdoSGAdiStatEntry 19 }

tmnxVdoSGAdiSucSpliceInCompResp OBJECT-TYPE
    SYNTAX     Counter32
    MAX-ACCESS read-only
    STATUS     current
    DESCRIPTION
        "The value of tmnxVdoSGAdiSucSpliceInCompResp indicates the total 
         number of successful splice-in complete responses sent to the Ad 
         Insert (ADI) server."
    ::= { tmnxVdoSGAdiStatEntry 20 }

tmnxVdoSGAdiSucSpliceOutCompResp OBJECT-TYPE
    SYNTAX     Counter32
    MAX-ACCESS read-only
    STATUS     current
    DESCRIPTION
        "The value of tmnxVdoSGAdiSucSpliceOutCompResp indicates the total 
         number of successful splice-out complete responses sent to the Ad 
         Insert (ADI) server."
    ::= { tmnxVdoSGAdiStatEntry 21 }

tmnxVdoSGAdiUnsucSpliceOutComRes OBJECT-TYPE
    SYNTAX     Counter32
    MAX-ACCESS read-only
    STATUS     current
    DESCRIPTION
        "The value of tmnxVdoSGAdiUnsucSpliceOutComRes indicates the total 
         number of unsuccessful splice-out complete responses sent to the Ad 
         Insert (ADI) server."
    ::= { tmnxVdoSGAdiStatEntry 22 }

tmnxVdoSGAdiMinPort OBJECT-TYPE
    SYNTAX     Counter32
    MAX-ACCESS read-only
    STATUS     current
    DESCRIPTION
        "The value of tmnxVdoSGAdiMinPort indicates the minimum ip port number
         where the Ad Insert (ADI) server's insertion stream is connected."
    ::= { tmnxVdoSGAdiStatEntry 23 }

tmnxVdoSGAdiMaxPort OBJECT-TYPE
    SYNTAX     Counter32
    MAX-ACCESS read-only
    STATUS     current
    DESCRIPTION
        "The value of tmnxVdoSGAdiMinPort indicates the maximum ip port number
         where the Ad Insert (ADI) server's insertion stream is connected."
    ::= { tmnxVdoSGAdiStatEntry 24 }

tmnxVdoSGAdiChlName OBJECT-TYPE
    SYNTAX     TNamedItem
    MAX-ACCESS read-only
    STATUS     current
    DESCRIPTION
        "The value of tmnxVdoSGAdiChlName indicates the channel name associated 
         for this multicast group."
    ::= { tmnxVdoSGAdiStatEntry 25 }

--
-- Splice Status Table
--

tmnxVdoSGSpliceStatusTable OBJECT-TYPE
    SYNTAX     SEQUENCE OF TmnxVdoSGSpliceStatusEntry
    MAX-ACCESS not-accessible
    STATUS     current
    DESCRIPTION
        "The tmnxVdoSGSpliceStatusTable has an entry for each splice request 
         received by the splicer. This table contains information about 
         the splice request."
    ::= { tmnxVdoObjs 16 }

tmnxVdoSGSpliceStatusEntry OBJECT-TYPE
    SYNTAX     TmnxVdoSGSpliceStatusEntry
    MAX-ACCESS not-accessible
    STATUS     current
    DESCRIPTION
        "An entry in the tmnxVdoSGSpliceStatusEntry. Each entry represents a 
         splice request received by the splicer."
    INDEX      { 
                 svcId,
                 tmnxVdoIfName,
                 tmnxVdoGrpSrcGrpAddrType, 
                 tmnxVdoGrpSrcGroupAddress,
                 tmnxVdoGrpSrcSrcAddrType, 
                 tmnxVdoGrpSrcSourceAddress,
                 tmnxVdoSGSpliceStartTime
               }
    ::= { tmnxVdoSGSpliceStatusTable 1 }

TmnxVdoSGSpliceStatusEntry ::= SEQUENCE {
    tmnxVdoSGSpliceStartTime          Unsigned32,
    tmnxVdoSGSpliceAdServerAddrType   InetAddressType,
    tmnxVdoSGSpliceAdServerAddr       InetAddress,
    tmnxVdoSGSpliceStatus             INTEGER,
    tmnxVdoSGSpliceDurationReq        Unsigned32,
    tmnxVdoSGSpliceDurationPlayed     Unsigned32,
    tmnxVdoSGSpliceRate               Unsigned32,
    tmnxVdoSGSpliceSessionId          Unsigned32,
    tmnxVdoSGSplicePriorSessionId     Unsigned32,
    tmnxVdoSGSpliceAbortReason        INTEGER,
    tmnxVdoSGSpliceSpliceInSeqNum     Unsigned32,
    tmnxVdoSGSpliceSpliceOutSeqNum    Unsigned32,
    tmnxVdoSGSpliceNumBlkFrames       Unsigned32,
    tmnxVdoSGSpliceBlkFramePTS        TmnxVdoPTS,
    tmnxVdoSGSpliceMaxAdPTS           TmnxVdoPTS,
    tmnxVdoSGSpliceMinNwPTS           TmnxVdoPTS
}

tmnxVdoSGSpliceStartTime OBJECT-TYPE
    SYNTAX     Unsigned32
    UNITS      "seconds"
    MAX-ACCESS not-accessible
    STATUS     current
    DESCRIPTION
        "The value of tmnxVdoSGSpliceStartTime indicates the start time of 
         splice in seconds."
    ::= { tmnxVdoSGSpliceStatusEntry 1 }

tmnxVdoSGSpliceAdServerAddrType OBJECT-TYPE
    SYNTAX     InetAddressType
    MAX-ACCESS read-only
    STATUS     current
    DESCRIPTION
        "The value of tmnxVdoSGSpliceAdServerAddrType indicates the type of 
         Ad Insert (ADI) server address represented by 
         tmnxVdoSGSpliceAdServerAddr."
    ::= { tmnxVdoSGSpliceStatusEntry 2 }

tmnxVdoSGSpliceAdServerAddr OBJECT-TYPE
    SYNTAX     InetAddress (SIZE (4|16))
    MAX-ACCESS read-only
    STATUS     current
    DESCRIPTION
        "The value of tmnxVdoSGSpliceAdServerAddr indicates the address of the 
         Ad Insert (ADI) server that issued the splice request."
    ::= { tmnxVdoSGSpliceStatusEntry 3 }

tmnxVdoSGSpliceStatus OBJECT-TYPE
    SYNTAX     INTEGER {
                   init       (1),
                   pending    (2),
                   inProgress (3),
                   complete   (4)
               }
    MAX-ACCESS read-only
    STATUS     current
    DESCRIPTION
        "The value of tmnxVdoSGSpliceStatus indicates the status of this splice 
         request."
    ::= { tmnxVdoSGSpliceStatusEntry 4 }

tmnxVdoSGSpliceDurationReq OBJECT-TYPE
    SYNTAX     Unsigned32
    UNITS      "seconds"
    MAX-ACCESS read-only
    STATUS     current
    DESCRIPTION
        "The value of tmnxVdoSGSpliceDurationReq indicates the splice duration, 
         in seconds, of the ad requested by the Ad Insert (ADI) server."
    ::= { tmnxVdoSGSpliceStatusEntry 5 }

tmnxVdoSGSpliceDurationPlayed OBJECT-TYPE
    SYNTAX     Unsigned32
    UNITS      "seconds"
    MAX-ACCESS read-only
    STATUS     current
    DESCRIPTION
        "The value of tmnxVdoSGSpliceDurationPlayed indicates the splice 
         duration, in seconds, played by the splicer."
    ::= { tmnxVdoSGSpliceStatusEntry 6 }

tmnxVdoSGSpliceRate OBJECT-TYPE
    SYNTAX     Unsigned32
    UNITS      "kbps"
    MAX-ACCESS read-only
    STATUS     current
    DESCRIPTION
        "The value of tmnxVdoSGSpliceRate indicates the rate of the ad stream, 
         in kilo-bits per second (kbps), received by the splicer."
    ::= { tmnxVdoSGSpliceStatusEntry 7 }

tmnxVdoSGSpliceSessionId OBJECT-TYPE
    SYNTAX     Unsigned32
    MAX-ACCESS read-only
    STATUS     current
    DESCRIPTION
        "The value of tmnxVdoSGSpliceSessionId indicates the session ID of the 
         ad request."
    ::= { tmnxVdoSGSpliceStatusEntry 8 }

tmnxVdoSGSplicePriorSessionId OBJECT-TYPE
    SYNTAX     Unsigned32
    MAX-ACCESS read-only
    STATUS     current
    DESCRIPTION
        "The value of tmnxVdoSGSplicePriorSessionId indicates the prior session 
         id of the ad. If the value of this object is not equal to 0xFFFFFFFF, 
         then this splice is a back-to-back ad insertion."
    ::= { tmnxVdoSGSpliceStatusEntry 9 }

tmnxVdoSGSpliceAbortReason OBJECT-TYPE
    SYNTAX     INTEGER {
                   none              (0),
                   unknown           (1),
                   adSrvrReq         (2),
                   spliceNotFound    (3),
                   noPrimaryChannel  (4),
                   noInsertChannel   (5),
                   tooEarly          (6),
                   spliceFailed      (7),
                   spliceCollision   (8),
                   spliceTooLate     (9),
                   spliceQueueFull   (10),
                   invalidSessionId  (11),
                   sessionIncomplete (12)
               }
    MAX-ACCESS read-only
    STATUS     current
    DESCRIPTION
        "The value of tmnxVdoSGSpliceAbortReason indicates the reason if a 
         splice operation has been aborted. If the value of this object is 
         equal to 'none', then the splice has not been aborted. "
    ::= { tmnxVdoSGSpliceStatusEntry 10 }

tmnxVdoSGSpliceSpliceInSeqNum OBJECT-TYPE
    SYNTAX     Unsigned32
    MAX-ACCESS read-only
    STATUS     current
    DESCRIPTION
        "The value of tmnxVdoSGSpliceSpliceInSeqNum indicates the sequence 
         number at which the splice-in to the ad occurred."
    ::= { tmnxVdoSGSpliceStatusEntry 11 }

tmnxVdoSGSpliceSpliceOutSeqNum OBJECT-TYPE
    SYNTAX     Unsigned32
    MAX-ACCESS read-only
    STATUS     current
    DESCRIPTION
        "The value of tmnxVdoSGSpliceSpliceOutSeqNum indicates the sequence 
         number at which the splice-out to the ad occurred."
    ::= { tmnxVdoSGSpliceStatusEntry 12 }

tmnxVdoSGSpliceNumBlkFrames OBJECT-TYPE
    SYNTAX     Unsigned32
    MAX-ACCESS read-only
    STATUS     current
    DESCRIPTION
        "The value of tmnxVdoSGSpliceNumBlkFrames indicates the number of black 
         frames inserted."
    ::= { tmnxVdoSGSpliceStatusEntry 13 }

tmnxVdoSGSpliceBlkFramePTS OBJECT-TYPE
    SYNTAX     TmnxVdoPTS
    MAX-ACCESS read-only
    STATUS     current
    DESCRIPTION
        "The value of tmnxVdoSGSpliceBlkFramePTS indicates the Presentation 
         Timestamp (PTS) of the first black frame."
    ::= { tmnxVdoSGSpliceStatusEntry 14 }

tmnxVdoSGSpliceMaxAdPTS OBJECT-TYPE
    SYNTAX     TmnxVdoPTS
    MAX-ACCESS read-only
    STATUS     current
    DESCRIPTION
        "The value of tmnxVdoSGSpliceMaxAdPTS indicates the maximum Presentation
         Timestamp (PTS) value of the last Group of Pictures (GOP) of ad stream 
         (non-black frame)."
    ::= { tmnxVdoSGSpliceStatusEntry 15 }

tmnxVdoSGSpliceMinNwPTS OBJECT-TYPE
    SYNTAX     TmnxVdoPTS
    MAX-ACCESS read-only
    STATUS     current
    DESCRIPTION
        "The value of tmnxVdoSGSpliceMinNwPTS indicates the minimum Presentation
         Timestamp (PTS) value from the first Group of Pictures (GOP) of the
         network stream after the splice out has occured."
    ::= { tmnxVdoSGSpliceStatusEntry 16 }

tmnxVdoIfStatExtTable OBJECT-TYPE
    SYNTAX     SEQUENCE OF TmnxVdoIfStatExtEntry
    MAX-ACCESS not-accessible
    STATUS     current
    DESCRIPTION
        "tmnxVdoIfStatExtTable contains information and statistics for each 
         video interface configured in the system."
    ::= { tmnxVdoObjs 17 }

tmnxVdoIfStatExtEntry OBJECT-TYPE
    SYNTAX     TmnxVdoIfStatExtEntry
    MAX-ACCESS not-accessible
    STATUS     current
    DESCRIPTION
        "An entry in the tmnxVdoIfStatExtTable. Each row entry represents an 
         IP address assigned to a video interface."
    AUGMENTS { tmnxVdoIfAddrEntry }
    ::= { tmnxVdoIfStatExtTable 1 }

TmnxVdoIfStatExtEntry ::= SEQUENCE {
        tmnxVdoIfStatExtRxRtcpAppRepSum          Counter64,
        tmnxVdoIfStatExtRxRtcpAppRepSumL         Counter32,
        tmnxVdoIfStatExtRxRtcpAppRepSumH         Counter32,
        tmnxVdoIfStatExtRxRtcpAppReqSum          Counter64,
        tmnxVdoIfStatExtRxRtcpAppReqSumL         Counter32,
        tmnxVdoIfStatExtRxRtcpAppReqSumH         Counter32,
        tmnxVdoIfStatExtRxRtcpFbRepSum           Counter64,   
        tmnxVdoIfStatExtRxRtcpFbRepSumL          Counter32,
        tmnxVdoIfStatExtRxRtcpFbRepSumH          Counter32,
        tmnxVdoIfStatExtRxRtcpFbReqSum           Counter64,   
        tmnxVdoIfStatExtRxRtcpFbReqSumL          Counter32,
        tmnxVdoIfStatExtRxRtcpFbReqSumH          Counter32,
        tmnxVdoIfStatExtRxRudpFbRepSum           Counter64,   
        tmnxVdoIfStatExtRxRudpFbRepSumL          Counter32,
        tmnxVdoIfStatExtRxRudpFbRepSumH          Counter32,
        tmnxVdoIfStatExtTxFccPktsSum             Counter64,   
        tmnxVdoIfStatExtTxFccPktsSumL            Counter32,
        tmnxVdoIfStatExtTxFccPktsSumH            Counter32,
        tmnxVdoIfStatExtTxFccOctetsSum           Counter64,   
        tmnxVdoIfStatExtTxFccOctetsSumL          Counter32,
        tmnxVdoIfStatExtTxFccOctetsSumH          Counter32,
        tmnxVdoIfStatExtTxRetPktsSum             Counter64,   
        tmnxVdoIfStatExtTxRetPktsSumL            Counter32,
        tmnxVdoIfStatExtTxRetPktsSumH            Counter32,
        tmnxVdoIfStatExtTxRetOctetsSum           Counter64,   
        tmnxVdoIfStatExtTxRetOctetsSumL          Counter32,
        tmnxVdoIfStatExtTxRetOctetsSumH          Counter32,
        tmnxVdoIfStatExtTxRudpPktsSum            Counter64,   
        tmnxVdoIfStatExtTxRudpPktsSumL           Counter32,
        tmnxVdoIfStatExtTxRudpPktsSumH           Counter32,
        tmnxVdoIfStatExtTxRudpByteSum            Counter64,   
        tmnxVdoIfStatExtTxRudpByteSumL           Counter32,
        tmnxVdoIfStatExtTxRudpByteSumH           Counter32
    }

tmnxVdoIfStatExtRxRtcpAppRepSum OBJECT-TYPE
    SYNTAX     Counter64
    MAX-ACCESS read-only
    STATUS     current
    DESCRIPTION
        "The value of tmnxVdoIfStatExtRxRtcpAppRepSum indicates the total 
         number of  Real Time Transport Control Protocol (RTCP) App requests 
         processed for currently active sessions for the interface."
    ::= { tmnxVdoIfStatExtEntry 1 }

tmnxVdoIfStatExtRxRtcpAppRepSumL OBJECT-TYPE
    SYNTAX     Counter32
    MAX-ACCESS read-only
    STATUS     current
    DESCRIPTION
        "The value of tmnxVdoIfStatExtRxRtcpAppRepSumL indicates the lower 32 
         bits of the value of tmnxVdoIfStatExtRxRtcpAppRepSum."
    ::= { tmnxVdoIfStatExtEntry 2 }

tmnxVdoIfStatExtRxRtcpAppRepSumH OBJECT-TYPE
    SYNTAX     Counter32
    MAX-ACCESS read-only
    STATUS     current
    DESCRIPTION
        "The value of tmnxVdoIfStatExtRxRtcpAppRepSumH indicates the higher 32 
         bits of the value of tmnxVdoIfStatExtRxRtcpAppRepSum."
    ::= { tmnxVdoIfStatExtEntry 3 }
 
tmnxVdoIfStatExtRxRtcpAppReqSum OBJECT-TYPE
    SYNTAX     Counter64
    MAX-ACCESS read-only
    STATUS     current
    DESCRIPTION
        "The value of tmnxVdoIfStatExtRxRtcpAppReqSum indicates the total 
         number of  Real Time Transport Control Protocol (RTCP) App requests  
         received for currently active sessions for the interface."
    ::= { tmnxVdoIfStatExtEntry 4 }

tmnxVdoIfStatExtRxRtcpAppReqSumL OBJECT-TYPE
    SYNTAX     Counter32
    MAX-ACCESS read-only
    STATUS     current
    DESCRIPTION
        "The value of tmnxVdoIfStatExtRxRtcpAppReqSumL indicates the lower 32 
         bits of the value of tmnxVdoIfStatExtRxRtcpAppRepSum."
    ::= { tmnxVdoIfStatExtEntry 5 }

tmnxVdoIfStatExtRxRtcpAppReqSumH OBJECT-TYPE
    SYNTAX     Counter32
    MAX-ACCESS read-only
    STATUS     current
    DESCRIPTION
        "The value of tmnxVdoIfStatExtRxRtcpAppReqSumH indicates the higher 32 
         bits of the value of tmnxVdoIfStatExtRxRtcpAppReqSum."
    ::= { tmnxVdoIfStatExtEntry 6 }
 
tmnxVdoIfStatExtRxRtcpFbRepSum OBJECT-TYPE
    SYNTAX     Counter64
    MAX-ACCESS read-only
    STATUS     current
    DESCRIPTION
        "The value of tmnxVdoIfStatExtRxRtcpFbRepSum indicates the total 
         number of Real Time Transport Control Protocol (RTCP) feedback (FB) 
         requests processed for currently active sessions for the interface."
    ::= { tmnxVdoIfStatExtEntry 7 }
 
 tmnxVdoIfStatExtRxRtcpFbRepSumL OBJECT-TYPE
     SYNTAX     Counter32
     MAX-ACCESS read-only
     STATUS     current
     DESCRIPTION
         "The value of tmnxVdoIfStatExtRxRtcpFbRepSumL indicates the lower 32 
          bits of the value of tmnxVdoIfStatExtRxRtcpFbRepSum."
     ::= { tmnxVdoIfStatExtEntry 8 }
 
 tmnxVdoIfStatExtRxRtcpFbRepSumH OBJECT-TYPE
     SYNTAX     Counter32
     MAX-ACCESS read-only
     STATUS     current
     DESCRIPTION
         "The value of tmnxVdoIfStatExtRxRtcpFbRepSumH indicates the higher 32 
          bits of the value of tmnxVdoIfStatExtRxRtcpFbRepSum."
     ::= { tmnxVdoIfStatExtEntry 9 }

tmnxVdoIfStatExtRxRtcpFbReqSum OBJECT-TYPE
    SYNTAX     Counter64
    MAX-ACCESS read-only
    STATUS     current
    DESCRIPTION
        "The value of tmnxVdoIfStatExtRxRtcpFbReqSum indicates the total 
         number of Real Time Transport Control Protocol (RTCP) feedback (FB) 
         requests received for currently active sessions for the interface."
    ::= { tmnxVdoIfStatExtEntry 10 }

tmnxVdoIfStatExtRxRtcpFbReqSumL OBJECT-TYPE
    SYNTAX     Counter32
    MAX-ACCESS read-only
    STATUS     current
    DESCRIPTION
        "The value of tmnxVdoIfStatExtRxRtcpFbReqSumL indicates the lower 32 
         bits of the value of tmnxVdoIfStatExtRxRtcpFbReqSum."
    ::= { tmnxVdoIfStatExtEntry 11 }

tmnxVdoIfStatExtRxRtcpFbReqSumH OBJECT-TYPE
    SYNTAX     Counter32
    MAX-ACCESS read-only
    STATUS     current
    DESCRIPTION
        "The value of tmnxVdoIfStatExtRxRtcpFbReqSumH indicates the higher 32 
         bits of the value of tmnxVdoIfStatExtRxRtcpFbReqSum."
    ::= { tmnxVdoIfStatExtEntry 12 }
 
tmnxVdoIfStatExtRxRudpFbRepSum OBJECT-TYPE
    SYNTAX     Counter64
    MAX-ACCESS read-only
    STATUS     current
    DESCRIPTION
        "The value of tmnxVdoIfStatExtRxRudpFbRepSum indicates the total 
         number of Reliable User Datagram Protocol (RUDP) feedback (FB) messages
         processed for currently active sessions for the interface."
    ::= { tmnxVdoIfStatExtEntry 13 }

tmnxVdoIfStatExtRxRudpFbRepSumL OBJECT-TYPE
    SYNTAX     Counter32
    MAX-ACCESS read-only
    STATUS     current
    DESCRIPTION
        "The value of tmnxVdoIfStatExtRxRudpFbRepSumL indicates the lower 32 
         bits of the value of tmnxVdoIfStatExtRxRudpFbRepSum."
    ::= { tmnxVdoIfStatExtEntry 14 }

tmnxVdoIfStatExtRxRudpFbRepSumH OBJECT-TYPE
    SYNTAX     Counter32
    MAX-ACCESS read-only
    STATUS     current
    DESCRIPTION
        "The value of tmnxVdoIfStatExtRxRudpFbRepSumH indicates the higher 32 
         bits of the value of tmnxVdoIfStatExtRxRudpFbRepSum."
    ::= { tmnxVdoIfStatExtEntry 15 }
 
tmnxVdoIfStatExtTxFccPktsSum OBJECT-TYPE
    SYNTAX     Counter64
    MAX-ACCESS read-only
    STATUS     current
    DESCRIPTION
        "The value of tmnxVdoIfStatExtTxFccPktsSum indicates the total number 
         of data packets sent against Fast Channel Change (FCC) requests for 
         the interface for currently active sessions."
    ::= { tmnxVdoIfStatExtEntry 16 }

tmnxVdoIfStatExtTxFccPktsSumL OBJECT-TYPE
    SYNTAX     Counter32
    MAX-ACCESS read-only
    STATUS     current
    DESCRIPTION
        "The value of tmnxVdoIfStatExtTxFccPktsSumL indicates the lower 32 
         bits of the value of tmnxVdoIfStatExtTxFccPktsSum."
    ::= { tmnxVdoIfStatExtEntry 17 }

tmnxVdoIfStatExtTxFccPktsSumH OBJECT-TYPE
    SYNTAX     Counter32
    MAX-ACCESS read-only
    STATUS     current
    DESCRIPTION
        "The value of tmnxVdoIfStatExtTxFccPktsSumH indicates the higher 32 
         bits of the value of tmnxVdoIfStatExtTxFccPktsSum."
    ::= { tmnxVdoIfStatExtEntry 18 }

 
tmnxVdoIfStatExtTxFccOctetsSum OBJECT-TYPE
    SYNTAX     Counter64
    MAX-ACCESS read-only
    STATUS     current
    DESCRIPTION
        "The value of tmnxVdoIfStatExtTxFccOctetsSum indicates the total number 
         of data octets sent against Fast Channel Change (FCC) requests for the
         interface for currently active sessions."
    ::= { tmnxVdoIfStatExtEntry 19 }

tmnxVdoIfStatExtTxFccOctetsSumL OBJECT-TYPE
    SYNTAX     Counter32
    MAX-ACCESS read-only
    STATUS     current
    DESCRIPTION
        "The value of tmnxVdoIfStatExtTxFccOctetsSumL indicates the lower 32 
         bits of the value of tmnxVdoIfStatExtTxFccOctetsSum."
    ::= { tmnxVdoIfStatExtEntry 20 }

tmnxVdoIfStatExtTxFccOctetsSumH OBJECT-TYPE
    SYNTAX     Counter32
    MAX-ACCESS read-only
    STATUS     current
    DESCRIPTION
        "The value of tmnxVdoIfStatExtTxFccOctetsSumH indicates the higher 32 
         bits of the value of tmnxVdoIfStatExtTxFccOctetsSum."
    ::= { tmnxVdoIfStatExtEntry 21 }
 
tmnxVdoIfStatExtTxRetPktsSum OBJECT-TYPE
    SYNTAX     Counter64
    MAX-ACCESS read-only
    STATUS     current
    DESCRIPTION
        "The value of tmnxVdoIfStatExtTxRetPktsSum indicates the total number 
         of data packets sent against retransmission (Ret) requests for 
         the interface for currently active sessions."
    ::= { tmnxVdoIfStatExtEntry 22 }

tmnxVdoIfStatExtTxRetPktsSumL OBJECT-TYPE
    SYNTAX     Counter32
    MAX-ACCESS read-only
    STATUS     current
    DESCRIPTION
        "The value of tmnxVdoIfStatExtTxRetPktsSumL indicates the lower 32 
         bits of the value of tmnxVdoIfStatExtTxRetPktsSum."
    ::= { tmnxVdoIfStatExtEntry 23 }

tmnxVdoIfStatExtTxRetPktsSumH OBJECT-TYPE
    SYNTAX     Counter32
    MAX-ACCESS read-only
    STATUS     current
    DESCRIPTION
        "The value of tmnxVdoIfStatExtTxRetPktsSumH indicates the higher 32 
         bits of the value of tmnxVdoIfStatExtTxRetPktsSum."
    ::= { tmnxVdoIfStatExtEntry 24 }
 
tmnxVdoIfStatExtTxRetOctetsSum OBJECT-TYPE
    SYNTAX     Counter64
    MAX-ACCESS read-only
    STATUS     current
    DESCRIPTION
        "The value of tmnxVdoIfStatExtTxRetOctetsSum indicates the total number 
         of data octets sent against retransmission (Ret) requests for the interface
         for currently active sessions."
    ::= { tmnxVdoIfStatExtEntry 25 }

tmnxVdoIfStatExtTxRetOctetsSumL OBJECT-TYPE
    SYNTAX     Counter32
    MAX-ACCESS read-only
    STATUS     current
    DESCRIPTION
        "The value of tmnxVdoIfStatExtTxRetOctetsSumL indicates the lower 32 
         bits of the value of tmnxVdoIfStatExtTxRetOctetsSum."
    ::= { tmnxVdoIfStatExtEntry 26 }

tmnxVdoIfStatExtTxRetOctetsSumH OBJECT-TYPE
    SYNTAX     Counter32
    MAX-ACCESS read-only
    STATUS     current
    DESCRIPTION
        "The value of tmnxVdoIfStatExtTxRetOctetsSumH indicates the higher 32 
         bits of the value of tmnxVdoIfStatExtTxRetOctetsSum."
    ::= { tmnxVdoIfStatExtEntry 27 }
 
tmnxVdoIfStatExtTxRudpPktsSum OBJECT-TYPE
    SYNTAX     Counter64
    MAX-ACCESS read-only
    STATUS     current
    DESCRIPTION
        "The value of tmnxVdoIfStatExtTxRudpPktsSum indicates the total number 
         of data packets sent against Reliable User Datagram Protocol (RUDP) 
         retransmission requests for the interface for currently active sessions."
    ::= { tmnxVdoIfStatExtEntry 28 }

tmnxVdoIfStatExtTxRudpPktsSumL OBJECT-TYPE
    SYNTAX     Counter32
    MAX-ACCESS read-only
    STATUS     current
    DESCRIPTION
        "The value of tmnxVdoIfStatExtTxRudpPktsSumL indicates the lower 32 
         bits of the value of tmnxVdoIfStatExtTxRudpPktsSum."
    ::= { tmnxVdoIfStatExtEntry 29 }

tmnxVdoIfStatExtTxRudpPktsSumH OBJECT-TYPE
    SYNTAX     Counter32
    MAX-ACCESS read-only
    STATUS     current
    DESCRIPTION
        "The value of tmnxVdoIfStatExtTxRudpPktsSumH indicates the higher 32 
         bits of the value of tmnxVdoIfStatExtTxRudpPktsSum."
    ::= { tmnxVdoIfStatExtEntry 30 }
 
tmnxVdoIfStatExtTxRudpByteSum OBJECT-TYPE
    SYNTAX     Counter64
    MAX-ACCESS read-only
    STATUS     current
    DESCRIPTION
        "The value of tmnxVdoIfStatExtTxRudpByteSum indicates the total number 
         of data octets sent against Reliable User Datagram Protocol (RUDP) 
         retransmission requests for the interface for currently active sessions."
    ::= { tmnxVdoIfStatExtEntry 31 }

tmnxVdoIfStatExtTxRudpByteSumL OBJECT-TYPE
    SYNTAX     Counter32
    MAX-ACCESS read-only
    STATUS     current
    DESCRIPTION
        "The value of tmnxVdoIfStatExtTxRudpByteSumL indicates the lower 32 
         bits of the value of tmnxVdoIfStatExtTxRudpByteSum."
    ::= { tmnxVdoIfStatExtEntry 32 }

tmnxVdoIfStatExtTxRudpByteSumH OBJECT-TYPE
    SYNTAX     Counter32
    MAX-ACCESS read-only
    STATUS     current
    DESCRIPTION
        "The value of tmnxVdoIfStatExtTxRudpByteSumH indicates the higher 32 
         bits of the value of tmnxVdoIfStatExtTxRudpByteSum."
    ::= { tmnxVdoIfStatExtEntry 33 }

-- -------------------------------------------------------------
-- Group Source Vqm Stat table
-- -------------------------------------------------------------

tmnxVdoGrpSrcVqmStatTable OBJECT-TYPE
    SYNTAX     SEQUENCE OF TmnxVdoGrpSrcVqmStatEntry
    MAX-ACCESS not-accessible
    STATUS     current
    DESCRIPTION
        "tmnxVdoGrpSrcVqmStatTable contains VQM (Video Quality Monitoring) 
         statistics and heuristics for the multicast video channel."
    ::= { tmnxVdoObjs 18 }

tmnxVdoGrpSrcVqmStatEntry OBJECT-TYPE
    SYNTAX     TmnxVdoGrpSrcVqmStatEntry
    MAX-ACCESS not-accessible
    STATUS     current
    DESCRIPTION
        "An entry in the tmnxVdoGrpSrcVqmStatTable. Each entry represents a 
         source address for the corresponding multicast group."
    INDEX      { 
                 svcId,
                 tmnxVdoIfName,
                 tmnxVdoGrpSrcGrpAddrType, 
                 tmnxVdoGrpSrcGroupAddress,
                 tmnxVdoGrpSrcSrcAddrType, 
                 tmnxVdoGrpSrcSourceAddress,
                 tmnxVdoGrpSrcVqmStatsPeriod,
                 tmnxVdoGrpSrcVqmStatsTime
               }
    ::= { tmnxVdoGrpSrcVqmStatTable 1 }

TmnxVdoGrpSrcVqmStatEntry ::= SEQUENCE {
        
        tmnxVdoGrpSrcVqmStatsPeriod          TmnxVdoStatInt,
        tmnxVdoGrpSrcVqmStatsTime            Unsigned32,
        tmnxVdoGrpSrcVqmGoodSecs             Unsigned32,      
        tmnxVdoGrpSrcVqmErrSecs              Unsigned32,
        tmnxVdoGrpSrcVqmDegrSecs             Unsigned32,
        tmnxVdoGrpSrcVqmImpairSecs           Unsigned32,
        tmnxVdoGrpSrcVqmPmtRepErrSecs        Unsigned32,
        tmnxVdoGrpSrcVqmPmtRepDegSecs        Unsigned32,
        tmnxVdoGrpSrcVqmPmtRepImpSecs        Unsigned32,
        tmnxVdoGrpSrcVqmPmtSyntxErrSecs      Unsigned32,
        tmnxVdoGrpSrcVqmPatRepErrSecs        Unsigned32,
        tmnxVdoGrpSrcVqmPatRepDegSecs        Unsigned32,
        tmnxVdoGrpSrcVqmPatRepImpSecs        Unsigned32,
        tmnxVdoGrpSrcVqmPatSyntxErrSecs      Unsigned32,
        tmnxVdoGrpSrcVqmPcrRepErrSecs        Unsigned32,
        tmnxVdoGrpSrcVqmPcrRepDegSecs        Unsigned32,
        tmnxVdoGrpSrcVqmPcrRepImpSecs        Unsigned32,
        tmnxVdoGrpSrcVqmSyncByteErrSecs      Unsigned32,
        tmnxVdoGrpSrcVqmSyncLossSecs         Unsigned32,
        tmnxVdoGrpSrcVqmCatErrSecs           Unsigned32,
        tmnxVdoGrpSrcVqmUnrefPidErrSecs      Unsigned32,
        tmnxVdoGrpSrcVqmMDIDelayFactor       Unsigned32,
        tmnxVdoGrpSrcVqmMDILossRate          TmnxMDILossRate,
        tmnxVdoGrpSrcVqmMinGOPLength         Unsigned32,
        tmnxVdoGrpSrcVqmMinFrmPerSec         Unsigned32,
        tmnxVdoGrpSrcVqmAvgGOPLength         Unsigned32,
        tmnxVdoGrpSrcVqmAvgFrmPerSec         Unsigned32,
        tmnxVdoGrpSrcVqmMaxGOPLength         Unsigned32,
        tmnxVdoGrpSrcVqmMaxFrmPerSec         Unsigned32,
        tmnxVdoGrpSrcVqmGoodIFrames          Unsigned32,
        tmnxVdoGrpSrcVqmBadIFrames           Unsigned32,
        tmnxVdoGrpSrcVqmGoodPFrames          Unsigned32,
        tmnxVdoGrpSrcVqmBadPFrames           Unsigned32,
        tmnxVdoGrpSrcVqmGoodBFrames          Unsigned32,
        tmnxVdoGrpSrcVqmBadBFrames           Unsigned32,
        tmnxVdoGrpSrcVqmTrafficLossSecs      Unsigned32,
        tmnxVdoGrpSrcVqmSCTE35ErrSecs        Unsigned32
}

tmnxVdoGrpSrcVqmStatsPeriod        OBJECT-TYPE
    SYNTAX      TmnxVdoStatInt 
    MAX-ACCESS  not-accessible
    STATUS      current
    DESCRIPTION
        "The value of tmnxVdoGrpSrcVqmStatsPeriod indicates the period of 
         statistics that the user is interested in. The parameter can take a 
         value of 'current' which would display to the user all statistics 
         within the last second. Alternatively it could a value of 'interval' in 
         which case the actual time-duration for which statistics are displayed 
         to the user is specified by MIB object 'tmnxVdoGrpSrcVqmStatsTime'."
    ::= { tmnxVdoGrpSrcVqmStatEntry 1 }

tmnxVdoGrpSrcVqmStatsTime        OBJECT-TYPE
    SYNTAX      Unsigned32
    MAX-ACCESS  not-accessible
    STATUS      current
    DESCRIPTION
        "The value of tmnxVdoGrpSrcVqmStatsTime is effectively based on the 
         value of 'tmnxVdoGrpSrcVqmStatsPeriod'. If 
         'tmnxVdoGrpSrcVqmStatsPeriod' has a value of 'current', then this 
         object has no functionality and gets assigned a numerical value of '0'. 
         If 'tmnxVdoGrpSrcVqmStatsPeriod' has a value of 'interval', then this 
         object specifies the duration of the time-interval in minutes for 
         which the statistics will be displayed to the user."
    ::= { tmnxVdoGrpSrcVqmStatEntry 2 }

tmnxVdoGrpSrcVqmGoodSecs        OBJECT-TYPE
    SYNTAX      Unsigned32 
    UNITS       "seconds" 
    MAX-ACCESS  read-only
    STATUS      current
    DESCRIPTION
        "The value of tmnxVdoGrpSrcVqmGoodSecs indicates the total number of 
         good seconds for the stream on this multicast channel."
    ::= { tmnxVdoGrpSrcVqmStatEntry 3 }

tmnxVdoGrpSrcVqmErrSecs        OBJECT-TYPE
    SYNTAX      Unsigned32
    UNITS       "seconds"
    MAX-ACCESS  read-only
    STATUS      current
    DESCRIPTION
        "The value of tmnxVdoGrpSrcVqmErrSecs indicates the total number of 
         errored seconds for the stream on this multicast channel."
    ::= { tmnxVdoGrpSrcVqmStatEntry 4 }

tmnxVdoGrpSrcVqmDegrSecs        OBJECT-TYPE
    SYNTAX      Unsigned32
    UNITS       "seconds"
    MAX-ACCESS  read-only
    STATUS      current
    DESCRIPTION
        "The value of tmnxVdoGrpSrcVqmDegrSecs indicates the total number of 
         degraded seconds for the stream on this multicast channel."
    ::= { tmnxVdoGrpSrcVqmStatEntry 5 }

tmnxVdoGrpSrcVqmImpairSecs        OBJECT-TYPE
    SYNTAX      Unsigned32
    UNITS       "seconds"
    MAX-ACCESS  read-only
    STATUS      current
    DESCRIPTION
        "The value of tmnxVdoGrpSrcVqmImpairSecs indicates the total number of 
         impaired seconds for the stream on this multicast channel."
    ::= { tmnxVdoGrpSrcVqmStatEntry 6 }

tmnxVdoGrpSrcVqmPmtRepErrSecs        OBJECT-TYPE
    SYNTAX      Unsigned32
    UNITS       "seconds"
    MAX-ACCESS  read-only
    STATUS      current
    DESCRIPTION
        "The value of tmnxVdoGrpSrcVqmPmtRepErrSecs indicates the total number 
         of PMT (Program Map Table) repetition error seconds for the stream on 
         this multicast channel."
    ::= { tmnxVdoGrpSrcVqmStatEntry 7 }

tmnxVdoGrpSrcVqmPmtRepDegSecs        OBJECT-TYPE
    SYNTAX      Unsigned32
    UNITS       "seconds"
    MAX-ACCESS  read-only
    STATUS      current
    DESCRIPTION
        "The value of tmnxVdoGrpSrcVqmPmtRepDegSecs indicates the total number 
         of PMT (Program Map Table) repetition degraded seconds for the stream 
         on this multicast channel."
    ::= { tmnxVdoGrpSrcVqmStatEntry 8 }

tmnxVdoGrpSrcVqmPmtRepImpSecs        OBJECT-TYPE
    SYNTAX      Unsigned32
    UNITS       "seconds"
    MAX-ACCESS  read-only
    STATUS      current
    DESCRIPTION
        "The value of tmnxVdoGrpSrcVqmPmtRepImpSecs indicates the total number 
         of PMT (Program Map Table) repetition impaired seconds for the stream 
         on this multicast channel."
    ::= { tmnxVdoGrpSrcVqmStatEntry 9 }

tmnxVdoGrpSrcVqmPmtSyntxErrSecs        OBJECT-TYPE
    SYNTAX      Unsigned32
    UNITS       "seconds"
    MAX-ACCESS  read-only
    STATUS      current
    DESCRIPTION
        "The value of tmnxVdoGrpSrcVqmPmtSyntxErrSecs indicates  the total 
         number of PMT syntax error seconds for the stream on this multicast 
         channel."
    ::= { tmnxVdoGrpSrcVqmStatEntry 10 }

tmnxVdoGrpSrcVqmPatRepErrSecs        OBJECT-TYPE
    SYNTAX      Unsigned32
    UNITS       "seconds"
    MAX-ACCESS  read-only
    STATUS      current
    DESCRIPTION
        "The value of tmnxVdoGrpSrcVqmPatRepErrSecs indicates the total number 
         of PAT (Program Association Table) repetition error seconds for the 
         stream on this multicast channel."
    ::= { tmnxVdoGrpSrcVqmStatEntry 11 }

tmnxVdoGrpSrcVqmPatRepDegSecs        OBJECT-TYPE
    SYNTAX      Unsigned32
    UNITS       "seconds"
    MAX-ACCESS  read-only
    STATUS      current
    DESCRIPTION
        "The value of tmnxVdoGrpSrcVqmPatRepDegSecs indicates the total number 
         of PAT (Program Association Table) repetition degraded seconds for the 
         stream on this multicast channel."
    ::= { tmnxVdoGrpSrcVqmStatEntry 12 }

tmnxVdoGrpSrcVqmPatRepImpSecs        OBJECT-TYPE
    SYNTAX      Unsigned32
    UNITS       "seconds"
    MAX-ACCESS  read-only
    STATUS      current
    DESCRIPTION
        "The value of tmnxVdoGrpSrcVqmPatRepImpSecs indicates the total number 
         of PAT (Program Association Table) repetition impaired seconds for the 
         stream on this multicast channel."
    ::= { tmnxVdoGrpSrcVqmStatEntry 13 }

tmnxVdoGrpSrcVqmPatSyntxErrSecs        OBJECT-TYPE
    SYNTAX      Unsigned32
    UNITS       "seconds"
    MAX-ACCESS  read-only
    STATUS      current
    DESCRIPTION
        "The value of tmnxVdoGrpSrcVqmPatSyntxErrSecs indicates  the total 
         number of PAT syntax error seconds for the stream on this multicast 
         channel."
    ::= { tmnxVdoGrpSrcVqmStatEntry 14 }

tmnxVdoGrpSrcVqmPcrRepErrSecs        OBJECT-TYPE
    SYNTAX      Unsigned32
    UNITS       "seconds"
    MAX-ACCESS  read-only
    STATUS      current
    DESCRIPTION
        "The value of tmnxVdoGrpSrcVqmPcrRepErrSecs indicates the total number 
         of PCR (Program Clock Reference) repetition error seconds for the 
         video stream with VQM."
    ::= { tmnxVdoGrpSrcVqmStatEntry 15 }

tmnxVdoGrpSrcVqmPcrRepDegSecs        OBJECT-TYPE
    SYNTAX      Unsigned32
    UNITS       "seconds"
    MAX-ACCESS  read-only
    STATUS      current
    DESCRIPTION
        "The value of tmnxVdoGrpSrcVqmPcrRepDegSecs indicates the total number 
         of PCR (Program Clock Reference) repetition degraded seconds for the 
         stream on this multicast channel."
    ::= { tmnxVdoGrpSrcVqmStatEntry 16 }

tmnxVdoGrpSrcVqmPcrRepImpSecs        OBJECT-TYPE
    SYNTAX      Unsigned32
    UNITS       "seconds"
    MAX-ACCESS  read-only
    STATUS      current
    DESCRIPTION
        "The value of tmnxVdoGrpSrcVqmPcrRepImpSecs indicates the total number 
         of PCR (Program Clock Reference) repetition impaired seconds for the 
         stream on this multicast channel."
    ::= { tmnxVdoGrpSrcVqmStatEntry 17 }

tmnxVdoGrpSrcVqmSyncByteErrSecs        OBJECT-TYPE
    SYNTAX      Unsigned32
    UNITS       "seconds"
    MAX-ACCESS  read-only
    STATUS      current
    DESCRIPTION
        "The value of tmnxVdoGrpSrcVqmSyncByteErrSecs indicates the total number 
         of sync byte error seconds for the stream on this multicast channel."
    ::= { tmnxVdoGrpSrcVqmStatEntry 18 }

tmnxVdoGrpSrcVqmSyncLossSecs        OBJECT-TYPE
    SYNTAX      Unsigned32
    UNITS       "seconds"
    MAX-ACCESS  read-only
    STATUS      current
    DESCRIPTION
        "The value of tmnxVdoGrpSrcVqmSyncLossSecs indicates the total number 
         of sync loss seconds for the stream on this multicast channel."
    ::= { tmnxVdoGrpSrcVqmStatEntry 19 }

tmnxVdoGrpSrcVqmCatErrSecs        OBJECT-TYPE
    SYNTAX      Unsigned32
    UNITS       "seconds"
    MAX-ACCESS  read-only
    STATUS      current
    DESCRIPTION
        "The value of tmnxVdoGrpSrcVqmCatErrSecs indicates the total number of 
         CAT (Conditional Access Table) error seconds for the stream on this 
         multicast channel."
    ::= { tmnxVdoGrpSrcVqmStatEntry 20 }

tmnxVdoGrpSrcVqmUnrefPidErrSecs        OBJECT-TYPE
    SYNTAX      Unsigned32
    UNITS       "seconds"
    MAX-ACCESS  read-only
    STATUS      current
    DESCRIPTION
        "The value of tmnxVdoGrpSrcVqmUnrefPidErrSecs indicates the total
         number of unreferenced PID error seconds for the stream on this 
         multicast channel."
    ::= { tmnxVdoGrpSrcVqmStatEntry 21 }

tmnxVdoGrpSrcVqmMDIDelayFactor        OBJECT-TYPE
    SYNTAX      Unsigned32
    UNITS       "milliseconds"
    MAX-ACCESS  read-only
    STATUS      current
    DESCRIPTION
        "The value of tmnxVdoGrpSrcVqmMDIDelayFactor indicates Media Delivery 
         Index (MDI) delay factor. If the value of this object is '4294967295' 
         (0xFFFFFFFF) then this indicates there is no media stream."
    REFERENCE "RFC-4445, April 2006, Section 3.1"
    ::= { tmnxVdoGrpSrcVqmStatEntry 22 }

tmnxVdoGrpSrcVqmMDILossRate        OBJECT-TYPE
    SYNTAX      TmnxMDILossRate
    UNITS       "TS/sec"
    MAX-ACCESS  read-only
    STATUS      current
    DESCRIPTION
        "The value of tmnxVdoGrpSrcVqmMDILossRate indicates Media Delivery Index 
         (MDI) loss Rate."
    REFERENCE "RFC-4445, April 2006, Section 3.2"
    ::= { tmnxVdoGrpSrcVqmStatEntry 23 }

tmnxVdoGrpSrcVqmMinGOPLength        OBJECT-TYPE
    SYNTAX      Unsigned32
    UNITS       "pictures"
    MAX-ACCESS  read-only
    STATUS      current
    DESCRIPTION
        "The value of tmnxVdoGrpSrcVqmMinGOPLength indicates the minimum 
         distance in a Group Of Pictures (GOP) between two consecutive I-frames 
         within a sequence of frames in that video stream on a multicast 
         channel."
    ::= { tmnxVdoGrpSrcVqmStatEntry 24 }

tmnxVdoGrpSrcVqmMinFrmPerSec        OBJECT-TYPE
    SYNTAX      Unsigned32
    UNITS       "fps"
    MAX-ACCESS  read-only
    STATUS      current
    DESCRIPTION
        "The value of tmnxVdoGrpSrcVqmMinFrmPerSec indicates the minimum number 
         of frames per second in a video stream on a multicast channel."
    ::= { tmnxVdoGrpSrcVqmStatEntry 25 }

tmnxVdoGrpSrcVqmAvgGOPLength        OBJECT-TYPE
    SYNTAX      Unsigned32
    UNITS       "pictures"
    MAX-ACCESS  read-only
    STATUS      current
    DESCRIPTION
        "The value of tmnxVdoGrpSrcVqmAvgGOPLength indicates the average 
         distance in a Group Of Pictures (GOP) between two consecutive I-frames 
         within a sequence of frames in that video stream on a multicast 
         channel."
    ::= { tmnxVdoGrpSrcVqmStatEntry 26 }

tmnxVdoGrpSrcVqmAvgFrmPerSec        OBJECT-TYPE
    SYNTAX      Unsigned32
    UNITS       "fps"
    MAX-ACCESS  read-only
    STATUS      current
    DESCRIPTION
        "The value of tmnxVdoGrpSrcVqmAvgFrmPerSec indicates the average number 
         of frames per second in a video stream on a multicast channel."
    ::= { tmnxVdoGrpSrcVqmStatEntry 27 }

tmnxVdoGrpSrcVqmMaxGOPLength        OBJECT-TYPE
    SYNTAX      Unsigned32
    UNITS       "pictures"
    MAX-ACCESS  read-only
    STATUS      current
    DESCRIPTION
        "The value of tmnxVdoGrpSrcVqmMaxGOPLength indicates the maximum
         distance in a Group Of Pictures (GOP) between two consecutive I-frames 
         within a sequence of frames in that video stream on a multicast 
         channel."
    ::= { tmnxVdoGrpSrcVqmStatEntry 28 }

tmnxVdoGrpSrcVqmMaxFrmPerSec        OBJECT-TYPE
    SYNTAX      Unsigned32
    UNITS       "fps"
    MAX-ACCESS  read-only
    STATUS      current
    DESCRIPTION
        "The value of tmnxVdoGrpSrcVqmMaxFrmPerSec indicates the maximum number 
         of frames per second in a video stream on a multicast channel."
    ::= { tmnxVdoGrpSrcVqmStatEntry 29 }

tmnxVdoGrpSrcVqmGoodIFrames        OBJECT-TYPE
    SYNTAX      Unsigned32
    MAX-ACCESS  read-only
    STATUS      current
    DESCRIPTION
        "The value of tmnxVdoGrpSrcVqmGoodIFrames indicates the number of good 
         'I' frames in a video stream on a multicast channel."
    ::= { tmnxVdoGrpSrcVqmStatEntry 30 }

tmnxVdoGrpSrcVqmBadIFrames        OBJECT-TYPE
    SYNTAX      Unsigned32
    MAX-ACCESS  read-only
    STATUS      current
    DESCRIPTION
        "The value of tmnxVdoGrpSrcVqmBadIFrames indicates the number of bad 'I' 
         frames in a video stream on a multicast channel."
    ::= { tmnxVdoGrpSrcVqmStatEntry 31 }

tmnxVdoGrpSrcVqmGoodPFrames        OBJECT-TYPE
    SYNTAX      Unsigned32
    MAX-ACCESS  read-only
    STATUS      current
    DESCRIPTION
        "The value of tmnxVdoGrpSrcVqmGoodPFrames indicates the number of good 
         'P' frames in a video stream on a multicast channel."
    ::= { tmnxVdoGrpSrcVqmStatEntry 32 }

tmnxVdoGrpSrcVqmBadPFrames        OBJECT-TYPE
    SYNTAX      Unsigned32
    MAX-ACCESS  read-only
    STATUS      current
    DESCRIPTION
        "The value of tmnxVdoGrpSrcVqmBadPFrames indicates the number of bad 'P' 
         frames in a video stream on a multicast channel."
    ::= { tmnxVdoGrpSrcVqmStatEntry 33 }

tmnxVdoGrpSrcVqmGoodBFrames        OBJECT-TYPE
    SYNTAX      Unsigned32
    MAX-ACCESS  read-only
    STATUS      current
    DESCRIPTION
        "The value of tmnxVdoGrpSrcVqmGoodBFrames indicates the number of good 
         'B' frames in a video stream on a multicast channel."
    ::= { tmnxVdoGrpSrcVqmStatEntry 34 }

tmnxVdoGrpSrcVqmBadBFrames        OBJECT-TYPE
    SYNTAX      Unsigned32
    MAX-ACCESS  read-only
    STATUS      current
    DESCRIPTION
        "The value of tmnxVdoGrpSrcVqmBadBFrames indicates the number of bad 'B' 
         frames in a video stream on a multicast channel."
    ::= { tmnxVdoGrpSrcVqmStatEntry 35 }

tmnxVdoGrpSrcVqmTrafficLossSecs        OBJECT-TYPE
    SYNTAX      Unsigned32
    UNITS       "seconds"
    MAX-ACCESS  read-only
    STATUS      current
    DESCRIPTION
        "The value of tmnxVdoGrpSrcVqmTrafficLossSecs indicates loss of 
         traffic seconds in a stream on a multicast channel."
    ::= { tmnxVdoGrpSrcVqmStatEntry 36 }

tmnxVdoGrpSrcVqmSCTE35ErrSecs        OBJECT-TYPE
    SYNTAX      Unsigned32
    UNITS       "seconds"
    MAX-ACCESS  read-only
    STATUS      obsolete
    DESCRIPTION
        "The value of tmnxVdoGrpSrcVqmSCTE35ErrSecs indicates the total number 
        of Society of Cable Telecommunications Engineers (SCTE-35) errors in a 
        stream on a multicast channel.

        This object was obsoleted in the 9.0 release."
    ::= { tmnxVdoGrpSrcVqmStatEntry 37 }

-- -------------------------------------------------------------
-- Group Source Vqm table
-- -------------------------------------------------------------

tmnxVdoGrpSrcVqmTable OBJECT-TYPE
    SYNTAX     SEQUENCE OF TmnxVdoGrpSrcVqmEntry
    MAX-ACCESS not-accessible
    STATUS     current
    DESCRIPTION
        "tmnxVdoGrpSrcVqmTable contains VQM (Video Quality Monitoring) 
         analyzer alarm configured and operational values."
    ::= { tmnxVdoObjs 19 }

tmnxVdoGrpSrcVqmEntry OBJECT-TYPE
    SYNTAX     TmnxVdoGrpSrcVqmEntry
    MAX-ACCESS not-accessible
    STATUS     current
    DESCRIPTION
        "An entry in the tmnxVdoGrpSrcVqmTable. Each entry represents an 
         VQM analyzer values for a particular video stream."
    INDEX      { 
                 svcId,
                 tmnxVdoIfName,
                 tmnxVdoGrpSrcGrpAddrType, 
                 tmnxVdoGrpSrcGroupAddress,
                 tmnxVdoGrpSrcSrcAddrType, 
                 tmnxVdoGrpSrcSourceAddress
               }
    ::= { tmnxVdoGrpSrcVqmTable 1 }

TmnxVdoGrpSrcVqmEntry ::= SEQUENCE {
        
        tmnxVdoGrpSrcVqmOperAnalyzerSt        TruthValue,
        tmnxVdoGrpSrcVqmOperCcError           TruthValue,   
        tmnxVdoGrpSrcVqmOperPatRepError       TruthValue,
        tmnxVdoGrpSrcVqmOperTncPatRep         Unsigned32,
        tmnxVdoGrpSrcVqmOperQosPatRep         Unsigned32,
        tmnxVdoGrpSrcVqmOperPoaPatRep         Unsigned32,
        tmnxVdoGrpSrcVqmOperPatSyntax         TruthValue,
        tmnxVdoGrpSrcVqmOperPcrRepError       TruthValue,
        tmnxVdoGrpSrcVqmOperTncPcrRep         Unsigned32,
        tmnxVdoGrpSrcVqmOperQosPcrRep         Unsigned32, 
        tmnxVdoGrpSrcVqmOperPoaPcrRep         Unsigned32,
        tmnxVdoGrpSrcVqmOperVidPIDAbs         Unsigned32,
        tmnxVdoGrpSrcVqmOperPIDPmtUnref       TruthValue,
        tmnxVdoGrpSrcVqmOperPmtRepError       TruthValue,
        tmnxVdoGrpSrcVqmOperTncPmtRep         Unsigned32,
        tmnxVdoGrpSrcVqmOperQosPmtRep         Unsigned32,
        tmnxVdoGrpSrcVqmOperPoaPmtRep         Unsigned32,
        tmnxVdoGrpSrcVqmOperPmtSyntax         TruthValue,
        tmnxVdoGrpSrcVqmOperSCTE35Error       TruthValue, 
        tmnxVdoGrpSrcVqmOperTeiError          TruthValue,  
        tmnxVdoGrpSrcVqmOperTsSyncLoss        TruthValue, 
        tmnxVdoGrpSrcVqmOperNonVidPIDAbs      Unsigned32,
        tmnxVdoGrpSrcVqmOperReportAlarm       TmnxVdoAnalyzerAlarm
}

tmnxVdoGrpSrcVqmOperAnalyzerSt        OBJECT-TYPE
    SYNTAX          TruthValue
    MAX-ACCESS      read-only
    STATUS          current
    DESCRIPTION
        "The value of tmnxVdoGrpSrcVqmOperAnalyzerSt indicates whether or not 
         the analyzer is enabled for the multicast stream."
    ::= { tmnxVdoGrpSrcVqmEntry 1 }

tmnxVdoGrpSrcVqmOperCcError        OBJECT-TYPE
    SYNTAX      TruthValue
    MAX-ACCESS  read-only
    STATUS      current
    DESCRIPTION
        "The value of tmnxVdoGrpSrcVqmOperCcError indicates whether or not
         the continuity counter error is enabled for the multicast stream."
    ::= { tmnxVdoGrpSrcVqmEntry 2 }

tmnxVdoGrpSrcVqmOperPatRepError         OBJECT-TYPE
    SYNTAX      TruthValue
    MAX-ACCESS  read-only
    STATUS      current
    DESCRIPTION
        "The value of tmnxVdoGrpSrcVqmOperPatRepError indicates whether or not
         PAT (Program Association Table) repetition error is enabled for the 
         multicast stream."
    ::= { tmnxVdoGrpSrcVqmEntry 3 }

tmnxVdoGrpSrcVqmOperTncPatRep        OBJECT-TYPE
    SYNTAX      Unsigned32 
    UNITS       "milliseconds" 
    MAX-ACCESS  read-only
    STATUS      current
    DESCRIPTION
        "The value of tmnxVdoGrpSrcVqmOperTncPatRep indicates the value of
         TNC (Tech Non-Conformant) in milli-seconds for PAT repitition and 
         is always a multiple of 100."
    ::= { tmnxVdoGrpSrcVqmEntry 4 }

tmnxVdoGrpSrcVqmOperQosPatRep        OBJECT-TYPE
    SYNTAX      Unsigned32 
    UNITS       "milliseconds"
    MAX-ACCESS  read-only
    STATUS      current
    DESCRIPTION
        "The value of tmnxVdoGrpSrcVqmOperQosPatRep indicates the value of
         QOS (Quality of Service) in milli-seconds for PAT repitition and is 
         always a multiple of 100."
    ::= { tmnxVdoGrpSrcVqmEntry 5 }

tmnxVdoGrpSrcVqmOperPoaPatRep       OBJECT-TYPE
    SYNTAX      Unsigned32
    UNITS       "milliseconds"
    MAX-ACCESS  read-only
    STATUS      current
    DESCRIPTION
        "The value of tmnxVdoGrpSrcVqmOperPoaPatRep indicates the value of
         TOA (Transport Stream off Air) in milli-seconds for PAT repitition and 
         is always a multiple of 100."
    ::= { tmnxVdoGrpSrcVqmEntry 6 }

tmnxVdoGrpSrcVqmOperPatSyntax       OBJECT-TYPE
    SYNTAX      TruthValue
    MAX-ACCESS  read-only
    STATUS      current
    DESCRIPTION
        "The value of tmnxVdoGrpSrcVqmOperPatSyntax indicates whether or not
         PAT syntax error is enabled for the multicast stream."
    ::= { tmnxVdoGrpSrcVqmEntry 7 }

tmnxVdoGrpSrcVqmOperPcrRepError        OBJECT-TYPE
    SYNTAX      TruthValue
    MAX-ACCESS  read-only
    STATUS      current
    DESCRIPTION
        "The value of tmnxVdoGrpSrcVqmOperPcrRepError indicates whether or not
         PCR (Program Clock Reference) repetition error is enabled for the 
         multicast stream."
    ::= { tmnxVdoGrpSrcVqmEntry 8 }

tmnxVdoGrpSrcVqmOperTncPcrRep         OBJECT-TYPE
    SYNTAX      Unsigned32
    UNITS       "milliseconds"
    MAX-ACCESS  read-only
    STATUS      current
    DESCRIPTION
        "The value of tmnxVdoGrpSrcVqmOperTncPcrRep indicates the value of
         TNC (Tech Non-Conformant) in milli-seconds for PCR repitition and 
         is always a multiple of 100."
    ::= { tmnxVdoGrpSrcVqmEntry 9 }

tmnxVdoGrpSrcVqmOperQosPcrRep        OBJECT-TYPE
    SYNTAX      Unsigned32
    UNITS       "milliseconds"
    MAX-ACCESS  read-only
    STATUS      current
    DESCRIPTION
        "The value of tmnxVdoGrpSrcVqmOperQosPcrRep indicates the value of
         QOS (Quality of Service) in milli-seconds for PCR repitition and is 
         always a multiple of 100."
    ::= { tmnxVdoGrpSrcVqmEntry 10 }

tmnxVdoGrpSrcVqmOperPoaPcrRep        OBJECT-TYPE
    SYNTAX      Unsigned32 
    UNITS       "milliseconds"
    MAX-ACCESS  read-only
    STATUS      current
    DESCRIPTION
        "The value of tmnxVdoGrpSrcVqmOperPoaPcrRep indicates the value of
         POA (Program off Air) in milli-seconds for PAT repitition and is 
         always a multiple of 100."
    ::= { tmnxVdoGrpSrcVqmEntry 11 }

tmnxVdoGrpSrcVqmOperVidPIDAbs        OBJECT-TYPE
    SYNTAX      Unsigned32
    UNITS       "milliseconds"
    MAX-ACCESS  read-only
    STATUS      current
    DESCRIPTION
        "The value of tmnxVdoGrpSrcVqmOperVidPIDAbs indicates the counting 
         interval for an instance of 
         'TIMETRA-VIDEO-MIB::tmnxVdoPIDAbsentErrSecs' which accumulates the 
         number of video PID absent errors for the multicast PID stream."
    ::= { tmnxVdoGrpSrcVqmEntry 12 }
    
tmnxVdoGrpSrcVqmOperPIDPmtUnref        OBJECT-TYPE
    SYNTAX      TruthValue
    MAX-ACCESS  read-only
    STATUS      current
    DESCRIPTION
        "The value of tmnxVdoGrpSrcVqmOperPIDPmtUnref indicates whether or not 
         unreferenced PID (i.e. PIDs not specified in the PMT) error is enabled 
         for the multicast stream."
    ::= { tmnxVdoGrpSrcVqmEntry 13 }

tmnxVdoGrpSrcVqmOperPmtRepError       OBJECT-TYPE
    SYNTAX      TruthValue
    MAX-ACCESS  read-only
    STATUS      current
    DESCRIPTION
        "The value of tmnxVdoGrpSrcVqmOperPmtRepError indicates whether or not
         PMT (Program Map Table) repetition error is enabled for the 
         multicast stream."
    ::= { tmnxVdoGrpSrcVqmEntry 14 }

tmnxVdoGrpSrcVqmOperTncPmtRep        OBJECT-TYPE
    SYNTAX      Unsigned32
    UNITS       "milliseconds"
    MAX-ACCESS  read-only
    STATUS      current
    DESCRIPTION
        "The value of tmnxVdoGrpSrcVqmOperTncPmtRep indicates the value of
         TNC (Tech Non-Conformance) in milli-seconds for PMT repitition and 
         is always a multiple of 100."
    ::= { tmnxVdoGrpSrcVqmEntry 15 }

tmnxVdoGrpSrcVqmOperQosPmtRep         OBJECT-TYPE
    SYNTAX      Unsigned32
    UNITS       "milliseconds"
    MAX-ACCESS  read-only
    STATUS      current
    DESCRIPTION
        "The value of tmnxVdoGrpSrcVqmOperQosPmtRep indicates the value of
         QOS (Quality of Service) in milli-seconds for PMT repitition and is 
         always a multiple of 100."
    ::= { tmnxVdoGrpSrcVqmEntry 16 }

tmnxVdoGrpSrcVqmOperPoaPmtRep        OBJECT-TYPE
    SYNTAX      Unsigned32
    UNITS       "milliseconds"
    MAX-ACCESS  read-only
    STATUS      current
    DESCRIPTION
        "The value of tmnxVdoGrpSrcVqmOperPoaPmtRep indicates the value of
         POA (Program off Air) in milli-seconds for PMT repitition and is  
         always a multiple of 100."
    ::= { tmnxVdoGrpSrcVqmEntry 17 }

tmnxVdoGrpSrcVqmOperPmtSyntax       OBJECT-TYPE
    SYNTAX      TruthValue
    MAX-ACCESS  read-only
    STATUS      current
    DESCRIPTION
        "The value of tmnxVdoGrpSrcVqmOperPmtSyntax indicates whether or not
         PMT syntax error is enabled for the multicast stream."
    ::= { tmnxVdoGrpSrcVqmEntry 18 }

tmnxVdoGrpSrcVqmOperSCTE35Error        OBJECT-TYPE
    SYNTAX      TruthValue
    MAX-ACCESS  read-only
    STATUS      current
    DESCRIPTION
        "The value of tmnxVdoGrpSrcVqmOperSCTE35Error indicates whether or not
         Society of Cable Telecommunications Engineers (SCTE-35) errors
         are enabled for the multicast stream."
    ::= { tmnxVdoGrpSrcVqmEntry 19 }

tmnxVdoGrpSrcVqmOperTeiError        OBJECT-TYPE
    SYNTAX      TruthValue
    MAX-ACCESS  read-only
    STATUS      current
    DESCRIPTION
        "The value of tmnxVdoGrpSrcVqmOperTeiError indicates whether or not TEI
        (Transport Error Indicator) error is enabled for the multicast stream."
    ::= { tmnxVdoGrpSrcVqmEntry 20 }

tmnxVdoGrpSrcVqmOperTsSyncLoss        OBJECT-TYPE
    SYNTAX      TruthValue
    MAX-ACCESS  read-only
    STATUS      current
    DESCRIPTION
        "The value of tmnxVdoGrpSrcVqmOperTsSyncLoss indicates whether or not  
         sync loss error is enabled for the multicast stream."
    ::= { tmnxVdoGrpSrcVqmEntry 21 }

tmnxVdoGrpSrcVqmOperNonVidPIDAbs        OBJECT-TYPE
    SYNTAX      Unsigned32
    UNITS       "milliseconds"
    MAX-ACCESS  read-only
    STATUS      current
    DESCRIPTION
        "The value of tmnxVdoGrpSrcVqmOperNonVidPIDAbs indicates the counting 
         interval for an the instance of 
         'TIMETRA-VIDEO-MIB::tmnxVdoPIDAbsentErrSecs' which accumulates the 
         number of non-video PID absent errors for the multicast PID stream."
    ::= { tmnxVdoGrpSrcVqmEntry 22 }

tmnxVdoGrpSrcVqmOperReportAlarm       OBJECT-TYPE
    SYNTAX      TmnxVdoAnalyzerAlarm
    MAX-ACCESS  read-only
    STATUS      current
    DESCRIPTION
        "The value of tmnxVdoGrpSrcVqmOperReportAlarm indicates the severity of 
         the analyzer state alarm for the multicast stream."
    ::= { tmnxVdoGrpSrcVqmEntry 23 }

-- -------------------------------------------------------------
-- Group Source Stat Extension Table
-- -------------------------------------------------------------

tmnxVdoGrpSrcStatExtTable OBJECT-TYPE
    SYNTAX     SEQUENCE OF TmnxVdoGrpSrcStatExtEntry
    MAX-ACCESS not-accessible
    STATUS     current
    DESCRIPTION
        "tmnxVdoGrpSrcStatExtTable contains channel information and 
         statistics for the multicast groups."
    ::= { tmnxVdoObjs 20 }

tmnxVdoGrpSrcStatExtEntry OBJECT-TYPE
    SYNTAX     TmnxVdoGrpSrcStatExtEntry
    MAX-ACCESS not-accessible
    STATUS     current
    DESCRIPTION
        "An entry in the tmnxVdoGrpSrcStatExtTable. Each entry represents a 
         source address for the corresponding multicast group."
    AUGMENTS { tmnxVdoGrpSrcStatEntry }
    ::= { tmnxVdoGrpSrcStatExtTable 1 }

TmnxVdoGrpSrcStatExtEntry ::= SEQUENCE {
        tmnxVdoGrpSrcExtMaxRtpTsDelta         Counter32,
        tmnxVdoGrpSrcExtMaxTicksDelta         Counter64,
        tmnxVdoGrpSrcExtMaxTicksDeltaL32      Counter32,
        tmnxVdoGrpSrcExtMaxTicksDeltaH32      Counter32,
        tmnxVdoGrpSrcExtCurTsJitter           Counter64,
        tmnxVdoGrpSrcExtCurTsJitterL32        Counter32,
        tmnxVdoGrpSrcExtCurTsJitterH32        Counter32,
        tmnxVdoGrpSrcExtMaxTsJitter           Counter64,
        tmnxVdoGrpSrcExtMaxTsJitterL32        Counter32,
        tmnxVdoGrpSrcExtMaxTsJitterH32        Counter32
}

tmnxVdoGrpSrcExtMaxRtpTsDelta OBJECT-TYPE
    SYNTAX     Counter32
    MAX-ACCESS read-only
    STATUS     current
    DESCRIPTION
        "The value of tmnxVdoGrpSrcExtMaxRtpTsDelta indicates the maximum Real 
         Time Protocol(RTP) Timestamps(Ts) delta recorded up to this point 
         in time."
    ::= { tmnxVdoGrpSrcStatExtEntry 1 }

tmnxVdoGrpSrcExtMaxTicksDelta OBJECT-TYPE
    SYNTAX     Counter64
    MAX-ACCESS read-only
    STATUS     current
    DESCRIPTION
        "The value of tmnxVdoGrpSrcExtMaxTicksDelta indicates the maximum 
         arrival Timestamps(Ts) delta recorded up to this point in time."
    ::= { tmnxVdoGrpSrcStatExtEntry 2 }

tmnxVdoGrpSrcExtMaxTicksDeltaL32 OBJECT-TYPE
    SYNTAX     Counter32
    MAX-ACCESS read-only
    STATUS     current
    DESCRIPTION
        "The value of tmnxVdoGrpSrcExtMaxTicksDeltaL32 indicates the lower 
         32 bits of the value of tmnxVdoGrpSrcExtMaxTicksDelta."
    ::= { tmnxVdoGrpSrcStatExtEntry 3 }

tmnxVdoGrpSrcExtMaxTicksDeltaH32 OBJECT-TYPE
    SYNTAX     Counter32
    MAX-ACCESS read-only
    STATUS     current
    DESCRIPTION
        "The value of tmnxVdoGrpSrcExtMaxTicksDeltaH32 indicates the higher 
         32 bits of the value of tmnxVdoGrpSrcExtMaxTicksDelta."
    ::= { tmnxVdoGrpSrcStatExtEntry 4 }

tmnxVdoGrpSrcExtCurTsJitter OBJECT-TYPE
    SYNTAX     Counter64
    MAX-ACCESS read-only
    STATUS     current
    DESCRIPTION
        "The value of tmnxVdoGrpSrcExtCurTsJitter indicates the difference 
         between the current arrival Timestamps(Ts) delta and current Real Time 
         Protocol(RTP) Timestamps(Ts) delta."
    ::= { tmnxVdoGrpSrcStatExtEntry 5 }

tmnxVdoGrpSrcExtCurTsJitterL32 OBJECT-TYPE
    SYNTAX     Counter32
    MAX-ACCESS read-only
    STATUS     current
    DESCRIPTION
        "The value of tmnxVdoGrpSrcExtCurTsJitterL32 indicates the lower 32 bits
         of the value of tmnxVdoGrpSrcExtCurTsJitter."
    ::= { tmnxVdoGrpSrcStatExtEntry 6 }

tmnxVdoGrpSrcExtCurTsJitterH32 OBJECT-TYPE
    SYNTAX     Counter32
    MAX-ACCESS read-only
    STATUS     current
    DESCRIPTION
        "The value of tmnxVdoGrpSrcExtCurTsJitterH32 indicates the higher 32 
         bits of the value of tmnxVdoGrpSrcExtCurTsJitter."
    ::= { tmnxVdoGrpSrcStatExtEntry 7 }

tmnxVdoGrpSrcExtMaxTsJitter OBJECT-TYPE
    SYNTAX     Counter64
    MAX-ACCESS read-only
    STATUS     current
    DESCRIPTION
        "The value of tmnxVdoGrpSrcExtMaxTsJitter indicates the maximum 
         difference between the arrival Timestamps(Ts) delta and current Real 
         Time Protocol(RTP) Timestamps(Ts) delta."
    ::= { tmnxVdoGrpSrcStatExtEntry 8 }

tmnxVdoGrpSrcExtMaxTsJitterL32 OBJECT-TYPE
    SYNTAX     Counter32
    MAX-ACCESS read-only
    STATUS     current
    DESCRIPTION
        "The value of tmnxVdoGrpSrcExtMaxTsJitterL32 indicates the lower 32 bits
         of the value of tmnxVdoGrpSrcExtMaxTsJitter."
    ::= { tmnxVdoGrpSrcStatExtEntry 9 }

tmnxVdoGrpSrcExtMaxTsJitterH32 OBJECT-TYPE
    SYNTAX     Counter32
    MAX-ACCESS read-only
    STATUS     current
    DESCRIPTION
        "The value of tmnxVdoGrpSrcExtMaxTsJitterH32 indicates the higher 32 
         bits of the value of tmnxVdoGrpSrcExtMaxTsJitter."
    ::= { tmnxVdoGrpSrcStatExtEntry 10 }

-- ----------------------------------------------
--     Notification Objects
-- ----------------------------------------------

tmnxVdoNotifysvcId  OBJECT-TYPE
    SYNTAX       TmnxServId
    MAX-ACCESS   accessible-for-notify
    STATUS       current
    DESCRIPTION
        "The value of tmnxVdoNotifysvcId indicates the Service identifier."
    ::= { tmnxVdoNotificationObjs 1 }

tmnxVdoNotifyIfName  OBJECT-TYPE
    SYNTAX       TmnxVdoIfName
    MAX-ACCESS   accessible-for-notify
    STATUS       current
    DESCRIPTION
        "The value of tmnxVdoNotifyIfName indicates the administrative name 
         of a video interface."
    ::= { tmnxVdoNotificationObjs 2 }

tmnxVdoNotifyGrpAddrType  OBJECT-TYPE
    SYNTAX       InetAddressType
    MAX-ACCESS   accessible-for-notify
    STATUS       current
    DESCRIPTION
        "The value of tmnxVdoNotifyGrpAddrType indicates the type of 
         IP multicast group address represented by tmnxVdoNotifyGroupAddress."
    ::= { tmnxVdoNotificationObjs 3 }

tmnxVdoNotifyGroupAddress  OBJECT-TYPE
    SYNTAX       InetAddress
    MAX-ACCESS   accessible-for-notify
    STATUS       current
    DESCRIPTION
        "The value of tmnxVdoNotifyGroupAddress indicates the IP multicast 
         group address of a channel."
    ::= { tmnxVdoNotificationObjs 4 }

tmnxVdoNotifySrcAddrType  OBJECT-TYPE
    SYNTAX       InetAddressType
    MAX-ACCESS   accessible-for-notify
    STATUS       current
    DESCRIPTION
        "The value of tmnxVdoNotifySrcAddrType indicates the type of 
         source address represented by tmnxVdoNotifySourceAddress."
    ::= { tmnxVdoNotificationObjs 5 }

tmnxVdoNotifySourceAddress  OBJECT-TYPE
    SYNTAX       InetAddress
    MAX-ACCESS   accessible-for-notify
    STATUS       current
    DESCRIPTION
        "The value of tmnxVdoNotifySourceAddress indicates the source address 
         of a channel."
    ::= { tmnxVdoNotificationObjs 6 }

tmnxVdoNotifyAdSpliceSessionId  OBJECT-TYPE
    SYNTAX       Unsigned32
    MAX-ACCESS   accessible-for-notify
    STATUS       current
    DESCRIPTION
        "The value of tmnxVdoNotifyAdSpliceSessionId indicates the session id 
         of an ad splice operation."
    ::= { tmnxVdoNotificationObjs 7 }

tmnxVdoNotifyAdSpliceAbortTime  OBJECT-TYPE
    SYNTAX       DateAndTime (SIZE (11))
    MAX-ACCESS   accessible-for-notify
    STATUS       current
    DESCRIPTION
        "The value of tmnxVdoNotifyAdSpliceAbortTime indicates the date and 
         time (in UTC) when the ad splice was aborted."
    ::= { tmnxVdoNotificationObjs 8 }

tmnxVdoNotifyAdSpliceDuration  OBJECT-TYPE
    SYNTAX       Unsigned32
    UNITS        "seconds"
    MAX-ACCESS   accessible-for-notify
    STATUS       current
    DESCRIPTION
        "The value of tmnxVdoNotifyAdSpliceDuration indicates the number of 
         seconds ads were played before the slice was aborted."
    ::= { tmnxVdoNotificationObjs 9 }

tmnxVdoNotifyClientAddrType  OBJECT-TYPE
    SYNTAX       InetAddressType
    MAX-ACCESS   accessible-for-notify
    STATUS       current
    DESCRIPTION
        "The value of tmnxVdoNotifyClientAddrType indicates the type of
         client address represented by tmnxVdoNotifyClientAddress."
    ::= { tmnxVdoNotificationObjs 10 }

tmnxVdoNotifyClientAddress  OBJECT-TYPE
    SYNTAX       InetAddress
    MAX-ACCESS   accessible-for-notify
    STATUS       current
    DESCRIPTION
        "The value of tmnxVdoNotifyClientAddress indicates the client address
         of a Real Time Transport Control Protocol (RTCP) stream."
    ::= { tmnxVdoNotificationObjs 11 }

tmnxVdoNotifyAnalyzerState  OBJECT-TYPE
    SYNTAX       TmnxVdoAnalyzerAlarmStates
    MAX-ACCESS   accessible-for-notify
    STATUS       current
    DESCRIPTION
        "The value of tmnxVdoNotifyAnalyzerState indicates the analyzer state 
         for the past 10 seconds of the video analyzer alarm."
    ::= { tmnxVdoNotificationObjs 12 }

-- ----------------------------------------------
-- Notifications 
-- ---------------------------------------------- 

tmnxVdoDuplicateSsrcId NOTIFICATION-TYPE 
    OBJECTS { 
        tmnxVdoGrpSrcSSRCId
    } 
    STATUS      current 
    DESCRIPTION 
        "A tmnxVdoDuplicateSsrcId notification is generated for a video channel 
         if it has a synchronization source (SSRC) identifier that conflicts 
         with another channel's SSRC identifier." 
    ::= { tmnxVdoNotifications 1 } 

tmnxVdoMdaSessionsLimitExceeded NOTIFICATION-TYPE 
    OBJECTS { 
        tmnxVdoGrpMdaActiveRtcpSessions
    } 
    STATUS      current 
    DESCRIPTION 
        "A tmnxVdoMdaSessionsLimitExceeded notification is generated when the 
         configuration exceeds the maximum number of Real Time Transport 
         Control Protocol (RTCP) sessions supported by a video Media Dependent 
         Adapter (MDA)." 
    ::= { tmnxVdoNotifications 2 } 

tmnxVdoMdaSGLimitExceeded NOTIFICATION-TYPE 
    OBJECTS {
        tmnxVdoGrpMdaChannels
    } 
    STATUS      current 
    DESCRIPTION 
        "A tmnxVdoMdaSGLimitExceeded notification is generated when the 
         configuration exceeds the maximum number of channels supported by a 
         video Media Dependent Adapter (MDA)." 
    ::= { tmnxVdoNotifications 3 } 

tmnxVdoMdaSessionsLimitCleared NOTIFICATION-TYPE 
    OBJECTS { 
        tmnxVdoGrpMdaActiveRtcpSessions
    } 
    STATUS      current 
    DESCRIPTION 
        "A tmnxVdoMdaSessionsLimitCleared notification is generated after a 
         tmnxVdoMdaSessionsLimitExceeded notification when the number of Real 
         Time Transport Control Protocol (RTCP) sessions goes back down to 
         the limit supported by a video Media Dependent Adapter (MDA)." 
    ::= { tmnxVdoNotifications 4 } 

tmnxVdoMdaSGLimitCleared NOTIFICATION-TYPE 
    OBJECTS {
        tmnxVdoGrpMdaChannels
    } 
    STATUS      current 
    DESCRIPTION 
        "A tmnxVdoMdaSGLimitCleared notification is generated after a 
         tmnxVdoMdaSGLimitExceeded notification when the number of channels 
         goes back down to the limit supported by a video Media Dependent 
         Adapter (MDA)."
    ::= { tmnxVdoNotifications 5 } 

tmnxVdoAdSpliceAbort NOTIFICATION-TYPE 
    OBJECTS { 
        tmnxVdoNotifysvcId,
        tmnxVdoNotifyIfName,
        tmnxVdoNotifyGrpAddrType,
        tmnxVdoNotifyGroupAddress,
        tmnxVdoNotifySrcAddrType,
        tmnxVdoNotifySourceAddress,
        tmnxVdoNotifyAdSpliceSessionId,
        tmnxVdoNotifyAdSpliceAbortTime,
        tmnxVdoNotifyAdSpliceDuration
    } 
    STATUS      current 
    DESCRIPTION 
        "A tmnxVdoAdSpliceAbort notification is generated when an ad splice is 
         aborted." 
    ::= { tmnxVdoNotifications 6 }

tmnxVdoClientSessionsLmtExceeded  NOTIFICATION-TYPE
    OBJECTS {
        tmnxVdoNotifyClientAddrType,
        tmnxVdoNotifyClientAddress
    }
    STATUS      current
    DESCRIPTION
        "A tmnxVdoClientSessionsLmtExceeded notification is generated when the
         number of Real Time Transport Control Protocol (RTCP) sessions per
         client IP address exceeds the limit supported by a video Media
         Dependent Adapter (MDA).

         The maximum number of RTCP sessions per client IP address supported
         by video MDA is specified by the value of the corresponding 
         TIMETRA-MCAST-PATH-MGMT-MIB::tmnxMcPathVdoPlcyMaxClntSessions object."
    ::= { tmnxVdoNotifications 7 }

tmnxVdoClientSessionsLmtCleared  NOTIFICATION-TYPE
    OBJECTS {
        tmnxVdoNotifyClientAddrType,
        tmnxVdoNotifyClientAddress
    }
    STATUS      current
    DESCRIPTION
        "A tmnxVdoClientSessionsLmtCleared notification is generated after a
         tmnxVdoClientSessionsLmtExceeded notification when the number of Real
         Time Transport Control Protocol (RTCP) sessions per client IP address
         goes back down to the limit supported by a video Media Dependent
         Adapter (MDA).

         The maximum number of RTCP sessions per client IP address supported
         by video MDA is specified by the value of the corresponding 
         TIMETRA-MCAST-PATH-MGMT-MIB::tmnxMcPathVdoPlcyMaxClntSessions object."
    ::= { tmnxVdoNotifications 8 }

tmnxVdoGrpSrcAnlyzrErrState NOTIFICATION-TYPE
    OBJECTS { tmnxVdoNotifysvcId,
              tmnxVdoNotifyIfName,
              tmnxVdoNotifyGrpAddrType,
              tmnxVdoNotifyGroupAddress,
              tmnxVdoNotifySrcAddrType,
              tmnxVdoNotifySourceAddress,
              tmnxVdoNotifyAnalyzerState              
               }
    STATUS     current
    DESCRIPTION
        "[CAUSE] The tmnxVdoGrpSrcAnlyzrErrState notification is raised whenever
        a video channel analyzer's error state changes to one of these values -
        TNC (Tech Non-Conformance), QOS (Quality of Service), POA (Program off 
        Air).

        [EFFECT] This trap is informational. No effects are caused by this trap.
        
        [RECOVERY] No recovery mechanism is required."
    ::= { tmnxVdoNotifications 9 }

tmnxVdoGrpSrcAnlyzrStClear NOTIFICATION-TYPE
    OBJECTS { tmnxVdoNotifysvcId,
              tmnxVdoNotifyIfName,
              tmnxVdoNotifyGrpAddrType,
              tmnxVdoNotifyGroupAddress,
              tmnxVdoNotifySrcAddrType,
              tmnxVdoNotifySourceAddress
               }
    STATUS     current
    DESCRIPTION
        "[CAUSE] The tmnxVdoGrpSrcAnlyzrStClear notification is raised whenever
        a video channel analyzer's error state has recovered from past errors 
        and is good for the last 10 seconds.  
    
        [EFFECT] This trap is informational. No effects are caused by this trap.
        
        [RECOVERY] No recovery mechanism is required."
    ::= { tmnxVdoNotifications 10 }

-- ----------------------------------------------
-- Compliance Statements
-- ----------------------------------------------

tmnxVdoV7v0Compliance   MODULE-COMPLIANCE
    STATUS      obsolete
    DESCRIPTION
        "The compliance statement for management of video features
        on version 7.0 of the Alcatel-Lucent SROS series systems."
    MODULE      --this module
        MANDATORY-GROUPS {
            tmnxVdoGlobalV7v0Group,
            tmnxVdoIfV7v0Group,
            tmnxVdoGrpV7v0Group,
            tmnxVdoAdiV7v0Group,
            tmnxVdoStatsV7v0Group,
            tmnxVdoGrpSrcV7v0Group,
            tmnxVdoNotificationsV7v0Group
        }
    ::= { tmnxVdoCompliances 1 }

tmnxVdoV8v0Compliance   MODULE-COMPLIANCE
    STATUS      obsolete
    DESCRIPTION
        "The compliance statement for management of video features
        on version 8.0 of the Alcatel-Lucent SROS series systems."
    MODULE      --this module
        MANDATORY-GROUPS {
            tmnxVdoGlobalV7v0Group,
            tmnxVdoIfV7v0Group,
            tmnxVdoGrpV7v0Group,
            tmnxVdoAdiV7v0Group,
            tmnxVdoStatsV7v0Group,
            tmnxVdoStatsV8v0Group,
            tmnxVdoNotificationsV7v0Group,
            tmnxVdoGrpSrcV7v0Group,
            tmnxVdoGrpV8v0Group,
            tmnxVdoIfV8v0Group,
            tmnxVdoNotificationsV8v0Group
        }
    ::= { tmnxVdoCompliances 2 }

tmnxVdoV9v0Compliance   MODULE-COMPLIANCE
    STATUS      current
    DESCRIPTION
        "The compliance statement for management of video features
        on version 9.0 of the Alcatel-Lucent SROS series systems."
    MODULE      --this module
        MANDATORY-GROUPS {
            tmnxVdoGlobalV7v0Group,
            tmnxVdoIfV7v0Group,
            tmnxVdoGrpV7v0Group,
            tmnxVdoAdiV7v0Group,
            tmnxVdoStatsV7v0Group,
            tmnxVdoStatsV9v0Group,
            tmnxVdoNotificationsV7v0Group,
            tmnxVdoGrpSrcV7v0Group,
            tmnxVdoGrpV8v0Group,
            tmnxVdoIfV8v0Group,
            tmnxVdoNotificationsV8v0Group
        }
    ::= { tmnxVdoCompliances 3 }


-- ----------------------------------------------
-- Units of Conformance
-- ----------------------------------------------

tmnxVdoGlobalV7v0Group   OBJECT-GROUP
    OBJECTS {
                 tmnxVdoIfTableLastChanged,
                 tmnxVdoGrpTableLastChanged,                 
                 tmnxVdoGrpMDATableLastChanged,
                 tmnxVdoIfAddrTableLastChanged,
                 tmnxVdoAdiChlTableLastChanged,
                 tmnxVdoAdiZoneChlTableLastChngd,
                 tmnxVdoIfScte30AdSrvrTblLstChngd
            }
    STATUS      current
    DESCRIPTION
        "The group of global objects supporting management of  
         the video features on version 7.0 of the Alcatel-Lucent SROS
         series systems."
    ::= { tmnxVdoGroups 1 }

tmnxVdoIfV7v0Group       OBJECT-GROUP
    OBJECTS {
        tmnxVdoIfRowStatus,
        tmnxVdoIfLastChanged,
        tmnxVdoIfAdminState,
        tmnxVdoIfOperState,
        tmnxVdoIfDescription,
        tmnxVdoIfVdoGrpId,
        tmnxVdoIfVrtrIfIndex,
        tmnxVdoIfIngressQosPolicyId,
        tmnxVdoIfEgressQosPolicyId,
        tmnxVdoIfAddrRowStatus,
        tmnxVdoIfAdi,
        tmnxVdoIfRTClientAddrType,
        tmnxVdoIfRTClientAddr,
        tmnxVdoIfGatewayAddrType,
        tmnxVdoIfGatewayAddr,
        tmnxVdoIfMcastSvcId,
        tmnxVdoIfIngressIpFilterId,
        tmnxVdoIfIngressMacFilterId,
        tmnxVdoIfEgressIpFilterId,
        tmnxVdoIfEgressMacFilterId,
        tmnxVdoIfScte30ControlAddrType,
        tmnxVdoIfScte30ControlAddr,
        tmnxVdoIfScte30DataAddrType,
        tmnxVdoIfScte30DataAddr,
        tmnxVdoIfSapId,
        tmnxVdoIfMcastProtocol,
        tmnxVdoIfSessions,
        tmnxVdoIfCpmProtectPolicyId,
        tmnxVdoIfScte30AdSrvrRowStatus
             }
    STATUS      current
    DESCRIPTION
        "The group of objects supporting management of video interfaces
         on version 7.0 of the Alcatel-Lucent SROS series systems."
    ::= { tmnxVdoGroups 2 }

tmnxVdoGrpV7v0Group       OBJECT-GROUP
    OBJECTS {
        tmnxVdoGrpDescription,
        tmnxVdoGrpAdminState,
        tmnxVdoGrpOperState,
        tmnxVdoGrpLocalRTServerState,
        tmnxVdoGrpFCCServerState,
        tmnxVdoGrpADIServerState,
        tmnxVdoGrpRowStatus,
        tmnxVdoGrpLastChanged,
        tmnxVdoGrpMdaRowStatus,
        tmnxVdoGrpMdaAdminState,
        tmnxVdoGrpMdaOperState,
        tmnxVdoGrpMdaUsedMemory,
        tmnxVdoGrpMdaAvailableMemory,
        tmnxVdoGrpMdaChannels,
        tmnxVdoGrpMdaChannelAllocFails,
        tmnxVdoGrpMdaMaxBwExceeded,
        tmnxVdoGrpMdaBwInUse,
        tmnxVdoGrpMdaActiveRtcpSessions,
        tmnxVdoGrpMdaEgressStreamResets,
        tmnxVdoGrpMdaIngressStreamResets,
        tmnxVdoGrpMdaAdStreamResets,
        tmnxVdoGrpMdaAdStreamAborts,
        tmnxVdoGrpMdaSsrcCollisions,        
        tmnxVdoGrpMdaRxDataPackets,
        tmnxVdoGrpMdaRxDataPacketsLow32,
        tmnxVdoGrpMdaRxDataPacketsHigh32,
        tmnxVdoGrpMdaRxDataOctets,
        tmnxVdoGrpMdaRxDataOctetsLow32,
        tmnxVdoGrpMdaRxDataOctetsHigh32,
        tmnxVdoGrpMdaRxDataPacketErrors,
        tmnxVdoGrpMdaRxDataPktErrsLow32,
        tmnxVdoGrpMdaRxDataPktErrsHigh32,
        tmnxVdoGrpMdaTxDataPackets,
        tmnxVdoGrpMdaTxDataPacketsLow32,
        tmnxVdoGrpMdaTxDataPacketsHigh32,
        tmnxVdoGrpMdaTxDataOctets,
        tmnxVdoGrpMdaTxDataOctetsLow32,
        tmnxVdoGrpMdaTxDataOctetsHigh32,
        tmnxVdoGrpMdaTxDataPacketErrors,
        tmnxVdoGrpMdaTxDataPktErrsLow32,
        tmnxVdoGrpMdaTxDataPktErrsHigh32,
        tmnxVdoGrpMdaRtcpParseErrors,
        tmnxVdoGrpMdaRtcpConfigErrors,
        tmnxVdoGrpMdaRtcpIpcErrors,
        tmnxVdoGrpMdaRtcpSgErrors,
        tmnxVdoGrpMdaRtcpSubErrors,
        tmnxVdoGrpMdaRtcpIntErrors,
        tmnxVdoGrpMdaTxLostPackets,
        tmnxVdoGrpMdaRequestedRtpPkts,
        tmnxVdoGrpMdaHighPktPoolLimitHit,
        tmnxVdoGrpMdaMallocFailures,
        tmnxVdoGrpMdaDentDroppedPkts
             }
    STATUS      current
    DESCRIPTION
        "The group of objects supporting management of video groups 
         on version 7.0 of the Alcatel-Lucent SROS series systems."
    ::= { tmnxVdoGroups 3 }

tmnxVdoAdiV7v0Group       OBJECT-GROUP
    OBJECTS {
        tmnxVdoAdiChlRowStatus,
        tmnxVdoAdiChlName,
        tmnxVdoAdiChlDescription,
        tmnxVdoAdiZoneChlRowStatus,
        tmnxVdoAdiZoneChlName,
        tmnxVdoAdiChlForwardScte35
             }
    STATUS      current
    DESCRIPTION
        "The group of objects supporting management of Ad-Insertion (ADI)
         feature on version 7.0 of the Alcatel-Lucent SROS series systems."
    ::= { tmnxVdoGroups 4 }

tmnxVdoStatsV7v0Group       OBJECT-GROUP
    OBJECTS {
        tmnxVdoGrpSrcStreamType,
        tmnxVdoGrpSrcVdoGrpId,
        tmnxVdoGrpSrcAdminRTBufferSize,
        tmnxVdoGrpSrcSSRCId,
        tmnxVdoGrpSrcUDPSrcPort,
        tmnxVdoGrpSrcUDPDestPort,
        tmnxVdoGrpSrcUptime,
        tmnxVdoGrpSrcAdminBW,
        tmnxVdoGrpSrcBufferSize,
        tmnxVdoGrpSrcRxBytes,
        tmnxVdoGrpSrcRxPackets,
        tmnxVdoGrpSrcRxInvalidPackets,
        tmnxVdoGrpSrcTxBytes,
        tmnxVdoGrpSrcTxPackets,
        tmnxVdoGrpSrcTxFailedPackets,
        tmnxVdoGrpSrcRTClientAdminState,
        tmnxVdoGrpSrcRTClntRTSvrAddrType,
        tmnxVdoGrpSrcRTClntRTSvrAddr,
        tmnxVdoGrpSrcRTClientRTSrvrPort,
        tmnxVdoGrpSrcRTClientRxReTxBytes,
        tmnxVdoGrpSrcRTClientRxReTxPkts,
        tmnxVdoGrpSrcRTClientTxRTReq,
        tmnxVdoGrpSrcRTClientTxRTReqReTx,
        tmnxVdoGrpSrcRTClientGapsDetectd,
        tmnxVdoGrpSrcRTClientFailedReq,
        tmnxVdoGrpSrcRTSrvrAdminState,
        tmnxVdoGrpSrcRTSrvrRtpPktsReq,
        tmnxVdoGrpSrcRTSrvrRxRTReq,
        tmnxVdoGrpSrcRTSrvrRxFailedReq,
        tmnxVdoGrpSrcRTSrvrTxRTReplies,
        tmnxVdoGrpSrcRTSrvrTxBytes,
        tmnxVdoGrpSrcRTSrvrTxPackets,
        tmnxVdoGrpSrcFCCSrvrAdminState,
        tmnxVdoGrpSrcFCCSrvrChnlType,
        tmnxVdoGrpSrcFCCSrvrRxFCCReq,
        tmnxVdoGrpSrcFCCSrvrRxFailedReq,
        tmnxVdoGrpSrcFCCSrvrTxFCCReplies,
        tmnxVdoGrpSrcFCCSrvrTxBytes,
        tmnxVdoGrpSrcFCCSrvrTxPackets,
        tmnxVdoGrpSrcADIAdminState,
        tmnxVdoGrpSrcADICurrentState,
        tmnxVdoGrpSrcADIPATVersion,
        tmnxVdoGrpSrcADIPMTVersion,
        tmnxVdoGrpSrcADIPATChanges,
        tmnxVdoGrpSrcADIPMTChanges,
        tmnxVdoGrpSrcADIRxPackets,
        tmnxVdoGrpSrcADITxPackets,
        tmnxVdoGrpSrcADIRxSCTE35Msgs,
        tmnxVdoGrpSrcADIRxSCTE35MsgEnc,
        tmnxVdoGrpSrcADIRxSCTE35MsgUnsup,
        tmnxVdoGrpSrcADIRxSCTE35MsgDisc,
        tmnxVdoGrpSrcADIUnsuppTSLenPkts,
        tmnxVdoGrpSrcRTClientPort,
        tmnxVdoGrpSrcDupSeqNumber,
        tmnxVdoSGV1RxBytesLow32,
        tmnxVdoSGV1RxBytesHigh32,
        tmnxVdoSGV1RxPacketsLow32,
        tmnxVdoSGV1RxPacketsHigh32,
        tmnxVdoSGV1RxInvalidPacketsLow32,
        tmnxVdoSGV1RxInvalidPacketsHgh32,
        tmnxVdoSGV1TxBytesLow32,
        tmnxVdoSGV1TxBytesHigh32,
        tmnxVdoSGV1TxPacketsLow32,
        tmnxVdoSGV1TxPacketsHigh32,
        tmnxVdoSGV1TxFailedPacketsLow32,
        tmnxVdoSGV1TxFailedPacketsHigh32,
        tmnxVdoSGV1RTClntRxReTxBytsLow32,
        tmnxVdoSGV1RTClntRxReTxBytsHgh32,
        tmnxVdoSGV1RTClntRxReTxPktsLow32,
        tmnxVdoSGV1RTClntRxReTxPktsHgh32,
        tmnxVdoSGV1RTSrvrTxBytesLow32,
        tmnxVdoSGV1RTSrvrTxBytesHigh32,
        tmnxVdoSGV1RTSrvrTxPacketsLow32,
        tmnxVdoSGV1RTSrvrTxPacketsHigh32,
        tmnxVdoSGV1FCCSrvrTxBytesLow32,
        tmnxVdoSGV1FCCSrvrTxBytesHigh32,
        tmnxVdoSGV1FCCSrvrTxPacketsLow32,
        tmnxVdoSGV1FCCSrvrTxPacketsHgh32,
        tmnxVdoSGV1ADIRxPacketsLow32,
        tmnxVdoSGV1ADIRxPacketsHigh32,
        tmnxVdoSGV1ADITxPacketsLow32,
        tmnxVdoSGV1ADITxPacketsHigh32,
        tmnxVdoSessionSSRCId,
        tmnxVdoSessionUpTime,
        tmnxVdoSessionExpireTime,
        tmnxVdoSessionCName,
        tmnxVdoSessionDestAddrType,
        tmnxVdoSessionDestAddr,
        tmnxVdoSessionRxFCCRequests,
        tmnxVdoSessionTxFCCReplies,
        tmnxVdoSessionTxFCCPackets,
        tmnxVdoSessionTxFCCOctets,
        tmnxVdoSessionTxFCCFailedPackets,
        tmnxVdoSessionRxRTRequests,
        tmnxVdoSessionTxRTReplies,
        tmnxVdoSessionTxRTPackets,
        tmnxVdoSessionTxRTOctets,
        tmnxVdoSessionTxRTFailedPackets,
        tmnxVdoSessionRequestedRtpPkts,
        tmnxVdoIfStatHdRTServerState,
        tmnxVdoIfStatSdRTServerState,
        tmnxVdoIfStatPipRTServerState,
        tmnxVdoIfStatRTSvrSdRtpPktsReq,
        tmnxVdoIfStatRTSvrHdRtpPktsReq,
        tmnxVdoIfStatRTSvrPipRtpPktsReq,
        tmnxVdoIfStatRTSvrRxSdRTReq,
        tmnxVdoIfStatRTSvrRxSdFailedReq,
        tmnxVdoIfStatRTSvrRxHdRTReq,
        tmnxVdoIfStatRTSvrRxHdFailedReq,
        tmnxVdoIfStatRTSvrRxPipRTReq,
        tmnxVdoIfStatRTSvrRxPipFailedReq,
        tmnxVdoIfStatRTSvrTxSdRTReplies,
        tmnxVdoIfStatRTSvrTxSdBytes,
        tmnxVdoIfStatRTSvrTxSdPackets,
        tmnxVdoIfStatRTSvrTxHdRTReplies,
        tmnxVdoIfStatRTSvrTxHdBytes,
        tmnxVdoIfStatRTSvrTxHdPackets,
        tmnxVdoIfStatRTSvrTxPipRTReplies,
        tmnxVdoIfStatRTSvrTxPipBytes,
        tmnxVdoIfStatRTSvrTxPipPackets,
        tmnxVdoIfStatHdFCCServerMode,
        tmnxVdoIfStatSdFCCServerMode,
        tmnxVdoIfStatPipFCCServerMode,
        tmnxVdoIfStatFCCSrRxSdFCCReq,
        tmnxVdoIfStatFCCSrRxSdFailedReq,
        tmnxVdoIfStatFCCSrRxHdFCCReq,
        tmnxVdoIfStatFCCSrRxHdFailedReq,
        tmnxVdoIfStatFCCSrRxPipFCCReq,
        tmnxVdoIfStatFCCSrRxPipFailedReq,
        tmnxVdoIfStatFCCSrTxSdFCCReplies,
        tmnxVdoIfStatFCCSrTxSdBytes,
        tmnxVdoIfStatFCCSrTxSdPackets,
        tmnxVdoIfStatFCCSrTxHdFCCReplies,
        tmnxVdoIfStatFCCSrTxHdBytes,
        tmnxVdoIfStatFCCSrTxHdPackets,
        tmnxVdoIfStatFCCSrTxPipFCCRplies,
        tmnxVdoIfStatFCCSrTxPipBytes,
        tmnxVdoIfStatFCCSrTxPipPackets,
        tmnxVdoIfStatTxFailedPackets,
        tmnxVdoIfScte30TcpSessions,
        tmnxVdoIfScte30InitSessions,
        tmnxVdoIfStLowRTSvrSdRtpPktsReq,
        tmnxVdoIfStLowRTSvrHdRtpPktsReq,
        tmnxVdoIfStLowRTSvrPipRtpPktsReq,
        tmnxVdoIfStLowRTSvrRxSdRTReq,
        tmnxVdoIfStLowRTSvrRxSdFailedReq,
        tmnxVdoIfStLowRTSvrRxHdRTReq,
        tmnxVdoIfStLowRTSvrRxHdFailedReq,
        tmnxVdoIfStLowRTSvrRxPipRTReq,
        tmnxVdoIfStLowRTSvrRxPipFailedRq,
        tmnxVdoIfStLowRTSvrTxSdRTReplies,
        tmnxVdoIfStLowRTSvrTxSdBytes,
        tmnxVdoIfStLowRTSvrTxSdPackets,
        tmnxVdoIfStLowRTSvrTxHdRTReplies,
        tmnxVdoIfStLowRTSvrTxHdBytes,
        tmnxVdoIfStLowRTSvrTxHdPackets,
        tmnxVdoIfStLowRTSvrTxPipRTReplis,
        tmnxVdoIfStLowRTSvrTxPipBytes,
        tmnxVdoIfStLowRTSvrTxPipPackets,
        tmnxVdoIfStLowFCCSrRxSdFCCReq,
        tmnxVdoIfStLowFCCSrRxSdFailedReq,
        tmnxVdoIfStLowFCCSrRxHdFCCReq,
        tmnxVdoIfStLowFCCSrRxHdFailedReq,
        tmnxVdoIfStLowFCCSrRxPipFCCReq,
        tmnxVdoIfStLowFCCSrRxPipFailedRq,
        tmnxVdoIfStLowFCCSrTxSdFCCReplis,
        tmnxVdoIfStLowFCCSrTxSdBytes,
        tmnxVdoIfStLowFCCSrTxSdPackets,
        tmnxVdoIfStLowFCCSrTxHdFCCReplis,
        tmnxVdoIfStLowFCCSrTxHdBytes,
        tmnxVdoIfStLowFCCSrTxHdPackets,
        tmnxVdoIfStLowFCCSrTxPipFCCRplis,
        tmnxVdoIfStLowFCCSrTxPipBytes,
        tmnxVdoIfStLowFCCSrTxPipPackets,
        tmnxVdoIfStLowTxFailedPackets,
        tmnxVdoIfStHghRTSvrSdRtpPktsReq,
        tmnxVdoIfStHghRTSvrHdRtpPktsReq,
        tmnxVdoIfStHghRTSvrPipRtpPktsReq,
        tmnxVdoIfStHghRTSvrRxSdRTReq,
        tmnxVdoIfStHghRTSvrRxSdFailedReq,
        tmnxVdoIfStHghRTSvrRxHdRTReq,
        tmnxVdoIfStHghRTSvrRxHdFailedReq,
        tmnxVdoIfStHghRTSvrRxPipRTReq,
        tmnxVdoIfStHghRTSvrRxPipFailedRq,
        tmnxVdoIfStHghRTSvrTxSdRTReplies,
        tmnxVdoIfStHghRTSvrTxSdBytes,
        tmnxVdoIfStHghRTSvrTxSdPackets,
        tmnxVdoIfStHghRTSvrTxHdRTReplies,
        tmnxVdoIfStHghRTSvrTxHdBytes,
        tmnxVdoIfStHghRTSvrTxHdPackets,
        tmnxVdoIfStHghRTSvrTxPipRTReplis,
        tmnxVdoIfStHghRTSvrTxPipBytes,
        tmnxVdoIfStHghRTSvrTxPipPackets,
        tmnxVdoIfStHghFCCSrRxSdFCCReq,
        tmnxVdoIfStHghFCCSrRxSdFailedReq,
        tmnxVdoIfStHghFCCSrRxHdFCCReq,
        tmnxVdoIfStHghFCCSrRxHdFailedReq,
        tmnxVdoIfStHghFCCSrRxPipFCCReq,
        tmnxVdoIfStHghFCCSrRxPipFailedRq,
        tmnxVdoIfStHghFCCSrTxSdFCCReplis,
        tmnxVdoIfStHghFCCSrTxSdBytes,
        tmnxVdoIfStHghFCCSrTxSdPackets,
        tmnxVdoIfStHghFCCSrTxHdFCCReplis,
        tmnxVdoIfStHghFCCSrTxHdBytes,
        tmnxVdoIfStHghFCCSrTxHdPackets,
        tmnxVdoIfStHghFCCSrTxPipFCCRplis,
        tmnxVdoIfStHghFCCSrTxPipBytes,
        tmnxVdoIfStHghFCCSrTxPipPackets,
        tmnxVdoIfStHghTxFailedPackets,
        tmnxVdoPIDType,
        tmnxVdoPIDMpegStreamType,
        tmnxVdoPIDLanguage,
        tmnxVdoSGAdiServerUptime,
        tmnxVdoSGAdiInitReq,
        tmnxVdoSGAdiSucInitResp,
        tmnxVdoSGAdiUnsucInitResp,
        tmnxVdoSGAdiAliveReq,
        tmnxVdoSGAdiSucAliveResp,
        tmnxVdoSGAdiUnSucAliveResp,
        tmnxVdoSGAdiCueReq,
        tmnxVdoSGAdiSucCueResp,
        tmnxVdoSGAdiUnsucCueResp,
        tmnxVdoSGAdiAbortReq,
        tmnxVdoSGAdiSucAbortResp,
        tmnxVdoSGAdiUnsucAbortResp,
        tmnxVdoSGAdiUnknownSCTE30Req,
        tmnxVdoSGAdiSpliceReq,
        tmnxVdoSGAdiSucSpliceResp,
        tmnxVdoSGAdiUnsucSpliceResp,
        tmnxVdoSGAdiSucSpliceInCompResp,
        tmnxVdoSGAdiSucSpliceOutCompResp,
        tmnxVdoSGAdiUnsucSpliceOutComRes,
        tmnxVdoSGSpliceAdServerAddrType,
        tmnxVdoSGSpliceAdServerAddr,
        tmnxVdoSGSpliceStatus,
        tmnxVdoSGSpliceDurationReq,
        tmnxVdoSGSpliceDurationPlayed,
        tmnxVdoSGSpliceRate,
        tmnxVdoSGSpliceSessionId,
        tmnxVdoSGSplicePriorSessionId,
        tmnxVdoSGSpliceAbortReason,
        tmnxVdoSGSpliceSpliceInSeqNum,
        tmnxVdoSGSpliceSpliceOutSeqNum,
        tmnxVdoSGSpliceNumBlkFrames,
        tmnxVdoSGSpliceBlkFramePTS,
        tmnxVdoSGSpliceMaxAdPTS,
        tmnxVdoSGSpliceMinNwPTS,
        tmnxVdoSGAdiMinPort,
        tmnxVdoSGAdiMaxPort,
        tmnxVdoSGAdiChlName
            }
    STATUS      current
    DESCRIPTION
        "The group of objects supporting FCC or RD or ADI statistics on version 
         7.0 of the Alcatel-Lucent SROS series systems."
    ::= { tmnxVdoGroups 5 }

tmnxVdoNotifyObjsV7v0Group   OBJECT-GROUP
    OBJECTS {
        tmnxVdoNotifysvcId,
        tmnxVdoNotifyIfName,
        tmnxVdoNotifyGrpAddrType,
        tmnxVdoNotifyGroupAddress,
        tmnxVdoNotifySrcAddrType,
        tmnxVdoNotifySourceAddress,
        tmnxVdoNotifyAdSpliceSessionId,
        tmnxVdoNotifyAdSpliceAbortTime,
        tmnxVdoNotifyAdSpliceDuration,
        tmnxVdoNotifyClientAddrType,
        tmnxVdoNotifyClientAddress
            }
    STATUS        current
    DESCRIPTION
        "The group of objects supporting video notifications on version 7.0 of 
         the Alcatel-Lucent SROS series systems."
    ::= { tmnxVdoGroups 6 }

tmnxVdoNotificationsV7v0Group NOTIFICATION-GROUP
    NOTIFICATIONS { 
        tmnxVdoDuplicateSsrcId,
        tmnxVdoMdaSessionsLimitExceeded,
        tmnxVdoMdaSGLimitExceeded,
        tmnxVdoMdaSessionsLimitCleared,
        tmnxVdoMdaSGLimitCleared,
        tmnxVdoAdSpliceAbort,
        tmnxVdoClientSessionsLmtExceeded,
        tmnxVdoClientSessionsLmtCleared
                  }
    STATUS        current
    DESCRIPTION
        "The group of notifications supporting management of video features
         on version 7.0 of the Alcatel-Lucent SROS series systems."
    ::= { tmnxVdoGroups 7 }

tmnxVdoGrpV8v0Group       OBJECT-GROUP
    OBJECTS {
        tmnxVdoGrpMdaBwPeak,
        tmnxVdoGrpResvRet,
        tmnxVdoGrpAnalyzerState,
        tmnxVdoGrpStreamSelectionState,
        tmnxVdoGrpMdaCurTotalRetBw,
        tmnxVdoGrpMdaPeakRetBw,
        tmnxVdoGrpMdaCurFccBw,
        tmnxVdoGrpMdaFccDropCntReq,
        tmnxVdoGrpMdaMcRtcp,  
        tmnxVdoGrpMdaMcRtcpLow32,  
        tmnxVdoGrpMdaMcRtcpHigh32,  
        tmnxVdoGrpMdaMcRudp,
        tmnxVdoGrpMdaMcRudpLow32,
        tmnxVdoGrpMdaMcRudpHigh32,
        tmnxVdoGrpMdaMcRetReqCrt,
        tmnxVdoGrpMdaMcRetReqCrtLow32,  
        tmnxVdoGrpMdaMcRetReqCrtHigh32,
        tmnxVdoGrpMdaRetReqQnc,
        tmnxVdoGrpMdaRetReqQncLow32,
        tmnxVdoGrpMdaRetReqQncHigh32,
        tmnxVdoGrpMdaPktsLostInSeq10,
        tmnxVdoGrpMdaPktsLostInSeq20,
        tmnxVdoGrpMdaPktsLostInSeq30,
        tmnxVdoGrpMdaPktsLostInSeq40,
        tmnxVdoGrpMdaPktsLostInSeqMore
            }
    STATUS      current
    DESCRIPTION
        "The group of objects supporting management of video groups 
         on version 8.0 of the Alcatel-Lucent SROS series systems."
    ::= { tmnxVdoGroups 8 }

tmnxVdoIfV8v0Group       OBJECT-GROUP
    OBJECTS {
        tmnxVdoIfRTMcastReply,
        tmnxVdoIfRTCount, 
        tmnxVdoIfRTInterval,
        tmnxVdoIfRTHoldTime,
        tmnxVdoIfAcctPolicyId,
        tmnxVdoIfOutputFormat
             }
    STATUS      current
    DESCRIPTION
        "The group of objects supporting management of video interfaces
         on version 8.0 of the Alcatel-Lucent SROS series systems."
    ::= { tmnxVdoGroups 9 }

tmnxVdoStatsV8v0Group       OBJECT-GROUP
    OBJECTS {
        tmnxVdoGrpSrcRTSTxMcRetPkts,  
        tmnxVdoGrpSrcRTSTxMcRetPktsL32,  
        tmnxVdoGrpSrcRTSTxMcRetPktsH32,  
        tmnxVdoGrpSrcRTSTxMcRetBytes,
        tmnxVdoGrpSrcRTSTxMcRetBytesL32,
        tmnxVdoGrpSrcRTSTxMcRetBytesH32,
        tmnxVdoGrpSrcRTSTxMcRetErrs,   
        tmnxVdoGrpSrcRTSTxMcRetErrsL32,   
        tmnxVdoGrpSrcRTSTxMcRetErrsH32,
        tmnxVdoGrpSrcRTSRetReqQnc,   
        tmnxVdoGrpSrcRTSRetReqQncL32,   
        tmnxVdoGrpSrcRTSRetReqQncH32,
        tmnxVdoGrpSrcRTSRetReqCrt,  
        tmnxVdoGrpSrcRTSRetReqCrtL32,  
        tmnxVdoGrpSrcRTSRetReqCrtH32,
        tmnxVdoGrpSrcFccMinDuration,
        tmnxVdoGrpSrcAudioReorder,
        tmnxVdoGrpSrcRxBytesSaved,
        tmnxVdoGrpSrcRxBytesSavedL32,
        tmnxVdoGrpSrcRxBytesSavedH32,
        tmnxVdoGrpSrcRxPacketsSaved,
        tmnxVdoGrpSrcRxPacketsSavedL32,
        tmnxVdoGrpSrcRxPacketsSavedH32,
        tmnxVdoGrpSrcStatOperBW,
        tmnxVdoGrpSrcRouterIfName,
        tmnxVdoIfStatRTSSdMcRdPktsReq,
        tmnxVdoIfStatRTSSdMcRdPktsReqL32,
        tmnxVdoIfStatRTSSdMcRdPktsReqH32,
        tmnxVdoIfStatRTSHDMcRdPktsReq,
        tmnxVdoIfStatRTSHDMcRdPktsReqL32,
        tmnxVdoIfStatRTSHDMcRdPktsReqH32,
        tmnxVdoIfStatRTSPipMcRdPktReq,
        tmnxVdoIfStatRTSPipMcRdPktReqL32,
        tmnxVdoIfStatRTSPipMcRdPktReqH32,
        tmnxVdoSessionRTReqQuenched,
        tmnxVdoSessionRTMcastReqCreated,  
        tmnxVdoSessionPktsLostInSeq10,
        tmnxVdoSessionPktsLostInSeq20,
        tmnxVdoSessionPktsLostInSeq30,
        tmnxVdoSessionPktsLostInSeq40,
        tmnxVdoSessionPktsLostInSeqMore,
        tmnxVdoIfStatSDPktLostInSeq10,
        tmnxVdoIfStatSDPktLostInSeq20,
        tmnxVdoIfStatSDPktLostInSeq30,
        tmnxVdoIfStatSDPktLostInSeq40,
        tmnxVdoIfStatSDPktLostInSeqMore,
        tmnxVdoIfStatHDPktLostInSeq10,
        tmnxVdoIfStatHDPktLostInSeq20,
        tmnxVdoIfStatHDPktLostInSeq30,
        tmnxVdoIfStatHDPktLostInSeq40,
        tmnxVdoIfStatHDPktLostInSeqMore,
        tmnxVdoIfStatPipPktLostInSeq10,
        tmnxVdoIfStatPipPktLostInSeq20,
        tmnxVdoIfStatPipPktLostInSeq30,
        tmnxVdoIfStatPipPktLostInSeq40,
        tmnxVdoIfStatPipPktLostInSeqMore,
        tmnxVdoIfStatExtRxRtcpAppRepSum,
        tmnxVdoIfStatExtRxRtcpAppRepSumL,
        tmnxVdoIfStatExtRxRtcpAppRepSumH,
        tmnxVdoIfStatExtRxRtcpAppReqSum,
        tmnxVdoIfStatExtRxRtcpAppReqSumL,
        tmnxVdoIfStatExtRxRtcpAppReqSumH,
        tmnxVdoIfStatExtRxRtcpFbRepSum,   
        tmnxVdoIfStatExtRxRtcpFbRepSumL,
        tmnxVdoIfStatExtRxRtcpFbRepSumH,
        tmnxVdoIfStatExtRxRtcpFbReqSum,   
        tmnxVdoIfStatExtRxRtcpFbReqSumL,
        tmnxVdoIfStatExtRxRtcpFbReqSumH,
        tmnxVdoIfStatExtRxRudpFbRepSum,   
        tmnxVdoIfStatExtRxRudpFbRepSumL,
        tmnxVdoIfStatExtRxRudpFbRepSumH,
        tmnxVdoIfStatExtTxFccPktsSum,   
        tmnxVdoIfStatExtTxFccPktsSumL,
        tmnxVdoIfStatExtTxFccPktsSumH,
        tmnxVdoIfStatExtTxFccOctetsSum,   
        tmnxVdoIfStatExtTxFccOctetsSumL,
        tmnxVdoIfStatExtTxFccOctetsSumH,
        tmnxVdoIfStatExtTxRetPktsSum,   
        tmnxVdoIfStatExtTxRetPktsSumL,
        tmnxVdoIfStatExtTxRetPktsSumH,
        tmnxVdoIfStatExtTxRetOctetsSum,   
        tmnxVdoIfStatExtTxRetOctetsSumL,
        tmnxVdoIfStatExtTxRetOctetsSumH,
        tmnxVdoIfStatExtTxRudpPktsSum,   
        tmnxVdoIfStatExtTxRudpPktsSumL,
        tmnxVdoIfStatExtTxRudpPktsSumH,
        tmnxVdoIfStatExtTxRudpByteSum,   
        tmnxVdoIfStatExtTxRudpByteSumL,
        tmnxVdoIfStatExtTxRudpByteSumH,
        tmnxVdoGrpSrcVqmGoodSecs,
        tmnxVdoGrpSrcVqmErrSecs,
        tmnxVdoGrpSrcVqmDegrSecs,
        tmnxVdoGrpSrcVqmImpairSecs,
        tmnxVdoGrpSrcVqmPmtRepErrSecs,
        tmnxVdoGrpSrcVqmPmtRepDegSecs,
        tmnxVdoGrpSrcVqmPmtRepImpSecs,
        tmnxVdoGrpSrcVqmPmtSyntxErrSecs,
        tmnxVdoGrpSrcVqmPatRepErrSecs,
        tmnxVdoGrpSrcVqmPatRepDegSecs,
        tmnxVdoGrpSrcVqmPatRepImpSecs,
        tmnxVdoGrpSrcVqmPatSyntxErrSecs,
        tmnxVdoGrpSrcVqmPcrRepErrSecs,
        tmnxVdoGrpSrcVqmPcrRepDegSecs,
        tmnxVdoGrpSrcVqmPcrRepImpSecs,
        tmnxVdoGrpSrcVqmSyncByteErrSecs,
        tmnxVdoGrpSrcVqmSyncLossSecs,
        tmnxVdoGrpSrcVqmCatErrSecs,
        tmnxVdoGrpSrcVqmUnrefPidErrSecs,
        tmnxVdoGrpSrcVqmMDIDelayFactor,
        tmnxVdoGrpSrcVqmMDILossRate,
        tmnxVdoGrpSrcVqmMinGOPLength,
        tmnxVdoGrpSrcVqmMinFrmPerSec,
        tmnxVdoGrpSrcVqmAvgGOPLength,
        tmnxVdoGrpSrcVqmAvgFrmPerSec,
        tmnxVdoGrpSrcVqmMaxGOPLength,
        tmnxVdoGrpSrcVqmMaxFrmPerSec, 
        tmnxVdoGrpSrcVqmGoodIFrames,
        tmnxVdoGrpSrcVqmBadIFrames,
        tmnxVdoGrpSrcVqmGoodPFrames,
        tmnxVdoGrpSrcVqmBadPFrames,
        tmnxVdoGrpSrcVqmGoodBFrames,
        tmnxVdoGrpSrcVqmBadBFrames,
        tmnxVdoGrpSrcVqmTrafficLossSecs,
        tmnxVdoGrpSrcVqmSCTE35ErrSecs,
        tmnxVdoGrpSrcVqmOperAnalyzerSt,
        tmnxVdoGrpSrcVqmOperCcError,   
        tmnxVdoGrpSrcVqmOperPatRepError,
        tmnxVdoGrpSrcVqmOperTncPatRep,
        tmnxVdoGrpSrcVqmOperQosPatRep,
        tmnxVdoGrpSrcVqmOperPoaPatRep,
        tmnxVdoGrpSrcVqmOperPatSyntax,
        tmnxVdoGrpSrcVqmOperPcrRepError,
        tmnxVdoGrpSrcVqmOperTncPcrRep,
        tmnxVdoGrpSrcVqmOperQosPcrRep, 
        tmnxVdoGrpSrcVqmOperPoaPcrRep,
        tmnxVdoGrpSrcVqmOperVidPIDAbs,
        tmnxVdoGrpSrcVqmOperPIDPmtUnref,
        tmnxVdoGrpSrcVqmOperPmtRepError,
        tmnxVdoGrpSrcVqmOperTncPmtRep,
        tmnxVdoGrpSrcVqmOperQosPmtRep,
        tmnxVdoGrpSrcVqmOperPoaPmtRep,
        tmnxVdoGrpSrcVqmOperPmtSyntax,
        tmnxVdoGrpSrcVqmOperSCTE35Error, 
        tmnxVdoGrpSrcVqmOperTeiError,  
        tmnxVdoGrpSrcVqmOperTsSyncLoss, 
        tmnxVdoGrpSrcVqmOperNonVidPIDAbs,
        tmnxVdoGrpSrcVqmOperReportAlarm,
        tmnxVdoPIDCcErrSecs,
        tmnxVdoPIDTeiErrSecs,
        tmnxVdoPIDAbsentErrSecs,
        tmnxVdoPIDBitrate,
        tmnxVdoPIDIsPCR,
        tmnxVdoGrpSrcExtMaxRtpTsDelta,
        tmnxVdoGrpSrcExtMaxTicksDelta,
        tmnxVdoGrpSrcExtMaxTicksDeltaL32,
        tmnxVdoGrpSrcExtMaxTicksDeltaH32,
        tmnxVdoGrpSrcExtCurTsJitter,
        tmnxVdoGrpSrcExtCurTsJitterL32,
        tmnxVdoGrpSrcExtCurTsJitterH32,
        tmnxVdoGrpSrcExtMaxTsJitter,
        tmnxVdoGrpSrcExtMaxTsJitterL32,
        tmnxVdoGrpSrcExtMaxTsJitterH32,
        tmnxVdoGrpSrcNumFccDentedPkts
            }
    STATUS      obsolete
    DESCRIPTION
        "The group of objects supporting Fast Channel Change (FCC) or 
         Reliable Delivery (RD) or Ad Insert (ADI) statistics on version 
         8.0 of the Alcatel-Lucent SROS series systems."
    ::= { tmnxVdoGroups 10 }

tmnxVdoGrpSrcV7v0Group       OBJECT-GROUP
    OBJECTS {
        tmnxVdoGrpSrcRxDupSsrcDrops,
        tmnxVdoGrpSrcDupSsrc
            }
    STATUS      current
    DESCRIPTION
        "The group of objects supporting multicast group statistics on version 
         7.0 of the Alcatel-Lucent SROS series systems."
    ::= { tmnxVdoGroups 11 }

tmnxVdoNotifyObjsV8v0Group   OBJECT-GROUP
    OBJECTS {
        tmnxVdoNotifyAnalyzerState
            }
    STATUS        current
    DESCRIPTION
        "The group of objects supporting video notifications on version 8.0 of 
         the Alcatel-Lucent SROS series systems."
    ::= { tmnxVdoGroups 12 }

tmnxVdoNotificationsV8v0Group NOTIFICATION-GROUP
    NOTIFICATIONS { 
        tmnxVdoGrpSrcAnlyzrErrState,
        tmnxVdoGrpSrcAnlyzrStClear
                  }
    STATUS        current
    DESCRIPTION
        "The group of notifications supporting management of video features
         on version 8.0 of the Alcatel-Lucent SROS series systems."
    ::= { tmnxVdoGroups 13 }

tmnxVdoStatsV9v0Group       OBJECT-GROUP
    OBJECTS {
        tmnxVdoGrpSrcRTSTxMcRetPkts,  
        tmnxVdoGrpSrcRTSTxMcRetPktsL32,  
        tmnxVdoGrpSrcRTSTxMcRetPktsH32,  
        tmnxVdoGrpSrcRTSTxMcRetBytes,
        tmnxVdoGrpSrcRTSTxMcRetBytesL32,
        tmnxVdoGrpSrcRTSTxMcRetBytesH32,
        tmnxVdoGrpSrcRTSTxMcRetErrs,   
        tmnxVdoGrpSrcRTSTxMcRetErrsL32,   
        tmnxVdoGrpSrcRTSTxMcRetErrsH32,
        tmnxVdoGrpSrcRTSRetReqQnc,   
        tmnxVdoGrpSrcRTSRetReqQncL32,   
        tmnxVdoGrpSrcRTSRetReqQncH32,
        tmnxVdoGrpSrcRTSRetReqCrt,  
        tmnxVdoGrpSrcRTSRetReqCrtL32,  
        tmnxVdoGrpSrcRTSRetReqCrtH32,
        tmnxVdoGrpSrcFccMinDuration,
        tmnxVdoGrpSrcAudioReorder,
        tmnxVdoGrpSrcRxBytesSaved,
        tmnxVdoGrpSrcRxBytesSavedL32,
        tmnxVdoGrpSrcRxBytesSavedH32,
        tmnxVdoGrpSrcRxPacketsSaved,
        tmnxVdoGrpSrcRxPacketsSavedL32,
        tmnxVdoGrpSrcRxPacketsSavedH32,
        tmnxVdoGrpSrcStatOperBW,
        tmnxVdoGrpSrcRouterIfName,
        tmnxVdoIfStatRTSSdMcRdPktsReq,
        tmnxVdoIfStatRTSSdMcRdPktsReqL32,
        tmnxVdoIfStatRTSSdMcRdPktsReqH32,
        tmnxVdoIfStatRTSHDMcRdPktsReq,
        tmnxVdoIfStatRTSHDMcRdPktsReqL32,
        tmnxVdoIfStatRTSHDMcRdPktsReqH32,
        tmnxVdoIfStatRTSPipMcRdPktReq,
        tmnxVdoIfStatRTSPipMcRdPktReqL32,
        tmnxVdoIfStatRTSPipMcRdPktReqH32,
        tmnxVdoSessionRTReqQuenched,
        tmnxVdoSessionRTMcastReqCreated,  
        tmnxVdoSessionPktsLostInSeq10,
        tmnxVdoSessionPktsLostInSeq20,
        tmnxVdoSessionPktsLostInSeq30,
        tmnxVdoSessionPktsLostInSeq40,
        tmnxVdoSessionPktsLostInSeqMore,
        tmnxVdoIfStatSDPktLostInSeq10,
        tmnxVdoIfStatSDPktLostInSeq20,
        tmnxVdoIfStatSDPktLostInSeq30,
        tmnxVdoIfStatSDPktLostInSeq40,
        tmnxVdoIfStatSDPktLostInSeqMore,
        tmnxVdoIfStatHDPktLostInSeq10,
        tmnxVdoIfStatHDPktLostInSeq20,
        tmnxVdoIfStatHDPktLostInSeq30,
        tmnxVdoIfStatHDPktLostInSeq40,
        tmnxVdoIfStatHDPktLostInSeqMore,
        tmnxVdoIfStatPipPktLostInSeq10,
        tmnxVdoIfStatPipPktLostInSeq20,
        tmnxVdoIfStatPipPktLostInSeq30,
        tmnxVdoIfStatPipPktLostInSeq40,
        tmnxVdoIfStatPipPktLostInSeqMore,
        tmnxVdoIfStatExtRxRtcpAppRepSum,
        tmnxVdoIfStatExtRxRtcpAppRepSumL,
        tmnxVdoIfStatExtRxRtcpAppRepSumH,
        tmnxVdoIfStatExtRxRtcpAppReqSum,
        tmnxVdoIfStatExtRxRtcpAppReqSumL,
        tmnxVdoIfStatExtRxRtcpAppReqSumH,
        tmnxVdoIfStatExtRxRtcpFbRepSum,   
        tmnxVdoIfStatExtRxRtcpFbRepSumL,
        tmnxVdoIfStatExtRxRtcpFbRepSumH,
        tmnxVdoIfStatExtRxRtcpFbReqSum,   
        tmnxVdoIfStatExtRxRtcpFbReqSumL,
        tmnxVdoIfStatExtRxRtcpFbReqSumH,
        tmnxVdoIfStatExtRxRudpFbRepSum,   
        tmnxVdoIfStatExtRxRudpFbRepSumL,
        tmnxVdoIfStatExtRxRudpFbRepSumH,
        tmnxVdoIfStatExtTxFccPktsSum,   
        tmnxVdoIfStatExtTxFccPktsSumL,
        tmnxVdoIfStatExtTxFccPktsSumH,
        tmnxVdoIfStatExtTxFccOctetsSum,   
        tmnxVdoIfStatExtTxFccOctetsSumL,
        tmnxVdoIfStatExtTxFccOctetsSumH,
        tmnxVdoIfStatExtTxRetPktsSum,   
        tmnxVdoIfStatExtTxRetPktsSumL,
        tmnxVdoIfStatExtTxRetPktsSumH,
        tmnxVdoIfStatExtTxRetOctetsSum,   
        tmnxVdoIfStatExtTxRetOctetsSumL,
        tmnxVdoIfStatExtTxRetOctetsSumH,
        tmnxVdoIfStatExtTxRudpPktsSum,   
        tmnxVdoIfStatExtTxRudpPktsSumL,
        tmnxVdoIfStatExtTxRudpPktsSumH,
        tmnxVdoIfStatExtTxRudpByteSum,   
        tmnxVdoIfStatExtTxRudpByteSumL,
        tmnxVdoIfStatExtTxRudpByteSumH,
        tmnxVdoGrpSrcVqmGoodSecs,
        tmnxVdoGrpSrcVqmErrSecs,
        tmnxVdoGrpSrcVqmDegrSecs,
        tmnxVdoGrpSrcVqmImpairSecs,
        tmnxVdoGrpSrcVqmPmtRepErrSecs,
        tmnxVdoGrpSrcVqmPmtRepDegSecs,
        tmnxVdoGrpSrcVqmPmtRepImpSecs,
        tmnxVdoGrpSrcVqmPmtSyntxErrSecs,
        tmnxVdoGrpSrcVqmPatRepErrSecs,
        tmnxVdoGrpSrcVqmPatRepDegSecs,
        tmnxVdoGrpSrcVqmPatRepImpSecs,
        tmnxVdoGrpSrcVqmPatSyntxErrSecs,
        tmnxVdoGrpSrcVqmPcrRepErrSecs,
        tmnxVdoGrpSrcVqmPcrRepDegSecs,
        tmnxVdoGrpSrcVqmPcrRepImpSecs,
        tmnxVdoGrpSrcVqmSyncByteErrSecs,
        tmnxVdoGrpSrcVqmSyncLossSecs,
        tmnxVdoGrpSrcVqmCatErrSecs,
        tmnxVdoGrpSrcVqmUnrefPidErrSecs,
        tmnxVdoGrpSrcVqmMDIDelayFactor,
        tmnxVdoGrpSrcVqmMDILossRate,
        tmnxVdoGrpSrcVqmMinGOPLength,
        tmnxVdoGrpSrcVqmMinFrmPerSec,
        tmnxVdoGrpSrcVqmAvgGOPLength,
        tmnxVdoGrpSrcVqmAvgFrmPerSec,
        tmnxVdoGrpSrcVqmMaxGOPLength,
        tmnxVdoGrpSrcVqmMaxFrmPerSec, 
        tmnxVdoGrpSrcVqmGoodIFrames,
        tmnxVdoGrpSrcVqmBadIFrames,
        tmnxVdoGrpSrcVqmGoodPFrames,
        tmnxVdoGrpSrcVqmBadPFrames,
        tmnxVdoGrpSrcVqmGoodBFrames,
        tmnxVdoGrpSrcVqmBadBFrames,
        tmnxVdoGrpSrcVqmTrafficLossSecs,
        tmnxVdoGrpSrcVqmOperAnalyzerSt,
        tmnxVdoGrpSrcVqmOperCcError,   
        tmnxVdoGrpSrcVqmOperPatRepError,
        tmnxVdoGrpSrcVqmOperTncPatRep,
        tmnxVdoGrpSrcVqmOperQosPatRep,
        tmnxVdoGrpSrcVqmOperPoaPatRep,
        tmnxVdoGrpSrcVqmOperPatSyntax,
        tmnxVdoGrpSrcVqmOperPcrRepError,
        tmnxVdoGrpSrcVqmOperTncPcrRep,
        tmnxVdoGrpSrcVqmOperQosPcrRep, 
        tmnxVdoGrpSrcVqmOperPoaPcrRep,
        tmnxVdoGrpSrcVqmOperVidPIDAbs,
        tmnxVdoGrpSrcVqmOperPIDPmtUnref,
        tmnxVdoGrpSrcVqmOperPmtRepError,
        tmnxVdoGrpSrcVqmOperTncPmtRep,
        tmnxVdoGrpSrcVqmOperQosPmtRep,
        tmnxVdoGrpSrcVqmOperPoaPmtRep,
        tmnxVdoGrpSrcVqmOperPmtSyntax,
        tmnxVdoGrpSrcVqmOperSCTE35Error, 
        tmnxVdoGrpSrcVqmOperTeiError,  
        tmnxVdoGrpSrcVqmOperTsSyncLoss, 
        tmnxVdoGrpSrcVqmOperNonVidPIDAbs,
        tmnxVdoGrpSrcVqmOperReportAlarm,
        tmnxVdoPIDCcErrSecs,
        tmnxVdoPIDTeiErrSecs,
        tmnxVdoPIDAbsentErrSecs,
        tmnxVdoPIDBitrate,
        tmnxVdoPIDIsPCR,
        tmnxVdoGrpSrcExtMaxRtpTsDelta,
        tmnxVdoGrpSrcExtMaxTicksDelta,
        tmnxVdoGrpSrcExtMaxTicksDeltaL32,
        tmnxVdoGrpSrcExtMaxTicksDeltaH32,
        tmnxVdoGrpSrcExtCurTsJitter,
        tmnxVdoGrpSrcExtCurTsJitterL32,
        tmnxVdoGrpSrcExtCurTsJitterH32,
        tmnxVdoGrpSrcExtMaxTsJitter,
        tmnxVdoGrpSrcExtMaxTsJitterL32,
        tmnxVdoGrpSrcExtMaxTsJitterH32,
        tmnxVdoGrpSrcNumFccDentedPkts
            }
    STATUS      current
    DESCRIPTION
        "The group of objects supporting Fast Channel Change (FCC) or 
         Reliable Delivery (RD) or Ad Insert (ADI) statistics on version 
         9.0 of the Alcatel-Lucent SROS series systems."
    ::= { tmnxVdoGroups 14 }

tmnxVdoObsoletedV9v0Group      OBJECT-GROUP
    OBJECTS {
        tmnxVdoGrpSrcVqmSCTE35ErrSecs
            }
    STATUS      current
    DESCRIPTION
        "The group of objects obsoleted on version 9.0 of the Alcatel-Lucent 
         SROS series systems."
    ::= { tmnxVdoGroups 15 }

END
