GIGA-PRO-MIB DEFINITIONS ::= BEGIN

IMPORTS
	MODULE-IDENTITY,
	OBJECT-TYPE,
	OBJECT-IDENTITY,
	Unsigned32,
	NOTIFICATION-TYPE,
	enterprises
		FROM SNMPv2-SMI
	MODULE-COMPLIANCE
		FROM SNMPv2-CONF
        DisplayString
                FROM SNMPv2-TC;
	
-- *******************************************************************
-- * Trango module
-- *******************************************************************
trango		OBJECT IDENTIFIER ::= { enterprises 5454 }
tbw 		OBJECT IDENTIFIER ::= { trango 1 }
gigapro		OBJECT IDENTIFIER ::= { tbw 70 }

sys		OBJECT IDENTIFIER ::= { gigapro 1 }
modem		OBJECT IDENTIFIER ::= { gigapro 2 }
rf		OBJECT IDENTIFIER ::= { gigapro 3 }
gige		OBJECT IDENTIFIER ::= { gigapro 4 }
stm1		OBJECT IDENTIFIER ::= { gigapro 5 }
tdm		OBJECT IDENTIFIER ::= { gigapro 6 }
trangotrap	OBJECT IDENTIFIER ::= { gigapro 7 }

-- *******************************************************************
-- ** System Information ** trango.tbw.gigapro.sys
-- *******************************************************************

ver             OBJECT IDENTIFIER ::= { sys 1  }

sysFPGA1Ver      		OBJECT-TYPE
    	SYNTAX      		DisplayString (SIZE(0..80))
    	MAX-ACCESS  		read-only
	STATUS      		current
    	DESCRIPTION 		"FPGA 1 Version"
    	::= { ver 1 }

sysFPGA2Ver      		OBJECT-TYPE
    	SYNTAX      		DisplayString (SIZE(0..80))
    	MAX-ACCESS  		read-only
    	STATUS      		current
    	DESCRIPTION 		"FPGA 2 Version"
    	::= { ver 2 }

sysOSVer      			OBJECT-TYPE
    	SYNTAX      		DisplayString (SIZE(0..80))
    	MAX-ACCESS  		read-only
    	STATUS      		current
    	DESCRIPTION 		"IDU OS Version"
    	::= { ver 3 }

sysFWVer      			OBJECT-TYPE
    	SYNTAX      		DisplayString (SIZE(0..80))
    	MAX-ACCESS  		read-only
    	STATUS      		current
    	DESCRIPTION 		"IDU FW Version"
    	::= { ver 4 }

sysPICVer      			OBJECT-TYPE
    	SYNTAX      		DisplayString (SIZE(0..80))
    	MAX-ACCESS  		read-only
    	STATUS      		current
    	DESCRIPTION 		"IDU PIC Version"
    	::= { ver 5 }

sysModemVer      		OBJECT-TYPE
    	SYNTAX      		DisplayString (SIZE(0..80))
    	MAX-ACCESS  		read-only
    	STATUS      		current
    	DESCRIPTION 		"IDU Modem Version"
    	::= { ver 6 }

sysODU1FWVer      		OBJECT-TYPE
    	SYNTAX      		DisplayString (SIZE(0..80))
    	MAX-ACCESS  		read-only
    	STATUS      		current
    	DESCRIPTION 		"ODU 1 FW Version"
    	::= { ver 7 }

sysODU2FWVer      		OBJECT-TYPE
    	SYNTAX      		DisplayString (SIZE(0..80))
    	MAX-ACCESS  		read-only
    	STATUS      		current
    	DESCRIPTION 		"ODU 2 FW Version"
    	::= { ver 8 }

sysIF1RevVer      		OBJECT-TYPE
    	SYNTAX      		DisplayString (SIZE(0..80))
    	MAX-ACCESS  		read-only
    	STATUS      		current
    	DESCRIPTION 		"IF 1 Rev Version"
    	::= { ver 9 }

sysIF2RevVer      		OBJECT-TYPE
    	SYNTAX      		DisplayString (SIZE(0..80))
    	MAX-ACCESS  		read-only
    	STATUS      		current
    	DESCRIPTION 		"IF 2 Rev Version"
    	::= { ver 10 }

prever             OBJECT IDENTIFIER ::= { sys 2  }

sysFPGA1PreVer      		OBJECT-TYPE
    	SYNTAX      		DisplayString (SIZE(0..80))
    	MAX-ACCESS  		read-only
    	STATUS      		current
    	DESCRIPTION 		"FPGA 1 PreVersion"
    	::= { prever 1 }

sysFPGA2PreVer      		OBJECT-TYPE
    	SYNTAX      		DisplayString (SIZE(0..80))
    	MAX-ACCESS  		read-only
    	STATUS      		current
    	DESCRIPTION 		"FPGA 2 PreVersion"
    	::= { prever 2 }

sysOSPreVer      		OBJECT-TYPE
    	SYNTAX      		DisplayString (SIZE(0..80))
    	MAX-ACCESS  		read-only
    	STATUS      		current
    	DESCRIPTION 		"IDU OS PreVersion"
    	::= { prever 3 }

sysFWPreVer      		OBJECT-TYPE
    	SYNTAX      		DisplayString (SIZE(0..80))
    	MAX-ACCESS  		read-only
    	STATUS      		current
    	DESCRIPTION 		"IDU FW PreVersion"
    	::= { prever 4 }

sysPICPreVer      		OBJECT-TYPE
    	SYNTAX      		DisplayString (SIZE(0..80))
    	MAX-ACCESS  		read-only
    	STATUS      		current
    	DESCRIPTION 		"IDU PIC PreVersion"
    	::= { prever 5 }

sysModemPreVer      		OBJECT-TYPE
    	SYNTAX      		DisplayString (SIZE(0..80))
    	MAX-ACCESS  		read-only
    	STATUS      		current
    	DESCRIPTION 		"IDU Modem PreVersion"
    	::= { prever 6 }

sysODU1FWPreVer      		OBJECT-TYPE
    	SYNTAX      		DisplayString (SIZE(0..80))
    	MAX-ACCESS  		read-only
    	STATUS      		current
    	DESCRIPTION 		"ODU 1 FW PreVersion"
    	::= { prever 7 }

sysODU2FWPreVer      		OBJECT-TYPE
    	SYNTAX      		DisplayString (SIZE(0..80))
    	MAX-ACCESS  		read-only
    	STATUS      		current
    	DESCRIPTION 		"ODU 2 FW PreVersion"
    	::= { prever 8 }

model             		OBJECT IDENTIFIER ::= { sys 3  }

sysIDUModel      		OBJECT-TYPE
    	SYNTAX      		DisplayString (SIZE(0..80))
    	MAX-ACCESS  		read-only
    	STATUS      		current
    	DESCRIPTION 		"IDU Model"
    	::= { model 1 }

sysIDUSerialID      		OBJECT-TYPE
    	SYNTAX      		DisplayString (SIZE(0..80))
    	MAX-ACCESS  		read-only
    	STATUS      		current
    	DESCRIPTION 		"IDU Serial ID"
    	::= { model 2 }

sysODU1Model      		OBJECT-TYPE
    	SYNTAX      		DisplayString (SIZE(0..80))
    	MAX-ACCESS  		read-only
    	STATUS      		current
    	DESCRIPTION 		"ODU 1 model"
    	::= { model 3 }

sysODU2Model      		OBJECT-TYPE
    	SYNTAX      		DisplayString (SIZE(0..80))
    	MAX-ACCESS  		read-only
    	STATUS      		current
    	DESCRIPTION 		"ODU 2 model"
    	::= { model 4 }

sysODU1SerialID      		OBJECT-TYPE
    	SYNTAX      		DisplayString (SIZE(0..80))
    	MAX-ACCESS  		read-only
    	STATUS      		current
    	DESCRIPTION 		"ODU 1 Serial ID"
    	::= { model 5 }

sysODU2SerialID      		OBJECT-TYPE
    	SYNTAX      		DisplayString (SIZE(0..80))
    	MAX-ACCESS  		read-only
    	STATUS      		current
    	DESCRIPTION 		"ODU 2 Serial ID"
    	::= { model 6 }

sysIF1SerialID      		OBJECT-TYPE
    	SYNTAX      		DisplayString (SIZE(0..80))
    	MAX-ACCESS  		read-only
    	STATUS      		current
    	DESCRIPTION 		"IF card 1 Serial ID"
    	::= { model 7 }

sysIF2SerialID      		OBJECT-TYPE
    	SYNTAX      		DisplayString (SIZE(0..80))
    	MAX-ACCESS  		read-only
    	STATUS      		current
    	DESCRIPTION 		"IF card 2 Serial ID"
    	::= { model 8 }

mac 				OBJECT IDENTIFIER ::= { sys 4  }

sysMACFPGA      		OBJECT-TYPE
    	SYNTAX      		DisplayString (SIZE(12))
    	MAX-ACCESS  		read-only
    	STATUS      		current
    	DESCRIPTION 		"MAC address of FPGA"
    	::= { mac 1 }

sysMACeth1      		OBJECT-TYPE
    	SYNTAX      		DisplayString (SIZE(12))
    	MAX-ACCESS  		read-only
    	STATUS      		current
    	DESCRIPTION 		"MAC address of Ethernet 1"
    	::= { mac 2 }

sysMACeth2      		OBJECT-TYPE
    	SYNTAX      		DisplayString (SIZE(12))
    	MAX-ACCESS  		read-only
    	STATUS      		current
    	DESCRIPTION 		"MAC address of Ethernet 2"
    	::= { mac 3 }

ipconfig 			OBJECT IDENTIFIER ::= { sys 5  }

sysIpAddress      		OBJECT-TYPE
    	SYNTAX      		IpAddr
    	MAX-ACCESS  		read-write
    	STATUS      		current
    	DESCRIPTION 		"IP address"
    	::= { ipconfig 1 }

sysSubnetMask      		OBJECT-TYPE
    	SYNTAX      		IpAddr
    	MAX-ACCESS  		read-write
    	STATUS      		current
    	DESCRIPTION 		"Subnet mask"
    	::= { ipconfig 2 }

sysDefaultGateway      		OBJECT-TYPE
    	SYNTAX      		IpAddr
    	MAX-ACCESS  		read-write
    	STATUS      		current
    	DESCRIPTION 		"Default gateway"
    	::= { ipconfig 3 }

sysRemoteIp      		OBJECT-TYPE
    	SYNTAX      		IpAddr
    	MAX-ACCESS  		read-write
    	STATUS      		current
    	DESCRIPTION 		"IP address of the remote unit"
    	::= { ipconfig 4 }

remark 				OBJECT IDENTIFIER ::= { sys 6  }

sysRemarkSystem      		OBJECT-TYPE
    	SYNTAX      		DisplayString (SIZE(1..100))
    	MAX-ACCESS  		read-write
    	STATUS      		current
    	DESCRIPTION 		"System remarks"
    	::= { remark 1 }

sysRemarkRadio1      		OBJECT-TYPE
    	SYNTAX      		DisplayString (SIZE(1..15))
    	MAX-ACCESS  		read-write
    	STATUS      		current
    	DESCRIPTION 		"Radio 1 remarks"
    	::= { remark 2 }

sysRemarkRadio2     		OBJECT-TYPE
    	SYNTAX      		DisplayString (SIZE(1..15))
    	MAX-ACCESS  		read-write
    	STATUS      		current
    	DESCRIPTION 		"Radio 2 remarks"
    	::= { remark 3 }

ibm 				OBJECT IDENTIFIER ::= { sys 7  }

sysIBMEnable                   	OBJECT-TYPE
        SYNTAX                  INTEGER { disable(0), enable(1) }
        MAX-ACCESS              read-write
        STATUS                  current
        DESCRIPTION             "Enable/Disable Inband Management feature"
        ::= { ibm 1 }

sysIBMIp                       	OBJECT-TYPE
        SYNTAX                  IpAddr
        MAX-ACCESS              read-write
        STATUS                  current
        DESCRIPTION             "Assign/Display IBM Vlan IP"
        ::= { ibm 2 }

sysIBMNetmask                  	OBJECT-TYPE
        SYNTAX                  IpAddr
        MAX-ACCESS              read-write
        STATUS                  current
        DESCRIPTION             "Assign/Display IBM Netmask"
        ::= { ibm 3 }

sysIBMVlanID                   	OBJECT-TYPE
        SYNTAX                  INTEGER
        MAX-ACCESS              read-write
        STATUS                  current
        DESCRIPTION             "Assign/Display IBM Vlan ID"
        ::= { ibm 4 }

sysIBMPort                   	OBJECT-TYPE
        SYNTAX                  INTEGER
        MAX-ACCESS              read-write
        STATUS                  current
        DESCRIPTION             "Configure IBM port mapping"
        ::= { ibm 5 }

community       		OBJECT IDENTIFIER ::= { sys 8 }

sysSNMPReadCommStr  		OBJECT-TYPE
    	SYNTAX      		DisplayString (SIZE(1..32))
    	MAX-ACCESS  		read-write
    	STATUS      		current
    	DESCRIPTION 		"SNMP agent read community string"
    	::= { community 1 }

sysSNMPWriteCommStr 		OBJECT-TYPE
    	SYNTAX      		DisplayString (SIZE(1..32))
    	MAX-ACCESS  		read-write
    	STATUS      		current
    	DESCRIPTION 		"SNMP agent Write community string"
    	::= { community 2 }

sysSNMPTrapCommStr 		OBJECT-TYPE
    	SYNTAX      		DisplayString (SIZE(1..32))
    	MAX-ACCESS  		read-write
    	STATUS      		current
    	DESCRIPTION 		"SNMP trap community string"
    	::= { community 3 }

trapinfo       			OBJECT IDENTIFIER ::= { sys 9 }

trap1       			OBJECT IDENTIFIER ::= { trapinfo 1 }

sysSNMPTrap1Enable           	OBJECT-TYPE
    	SYNTAX              	INTEGER { off(0), on(1) }
    	MAX-ACCESS          	read-write
    	STATUS              	current
    	DESCRIPTION         	"Enable/Disable SNMP Trap 1"
    	::= { trap1 1 }

sysSNMPTrapIp1       		OBJECT-TYPE
    	SYNTAX              	IpAddr
    	MAX-ACCESS          	read-write
    	STATUS              	current
    	DESCRIPTION         	"Trap Destination IP Address 1"
    	::= { trap1 2 }

trap2       			OBJECT IDENTIFIER ::= { trapinfo 2 }

sysSNMPTrap2Enable           	OBJECT-TYPE
    	SYNTAX              	INTEGER { off(0), on(1) }
    	MAX-ACCESS          	read-write
    	STATUS              	current
    	DESCRIPTION         	"Enable/Disable SNMP Trap 2"
    	::= { trap2 1 }

sysSNMPTrapIP2       		OBJECT-TYPE
    	SYNTAX              	IpAddr
    	MAX-ACCESS          	read-write
    	STATUS              	current
    	DESCRIPTION         	"Trap Destination IP Address 2"
    	::= { trap2 2 }

trap3       			OBJECT IDENTIFIER ::= { trapinfo 3 }

sysSNMPTrap3Enable           	OBJECT-TYPE
    	SYNTAX              	INTEGER { off(0), on(1) }
    	MAX-ACCESS          	read-write
    	STATUS              	current
    	DESCRIPTION         	"Enable/Disable SNMP Trap 2"
    	::= { trap3 1 }

sysSNMPTrapIP3       		OBJECT-TYPE
    	SYNTAX              	IpAddr
    	MAX-ACCESS          	read-write
    	STATUS              	current
    	DESCRIPTION         	"Trap Destination IP Address 3"
    	::= { trap3 2 }

trap4       			OBJECT IDENTIFIER ::= { trapinfo 4 }

sysSNMPTrap3Enable           	OBJECT-TYPE
    	SYNTAX              	INTEGER { off(0), on(1) }
    	MAX-ACCESS          	read-write
    	STATUS              	current
    	DESCRIPTION         	"Enable/Disable SNMP Trap 4"
    	::= { trap4 1 }

sysSNMPTrapIP4       		OBJECT-TYPE
    	SYNTAX              	IpAddr
    	MAX-ACCESS          	read-write
    	STATUS              	current
    	DESCRIPTION         	"Trap Destination IP Address 4"
    	::= { trap4 2 }

trap5       			OBJECT IDENTIFIER ::= { trapinfo 5 }

sysSNMPTrap3Enable           	OBJECT-TYPE
    	SYNTAX              	INTEGER { off(0), on(1) }
    	MAX-ACCESS          	read-write
    	STATUS              	current
    	DESCRIPTION         	"Enable/Disable SNMP Trap 5"
    	::= { trap5 1 }

sysSNMPTrapIP5       		OBJECT-TYPE
    	SYNTAX              	IpAddr
    	MAX-ACCESS          	read-write
    	STATUS              	current
    	DESCRIPTION         	"Trap Destination IP Address 5"
    	::= { trap5 2 }

image       			OBJECT IDENTIFIER ::= { sys 10 }

sysImageUpgrade           	OBJECT-TYPE
   	SYNTAX              	INTEGER { idu(0), odu1(1), odu2(2) }
    	MAX-ACCESS          	read-write
    	STATUS              	current
    	DESCRIPTION         	"Upgrade SW image"
    	::= { image 1 }

sysImageUpgradeStatus   	OBJECT-TYPE
    	SYNTAX              	INTEGER { success(0), failed(1), inprogress(2) }
    	MAX-ACCESS          	read-only
    	STATUS              	current
    	DESCRIPTION         	"Get the current image upgrade progress status"
    	::= { image 2 }

sysImageToggle          	OBJECT-TYPE
    	SYNTAX              	INTEGER { current(0), toggle(1) }
    	MAX-ACCESS          	read-write
    	STATUS              	current
    	DESCRIPTION         	"Toggle to previous image"
    	::= { image 3 }

sysConfigOption         	OBJECT-TYPE
    	SYNTAX              	INTEGER { na(0), export(1), import(2), remove(3), save(4) }
    	MAX-ACCESS          	read-write
    	STATUS              	current
    	DESCRIPTION         	"Perform config export, import or remove configuration file"
    	::= { sys 11 }

diagnostic              	OBJECT IDENTIFIER ::= { sys 12 }

sysDiagnostic           	OBJECT-TYPE
    	SYNTAX              	INTEGER { na(0), diagnostic(1) }
    	MAX-ACCESS          	read-write
    	STATUS              	current
    	DESCRIPTION         	"Run diagnostic and put the data in a file"
    	::= { diagnostic 1 }

sysDiagnosticStatus     	OBJECT-TYPE
    	SYNTAX              	INTEGER { success(0), notready(1) }
    	MAX-ACCESS          	read-only
    	STATUS              	current
    	DESCRIPTION         	"Display current status of diagnostic command"
    	::= { diagnostic 2 }

syslog                  	OBJECT IDENTIFIER ::= { sys 13 }

sysSyslogExport         	OBJECT-TYPE
    	SYNTAX              	INTEGER { na(0), export(1), clear(2) }
    	MAX-ACCESS          	read-write
   	STATUS              	current
    	DESCRIPTION         	"export syslog into a file"
    	::= { syslog 1 }

sysSyslogLevel          	OBJECT-TYPE
    	SYNTAX              	INTEGER { nosyslog(0), level0(1), level1(2), level01(3),
				level2(4), level02(5), level12(6), level012(7) }
    	MAX-ACCESS          	read-write
    	STATUS              	current
    	DESCRIPTION         	"bitmap value for the loglevel"
    	::= { syslog 2 }

sysReboot               	OBJECT-TYPE
    	SYNTAX              	INTEGER { na(0), reboot(1) }
    	MAX-ACCESS          	read-write
    	STATUS              	current
    	DESCRIPTION         	"Reboot the system"
    	::= { sys 14 }

sysResetOption         		OBJECT-TYPE
    	SYNTAX              	INTEGER { na(0), ipconfig(1), factory(2), license(3) }
    	MAX-ACCESS          	read-write
    	STATUS              	current
    	DESCRIPTION         	"Perform config export, import or remove configuration file"
    	::= { sys 15 }

sysSystemConfig         	OBJECT-TYPE
    	SYNTAX              	INTEGER 
    	MAX-ACCESS          	read-write
    	STATUS              	current
    	DESCRIPTION         	"Configure system profile"
    	::= { sys 16 }

sysDatapath         		OBJECT-TYPE
    	SYNTAX              	INTEGER 
    	MAX-ACCESS          	read-write
    	STATUS              	current
    	DESCRIPTION         	"Configure Datapath profile"
    	::= { sys 17 }

alarm                   	OBJECT IDENTIFIER ::= { sys 18 }

sysAlarm1               	OBJECT-TYPE
    	SYNTAX              	INTEGER { off(0), on(1) }
    	MAX-ACCESS          	read-write
    	STATUS              	current
    	DESCRIPTION         	"Enable/Disable Alarm1"
    	::= { alarm 1 }

sysAlarm2               	OBJECT-TYPE
    	SYNTAX              	INTEGER { off(0), on(1) }
    	MAX-ACCESS          	read-write
    	STATUS              	current
    	DESCRIPTION         	"Enable/Disable Alarm2"
    	::= { alarm 2 }

sysFanCtrl         		OBJECT-TYPE
    	SYNTAX              	INTEGER { fanoff(0), fan1on(1), fan2ON(2) }
    	MAX-ACCESS          	read-write
    	STATUS              	current
    	DESCRIPTION         	"Turn On/Off Fans"
    	::= { sys 19 }

sysIDUTemp              	OBJECT-TYPE
    	SYNTAX              	INTEGER
    	MAX-ACCESS          	read-only
    	STATUS              	current
    	DESCRIPTION         	"PIC's current temperatur reading in Celsius"
    	::= { sys 20 }

daemon                  	OBJECT IDENTIFIER ::= { sys 21 }

sysReserved                	OBJECT-TYPE
    	SYNTAX              	INTEGER { off(0), on(1) }
    	MAX-ACCESS          	read-write
    	STATUS              	current
    	DESCRIPTION         	"Reserve field"
    	::= { daemon 1 }

sysHTTPD                	OBJECT-TYPE
    	SYNTAX              	INTEGER { off(0), on(1) }
    	MAX-ACCESS          	read-write
    	STATUS              	current
    	DESCRIPTION         	"Enable or disable HTTPD"
    	::= { daemon 2 }

sysTFTPD                	OBJECT-TYPE
    	SYNTAX              	INTEGER { off(0), on(1) }
    	MAX-ACCESS          	read-write
    	STATUS              	current
    	DESCRIPTION         	"Enable or disable TFPTD"
    	::= { daemon 3 }

sysTelnetd                	OBJECT-TYPE
    	SYNTAX              	INTEGER { off(0), on(1) }
    	MAX-ACCESS          	read-write
    	STATUS              	current
    	DESCRIPTION         	"Enable or disable Telnetd"
    	::= { daemon 4 }

sysRPSEnable              	OBJECT-TYPE
    	SYNTAX              	INTEGER { off(0), on(1) }
    	MAX-ACCESS          	read-write
    	STATUS              	current
    	DESCRIPTION         	"Enable or disable Rapid port shutdown feature"
    	::= { sys 22 }

sysSmartMode              	OBJECT-TYPE
    	SYNTAX              	INTEGER { off(0), on(1) }
    	MAX-ACCESS          	read-only
    	STATUS              	current
    	DESCRIPTION         	"Enable or disable smart mode feature"
    	::= { sys 23 }

sysClearCounter              	OBJECT-TYPE
    	SYNTAX              	INTEGER { na(0), clear(1) }
    	MAX-ACCESS          	read-write
    	STATUS              	current
    	DESCRIPTION         	"Clear data port counters"
    	::= { sys 24 }

tdm_mode                     	OBJECT IDENTIFIER ::= { sys 25 }

sysTdmMode              	OBJECT-TYPE
    	SYNTAX              	INTEGER { t1(0), e1(1) }
    	MAX-ACCESS          	read-only
    	STATUS              	current
    	DESCRIPTION         	"Select TDM Mdoe - T1 or E1"
    	::= { tdm_mode 1 }

sysTdmCoding            	OBJECT-TYPE
    	SYNTAX              	INTEGER { ami(0), b8zs(1), hdb3(2) }
    	MAX-ACCESS          	read-only
    	STATUS              	current
    	DESCRIPTION         	"Select TDM line coding"
    	::= { tdm_mode 2 }

license                     	OBJECT IDENTIFIER ::= { sys 26 }

syslicense                     	OBJECT IDENTIFIER ::= { license 1 }

sysSystemLicenseEnable          OBJECT-TYPE
    	SYNTAX              	INTEGER 
    	MAX-ACCESS          	read-only
    	STATUS              	current
    	DESCRIPTION         	"LicenseKey enable flag for the System Config"
    	::= { syslicense 1 }

sysSystemLicenseKey             OBJECT-TYPE
    	SYNTAX      		DisplayString (SIZE(0..40))
    	MAX-ACCESS          	read-write
    	STATUS              	current
    	DESCRIPTION         	"LicenseKey for the SystemMode"
    	::= { syslicense 2 }

speedlicense                     OBJECT IDENTIFIER ::= { license 2 }

sysSpeedLicenseEnable          OBJECT-TYPE
    	SYNTAX              	INTEGER 
    	MAX-ACCESS          	read-only
    	STATUS              	current
    	DESCRIPTION         	"License Key enable flag for the speed"
    	::= { speedlicense 1 }

sysSpeedLicenseKey1              OBJECT-TYPE
    	SYNTAX      		DisplayString (SIZE(0..40))
    	MAX-ACCESS          	read-write
    	STATUS              	current
    	DESCRIPTION         	"LicenseKey for the frequency"
    	::= { speedlicense 2 }

sysSpeedLicenseKey2              OBJECT-TYPE
    	SYNTAX      		DisplayString (SIZE(0..40))
    	MAX-ACCESS          	read-write
    	STATUS              	current
    	DESCRIPTION         	"LicenseKey for the frequency"
    	::= { speedlicense 3 }

sysReserved1              	OBJECT-TYPE
    	SYNTAX      		DisplayString (SIZE(0..40))
    	MAX-ACCESS          	read-only
    	STATUS              	current
    	DESCRIPTION         	"LicenseKey for the frequency"
    	::= { speedlicense 4 }

sysReserved2              	OBJECT-TYPE
    	SYNTAX      		DisplayString (SIZE(0..40))
    	MAX-ACCESS          	read-only
    	STATUS              	current
    	DESCRIPTION         	"LicenseKey for the frequency"
    	::= { speedlicense 5 }

sysReserved3              	OBJECT-TYPE
    	SYNTAX      		DisplayString (SIZE(0..40))
    	MAX-ACCESS          	read-only
    	STATUS              	current
    	DESCRIPTION         	"LicenseKey for the frequency"
    	::= { speedlicense 6 }

stm1license                     OBJECT IDENTIFIER ::= { license 3 }

sysSTM1LicenseEnable          OBJECT-TYPE
    	SYNTAX              	INTEGER 
    	MAX-ACCESS          	read-only
    	STATUS              	current
    	DESCRIPTION         	"LicenseKey enable flag for the STM1"
    	::= { stm1license 1 }

sysSTM1LicenseKey             OBJECT-TYPE
    	SYNTAX      		DisplayString (SIZE(0..40))
    	MAX-ACCESS          	read-write
    	STATUS              	current
    	DESCRIPTION         	"LicenseKey for the STM1"
    	::= { stm1license 2 }

tdmlicense                     OBJECT IDENTIFIER ::= { license 4 }

sysTDMLicenseEnable          OBJECT-TYPE
    	SYNTAX              	INTEGER 
    	MAX-ACCESS          	read-only
    	STATUS              	current
    	DESCRIPTION         	"LicenseKey enable flag for the TDM"
    	::= { tdmlicense 1 }

sysTDMLicenseKey             OBJECT-TYPE
    	SYNTAX      		DisplayString (SIZE(0..40))
    	MAX-ACCESS          	read-write
    	STATUS              	current
    	DESCRIPTION         	"LicenseKey for the TDM"
    	::= { tdmlicense 2 }

m1             			OBJECT IDENTIFIER ::= { modem 1  }

modem1LoopbackMode       	OBJECT-TYPE
        SYNTAX          	INTEGER { off(0), digital(1), if(2), rfgen(3), rfrefl(4) }
        MAX-ACCESS      	read-write
        STATUS          	current
        DESCRIPTION     	"Set/Display the Loopback Mode"
        ::= { m1 1 }

modem1DataPattern        	OBJECT-TYPE
        SYNTAX          	INTEGER { external(0), internal(1) }
        MAX-ACCESS      	read-write
        STATUS          	current
        DESCRIPTION     	"Set/Display the current Loopback Pattern (source)"
        ::= { m1 2 }

protection1             	OBJECT IDENTIFIER ::= { m1 3  }

modem1ProtectionModeTx        	OBJECT-TYPE
        SYNTAX          	INTEGER { na(0), working(1), protection(2) }
        MAX-ACCESS      	read-only
        STATUS          	current
        DESCRIPTION     	"Set/Display protection mode for modem 1"
        ::= { protection1 1 }

modem1Reserved        		OBJECT-TYPE
        SYNTAX          	INTEGER
        MAX-ACCESS      	read-only
        STATUS          	current
        DESCRIPTION     	"Reserve field for modem1"
        ::= { protection1 2 }

acm1             		OBJECT IDENTIFIER ::= { m1 4  }

modem1ACMEnable        		OBJECT-TYPE
        SYNTAX          	INTEGER { off(0), on(1) }
        MAX-ACCESS      	read-write
        STATUS          	current
        DESCRIPTION     	"Set/Display acm feature for modem 2"
        ::= { acm1 1 }

profile1             		OBJECT IDENTIFIER ::= { acm1 2  }

modem1ACMProfileQPSKEnable      OBJECT-TYPE
        SYNTAX          	INTEGER { off(0), on(1) }
        MAX-ACCESS      	read-only
        STATUS          	current
        DESCRIPTION     	"Set/Display ACM profile enable flag for modem 2"
        ::= { profile1 1 }

modem1ACMProfile16QEnable      OBJECT-TYPE
        SYNTAX          	INTEGER { off(0), on(1) }
        MAX-ACCESS      	read-only
        STATUS          	current
        DESCRIPTION     	"Set/Display ACM profile enable flag for modem 2"
        ::= { profile1 2 }

modem1ACMProfile32QEnable      OBJECT-TYPE
        SYNTAX          	INTEGER { off(0), on(1) }
        MAX-ACCESS      	read-only
        STATUS          	current
        DESCRIPTION     	"Set/Display ACM profile enable flag for modem 2"
        ::= { profile1 3 }

modem1ACMProfile64QEnable      OBJECT-TYPE
        SYNTAX          	INTEGER { off(0), on(1) }
        MAX-ACCESS      	read-only
        STATUS          	current
        DESCRIPTION     	"Set/Display ACM profile enable flag for modem 2"
        ::= { profile1 4 }

modem1ACMProfile128QEnable      OBJECT-TYPE
        SYNTAX          	INTEGER { off(0), on(1) }
        MAX-ACCESS      	read-only
        STATUS          	current
        DESCRIPTION     	"Set/Display ACM profile enable flag for modem 2"
        ::= { profile1 5 }

modem1ACMProfile256QEnable      OBJECT-TYPE
        SYNTAX          	INTEGER { off(0), on(1) }
        MAX-ACCESS      	read-only
        STATUS          	current
        DESCRIPTION     	"Set/Display ACM profile enable flag for modem 2"
        ::= { profile1 6 }

improve1             		OBJECT IDENTIFIER ::= { acm1 3  }

modem1ACMQPSKMSEImporve      	OBJECT-TYPE
        SYNTAX          	Opaque
        MAX-ACCESS      	read-write
        STATUS          	current
        DESCRIPTION     	"Set/Display ACM MSE improve value for QPSK"
        ::= { improve1 1 }

modem1ACM16QMSEImprove      	OBJECT-TYPE
        SYNTAX          	Opaque
        MAX-ACCESS      	read-write
        STATUS          	current
        DESCRIPTION     	"Set/Display ACM MSE improve value for 16Q"
        ::= { improve1 2 }

modem1ACM32QMSEImprove      	OBJECT-TYPE
        SYNTAX          	Opaque
        MAX-ACCESS      	read-write
        STATUS          	current
        DESCRIPTION     	"Set/Display ACM MSE improve value for 32Q"
        ::= { improve1 3 }

modem1ACM64QMSEImprove      	OBJECT-TYPE
        SYNTAX          	Opaque
        MAX-ACCESS      	read-write
        STATUS          	current
        DESCRIPTION     	"Set/Display ACM MSE improve value for 64Q"
        ::= { improve1 4 }

modem1ACM128QMSEImprove      	OBJECT-TYPE
        SYNTAX          	Opaque
        MAX-ACCESS      	read-write
        STATUS          	current
        DESCRIPTION     	"Set/Display ACM MSE improve value for 128Q"
        ::= { improve1 5 }

modem1ACM256QMSEImprove      	OBJECT-TYPE
        SYNTAX          	Opaque
        MAX-ACCESS      	read-write
        STATUS          	current
        DESCRIPTION     	"Set/Display ACM MSE improve value for 256Q"
        ::= { improve1 6 }

degrade1             		OBJECT IDENTIFIER ::= { acm1 4  }

modem1ACMQPSKMSEDegrade      	OBJECT-TYPE
        SYNTAX          	Opaque
        MAX-ACCESS      	read-write
        STATUS          	current
        DESCRIPTION     	"Set/Display ACM MSE degrade value for QPSK"
        ::= { degrade1 1 }

modem1ACM16QMSEDegrade      	OBJECT-TYPE
        SYNTAX          	Opaque
        MAX-ACCESS      	read-write
        STATUS          	current
        DESCRIPTION     	"Set/Display ACM MSE degrade value for 16Q"
        ::= { degrade1 2 }

modem1ACM32QMSEDegrade      	OBJECT-TYPE
        SYNTAX          	Opaque
        MAX-ACCESS      	read-write
        STATUS          	current
        DESCRIPTION     	"Set/Display ACM MSE degrade value for 32Q"
        ::= { degrade1 3 }

modem1ACM64QMSEDegrade      	OBJECT-TYPE
        SYNTAX          	Opaque
        MAX-ACCESS      	read-write
        STATUS          	current
        DESCRIPTION     	"Set/Display ACM MSE degrade value for 64Q"
        ::= { degrade1 4 }

modem1ACM128QMSEDegrade      	OBJECT-TYPE
        SYNTAX          	Opaque
        MAX-ACCESS      	read-write
        STATUS          	current
        DESCRIPTION     	"Set/Display ACM MSE degrade value for 128Q"
        ::= { degrade1 5 }

modem1ACM256QMSEDegrade      	OBJECT-TYPE
        SYNTAX          	Opaque
        MAX-ACCESS      	read-write
        STATUS          	current
        DESCRIPTION     	"Set/Display ACM MSE degrade value for 256Q"
        ::= { degrade1 6 }

profile1             		OBJECT IDENTIFIER ::= { acm1 5  }

modem1ACMTxProfile      	OBJECT-TYPE
        SYNTAX          	INTEGER
        MAX-ACCESS      	read-only
        STATUS          	current
        DESCRIPTION     	"Display current ACM Tx profile"
        ::= { profile1 1 }

modem1ACMRxProfile      	OBJECT-TYPE
        SYNTAX          	INTEGER
        MAX-ACCESS      	read-only
        STATUS          	current
        DESCRIPTION     	"Display current ACM Rx profile"
        ::= { profile1 2 }

link1             		OBJECT IDENTIFIER ::= { m1 5  }

modem1BER      			OBJECT-TYPE
        SYNTAX          	INTEGER
        MAX-ACCESS      	read-only
        STATUS          	current
        DESCRIPTION     	"Set/Display BER value"
        ::= { link1 1 }

modem1MSE      			OBJECT-TYPE
        SYNTAX          	INTEGER
        MAX-ACCESS      	read-only
        STATUS          	current
        DESCRIPTION     	"Set/Display MSE value"
        ::= { link1 2 }

modem1FER      			OBJECT-TYPE
        SYNTAX          	INTEGER
        MAX-ACCESS      	read-only
        STATUS          	current
        DESCRIPTION     	"Set/Display FER value"
        ::= { link1 3 }

lock1             		OBJECT IDENTIFIER ::= { m1 6  }

modem1LockStatus      		OBJECT-TYPE
        SYNTAX          	INTEGER { nolock(0), lock(1) }
        MAX-ACCESS      	read-only
        STATUS          	current
        DESCRIPTION     	"Set/Display link lock statsu"
        ::= { lock1 1 }

modem1TimingLockStatus      	OBJECT-TYPE
        SYNTAX          	INTEGER { nolock(0), lock(1) }
        MAX-ACCESS      	read-only
        STATUS          	current
        DESCRIPTION     	"Set/Display timing lock statsu"
        ::= { lock1 2 }

modem1PreambleLockStatus      	OBJECT-TYPE
        SYNTAX          	INTEGER { nolock(0), lock(1) }
        MAX-ACCESS      	read-only
        STATUS          	current
        DESCRIPTION     	"Set/Display preamble lock statsu"
        ::= { lock1 3 }

modem1LDPCLocktatus      	OBJECT-TYPE
        SYNTAX          	INTEGER { nolock(0), lock(1) }
        MAX-ACCESS      	read-only
        STATUS          	current
        DESCRIPTION     	"Set/Display LDPC lock statsu"
        ::= { lock1 4 }

m2             			OBJECT IDENTIFIER ::= { modem 2  }

modem2LoopbackMode       	OBJECT-TYPE
        SYNTAX          	INTEGER { off(0), digital(1), if(2), rfgen(3), rfrefl(4) }
        MAX-ACCESS      	read-write
        STATUS          	current
        DESCRIPTION     	"Set/Display the Loopback Mode"
        ::= { m2 1 }

modem2DataPattern        	OBJECT-TYPE
        SYNTAX          	INTEGER { external(0), internal(1) }
        MAX-ACCESS      	read-write
        STATUS          	current
        DESCRIPTION     	"Set/Display the current Loopback Pattern (source)"
        ::= { m2 2 }

protection2             	OBJECT IDENTIFIER ::= { m2 3  }

modem2ProtectionModeTx        	OBJECT-TYPE
        SYNTAX          	INTEGER { na(0), working(1), protection(2) }
        MAX-ACCESS      	read-only
        STATUS          	current
        DESCRIPTION     	"Set/Display protection mode for modem 1"
        ::= { protection2 1 }

modem2Reserved        	OBJECT-TYPE
        SYNTAX          	INTEGER 
        MAX-ACCESS      	read-only
        STATUS          	current
        DESCRIPTION     	"Reserved field for modem 2"
        ::= { protection2 2 }

acm2             		OBJECT IDENTIFIER ::= { m2 4  }

modem2ACMEnable        		OBJECT-TYPE
        SYNTAX          	INTEGER { off(0), on(1) }
        MAX-ACCESS      	read-write
        STATUS          	current
        DESCRIPTION     	"Set/Display acm feature for modem 2"
        ::= { acm2 1 }

profile2             		OBJECT IDENTIFIER ::= { acm2 2  }

modem2ACMProfileQPSKEnable      OBJECT-TYPE
        SYNTAX          	INTEGER { off(0), on(1) }
        MAX-ACCESS      	read-only
        STATUS          	current
        DESCRIPTION     	"Set/Display ACM profile enable flag for modem 2"
        ::= { profile2 1 }

modem2ACMProfile16QEnable      OBJECT-TYPE
        SYNTAX          	INTEGER { off(0), on(1) }
        MAX-ACCESS      	read-only
        STATUS          	current
        DESCRIPTION     	"Set/Display ACM profile enable flag for modem 2"
        ::= { profile2 2 }

modem2ACMProfile32QEnable      OBJECT-TYPE
        SYNTAX          	INTEGER { off(0), on(1) }
        MAX-ACCESS      	read-only
        STATUS          	current
        DESCRIPTION     	"Set/Display ACM profile enable flag for modem 2"
        ::= { profile2 3 }

modem2ACMProfile64QEnable      OBJECT-TYPE
        SYNTAX          	INTEGER { off(0), on(1) }
        MAX-ACCESS      	read-only
        STATUS          	current
        DESCRIPTION     	"Set/Display ACM profile enable flag for modem 2"
        ::= { profile2 4 }

modem2ACMProfile128QEnable      OBJECT-TYPE
        SYNTAX          	INTEGER { off(0), on(1) }
        MAX-ACCESS      	read-only
        STATUS          	current
        DESCRIPTION     	"Set/Display ACM profile enable flag for modem 2"
        ::= { profile2 5 }

modem2ACMProfile256QEnable      OBJECT-TYPE
        SYNTAX          	INTEGER { off(0), on(1) }
        MAX-ACCESS      	read-only
        STATUS          	current
        DESCRIPTION     	"Set/Display ACM profile enable flag for modem 2"
        ::= { profile2 6 }

improve2             		OBJECT IDENTIFIER ::= { acm2 3  }

modem2ACMQPSKMSEImporve      	OBJECT-TYPE
        SYNTAX          	Opaque
        MAX-ACCESS      	read-write
        STATUS          	current
        DESCRIPTION     	"Set/Display ACM MSE improve value for QPSK"
        ::= { improve2 1 }

modem2ACM16QMSEImprove      	OBJECT-TYPE
        SYNTAX          	Opaque
        MAX-ACCESS      	read-write
        STATUS          	current
        DESCRIPTION     	"Set/Display ACM MSE improve value for 16Q"
        ::= { improve2 2 }

modem2ACM32QMSEImprove      	OBJECT-TYPE
        SYNTAX          	Opaque
        MAX-ACCESS      	read-write
        STATUS          	current
        DESCRIPTION     	"Set/Display ACM MSE improve value for 32Q"
        ::= { improve2 3 }

modem2ACM64QMSEImprove      	OBJECT-TYPE
        SYNTAX          	Opaque
        MAX-ACCESS      	read-write
        STATUS          	current
        DESCRIPTION     	"Set/Display ACM MSE improve value for 64Q"
        ::= { improve2 4 }

modem2ACM128QMSEImprove      	OBJECT-TYPE
        SYNTAX          	Opaque
        MAX-ACCESS      	read-write
        STATUS          	current
        DESCRIPTION     	"Set/Display ACM MSE improve value for 128Q"
        ::= { improve2 5 }

modem2ACM256QMSEImprove      	OBJECT-TYPE
        SYNTAX          	Opaque
        MAX-ACCESS      	read-write
        STATUS          	current
        DESCRIPTION     	"Set/Display ACM MSE improve value for 256Q"
        ::= { improve2 6 }

degrade2             		OBJECT IDENTIFIER ::= { acm2 4  }

modem2ACMQPSKMSEDegrade      	OBJECT-TYPE
        SYNTAX          	Opaque
        MAX-ACCESS      	read-write
        STATUS          	current
        DESCRIPTION     	"Set/Display ACM MSE degrade value for QPSK"
        ::= { degrade2 1 }

modem2ACM16QMSEDegrade      	OBJECT-TYPE
        SYNTAX          	Opaque
        MAX-ACCESS      	read-write
        STATUS          	current
        DESCRIPTION     	"Set/Display ACM MSE degrade value for 16Q"
        ::= { degrade2 2 }

modem2ACM32QMSEDegrade      	OBJECT-TYPE
        SYNTAX          	Opaque
        MAX-ACCESS      	read-write
        STATUS          	current
        DESCRIPTION     	"Set/Display ACM MSE degrade value for 32Q"
        ::= { degrade2 3 }

modem2ACM64QMSEDegrade      	OBJECT-TYPE
        SYNTAX          	Opaque
        MAX-ACCESS      	read-write
        STATUS          	current
        DESCRIPTION     	"Set/Display ACM MSE degrade value for 64Q"
        ::= { degrade2 4 }

modem2ACM128QMSEDegrade      	OBJECT-TYPE
        SYNTAX          	Opaque
        MAX-ACCESS      	read-write
        STATUS          	current
        DESCRIPTION     	"Set/Display ACM MSE degrade value for 128Q"
        ::= { degrade2 5 }

modem2ACM256QMSEDegrade      	OBJECT-TYPE
        SYNTAX          	Opaque
        MAX-ACCESS      	read-write
        STATUS          	current
        DESCRIPTION     	"Set/Display ACM MSE degrade value for 256Q"
        ::= { degrade2 6 }

profile2             		OBJECT IDENTIFIER ::= { acm2 5  }

modem2ACMTxProfile      	OBJECT-TYPE
        SYNTAX          	INTEGER
        MAX-ACCESS      	read-only
        STATUS          	current
        DESCRIPTION     	"Display current ACM Tx profile"
        ::= { profile2 1 }

modem2ACMRxProfile      	OBJECT-TYPE
        SYNTAX          	INTEGER
        MAX-ACCESS      	read-only
        STATUS          	current
        DESCRIPTION     	"Display current ACM Rx profile"
        ::= { profile2 2 }

link2             		OBJECT IDENTIFIER ::= { m2 5  }

modem2BER      			OBJECT-TYPE
        SYNTAX          	INTEGER
        MAX-ACCESS      	read-only
        STATUS          	current
        DESCRIPTION     	"Set/Display BER value"
        ::= { link2 1 }

modem2MSE      			OBJECT-TYPE
        SYNTAX          	INTEGER
        MAX-ACCESS      	read-only
        STATUS          	current
        DESCRIPTION     	"Set/Display MSE value"
        ::= { link2 2 }

modem2FER      			OBJECT-TYPE
        SYNTAX          	INTEGER
        MAX-ACCESS      	read-only
        STATUS          	current
        DESCRIPTION     	"Set/Display FER value"
        ::= { link2 3 }

lock2             		OBJECT IDENTIFIER ::= { m2 6  }

modem2LockStatus      		OBJECT-TYPE
        SYNTAX          	INTEGER { nolock(0), lock(1) }
        MAX-ACCESS      	read-only
        STATUS          	current
        DESCRIPTION     	"Set/Display link lock statsu"
        ::= { lock2 1 }

modem2TimingLockStatus      	OBJECT-TYPE
        SYNTAX          	INTEGER { nolock(0), lock(1) }
        MAX-ACCESS      	read-only
        STATUS          	current
        DESCRIPTION     	"Set/Display timing lock statsu"
        ::= { lock2 2 }

modem2PreambleLockStatus      	OBJECT-TYPE
        SYNTAX          	INTEGER { nolock(0), lock(1) }
        MAX-ACCESS      	read-only
        STATUS          	current
        DESCRIPTION     	"Set/Display preamble lock statsu"
        ::= { lock2 3 }

modem2LDPCLocktatus      	OBJECT-TYPE
        SYNTAX          	INTEGER { nolock(0), lock(1) }
        MAX-ACCESS      	read-only
        STATUS          	current
        DESCRIPTION     	"Set/Display LDPC lock statsu"
        ::= { lock2 4 }

rf1             			OBJECT IDENTIFIER ::= { rf 1  }

freq1             		OBJECT IDENTIFIER ::= { rf1 1  }

txfreq1             		OBJECT IDENTIFIER ::= { freq1 1  }

rf1TxFrequency      		OBJECT-TYPE
        SYNTAX          	Opaque
        MAX-ACCESS      	read-write
        STATUS          	current
        DESCRIPTION     	"Set/Display TX frequency for radio 1"
        ::= { txfreq1 1 }

rf1TxFrequencyInt      		OBJECT-TYPE
        SYNTAX          	Integer
        MAX-ACCESS      	read-write
        STATUS          	current
        DESCRIPTION     	"Set/Display TX frequency for radio 1 in INTEGER"
        ::= { txfreq1 2 }

rxfreq1             		OBJECT IDENTIFIER ::= { freq1 2  }

rf1RxFrequency      		OBJECT-TYPE
        SYNTAX          	Opaque
        MAX-ACCESS      	read-only
        STATUS          	current
        DESCRIPTION     	"Display RX frequency for radio 1"
        ::= { rxfreq1 1 }

rf1RxFrequencyInt      		OBJECT-TYPE
        SYNTAX          	Integer
        MAX-ACCESS      	read-only
        STATUS          	current
        DESCRIPTION     	"Display RX frequency for radio 1 in integer"
        ::= { rxfreq1 2 }

txduplex1             		OBJECT IDENTIFIER ::= { freq1 3  }

rf1FreqDuplex      		OBJECT-TYPE
        SYNTAX          	Opaque
        MAX-ACCESS      	read-only
        STATUS          	current
        DESCRIPTION     	"Display frequency duplex for radio 1"
        ::= { txduplex1 1 }

rf1FreqDuplex     		OBJECT-TYPE
        SYNTAX          	Integer
        MAX-ACCESS      	read-only
        STATUS          	current
        DESCRIPTION     	"Display frequency duplex for radio 1 in integer"
        ::= { txduplex1 2 }


rf1DefaultOpmode      		OBJECT-TYPE
    	SYNTAX              	Integer { off(0), on(1) }
        MAX-ACCESS      	read-write
        STATUS          	current
        DESCRIPTION     	"Set/Display default opmode setting for radio 1"
        ::= { rf1 2 }

rf1Opmode      			OBJECT-TYPE
    	SYNTAX              	INTEGER { off(0), on(1) }
        MAX-ACCESS      	read-write
        STATUS          	current
        DESCRIPTION     	"Set/Display current opmode setting for radio 1"
        ::= { rf1 3 }
power1             		OBJECT IDENTIFIER ::= { rf1 4  }

rf1Power      			OBJECT-TYPE
        SYNTAX          	Opaque
        MAX-ACCESS      	read-write
        STATUS          	current
        DESCRIPTION     	"Set/Display TX power for radio 1"
        ::= { power1 1 }

rf1PowerInt      			OBJECT-TYPE
        SYNTAX          	Integer
        MAX-ACCESS      	read-write
        STATUS          	current
        DESCRIPTION     	"Set/Display TX power for radio 1 in Integer"
        ::= { power1 2 }


cableloss1             		OBJECT IDENTIFIER ::= { rf1 5  }

loss1401             		OBJECT IDENTIFIER ::= { cableloss1 1  }

rf1Cableloss140      		OBJECT-TYPE
        SYNTAX          	Opaque
        MAX-ACCESS      	read-write
        STATUS          	current
        DESCRIPTION     	"Set/Display Cableloss 140 for radio 1"
        ::= { loss1401 1 }

rf1Cableloss140Int      	OBJECT-TYPE
        SYNTAX          	Integer
        MAX-ACCESS      	read-write
        STATUS          	current
        DESCRIPTION     	"Set/Display Cableloss 140 for radio 1 in Integer"
        ::= { loss1401 2 }

loss3151             		OBJECT IDENTIFIER ::= { cableloss1 2  }

rf1Cableloss315      		OBJECT-TYPE
        SYNTAX          	Opaque
        MAX-ACCESS      	read-write
        STATUS          	current
        DESCRIPTION     	"Set/Display Cableloss 315 for radio 1"
        ::= { loss3151 1 }

rf1Cableloss315Int      	OBJECT-TYPE
        SYNTAX          	Integer
        MAX-ACCESS      	read-write
        STATUS          	current
        DESCRIPTION     	"Set/Display Cableloss 315 for radio 1 in Integer"
        ::= { loss3151 2 }

loss9151             		OBJECT IDENTIFIER ::= { cableloss1 3  }

rf1Cableloss915      		OBJECT-TYPE
        SYNTAX          	Opaque
        MAX-ACCESS      	read-write
        STATUS          	current
        DESCRIPTION     	"Set/Display Cableloss 915 for radio 1"
        ::= { loss9151 1 }

rf1Cableloss915Int      	OBJECT-TYPE
        SYNTAX          	Integer
        MAX-ACCESS      	read-write
        STATUS          	current
        DESCRIPTION     	"Set/Display Cableloss 915 for radio 1 in Integer"
        ::= { loss9151 2 }


speed1             		OBJECT IDENTIFIER ::= { rf1 6  }

rf1ChannelWidth      		OBJECT-TYPE
        SYNTAX          	INTEGER
        MAX-ACCESS      	read-write
        STATUS          	current
        DESCRIPTION     	"Set/Display Speed channel width for radio 1"
        ::= { speed1 1 }

rf1Modulation      		OBJECT-TYPE
	SYNTAX          	INTEGER { qpsk(0), qam16(1), qam32(2), qam64(3), qam128(4), qam256(5) }
        MAX-ACCESS      	read-write
        STATUS          	current
        DESCRIPTION     	"Set/Display Speed modulation for radio 1"
        ::= { speed1 2 }

rf1Symrate      		OBJECT-TYPE
        SYNTAX          	Opaque
        MAX-ACCESS      	read-only
        STATUS          	current
        DESCRIPTION     	"Display Speed symbol rate for radio 1"
        ::= { speed1 4 }

rf1Speed      			OBJECT-TYPE
        SYNTAX          	Opaque
        MAX-ACCESS      	read-only
        STATUS          	current
        DESCRIPTION     	"Display Speed rate for radio 1"
        ::= { speed1 5 }

atpc1             		OBJECT IDENTIFIER ::= { rf1 7  }

rf1ATPCEnable      		OBJECT-TYPE
    	SYNTAX              	INTEGER { off(0), on(1) }
        MAX-ACCESS      	read-write
        STATUS          	current
        DESCRIPTION     	"Set/Display current status of ATPC feature for radio 1"
        ::= { atpc1 1 }

rf1ATPCMaxPower      		OBJECT-TYPE
        SYNTAX          	Opaque
        MAX-ACCESS      	read-write
        STATUS          	current
        DESCRIPTION     	"Display ATPC maximum power for radio 1"
        ::= { atpc1 2 }

rf1ATPCStepSize      		OBJECT-TYPE
        SYNTAX          	INTEGER
        MAX-ACCESS      	read-write
        STATUS          	current
        DESCRIPTION     	"Display ATPC step size for radio 1"
        ::= { atpc1 3 }

rf1AlignmentMode      		OBJECT-TYPE
    	SYNTAX              	INTEGER { off(0), on(1) }
        MAX-ACCESS      	read-write
        STATUS          	current
        DESCRIPTION     	"Set/Display current status of alignment mode for radio 1"
        ::= { rf1 8 }

target1             		OBJECT IDENTIFIER ::= { rf1 9  }

rf1TargetRSSI      		OBJECT-TYPE
        SYNTAX          	Opaque
        MAX-ACCESS      	read-write
        STATUS          	current
        DESCRIPTION     	"Set/Display target RSSI value for radio 1"
        ::= { target1 1 }

rf1TargetRSSIInt     		OBJECT-TYPE
        SYNTAX          	INTEGER
        MAX-ACCESS      	read-write
        STATUS          	current
        DESCRIPTION     	"Set/Display target RSSI value for radio 1 in Integer"
        ::= { target1 2 }


rf1ODULEDEnable      		OBJECT-TYPE
    	SYNTAX              	INTEGER { off(0), on(1) }
        MAX-ACCESS      	read-write
        STATUS          	current
        DESCRIPTION     	"Set/Display current status of ODU LED display for radio 1"
        ::= { rf1 10 }

rf1ODUPowerEnable      		OBJECT-TYPE
    	SYNTAX              	INTEGER { off(0), on(1) }
        MAX-ACCESS      	read-write
        STATUS          	current
        DESCRIPTION     	"Set/Display current status of ODU power for radio 1"
        ::= { rf1 11 }

rf1ODURxAGC      		OBJECT-TYPE
    	SYNTAX              	INTEGER { off(0), on(1) }
        MAX-ACCESS      	read-write
        STATUS          	current
        DESCRIPTION     	"Set/Display current status of ODU RXAGC loop for radio 1"
        ::= { rf1 12 }

rf1ODUTemp      		OBJECT-TYPE
    	SYNTAX              	INTEGER
        MAX-ACCESS      	read-only
        STATUS          	current
        DESCRIPTION     	"Display current ODU temperature for radio 1"
        ::= { rf1 13 }

rssi1             		OBJECT IDENTIFIER ::= { rf1 14  }

rf1RSSI      			OBJECT-TYPE
    	SYNTAX              	Opaque
        MAX-ACCESS      	read-only
        STATUS          	current
        DESCRIPTION     	"Display current RSSI value for radio 1"
        ::= { rssi1 1 }

rf1RSSI      			OBJECT-TYPE
    	SYNTAX              	Integer
        MAX-ACCESS      	read-only
        STATUS          	current
        DESCRIPTION     	"Display current RSSI value for radio 1 in Integer"
        ::= { rssi1 2 }


pll1             		OBJECT IDENTIFIER ::= { rf1 15  }

rf1ODURFpll      		OBJECT-TYPE
    	SYNTAX              	INTEGER { nolock(0), lock(1) }
        MAX-ACCESS      	read-write
        STATUS          	current
        DESCRIPTION     	"Display current status of ODU RF PLL for radio 1"
        ::= { pll1 1 }

rf1ODUIFpll      		OBJECT-TYPE
    	SYNTAX              	INTEGER { nolock(0), lock(1) }
        MAX-ACCESS      	read-write
        STATUS          	current
        DESCRIPTION     	"Display current status of ODU IF PLL for radio 1"
        ::= { pll1 2 }

rf1ODUTxpll      		OBJECT-TYPE
    	SYNTAX              	INTEGER { nolock(0), lock(1) }
        MAX-ACCESS      	read-write
        STATUS          	current
        DESCRIPTION     	"Display current status of ODU TX PLL for radio 1"
        ::= { pll1 3 }

rf1ODURxpll      		OBJECT-TYPE
    	SYNTAX              	INTEGER { nolock(0), lock(1) }
        MAX-ACCESS      	read-write
        STATUS          	current
        DESCRIPTION     	"Display current status of ODU RX PLL for radio 1"
        ::= { pll1 4 }

incounter             		OBJECT IDENTIFIER ::= { rf1 16  }

rf1InDataOctets      		OBJECT-TYPE
    	SYNTAX             	Counter32
        MAX-ACCESS      	read-only
        STATUS          	current
        DESCRIPTION     	"Display RF IN data octets counter for radio 1"
        ::= { incounter 1 }

rf1InDataPackets      		OBJECT-TYPE
    	SYNTAX             	Counter32
        MAX-ACCESS      	read-only
        STATUS          	current
        DESCRIPTION     	"Display RF IN data packets counter for radio 1"
        ::= { incounter 2 }

rf1InDataDropPackets      	OBJECT-TYPE
    	SYNTAX             	Counter32
        MAX-ACCESS      	read-only
        STATUS          	current
        DESCRIPTION     	"Display RF IN data drop packets counter for radio 1"
        ::= { incounter 3 }

rf1InPortUtil      		OBJECT-TYPE
    	SYNTAX             	INTEGER
        MAX-ACCESS      	read-only
        STATUS          	current
        DESCRIPTION     	"Display RF IN port utilization for radio 1"
        ::= { incounter 4 }

outcounter1             		OBJECT IDENTIFIER ::= { rf1 17  }

rf1OutDataOctets      		OBJECT-TYPE
    	SYNTAX             	Counter32
        MAX-ACCESS      	read-only
        STATUS          	current
        DESCRIPTION     	"Display RF OUT data octets counter for radio 1"
        ::= { outcounter1 1 }

rf1OutDataPackets      		OBJECT-TYPE
    	SYNTAX             	Counter32
        MAX-ACCESS      	read-only
        STATUS          	current
        DESCRIPTION     	"Display RF OUT data packets counter for radio 1"
        ::= { outcounter1 2 }

rf1OutPortUtil      		OBJECT-TYPE
    	SYNTAX             	INTEGER
        MAX-ACCESS      	read-only
        STATUS          	current
        DESCRIPTION     	"Display RF OUT port utilization for radio 1"
        ::= { outcounter1 3 }

rf2             		OBJECT IDENTIFIER ::= { rf 2  }

freq2             		OBJECT IDENTIFIER ::= { rf2 1  }

txfreq2             		OBJECT IDENTIFIER ::= { freq2 1  }

rf2TxFrequency      		OBJECT-TYPE
        SYNTAX          	Opaque
        MAX-ACCESS      	read-write
        STATUS          	current
        DESCRIPTION     	"Set/Display TX frequency for radio 2"
        ::= { txfreq2 1 }

rf2TxFrequencyInt      		OBJECT-TYPE
        SYNTAX          	Integer
        MAX-ACCESS      	read-write
        STATUS          	current
        DESCRIPTION     	"Set/Display TX frequency for radio 2 in INTEGER"
        ::= { txfreq2 2 }

rxfreq2             		OBJECT IDENTIFIER ::= { freq2 2  }

rf2RxFrequency      		OBJECT-TYPE
        SYNTAX          	Opaque
        MAX-ACCESS      	read-only
        STATUS          	current
        DESCRIPTION     	"Display RX frequency for radio 2"
        ::= { rxfreq2 1 }

rf2RxFrequencyInt      		OBJECT-TYPE
        SYNTAX          	Integer
        MAX-ACCESS      	read-only
        STATUS          	current
        DESCRIPTION     	"Display RX frequency for radio 2 in integer"
        ::= { rxfreq2 2 }

txduplex2             		OBJECT IDENTIFIER ::= { freq2 3  }

rf2FreqDuplex      		OBJECT-TYPE
        SYNTAX          	Opaque
        MAX-ACCESS      	read-only
        STATUS          	current
        DESCRIPTION     	"Display frequency duplex for radio 2"
        ::= { txduplex2 1 }

rf2FreqDuplex     		OBJECT-TYPE
        SYNTAX          	Integer
        MAX-ACCESS      	read-only
        STATUS          	current
        DESCRIPTION     	"Display frequency duplex for radio 2 in integer"
        ::= { txduplex2 2 }

rf2DefaultOpmode      		OBJECT-TYPE
    	SYNTAX              	INTEGER { off(0), on(1) }
        MAX-ACCESS      	read-write
        STATUS          	current
        DESCRIPTION     	"Set/Display default opmode setting for radio 2"
        ::= { rf2 2 }

rf2Opmode      			OBJECT-TYPE
    	SYNTAX              	INTEGER { off(0), on(1) }
        MAX-ACCESS      	read-write
        STATUS          	current
        DESCRIPTION     	"Set/Display current opmode setting for radio 2"
        ::= { rf2 3 }
power2             		OBJECT IDENTIFIER ::= { rf2 4  }

rf2Power      			OBJECT-TYPE
        SYNTAX          	Opaque
        MAX-ACCESS      	read-write
        STATUS          	current
        DESCRIPTION     	"Set/Display TX power for radio 1"
        ::= { power2 1 }

rf2PowerInt      			OBJECT-TYPE
        SYNTAX          	Integer
        MAX-ACCESS      	read-write
        STATUS          	current
        DESCRIPTION     	"Set/Display TX power for radio 2 in Integer"
        ::= { power2 2 }

cableloss2             		OBJECT IDENTIFIER ::= { rf2 5  }

loss1402             		OBJECT IDENTIFIER ::= { cableloss2 1  }

rf2Cableloss140      		OBJECT-TYPE
        SYNTAX          	Opaque
        MAX-ACCESS      	read-write
        STATUS          	current
        DESCRIPTION     	"Set/Display Cableloss 140 for radio 2"
        ::= { loss1402 1 }

rf2Cableloss140Int      	OBJECT-TYPE
        SYNTAX          	Integer
        MAX-ACCESS      	read-write
        STATUS          	current
        DESCRIPTION     	"Set/Display Cableloss 140 for radio 2 in Integer"
        ::= { loss1402 2 }

loss3152             		OBJECT IDENTIFIER ::= { cableloss2 2  }

rf2Cableloss315      		OBJECT-TYPE
        SYNTAX          	Opaque
        MAX-ACCESS      	read-write
        STATUS          	current
        DESCRIPTION     	"Set/Display Cableloss 315 for radio 2"
        ::= { loss3152 1 }

rf2Cableloss315Int      	OBJECT-TYPE
        SYNTAX          	Integer
        MAX-ACCESS      	read-write
        STATUS          	current
        DESCRIPTION     	"Set/Display Cableloss 315 for radio 2 in Integer"
        ::= { loss3152 2 }

loss9152             		OBJECT IDENTIFIER ::= { cableloss2 3  }

rf2Cableloss915      		OBJECT-TYPE
        SYNTAX          	Opaque
        MAX-ACCESS      	read-write
        STATUS          	current
        DESCRIPTION     	"Set/Display Cableloss 915 for radio 2"
        ::= { loss9152 1 }

rf2Cableloss915Int      	OBJECT-TYPE
        SYNTAX          	Integer
        MAX-ACCESS      	read-write
        STATUS          	current
        DESCRIPTION     	"Set/Display Cableloss 915 for radio 2 in Integer"
        ::= { loss9152 2 }

speed2             		OBJECT IDENTIFIER ::= { rf2 6  }

rf2ChannelWidth      		OBJECT-TYPE
        SYNTAX          	INTEGER
        MAX-ACCESS      	read-write
        STATUS          	current
        DESCRIPTION     	"Set/Display Speed channel width for radio 2"
        ::= { speed2 1 }

rf2Modulation      		OBJECT-TYPE
	SYNTAX          		INTEGER { qpsk(0), qam16(1), qam32(2), qam64(3), qam128(4), qam256(5) }
        MAX-ACCESS      	read-write
        STATUS          	current
        DESCRIPTION     	"Set/Display Speed modulation for radio 2"
        ::= { speed2 2 }

rf2Symrate      		OBJECT-TYPE
        SYNTAX          	Opaque
        MAX-ACCESS      	read-only
        STATUS          	current
        DESCRIPTION     	"Display Speed symbol rate for radio 2"
        ::= { speed2 4 }

rf2Speed      			OBJECT-TYPE
        SYNTAX          	Opaque
        MAX-ACCESS      	read-only
        STATUS          	current
        DESCRIPTION     	"Display Speed rate for radio 2"
        ::= { speed2 5 }

atpc2             		OBJECT IDENTIFIER ::= { rf2 7  }

rf2ATPCEnable      		OBJECT-TYPE
    	SYNTAX              	INTEGER { off(0), on(1) }
        MAX-ACCESS      	read-write
        STATUS          	current
        DESCRIPTION     	"Set/Display current status of ATPC feature for radio 2"
        ::= { atpc2 1 }

rf2ATPCMaxPower      		OBJECT-TYPE
        SYNTAX          	Opaque
        MAX-ACCESS      	read-only
        STATUS          	current
        DESCRIPTION     	"Display ATPC maximum power for radio 2"
        ::= { atpc2 2 }

rf2ATPCStepSize      		OBJECT-TYPE
        SYNTAX          	INTEGER
        MAX-ACCESS      	read-only
        STATUS          	current
        DESCRIPTION     	"Display ATPC step size for radio 2"
        ::= { atpc2 3 }

rf2AlignmentMode      		OBJECT-TYPE
    	SYNTAX              	INTEGER { off(0), on(1) }
        MAX-ACCESS      	read-write
        STATUS          	current
        DESCRIPTION     	"Set/Display current status of alignment mode for radio 2"
        ::= { rf2 8 }

target2             		OBJECT IDENTIFIER ::= { rf2 9  }

rf2TargetRSSI      		OBJECT-TYPE
        SYNTAX          	Opaque
        MAX-ACCESS      	read-write
        STATUS          	current
        DESCRIPTION     	"Set/Display target RSSI value for radio 2"
        ::= { target2 1 }

rf2TargetRSSIInt     		OBJECT-TYPE
        SYNTAX          	INTEGER
        MAX-ACCESS      	read-write
        STATUS          	current
        DESCRIPTION     	"Set/Display target RSSI value for radio 2 in Integer"
        ::= { target2 2 }

rf2ODULEDEnable      		OBJECT-TYPE
    	SYNTAX              	INTEGER { off(0), on(1) }
        MAX-ACCESS      	read-write
        STATUS          	current
        DESCRIPTION     	"Set/Display current status of ODU LED display for radio 2"
        ::= { rf2 10 }

rf2ODUPowerEnable      		OBJECT-TYPE
    	SYNTAX              	INTEGER { off(0), on(1) }
        MAX-ACCESS      	read-write
        STATUS          	current
        DESCRIPTION     	"Set/Display current status of ODU power for radio 2"
        ::= { rf2 11 }

rf2ODURxAGC      		OBJECT-TYPE
    	SYNTAX              	INTEGER { off(0), on(1) }
        MAX-ACCESS      	read-write
        STATUS          	current
        DESCRIPTION     	"Set/Display current status of ODU RXAGC loop for radio 2"
        ::= { rf2 12 }

rf2ODUTemp      		OBJECT-TYPE
    	SYNTAX              	INTEGER
        MAX-ACCESS      	read-only
        STATUS          	current
        DESCRIPTION     	"Display current ODU temperature for radio 2"
        ::= { rf2 13 }

rssi2             		OBJECT IDENTIFIER ::= { rf2 14  }

rf2RSSI      			OBJECT-TYPE
    	SYNTAX              	Opaque
        MAX-ACCESS      	read-only
        STATUS          	current
        DESCRIPTION     	"Display current RSSI value for radio 2"
        ::= { rssi2 1 }

rf2RSSI      			OBJECT-TYPE
    	SYNTAX              	Integer
        MAX-ACCESS      	read-only
        STATUS          	current
        DESCRIPTION     	"Display current RSSI value for radio 2 in Integer"
        ::= { rssi2 2 }

pll2             		OBJECT IDENTIFIER ::= { rf2 15  }

rf2ODURFpll      		OBJECT-TYPE
    	SYNTAX              	INTEGER { nolock(0), lock(1) }
        MAX-ACCESS      	read-write
        STATUS          	current
        DESCRIPTION     	"Display current status of ODU RF PLL for radio 2"
        ::= { pll2 1 }

rf2ODUIFpll      		OBJECT-TYPE
    	SYNTAX              	INTEGER { nolock(0), lock(1) }
        MAX-ACCESS      	read-write
        STATUS          	current
        DESCRIPTION     	"Display current status of ODU IF PLL for radio 2"
        ::= { pll2 2 }

rf2ODUTxpll      		OBJECT-TYPE
    	SYNTAX              	INTEGER { nolock(0), lock(1) }
        MAX-ACCESS      	read-write
        STATUS          	current
        DESCRIPTION     	"Display current status of ODU TX PLL for radio 2"
        ::= { pll2 3 }

rf2ODURxpll      		OBJECT-TYPE
    	SYNTAX              	INTEGER { nolock(0), lock(1) }
        MAX-ACCESS      	read-write
        STATUS          	current
        DESCRIPTION     	"Display current status of ODU RX PLL for radio 2"
        ::= { pll2 4 }

incounter2             		OBJECT IDENTIFIER ::= { rf2 16  }

rf2InDataOctets      		OBJECT-TYPE
    	SYNTAX             	Counter32
        MAX-ACCESS      	read-only
        STATUS          	current
        DESCRIPTION     	"Display RF IN data octets counter for radio 2"
        ::= { incounter2 1 }

rf2InDataPackets      		OBJECT-TYPE
    	SYNTAX             	Counter32
        MAX-ACCESS      	read-only
        STATUS          	current
        DESCRIPTION     	"Display RF IN data packets counter for radio 2"
        ::= { incounter2 2 }

rf2InDataDropPackets      	OBJECT-TYPE
    	SYNTAX             	Counter32
        MAX-ACCESS      	read-only
        STATUS          	current
        DESCRIPTION     	"Display RF IN data drop packets counter for radio 2"
        ::= { incounter2 3 }

rf2InPortUtil      		OBJECT-TYPE
    	SYNTAX             	INTEGER
        MAX-ACCESS      	read-only
        STATUS          	current
        DESCRIPTION     	"Display RF IN port utilization for radio 2"
        ::= { incounter2 4 }

outcounter2             		OBJECT IDENTIFIER ::= { rf2 17  }

rf2OutDataOctets      		OBJECT-TYPE
    	SYNTAX             	Counter32
        MAX-ACCESS      	read-only
        STATUS          	current
        DESCRIPTION     	"Display RF OUT data octets counter for radio 2"
        ::= { outcounter2 1 }

rf2OutDataPackets      		OBJECT-TYPE
    	SYNTAX             	Counter32
        MAX-ACCESS      	read-only
        STATUS          	current
        DESCRIPTION     	"Display RF OUT data packets counter for radio 2"
        ::= { outcounter2 2 }

rf2OutPortUtil      		OBJECT-TYPE
    	SYNTAX             	INTEGER
        MAX-ACCESS      	read-only
        STATUS          	current
        DESCRIPTION     	"Display RF OUT port utilization for radio 2"
        ::= { outcounter2 3 }

eth1             		OBJECT IDENTIFIER ::= { gige 1  }

config1             		OBJECT IDENTIFIER ::= { eth1 1  }

gigeEth1AutNegotiate      	OBJECT-TYPE
    	SYNTAX              	INTEGER { off(0), on(1) }
        MAX-ACCESS      	read-write
        STATUS          	current
        DESCRIPTION     	"Set/Display auto neogitate setting for ETH 1"
        ::= { config1 1 }

gigeEth1Duplex      		OBJECT-TYPE
    	SYNTAX              	INTEGER { half(0), full(1) }
        MAX-ACCESS      	read-write
        STATUS          	current
        DESCRIPTION     	"Set/Display duplex setting for ETH 1"
        ::= { config1 2 }

gigeEth1Enable      		OBJECT-TYPE
    	SYNTAX              	INTEGER { off(0), on(1) }
        MAX-ACCESS      	read-write
        STATUS          	current
        DESCRIPTION     	"Set/Display enable setting for ETH 1"
        ::= { config1 3 }

gigeEth1MaxRate      		OBJECT-TYPE
    	SYNTAX              	INTEGER
        MAX-ACCESS      	read-write
        STATUS          	current
        DESCRIPTION     	"Set/Display max rate setting for ETH 1"
        ::= { config1 4 }

gigeEth1PauseFrame      	OBJECT-TYPE
    	SYNTAX              	INTEGER { off(0), on(1) }
        MAX-ACCESS      	read-write
        STATUS          	current
        DESCRIPTION     	"Set/Display pause frame setting for ETH 1"
        ::= { config1 5 }

gigeEth1Priority      		OBJECT-TYPE
        SYNTAX          	INTEGER
        MAX-ACCESS      	read-write
        STATUS          	current
        DESCRIPTION     	"Set/Display priority setting for ETH 1"
        ::= { config1 6 }

gigeEth1Speed      		OBJECT-TYPE
        SYNTAX          	INTEGER 
        MAX-ACCESS      	read-write
        STATUS          	current
        DESCRIPTION     	"Set/Display speed setting for ETH 1"
        ::= { config1 7 }

gigeEth1Status      		OBJECT-TYPE
    	SYNTAX              	INTEGER { off(0), on(1) }
        MAX-ACCESS      	read-only
        STATUS          	current
        DESCRIPTION     	"Set/Display port status for ETH 1"
        ::= { config1 8 }

counter1             		OBJECT IDENTIFIER ::= { eth1 2  }

gigeEth1InOctets      		OBJECT-TYPE
        SYNTAX          	Counter32 
        MAX-ACCESS      	read-only
        STATUS          	current
        DESCRIPTION     	"Display ETH1 IN octets counter"
        ::= { counter1 1 }

gigeEth1InUcastPackets      	OBJECT-TYPE
        SYNTAX          	Counter32 
        MAX-ACCESS      	read-only
        STATUS          	current
        DESCRIPTION     	"Display ETH1 IN unicast packet counter"
        ::= { counter1 2 }

gigeEth1InNUcastPackets      	OBJECT-TYPE
        SYNTAX          	Counter32 
        MAX-ACCESS      	read-only
        STATUS          	current
        DESCRIPTION     	"Display ETH1 IN non-unicast packet counter"
        ::= { counter1 3 }

gigeEth1InTotalPackets      	OBJECT-TYPE
        SYNTAX          	Counter32 
        MAX-ACCESS      	read-only
        STATUS          	current
        DESCRIPTION     	"Display ETH1 IN non-unicast packet counter"
        ::= { counter1 4 }

gigeEth1OutOctets      		OBJECT-TYPE
        SYNTAX          	Counter32 
        MAX-ACCESS      	read-only
        STATUS          	current
        DESCRIPTION     	"Display ETH1 OUT octets counter"
        ::= { counter1 5 }

gigeEth1OutUcastPackets      	OBJECT-TYPE
        SYNTAX          	Counter32 
        MAX-ACCESS      	read-only
        STATUS          	current
        DESCRIPTION     	"Display ETH1 OUT unicast packet counter"
        ::= { counter1 6 }

gigeEth1OutNUcastPackets      	OBJECT-TYPE
        SYNTAX          	Counter32 
        MAX-ACCESS      	read-only
        STATUS          	current
        DESCRIPTION     	"Display ETH1 OUT non-unicast packet counter"
        ::= { counter1 7 }

gigeEth1OutTotalPackets      	OBJECT-TYPE
        SYNTAX          	Counter32 
        MAX-ACCESS      	read-only
        STATUS          	current
        DESCRIPTION     	"Display ETH1 OUT total packet counter"
        ::= { counter1 8 }

gigeEth1CRCError      		OBJECT-TYPE
        SYNTAX          	Counter32 
        MAX-ACCESS      	read-only
        STATUS          	current
        DESCRIPTION     	"Display ETH1 CRC error counter"
        ::= { counter1 9 }

gigeEth1CollisionError      	OBJECT-TYPE
        SYNTAX          	Counter32 
        MAX-ACCESS      	read-only
        STATUS          	current
        DESCRIPTION     	"Display ETH1 Collision error counter"
        ::= { counter1 10 }

eth2             		OBJECT IDENTIFIER ::= { gige 2  }

config2             		OBJECT IDENTIFIER ::= { eth2 1  }

gigeEth2AutNegotiate      	OBJECT-TYPE
    	SYNTAX              	INTEGER { off(0), on(1) }
        MAX-ACCESS      	read-write
        STATUS          	current
        DESCRIPTION     	"Set/Display auto neogitate setting for ETH 2"
        ::= { config2 1 }

gigeEth2Duplex      		OBJECT-TYPE
    	SYNTAX              	INTEGER { half(0), full(1) }
        MAX-ACCESS      	read-write
        STATUS          	current
        DESCRIPTION     	"Set/Display duplex setting for ETH 2"
        ::= { config2 2 }

gigeEth2Enable      		OBJECT-TYPE
    	SYNTAX              	INTEGER { off(0), on(1) }
        MAX-ACCESS      	read-write
        STATUS          	current
        DESCRIPTION     	"Set/Display enable setting for ETH 2"
        ::= { config2 3 }

gigeEth2MaxRate      		OBJECT-TYPE
    	SYNTAX              	INTEGER
        MAX-ACCESS      	read-write
        STATUS          	current
        DESCRIPTION     	"Set/Display max rate setting for ETH 2"
        ::= { config2 4 }

gigeEth2PauseFrame      	OBJECT-TYPE
    	SYNTAX              	INTEGER { off(0), on(1) }
        MAX-ACCESS      	read-write
        STATUS          	current
        DESCRIPTION     	"Set/Display pause frame setting for ETH 2"
        ::= { config2 5 }

gigeEth2Priority      		OBJECT-TYPE
        SYNTAX          	INTEGER
        MAX-ACCESS      	read-write
        STATUS          	current
        DESCRIPTION     	"Set/Display priority setting for ETH 2"
        ::= { config2 6 }

gigeEth2Speed      		OBJECT-TYPE
        SYNTAX          	INTEGER 
        MAX-ACCESS      	read-write
        STATUS          	current
        DESCRIPTION     	"Set/Display speed setting for ETH 2"
        ::= { config2 7 }

gigeEth2Status      		OBJECT-TYPE
    	SYNTAX              	INTEGER { off(0), on(1) }
        MAX-ACCESS      	read-only
        STATUS          	current
        DESCRIPTION     	"Set/Display port status for ETH 2"
        ::= { config2 8 }

counter2             		OBJECT IDENTIFIER ::= { eth2 2  }

gigeEth2InOctets      		OBJECT-TYPE
        SYNTAX          	Counter32 
        MAX-ACCESS      	read-only
        STATUS          	current
        DESCRIPTION     	"Display ETH2 IN octets counter"
        ::= { counter2 1 }

gigeEth2InUcastPackets      	OBJECT-TYPE
        SYNTAX          	Counter32 
        MAX-ACCESS      	read-only
        STATUS          	current
        DESCRIPTION     	"Display ETH2 IN unicast packet counter"
        ::= { counter2 2 }

gigeEth2InNUcastPackets      	OBJECT-TYPE
        SYNTAX          	Counter32 
        MAX-ACCESS      	read-only
        STATUS          	current
        DESCRIPTION     	"Display ETH2 IN non-unicast packet counter"
        ::= { counter2 3 }

gigeEth2InTotalPackets      	OBJECT-TYPE
        SYNTAX          	Counter32 
        MAX-ACCESS      	read-only
        STATUS          	current
        DESCRIPTION     	"Display ETH2 IN non-unicast packet counter"
        ::= { counter2 4 }

gigeEth2OutOctets      		OBJECT-TYPE
        SYNTAX          	Counter32 
        MAX-ACCESS      	read-only
        STATUS          	current
        DESCRIPTION     	"Display ETH2 OUT octets counter"
        ::= { counter2 5 }

gigeEth2OutUcastPackets      	OBJECT-TYPE
        SYNTAX          	Counter32 
        MAX-ACCESS      	read-only
        STATUS          	current
        DESCRIPTION     	"Display ETH2 OUT unicast packet counter"
        ::= { counter2 6 }

gigeEth2OutNUcastPackets      	OBJECT-TYPE
        SYNTAX          	Counter32 
        MAX-ACCESS      	read-only
        STATUS          	current
        DESCRIPTION     	"Display ETH2 OUT non-unicast packet counter"
        ::= { counter2 7 }

gigeEth2OutTotalPackets      	OBJECT-TYPE
        SYNTAX          	Counter32 
        MAX-ACCESS      	read-only
        STATUS          	current
        DESCRIPTION     	"Display ETH2 OUT total packet counter"
        ::= { counter2 8 }

gigeEth2CRCError      		OBJECT-TYPE
        SYNTAX          	Counter32 
        MAX-ACCESS      	read-only
        STATUS          	current
        DESCRIPTION     	"Display ETH2 CRC error counter"
        ::= { counter2 9 }

gigeEth2CollisionError      	OBJECT-TYPE
        SYNTAX          	Counter32 
        MAX-ACCESS      	read-only
        STATUS          	current
        DESCRIPTION     	"Display ETH2 Collision error counter"
        ::= { counter2 10 }

eth3             		OBJECT IDENTIFIER ::= { gige 3  }

config3             		OBJECT IDENTIFIER ::= { eth3 1  }

gigeEth3AutNegotiate      	OBJECT-TYPE
    	SYNTAX              	INTEGER { off(0), on(1) }
        MAX-ACCESS      	read-write
        STATUS          	current
        DESCRIPTION     	"Set/Display auto neogitate setting for ETH 3"
        ::= { config3 1 }

gigeEth3Duplex      		OBJECT-TYPE
    	SYNTAX              	INTEGER { half(0), full(1) }
        MAX-ACCESS      	read-write
        STATUS          	current
        DESCRIPTION     	"Set/Display duplex setting for ETH 3"
        ::= { config3 2 }

gigeEth3Enable      		OBJECT-TYPE
    	SYNTAX              	INTEGER { off(0), on(1) }
        MAX-ACCESS      	read-write
        STATUS          	current
        DESCRIPTION     	"Set/Display enable setting for ETH 3"
        ::= { config3 3 }

gigeEth3MaxRate      		OBJECT-TYPE
    	SYNTAX              	INTEGER
        MAX-ACCESS      	read-write
        STATUS          	current
        DESCRIPTION     	"Set/Display max rate setting for ETH 3"
        ::= { config3 4 }

gigeEth3PauseFrame      	OBJECT-TYPE
    	SYNTAX              	INTEGER { off(0), on(1) }
        MAX-ACCESS      	read-write
        STATUS          	current
        DESCRIPTION     	"Set/Display pause frame setting for ETH 3"
        ::= { config3 5 }

gigeEth3Priority      		OBJECT-TYPE
        SYNTAX          	INTEGER
        MAX-ACCESS      	read-write
        STATUS          	current
        DESCRIPTION     	"Set/Display priority setting for ETH 3"
        ::= { config3 6 }

gigeEth3Speed      		OBJECT-TYPE
        SYNTAX          	INTEGER 
        MAX-ACCESS      	read-write
        STATUS          	current
        DESCRIPTION     	"Set/Display speed setting for ETH 3"
        ::= { config3 7 }

gigeEth3Status      		OBJECT-TYPE
    	SYNTAX              	INTEGER { off(0), on(1) }
        MAX-ACCESS      	read-only
        STATUS          	current
        DESCRIPTION     	"Set/Display port status for ETH 3"
        ::= { config3 8 }

counter3             		OBJECT IDENTIFIER ::= { eth3 2  }

gigeEth2InOctets      		OBJECT-TYPE
        SYNTAX          	Counter32 
        MAX-ACCESS      	read-only
        STATUS          	current
        DESCRIPTION     	"Display ETH3 IN octets counter"
        ::= { counter3 1 }

gigeEth3InUcastPackets      	OBJECT-TYPE
        SYNTAX          	Counter32 
        MAX-ACCESS      	read-only
        STATUS          	current
        DESCRIPTION     	"Display ETH3 IN unicast packet counter"
        ::= { counter3 2 }

gigeEth3InNUcastPackets      	OBJECT-TYPE
        SYNTAX          	Counter32 
        MAX-ACCESS      	read-only
        STATUS          	current
        DESCRIPTION     	"Display ETH3 IN non-unicast packet counter"
        ::= { counter3 3 }

gigeEth3InTotalPackets      	OBJECT-TYPE
        SYNTAX          	Counter32 
        MAX-ACCESS      	read-only
        STATUS          	current
        DESCRIPTION     	"Display ETH3 IN non-unicast packet counter"
        ::= { counter3 4 }

gigeEth3OutOctets      		OBJECT-TYPE
        SYNTAX          	Counter32 
        MAX-ACCESS      	read-only
        STATUS          	current
        DESCRIPTION     	"Display ETH3 OUT octets counter"
        ::= { counter3 5 }

gigeEth3OutUcastPackets      	OBJECT-TYPE
        SYNTAX          	Counter32 
        MAX-ACCESS      	read-only
        STATUS          	current
        DESCRIPTION     	"Display ETH3 OUT unicast packet counter"
        ::= { counter3 6 }

gigeEth3OutNUcastPackets      	OBJECT-TYPE
        SYNTAX          	Counter32 
        MAX-ACCESS      	read-only
        STATUS          	current
        DESCRIPTION     	"Display ETH3 OUT non-unicast packet counter"
        ::= { counter3 7 }

gigeEth3OutTotalPackets      	OBJECT-TYPE
        SYNTAX          	Counter32 
        MAX-ACCESS      	read-only
        STATUS          	current
        DESCRIPTION     	"Display ETH3 OUT total packet counter"
        ::= { counter3 8 }

gigeEth3CRCError      		OBJECT-TYPE
        SYNTAX          	Counter32 
        MAX-ACCESS      	read-only
        STATUS          	current
        DESCRIPTION     	"Display ETH3 CRC error counter"
        ::= { counter3 9 }

gigeEth3CollisionError      	OBJECT-TYPE
        SYNTAX          	Counter32 
        MAX-ACCESS      	read-only
        STATUS          	current
        DESCRIPTION     	"Display ETH3 Collision error counter"
        ::= { counter3 10 }

eth4             		OBJECT IDENTIFIER ::= { gige 4  }

config4             		OBJECT IDENTIFIER ::= { eth4 1  }

gigeEth4AutNegotiate      	OBJECT-TYPE
    	SYNTAX              	INTEGER { off(0), on(1) }
        MAX-ACCESS      	read-write
        STATUS          	current
        DESCRIPTION     	"Set/Display auto neogitate setting for ETH 4"
        ::= { config4 1 }

gigeEth4Duplex      		OBJECT-TYPE
    	SYNTAX              	INTEGER { half(0), full(1) }
        MAX-ACCESS      	read-write
        STATUS          	current
        DESCRIPTION     	"Set/Display duplex setting for ETH 4"
        ::= { config4 2 }

gigeEth4Enable      		OBJECT-TYPE
    	SYNTAX              	INTEGER { off(0), on(1) }
        MAX-ACCESS      	read-write
        STATUS          	current
        DESCRIPTION     	"Set/Display enable setting for ETH 4"
        ::= { config4 3 }

gigeEth4MaxRate      		OBJECT-TYPE
    	SYNTAX              	INTEGER
        MAX-ACCESS      	read-write
        STATUS          	current
        DESCRIPTION     	"Set/Display max rate setting for ETH 4"
        ::= { config4 4 }

gigeEth4PauseFrame      	OBJECT-TYPE
    	SYNTAX              	INTEGER { off(0), on(1) }
        MAX-ACCESS      	read-write
        STATUS          	current
        DESCRIPTION     	"Set/Display pause frame setting for ETH 4"
        ::= { config4 5 }

gigeEth4Priority      		OBJECT-TYPE
        SYNTAX          	INTEGER
        MAX-ACCESS      	read-write
        STATUS          	current
        DESCRIPTION     	"Set/Display priority setting for ETH 4"
        ::= { config4 6 }

gigeEth4Speed      		OBJECT-TYPE
        SYNTAX          	INTEGER 
        MAX-ACCESS      	read-write
        STATUS          	current
        DESCRIPTION     	"Set/Display speed setting for ETH 4"
        ::= { config4 7 }

gigeEth4Status      		OBJECT-TYPE
    	SYNTAX              	INTEGER { off(0), on(1) }
        MAX-ACCESS      	read-only
        STATUS          	current
        DESCRIPTION     	"Set/Display port status for ETH 4"
        ::= { config4 8 }

counter4             		OBJECT IDENTIFIER ::= { eth4 2  }

gigeEth4InOctets      		OBJECT-TYPE
        SYNTAX          	Counter32 
        MAX-ACCESS      	read-only
        STATUS          	current
        DESCRIPTION     	"Display ETH4 IN octets counter"
        ::= { counter4 1 }

gigeEth4InUcastPackets      	OBJECT-TYPE
        SYNTAX          	Counter32 
        MAX-ACCESS      	read-only
        STATUS          	current
        DESCRIPTION     	"Display ETH4 IN unicast packet counter"
        ::= { counter4 2 }

gigeEth4InNUcastPackets      	OBJECT-TYPE
        SYNTAX          	Counter32 
        MAX-ACCESS      	read-only
        STATUS          	current
        DESCRIPTION     	"Display ETH4 IN non-unicast packet counter"
        ::= { counter4 3 }

gigeEth4InTotalPackets      	OBJECT-TYPE
        SYNTAX          	Counter32 
        MAX-ACCESS      	read-only
        STATUS          	current
        DESCRIPTION     	"Display ETH4 IN non-unicast packet counter"
        ::= { counter4 4 }

gigeEth4OutOctets      		OBJECT-TYPE
        SYNTAX          	Counter32 
        MAX-ACCESS      	read-only
        STATUS          	current
        DESCRIPTION     	"Display ETH4 OUT octets counter"
        ::= { counter4 5 }

gigeEth4OutUcastPackets      	OBJECT-TYPE
        SYNTAX          	Counter32 
        MAX-ACCESS      	read-only
        STATUS          	current
        DESCRIPTION     	"Display ETH4 OUT unicast packet counter"
        ::= { counter4 6 }

gigeEth4OutNUcastPackets      	OBJECT-TYPE
        SYNTAX          	Counter32 
        MAX-ACCESS      	read-only
        STATUS          	current
        DESCRIPTION     	"Display ETH4 OUT non-unicast packet counter"
        ::= { counter4 7 }

gigeEth4OutTotalPackets      	OBJECT-TYPE
        SYNTAX          	Counter32 
        MAX-ACCESS      	read-only
        STATUS          	current
        DESCRIPTION     	"Display ETH4 OUT total packet counter"
        ::= { counter4 8 }

gigeEth4CRCError      		OBJECT-TYPE
        SYNTAX          	Counter32 
        MAX-ACCESS      	read-only
        STATUS          	current
        DESCRIPTION     	"Display ETH4 CRC error counter"
        ::= { counter4 9 }

gigeEth4CollisionError      	OBJECT-TYPE
        SYNTAX          	Counter32 
        MAX-ACCESS      	read-only
        STATUS          	current
        DESCRIPTION     	"Display ETH4 Collision error counter"
        ::= { counter4 10 }

eth5             		OBJECT IDENTIFIER ::= { gige 5  }

config5             		OBJECT IDENTIFIER ::= { eth5 1  }

gigeEth5AutNegotiate      	OBJECT-TYPE
    	SYNTAX              	INTEGER { off(0), on(1) }
        MAX-ACCESS      	read-write
        STATUS          	current
        DESCRIPTION     	"Set/Display auto neogitate setting for ETH 5"
        ::= { config5 1 }

gigeEth5Duplex      		OBJECT-TYPE
    	SYNTAX              	INTEGER { half(0), full(1) }
        MAX-ACCESS      	read-write
        STATUS          	current
        DESCRIPTION     	"Set/Display duplex setting for ETH 5"
        ::= { config5 2 }

gigeEth5Enable      		OBJECT-TYPE
    	SYNTAX              	INTEGER { off(0), on(1) }
        MAX-ACCESS      	read-write
        STATUS          	current
        DESCRIPTION     	"Set/Display enable setting for ETH 5"
        ::= { config5 3 }

gigeEth5MaxRate      		OBJECT-TYPE
    	SYNTAX              	INTEGER
        MAX-ACCESS      	read-write
        STATUS          	current
        DESCRIPTION     	"Set/Display max rate setting for ETH 5"
        ::= { config5 4 }

gigeEth5PauseFrame      	OBJECT-TYPE
    	SYNTAX              	INTEGER { off(0), on(1) }
        MAX-ACCESS      	read-write
        STATUS          	current
        DESCRIPTION     	"Set/Display pause frame setting for ETH 5"
        ::= { config5 5 }

gigeEth5Priority      		OBJECT-TYPE
        SYNTAX          	INTEGER
        MAX-ACCESS      	read-write
        STATUS          	current
        DESCRIPTION     	"Set/Display priority setting for ETH 5"
        ::= { config5 6 }

gigeEth5Speed      		OBJECT-TYPE
        SYNTAX          	INTEGER 
        MAX-ACCESS      	read-write
        STATUS          	current
        DESCRIPTION     	"Set/Display speed setting for ETH 5"
        ::= { config5 7 }

gigeEth5Status      		OBJECT-TYPE
    	SYNTAX              	INTEGER { off(0), on(1) }
        MAX-ACCESS      	read-only
        STATUS          	current
        DESCRIPTION     	"Set/Display port status for ETH 5"
        ::= { config5 8 }

counter5             		OBJECT IDENTIFIER ::= { eth5 2  }

gigeEth5InOctets      		OBJECT-TYPE
        SYNTAX          	Counter32 
        MAX-ACCESS      	read-only
        STATUS          	current
        DESCRIPTION     	"Display ETH5 IN octets counter"
        ::= { counter5 1 }

gigeEth5InUcastPackets      	OBJECT-TYPE
        SYNTAX          	Counter32 
        MAX-ACCESS      	read-only
        STATUS          	current
        DESCRIPTION     	"Display ETH5 IN unicast packet counter"
        ::= { counter5 2 }

gigeEth5InNUcastPackets      	OBJECT-TYPE
        SYNTAX          	Counter32 
        MAX-ACCESS      	read-only
        STATUS          	current
        DESCRIPTION     	"Display ETH5 IN non-unicast packet counter"
        ::= { counter5 3 }

gigeEth5InTotalPackets      	OBJECT-TYPE
        SYNTAX          	Counter32 
        MAX-ACCESS      	read-only
        STATUS          	current
        DESCRIPTION     	"Display ETH5 IN non-unicast packet counter"
        ::= { counter5 4 }

gigeEth5OutOctets      		OBJECT-TYPE
        SYNTAX          	Counter32 
        MAX-ACCESS      	read-only
        STATUS          	current
        DESCRIPTION     	"Display ETH5 OUT octets counter"
        ::= { counter5 5 }

gigeEth5OutUcastPackets      	OBJECT-TYPE
        SYNTAX          	Counter32 
        MAX-ACCESS      	read-only
        STATUS          	current
        DESCRIPTION     	"Display ETH5 OUT unicast packet counter"
        ::= { counter5 6 }

gigeEth5OutNUcastPackets      	OBJECT-TYPE
        SYNTAX          	Counter32 
        MAX-ACCESS      	read-only
        STATUS          	current
        DESCRIPTION     	"Display ETH5 OUT non-unicast packet counter"
        ::= { counter5 7 }

gigeEth5OutTotalPackets      	OBJECT-TYPE
        SYNTAX          	Counter32 
        MAX-ACCESS      	read-only
        STATUS          	current
        DESCRIPTION     	"Display ETH5 OUT total packet counter"
        ::= { counter5 8 }

gigeEth5CRCError      		OBJECT-TYPE
        SYNTAX          	Counter32 
        MAX-ACCESS      	read-only
        STATUS          	current
        DESCRIPTION     	"Display ETH5 CRC error counter"
        ::= { counter5 9 }

gigeEth5CollisionError      	OBJECT-TYPE
        SYNTAX          	Counter32 
        MAX-ACCESS      	read-only
        STATUS          	current
        DESCRIPTION     	"Display ETH5 Collision error counter"
        ::= { counter5 10 }

eth6             		OBJECT IDENTIFIER ::= { gige 6  }

config6             		OBJECT IDENTIFIER ::= { eth6 1  }

gigeEth6AutNegotiate      	OBJECT-TYPE
    	SYNTAX              	INTEGER { off(0), on(1) }
        MAX-ACCESS      	read-write
        STATUS          	current
        DESCRIPTION     	"Set/Display auto neogitate setting for ETH 6"
        ::= { config6 1 }

gigeEth6Duplex      		OBJECT-TYPE
    	SYNTAX              	INTEGER { half(0), full(1) }
        MAX-ACCESS      	read-write
        STATUS          	current
        DESCRIPTION     	"Set/Display duplex setting for ETH 6"
        ::= { config6 2 }

gigeEth6Enable      		OBJECT-TYPE
    	SYNTAX              	INTEGER { off(0), on(1) }
        MAX-ACCESS      	read-write
        STATUS          	current
        DESCRIPTION     	"Set/Display enable setting for ETH 6"
        ::= { config6 3 }

gigeEth6MaxRate      		OBJECT-TYPE
    	SYNTAX              	INTEGER
        MAX-ACCESS      	read-write
        STATUS          	current
        DESCRIPTION     	"Set/Display max rate setting for ETH 6"
        ::= { config6 4 }

gigeEth6PauseFrame      	OBJECT-TYPE
    	SYNTAX              	INTEGER { off(0), on(1) }
        MAX-ACCESS      	read-write
        STATUS          	current
        DESCRIPTION     	"Set/Display pause frame setting for ETH 6"
        ::= { config6 5 }

gigeEth6Priority      		OBJECT-TYPE
        SYNTAX          	INTEGER
        MAX-ACCESS      	read-write
        STATUS          	current
        DESCRIPTION     	"Set/Display priority setting for ETH 6"
        ::= { config6 6 }

gigeEth6Speed      		OBJECT-TYPE
        SYNTAX          	INTEGER 
        MAX-ACCESS      	read-write
        STATUS          	current
        DESCRIPTION     	"Set/Display speed setting for ETH 6"
        ::= { config6 7 }

gigeEth6Status      		OBJECT-TYPE
    	SYNTAX              	INTEGER { off(0), on(1) }
        MAX-ACCESS      	read-only
        STATUS          	current
        DESCRIPTION     	"Set/Display port status for ETH 6"
        ::= { config6 8 }

counter6             		OBJECT IDENTIFIER ::= { eth6 2  }

gigeEth6InOctets      		OBJECT-TYPE
        SYNTAX          	Counter32 
        MAX-ACCESS      	read-only
        STATUS          	current
        DESCRIPTION     	"Display ETH6 IN octets counter"
        ::= { counter6 1 }

gigeEth6InUcastPackets      	OBJECT-TYPE
        SYNTAX          	Counter32 
        MAX-ACCESS      	read-only
        STATUS          	current
        DESCRIPTION     	"Display ETH6 IN unicast packet counter"
        ::= { counter6 2 }

gigeEth6InNUcastPackets      	OBJECT-TYPE
        SYNTAX          	Counter32 
        MAX-ACCESS      	read-only
        STATUS          	current
        DESCRIPTION     	"Display ETH6 IN non-unicast packet counter"
        ::= { counter6 3 }

gigeEth6InTotalPackets      	OBJECT-TYPE
        SYNTAX          	Counter32 
        MAX-ACCESS      	read-only
        STATUS          	current
        DESCRIPTION     	"Display ETH6 IN non-unicast packet counter"
        ::= { counter6 4 }

gigeEth6OutOctets      		OBJECT-TYPE
        SYNTAX          	Counter32 
        MAX-ACCESS      	read-only
        STATUS          	current
        DESCRIPTION     	"Display ETH6 OUT octets counter"
        ::= { counter6 5 }

gigeEth6OutUcastPackets      	OBJECT-TYPE
        SYNTAX          	Counter32 
        MAX-ACCESS      	read-only
        STATUS          	current
        DESCRIPTION     	"Display ETH6 OUT unicast packet counter"
        ::= { counter6 6 }

gigeEth6OutNUcastPackets      	OBJECT-TYPE
        SYNTAX          	Counter32 
        MAX-ACCESS      	read-only
        STATUS          	current
        DESCRIPTION     	"Display ETH6 OUT non-unicast packet counter"
        ::= { counter6 7 }

gigeEth6OutTotalPackets      	OBJECT-TYPE
        SYNTAX          	Counter32 
        MAX-ACCESS      	read-only
        STATUS          	current
        DESCRIPTION     	"Display ETH6 OUT total packet counter"
        ::= { counter6 8 }

gigeEth6CRCError      		OBJECT-TYPE
        SYNTAX          	Counter32 
        MAX-ACCESS      	read-only
        STATUS          	current
        DESCRIPTION     	"Display ETH6 CRC error counter"
        ::= { counter6 9 }

gigeEth6CollisionError      	OBJECT-TYPE
        SYNTAX          	Counter32 
        MAX-ACCESS      	read-only
        STATUS          	current
        DESCRIPTION     	"Display ETH6 Collision error counter"
        ::= { counter6 10 }

cos                             OBJECT IDENTIFIER ::= { gige 7 }

gigeEthPriority0COS             OBJECT-TYPE
        SYNTAX                  INTEGER
        MAX-ACCESS              read-write
        STATUS                  current
        DESCRIPTION             "Display ETH priority1 cOS queue number"
        ::= { cos 1 }

gigeEthPriority1COS             OBJECT-TYPE
        SYNTAX                  INTEGER
        MAX-ACCESS              read-write
        STATUS                  current
        DESCRIPTION             "Display ETH priority1 cOS queue number"
        ::= { cos 2 }

gigeEthPriority2COS             OBJECT-TYPE
        SYNTAX                  INTEGER
        MAX-ACCESS              read-write
        STATUS                  current
        DESCRIPTION             "Display ETH priority1 cOS queue number"
        ::= { cos 3 }

gigeEthPriority3COS             OBJECT-TYPE
        SYNTAX                  INTEGER
        MAX-ACCESS              read-write
        STATUS                  current
        DESCRIPTION             "Display ETH priority1 cOS queue number"
        ::= { cos 4 }

gigeEthPriority4COS             OBJECT-TYPE
        SYNTAX                  INTEGER
        MAX-ACCESS              read-write
        STATUS                  current
        DESCRIPTION             "Display ETH priority1 cOS queue number"
        ::= { cos 5 }

gigeEthPriority5COS             OBJECT-TYPE
        SYNTAX                  INTEGER
        MAX-ACCESS              read-write
        STATUS                  current
        DESCRIPTION             "Display ETH priority1 cOS queue number"
        ::= { cos 6 }

gigeEthPriority6COS             OBJECT-TYPE
        SYNTAX                  INTEGER
        MAX-ACCESS              read-write
        STATUS                  current
        DESCRIPTION             "Display ETH priority1 cOS queue number"
        ::= { cos 7 }

gigeEthPriority7COS             OBJECT-TYPE
        SYNTAX                  INTEGER
        MAX-ACCESS              read-write
        STATUS                  current
        DESCRIPTION             "Display ETH priority1 cOS queue number"
        ::= { cos 8 }

stm1_1             		OBJECT IDENTIFIER ::= { stm1 1  }

stm1_config1             	OBJECT IDENTIFIER ::= { stm1_1 1  }

stm1Port1Status      		OBJECT-TYPE
    	SYNTAX              	INTEGER { off(0), on(1) }
        MAX-ACCESS      	read-only
        STATUS          	current
        DESCRIPTION     	"Display STM1 port1 status"
        ::= { stm1_config1 1 }

stm1_counter1             	OBJECT IDENTIFIER ::= { stm1_1 2  }

stm1Port1CounterB1      	OBJECT-TYPE
    	SYNTAX              	Counter32
        MAX-ACCESS      	read-only
        STATUS          	current
        DESCRIPTION     	"Display STM1 port1 B1 Counter"
        ::= { stm1_counter1 1 }

stm1Port1CounterB2      	OBJECT-TYPE
    	SYNTAX              	Counter32
        MAX-ACCESS      	read-only
        STATUS          	current
        DESCRIPTION     	"Display STM1 port1 B2 Counter"
        ::= { stm1_counter1 2 }

stm1Port1CounterREI      	OBJECT-TYPE
    	SYNTAX              	Counter32
        MAX-ACCESS      	read-only
        STATUS          	current
        DESCRIPTION     	"Display STM1 port1 REI Counter"
        ::= { stm1_counter1 3 }

stm1_alarm1             	OBJECT IDENTIFIER ::= { stm1_1 3  }

stm1Port1AlarmLOS      		OBJECT-TYPE
    	SYNTAX              	Counter32
        MAX-ACCESS      	read-only
        STATUS          	current
        DESCRIPTION     	"Display STM1 port1 LOS alarm"
        ::= { stm1_alarm1 1 }

stm1Port1AlarmOOF      		OBJECT-TYPE
    	SYNTAX              	Counter32
        MAX-ACCESS      	read-only
        STATUS          	current
        DESCRIPTION     	"Display STM1 port1 OOF alarm"
        ::= { stm1_alarm1 2 }

stm1Port1AlarmLOF      		OBJECT-TYPE
    	SYNTAX              	Counter32
        MAX-ACCESS      	read-only
        STATUS          	current
        DESCRIPTION     	"Display STM1 port1 LOF alarm"
        ::= { stm1_alarm1 3 }

stm1Port1AlarmAIS      		OBJECT-TYPE
    	SYNTAX              	Counter32
        MAX-ACCESS      	read-only
        STATUS          	current
        DESCRIPTION     	"Display STM1 port1 AIS alarm"
        ::= { stm1_alarm1 4 }

stm1Port1AlarmRDI      		OBJECT-TYPE
    	SYNTAX              	Counter32
        MAX-ACCESS      	read-only
        STATUS          	current
        DESCRIPTION     	"Display STM1 port1 RDI alarm"
        ::= { stm1_alarm1 5 }

stm1Port1AlarmTIM      		OBJECT-TYPE
    	SYNTAX              	Counter32
        MAX-ACCESS      	read-only
        STATUS          	current
        DESCRIPTION     	"Display STM1 port1 TIM alarm"
        ::= { stm1_alarm1 6 }

stm1Port1AlarmREI      		OBJECT-TYPE
    	SYNTAX              	Counter32
        MAX-ACCESS      	read-only
        STATUS          	current
        DESCRIPTION     	"Display STM1 port1 REI alarm"
        ::= { stm1_alarm1 7 }

stm1_2             		OBJECT IDENTIFIER ::= { stm1 2  }

stm1_config2             	OBJECT IDENTIFIER ::= { stm1_2 1  }

stm1Port2Status      		OBJECT-TYPE
    	SYNTAX              	INTEGER { off(0), on(1) }
        MAX-ACCESS      	read-only
        STATUS          	current
        DESCRIPTION     	"Display STM1 port2 status"
        ::= { stm1_config2 1 }

stm1_counter2             	OBJECT IDENTIFIER ::= { stm1_2 2  }

stm1Port2CounterB1      	OBJECT-TYPE
    	SYNTAX              	Counter32
        MAX-ACCESS      	read-only
        STATUS          	current
        DESCRIPTION     	"Display STM1 port2 B1 Counter"
        ::= { stm1_counter2 1 }

stm1Port2CounterB2      	OBJECT-TYPE
    	SYNTAX              	Counter32
        MAX-ACCESS      	read-only
        STATUS          	current
        DESCRIPTION     	"Display STM1 port2 B2 Counter"
        ::= { stm1_counter2 2 }

stm1Port2CounterREI      	OBJECT-TYPE
    	SYNTAX              	Counter32
        MAX-ACCESS      	read-only
        STATUS          	current
        DESCRIPTION     	"Display STM1 port2 REI Counter"
        ::= { stm1_counter2 3 }

stm1_alarm2             	OBJECT IDENTIFIER ::= { stm1_2 3  }

stm1Port2AlarmLOS      		OBJECT-TYPE
    	SYNTAX              	Counter32
        MAX-ACCESS      	read-only
        STATUS          	current
        DESCRIPTION     	"Display STM1 port2 LOS alarm"
        ::= { stm1_alarm2 1 }

stm1Port2AlarmOOF      		OBJECT-TYPE
    	SYNTAX              	Counter32
        MAX-ACCESS      	read-only
        STATUS          	current
        DESCRIPTION     	"Display STM1 port2 OOF alarm"
        ::= { stm1_alarm2 2 }

stm1Port2AlarmLOF      		OBJECT-TYPE
    	SYNTAX              	Counter32
        MAX-ACCESS      	read-only
        STATUS          	current
        DESCRIPTION     	"Display STM1 port2 LOF alarm"
        ::= { stm1_alarm2 3 }

stm1Port2AlarmAIS      		OBJECT-TYPE
    	SYNTAX              	Counter32
        MAX-ACCESS      	read-only
        STATUS          	current
        DESCRIPTION     	"Display STM1 port2 AIS alarm"
        ::= { stm1_alarm2 4 }

stm1Port2AlarmRDI      		OBJECT-TYPE
    	SYNTAX              	Counter32
        MAX-ACCESS      	read-only
        STATUS          	current
        DESCRIPTION     	"Display STM1 port2 RDI alarm"
        ::= { stm1_alarm2 5 }

stm1Port2AlarmTIM      		OBJECT-TYPE
    	SYNTAX              	Counter32
        MAX-ACCESS      	read-only
        STATUS          	current
        DESCRIPTION     	"Display STM1 port2 TIM alarm"
        ::= { stm1_alarm2 6 }

tdm1             		OBJECT IDENTIFIER ::= { tdm 1  }

tdm_config1             	OBJECT IDENTIFIER ::= { tdm1 1  }

tdmPort1Status      		OBJECT-TYPE
    	SYNTAX              	INTEGER { off(0), on(1) }
        MAX-ACCESS      	read-only
        STATUS          	current
        DESCRIPTION     	"Display TDM port1 status"
        ::= { tdm_config1 1 }

tdmPort1CableConfig      	OBJECT-TYPE
    	SYNTAX              	INTEGER { len0_133(0), len133_266(1), len266_399(2), len399_533(3),
					  len355_655(4) }
        MAX-ACCESS      	read-only
        STATUS          	current
        DESCRIPTION     	"Display TDM port1 cable configuration"
        ::= { tdm_config1 2 }

tdm_counter1             	OBJECT IDENTIFIER ::= { tdm1 2  }

tdmPort1CounterCrcBlockErrors  	OBJECT-TYPE
    	SYNTAX              	Counter32
        MAX-ACCESS      	read-only
        STATUS          	current
        DESCRIPTION     	"Display TDM port1 Crc Block error Counter"
        ::= { tdm_counter1 1 }

tdmPort1CounterExCrcErrors      OBJECT-TYPE
    	SYNTAX              	Counter32
        MAX-ACCESS      	read-only
        STATUS          	current
        DESCRIPTION     	"Display TDM port1 excessive CRC block Counter"
        ::= { tdm_counter1 2 }

tdmPort1CounterFBAErrors      	OBJECT-TYPE
    	SYNTAX              	Counter32
        MAX-ACCESS      	read-only
        STATUS          	current
        DESCRIPTION     	"Display TDM port1 FBA Errors Counter"
        ::= { tdm_counter1 3 }

tdmPort1CounterFEBErrors      	OBJECT-TYPE
    	SYNTAX              	Counter32
        MAX-ACCESS      	read-only
        STATUS          	current
        DESCRIPTION     	"Display TDM port1 FEB Errors Counter"
        ::= { tdm_counter1 4 }

tdmPort1CounterLCViolations    	OBJECT-TYPE
    	SYNTAX              	Counter32
        MAX-ACCESS      	read-only
        STATUS          	current
        DESCRIPTION     	"Display TDM port1 LC Violations Counter"
        ::= { tdm_counter1 5 }

tdm_alarm1             	OBJECT IDENTIFIER ::= { tdm1 3  }

tdmPort1AlarmLOS      		OBJECT-TYPE
    	SYNTAX              	Counter32
        MAX-ACCESS      	read-only
        STATUS          	current
        DESCRIPTION     	"Display TDM port1 LOS alarm"
        ::= { tdm_alarm1 1 }

tdmPort1AlarmLOF      		OBJECT-TYPE
    	SYNTAX              	Counter32
        MAX-ACCESS      	read-only
        STATUS          	current
        DESCRIPTION     	"Display TDM port1 LOF alarm"
        ::= { tdm_alarm1 2 }

tdmPort1AlarmAIS      		OBJECT-TYPE
    	SYNTAX              	Counter32
        MAX-ACCESS      	read-only
        STATUS          	current
        DESCRIPTION     	"Display TDM port1 AIS alarm"
        ::= { tdm_alarm1 3 }

tdmPort1AlarmTS16AIS      	OBJECT-TYPE
    	SYNTAX              	Counter32
        MAX-ACCESS      	read-only
        STATUS          	current
        DESCRIPTION     	"Display TDM port1 TS16AIS alarm"
        ::= { tdm_alarm1 4 }

tdmPort1AlarmRAI      		OBJECT-TYPE
    	SYNTAX              	Counter32
        MAX-ACCESS      	read-only
        STATUS          	current
        DESCRIPTION     	"Display TDM port1 RAI alarm"
        ::= { tdm_alarm1 5 }

tdmPort1AlarmRMA      		OBJECT-TYPE
    	SYNTAX              	Counter32
        MAX-ACCESS      	read-only
        STATUS          	current
        DESCRIPTION     	"Display TDM port1 RMA alarm"
        ::= { tdm_alarm1 6 }

tdmPort1AlarmLCMFA      	OBJECT-TYPE
    	SYNTAX              	Counter32
        MAX-ACCESS      	read-only
        STATUS          	current
        DESCRIPTION     	"Display TDM port1 LCMFA alarm"
        ::= { tdm_alarm1 7 }

tdmPort1AlarmLSMFA      	OBJECT-TYPE
    	SYNTAX              	Counter32
        MAX-ACCESS      	read-only
        STATUS          	current
        DESCRIPTION     	"Display TDM port1 LSMFA alarm"
        ::= { tdm_alarm1 8 }

tdm2             		OBJECT IDENTIFIER ::= { tdm 2  }

tdm_config2             	OBJECT IDENTIFIER ::= { tdm2 1  }

tdmPort2Status      		OBJECT-TYPE
    	SYNTAX              	INTEGER { off(0), on(1) }
        MAX-ACCESS      	read-only
        STATUS          	current
        DESCRIPTION     	"Display TDM port2 status"
        ::= { tdm_config2 1 }

tdmPort2CableConfig      	OBJECT-TYPE
    	SYNTAX              	INTEGER { len0_133(0), len133_266(1), len266_399(2), len399_533(3),
					  len355_655(4) }
        MAX-ACCESS      	read-only
        STATUS          	current
        DESCRIPTION     	"Display TDM port2 cable configuration"
        ::= { tdm_config2 2 }

tdm_counter2             	OBJECT IDENTIFIER ::= { tdm2 2  }

tdmPort2CounterCrcBlockErrors  	OBJECT-TYPE
    	SYNTAX              	Counter32
        MAX-ACCESS      	read-only
        STATUS          	current
        DESCRIPTION     	"Display TDM port2 Crc Block error Counter"
        ::= { tdm_counter2 1 }

tdmPort2CounterExCrcErrors      OBJECT-TYPE
    	SYNTAX              	Counter32
        MAX-ACCESS      	read-only
        STATUS          	current
        DESCRIPTION     	"Display TDM port2 excessive CRC block Counter"
        ::= { tdm_counter2 2 }

tdmPort2CounterFBAErrors      	OBJECT-TYPE
    	SYNTAX              	Counter32
        MAX-ACCESS      	read-only
        STATUS          	current
        DESCRIPTION     	"Display TDM port2 FBA Errors Counter"
        ::= { tdm_counter2 3 }

tdmPort2CounterFEBErrors      	OBJECT-TYPE
    	SYNTAX              	Counter32
        MAX-ACCESS      	read-only
        STATUS          	current
        DESCRIPTION     	"Display TDM port2 FEB Errors Counter"
        ::= { tdm_counter2 4 }

tdmPort2CounterLCViolations    	OBJECT-TYPE
    	SYNTAX              	Counter32
        MAX-ACCESS      	read-only
        STATUS          	current
        DESCRIPTION     	"Display TDM port2 LC Violations Counter"
        ::= { tdm_counter2 5 }

tdm_alarm2             	OBJECT IDENTIFIER ::= { tdm2 3  }

tdmPort2AlarmLOS      		OBJECT-TYPE
    	SYNTAX              	Counter32
        MAX-ACCESS      	read-only
        STATUS          	current
        DESCRIPTION     	"Display TDM port2 LOS alarm"
        ::= { tdm_alarm2 1 }

tdmPort2AlarmLOF      		OBJECT-TYPE
    	SYNTAX              	Counter32
        MAX-ACCESS      	read-only
        STATUS          	current
        DESCRIPTION     	"Display TDM port2 LOF alarm"
        ::= { tdm_alarm2 2 }

tdmPort2AlarmAIS      		OBJECT-TYPE
    	SYNTAX              	Counter32
        MAX-ACCESS      	read-only
        STATUS          	current
        DESCRIPTION     	"Display TDM port2 AIS alarm"
        ::= { tdm_alarm2 3 }

tdmPort2AlarmTS16AIS      	OBJECT-TYPE
    	SYNTAX              	Counter32
        MAX-ACCESS      	read-only
        STATUS          	current
        DESCRIPTION     	"Display TDM port2 TS16AIS alarm"
        ::= { tdm_alarm2 4 }

tdmPort2AlarmRAI      		OBJECT-TYPE
    	SYNTAX              	Counter32
        MAX-ACCESS      	read-only
        STATUS          	current
        DESCRIPTION     	"Display TDM port2 RAI alarm"
        ::= { tdm_alarm2 5 }

tdmPort2AlarmRMA      		OBJECT-TYPE
    	SYNTAX              	Counter32
        MAX-ACCESS      	read-only
        STATUS          	current
        DESCRIPTION     	"Display TDM port2 RMA alarm"
        ::= { tdm_alarm2 6 }

tdmPort2AlarmLCMFA      	OBJECT-TYPE
    	SYNTAX              	Counter32
        MAX-ACCESS      	read-only
        STATUS          	current
        DESCRIPTION     	"Display TDM port2 LCMFA alarm"
        ::= { tdm_alarm2 7 }

tdmPort2AlarmLSMFA      	OBJECT-TYPE
    	SYNTAX              	Counter32
        MAX-ACCESS      	read-only
        STATUS          	current
        DESCRIPTION     	"Display TDM port2 LSMFA alarm"
        ::= { tdm_alarm2 8 }

tdm3             		OBJECT IDENTIFIER ::= { tdm 3  }

tdm_config3             	OBJECT IDENTIFIER ::= { tdm3 1  }

tdmPort3Status      		OBJECT-TYPE
    	SYNTAX              	INTEGER { off(0), on(1) }
        MAX-ACCESS      	read-only
        STATUS          	current
        DESCRIPTION     	"Display TDM port3 status"
        ::= { tdm_config3 1 }

tdmPort3CableConfig      	OBJECT-TYPE
    	SYNTAX              	INTEGER { len0_133(0), len133_266(1), len266_399(2), len399_533(3),
					  len355_655(4) }
        MAX-ACCESS      	read-only
        STATUS          	current
        DESCRIPTION     	"Display TDM port3 cable configuration"
        ::= { tdm_config3 2 }

tdm_counter3             	OBJECT IDENTIFIER ::= { tdm3 2  }

tdmPort3CounterCrcBlockErrors  	OBJECT-TYPE
    	SYNTAX              	Counter32
        MAX-ACCESS      	read-only
        STATUS          	current
        DESCRIPTION     	"Display TDM port3 Crc Block error Counter"
        ::= { tdm_counter3 1 }

tdmPort3CounterExCrcErrors      OBJECT-TYPE
    	SYNTAX              	Counter32
        MAX-ACCESS      	read-only
        STATUS          	current
        DESCRIPTION     	"Display TDM port3 excessive CRC block Counter"
        ::= { tdm_counter3 2 }

tdmPort3CounterFBAErrors      	OBJECT-TYPE
    	SYNTAX              	Counter32
        MAX-ACCESS      	read-only
        STATUS          	current
        DESCRIPTION     	"Display TDM port3 FBA Errors Counter"
        ::= { tdm_counter3 3 }

tdmPort3CounterFEBErrors      	OBJECT-TYPE
    	SYNTAX              	Counter32
        MAX-ACCESS      	read-only
        STATUS          	current
        DESCRIPTION     	"Display TDM port3 FEB Errors Counter"
        ::= { tdm_counter3 4 }

tdmPort3CounterLCViolations    	OBJECT-TYPE
    	SYNTAX              	Counter32
        MAX-ACCESS      	read-only
        STATUS          	current
        DESCRIPTION     	"Display TDM port3 LC Violations Counter"
        ::= { tdm_counter3 5 }

tdm_alarm3             	OBJECT IDENTIFIER ::= { tdm3 3  }

tdmPort3AlarmLOS      		OBJECT-TYPE
    	SYNTAX              	Counter32
        MAX-ACCESS      	read-only
        STATUS          	current
        DESCRIPTION     	"Display TDM port3 LOS alarm"
        ::= { tdm_alarm3 1 }

tdmPort3AlarmLOF      		OBJECT-TYPE
    	SYNTAX              	Counter32
        MAX-ACCESS      	read-only
        STATUS          	current
        DESCRIPTION     	"Display TDM port3 LOF alarm"
        ::= { tdm_alarm3 2 }

tdmPort3AlarmAIS      		OBJECT-TYPE
    	SYNTAX              	Counter32
        MAX-ACCESS      	read-only
        STATUS          	current
        DESCRIPTION     	"Display TDM port3 AIS alarm"
        ::= { tdm_alarm3 3 }

tdmPort3AlarmTS16AIS      	OBJECT-TYPE
    	SYNTAX              	Counter32
        MAX-ACCESS      	read-only
        STATUS          	current
        DESCRIPTION     	"Display TDM port3 TS16AIS alarm"
        ::= { tdm_alarm3 4 }

tdmPort3AlarmRAI      		OBJECT-TYPE
    	SYNTAX              	Counter32
        MAX-ACCESS      	read-only
        STATUS          	current
        DESCRIPTION     	"Display TDM port3 RAI alarm"
        ::= { tdm_alarm3 5 }

tdmPort3AlarmRMA      		OBJECT-TYPE
    	SYNTAX              	Counter32
        MAX-ACCESS      	read-only
        STATUS          	current
        DESCRIPTION     	"Display TDM port3 RMA alarm"
        ::= { tdm_alarm3 6 }

tdmPort3AlarmLCMFA      	OBJECT-TYPE
    	SYNTAX              	Counter32
        MAX-ACCESS      	read-only
        STATUS          	current
        DESCRIPTION     	"Display TDM port3 LCMFA alarm"
        ::= { tdm_alarm3 7 }

tdmPort3AlarmLSMFA      	OBJECT-TYPE
    	SYNTAX              	Counter32
        MAX-ACCESS      	read-only
        STATUS          	current
        DESCRIPTION     	"Display TDM port3 LSMFA alarm"
        ::= { tdm_alarm3 8 }

tdm4             		OBJECT IDENTIFIER ::= { tdm 4  }

tdm_config4             	OBJECT IDENTIFIER ::= { tdm4 1  }

tdmPort4Status      		OBJECT-TYPE
    	SYNTAX              	INTEGER { off(0), on(1) }
        MAX-ACCESS      	read-only
        STATUS          	current
        DESCRIPTION     	"Display TDM port4 status"
        ::= { tdm_config4 1 }

tdmPort4CableConfig      	OBJECT-TYPE
    	SYNTAX              	INTEGER { len0_133(0), len133_266(1), len266_399(2), len399_533(3),
					  len355_655(4) }
        MAX-ACCESS      	read-only
        STATUS          	current
        DESCRIPTION     	"Display TDM port4 cable configuration"
        ::= { tdm_config4 2 }

tdm_counter4             	OBJECT IDENTIFIER ::= { tdm4 2  }

tdmPort4CounterCrcBlockErrors  	OBJECT-TYPE
    	SYNTAX              	Counter32
        MAX-ACCESS      	read-only
        STATUS          	current
        DESCRIPTION     	"Display TDM port4 Crc Block error Counter"
        ::= { tdm_counter4 1 }

tdmPort4CounterExCrcErrors      OBJECT-TYPE
    	SYNTAX              	Counter32
        MAX-ACCESS      	read-only
        STATUS          	current
        DESCRIPTION     	"Display TDM port4 excessive CRC block Counter"
        ::= { tdm_counter4 2 }

tdmPort4CounterFBAErrors      	OBJECT-TYPE
    	SYNTAX              	Counter32
        MAX-ACCESS      	read-only
        STATUS          	current
        DESCRIPTION     	"Display TDM port4 FBA Errors Counter"
        ::= { tdm_counter4 3 }

tdmPort4CounterFEBErrors      	OBJECT-TYPE
    	SYNTAX              	Counter32
        MAX-ACCESS      	read-only
        STATUS          	current
        DESCRIPTION     	"Display TDM port4 FEB Errors Counter"
        ::= { tdm_counter4 4 }

tdmPort4CounterLCViolations    	OBJECT-TYPE
    	SYNTAX              	Counter32
        MAX-ACCESS      	read-only
        STATUS          	current
        DESCRIPTION     	"Display TDM port4 LC Violations Counter"
        ::= { tdm_counter4 5 }

tdm_alarm4             	OBJECT IDENTIFIER ::= { tdm4 3  }

tdmPort4AlarmLOS      		OBJECT-TYPE
    	SYNTAX              	Counter32
        MAX-ACCESS      	read-only
        STATUS          	current
        DESCRIPTION     	"Display TDM port4 LOS alarm"
        ::= { tdm_alarm4 1 }

tdmPort4AlarmLOF      		OBJECT-TYPE
    	SYNTAX              	Counter32
        MAX-ACCESS      	read-only
        STATUS          	current
        DESCRIPTION     	"Display TDM port4 LOF alarm"
        ::= { tdm_alarm4 2 }

tdmPort4AlarmAIS      		OBJECT-TYPE
    	SYNTAX              	Counter32
        MAX-ACCESS      	read-only
        STATUS          	current
        DESCRIPTION     	"Display TDM port4 AIS alarm"
        ::= { tdm_alarm4 3 }

tdmPort4AlarmTS16AIS      	OBJECT-TYPE
    	SYNTAX              	Counter32
        MAX-ACCESS      	read-only
        STATUS          	current
        DESCRIPTION     	"Display TDM port4 TS16AIS alarm"
        ::= { tdm_alarm4 4 }

tdmPort4AlarmRAI      		OBJECT-TYPE
    	SYNTAX              	Counter32
        MAX-ACCESS      	read-only
        STATUS          	current
        DESCRIPTION     	"Display TDM port4 RAI alarm"
        ::= { tdm_alarm4 5 }

tdmPort4AlarmRMA      		OBJECT-TYPE
    	SYNTAX              	Counter32
        MAX-ACCESS      	read-only
        STATUS          	current
        DESCRIPTION     	"Display TDM port4 RMA alarm"
        ::= { tdm_alarm4 6 }

tdmPort4AlarmLCMFA      	OBJECT-TYPE
    	SYNTAX              	Counter32
        MAX-ACCESS      	read-only
        STATUS          	current
        DESCRIPTION     	"Display TDM port4 LCMFA alarm"
        ::= { tdm_alarm4 7 }

tdmPort4AlarmLSMFA      	OBJECT-TYPE
    	SYNTAX              	Counter32
        MAX-ACCESS      	read-only
        STATUS          	current
        DESCRIPTION     	"Display TDM port4 LSMFA alarm"
        ::= { tdm_alarm4 8 }

tdm5             		OBJECT IDENTIFIER ::= { tdm 5  }

tdm_config5             	OBJECT IDENTIFIER ::= { tdm5 1  }

tdmPort5Status      		OBJECT-TYPE
    	SYNTAX              	INTEGER { off(0), on(1) }
        MAX-ACCESS      	read-only
        STATUS          	current
        DESCRIPTION     	"Display TDM port5 status"
        ::= { tdm_config5 1 }

tdmPort5CableConfig      	OBJECT-TYPE
    	SYNTAX              	INTEGER { len0_133(0), len133_266(1), len266_399(2), len399_533(3),
					  len355_655(4) }
        MAX-ACCESS      	read-only
        STATUS          	current
        DESCRIPTION     	"Display TDM port5 cable configuration"
        ::= { tdm_config5 2 }

tdm_counter5             	OBJECT IDENTIFIER ::= { tdm5 2  }

tdmPort5CounterCrcBlockErrors  	OBJECT-TYPE
    	SYNTAX              	Counter32
        MAX-ACCESS      	read-only
        STATUS          	current
        DESCRIPTION     	"Display TDM port5 Crc Block error Counter"
        ::= { tdm_counter5 1 }

tdmPort5CounterExCrcErrors      OBJECT-TYPE
    	SYNTAX              	Counter32
        MAX-ACCESS      	read-only
        STATUS          	current
        DESCRIPTION     	"Display TDM port5 excessive CRC block Counter"
        ::= { tdm_counter5 2 }

tdmPort5CounterFBAErrors      	OBJECT-TYPE
    	SYNTAX              	Counter32
        MAX-ACCESS      	read-only
        STATUS          	current
        DESCRIPTION     	"Display TDM port5 FBA Errors Counter"
        ::= { tdm_counter5 3 }

tdmPort5CounterFEBErrors      	OBJECT-TYPE
    	SYNTAX              	Counter32
        MAX-ACCESS      	read-only
        STATUS          	current
        DESCRIPTION     	"Display TDM port5 FEB Errors Counter"
        ::= { tdm_counter5 4 }

tdmPort5CounterLCViolations    	OBJECT-TYPE
    	SYNTAX              	Counter32
        MAX-ACCESS      	read-only
        STATUS          	current
        DESCRIPTION     	"Display TDM port5 LC Violations Counter"
        ::= { tdm_counter5 5 }

tdm_alarm5             	OBJECT IDENTIFIER ::= { tdm5 3  }

tdmPort5AlarmLOS      		OBJECT-TYPE
    	SYNTAX              	Counter32
        MAX-ACCESS      	read-only
        STATUS          	current
        DESCRIPTION     	"Display TDM port5 LOS alarm"
        ::= { tdm_alarm5 1 }

tdmPort5AlarmLOF      		OBJECT-TYPE
    	SYNTAX              	Counter32
        MAX-ACCESS      	read-only
        STATUS          	current
        DESCRIPTION     	"Display TDM port5 LOF alarm"
        ::= { tdm_alarm5 2 }

tdmPort5AlarmAIS      		OBJECT-TYPE
    	SYNTAX              	Counter32
        MAX-ACCESS      	read-only
        STATUS          	current
        DESCRIPTION     	"Display TDM port5 AIS alarm"
        ::= { tdm_alarm5 3 }

tdmPort5AlarmTS16AIS      	OBJECT-TYPE
    	SYNTAX              	Counter32
        MAX-ACCESS      	read-only
        STATUS          	current
        DESCRIPTION     	"Display TDM port5 TS16AIS alarm"
        ::= { tdm_alarm5 4 }

tdmPort5AlarmRAI      		OBJECT-TYPE
    	SYNTAX              	Counter32
        MAX-ACCESS      	read-only
        STATUS          	current
        DESCRIPTION     	"Display TDM port5 RAI alarm"
        ::= { tdm_alarm5 5 }

tdmPort5AlarmRMA      		OBJECT-TYPE
    	SYNTAX              	Counter32
        MAX-ACCESS      	read-only
        STATUS          	current
        DESCRIPTION     	"Display TDM port5 RMA alarm"
        ::= { tdm_alarm5 6 }

tdmPort5AlarmLCMFA      	OBJECT-TYPE
    	SYNTAX              	Counter32
        MAX-ACCESS      	read-only
        STATUS          	current
        DESCRIPTION     	"Display TDM port5 LCMFA alarm"
        ::= { tdm_alarm5 7 }

tdmPort5AlarmLSMFA      	OBJECT-TYPE
    	SYNTAX              	Counter32
        MAX-ACCESS      	read-only
        STATUS          	current
        DESCRIPTION     	"Display TDM port5 LSMFA alarm"
        ::= { tdm_alarm5 8 }

tdm6             		OBJECT IDENTIFIER ::= { tdm 6  }

tdm_config6             	OBJECT IDENTIFIER ::= { tdm6 1  }

tdmPort6Status      		OBJECT-TYPE
    	SYNTAX              	INTEGER { off(0), on(1) }
        MAX-ACCESS      	read-only
        STATUS          	current
        DESCRIPTION     	"Display TDM port6 status"
        ::= { tdm_config6 1 }

tdmPort6CableConfig      	OBJECT-TYPE
    	SYNTAX              	INTEGER { len0_133(0), len133_266(1), len266_399(2), len399_533(3),
					  len355_655(4) }
        MAX-ACCESS      	read-only
        STATUS          	current
        DESCRIPTION     	"Display TDM port6 cable configuration"
        ::= { tdm_config6 2 }

tdm_counter6             	OBJECT IDENTIFIER ::= { tdm6 2  }

tdmPort6CounterCrcBlockErrors  	OBJECT-TYPE
    	SYNTAX              	Counter32
        MAX-ACCESS      	read-only
        STATUS          	current
        DESCRIPTION     	"Display TDM port6 Crc Block error Counter"
        ::= { tdm_counter6 1 }

tdmPort6CounterExCrcErrors      OBJECT-TYPE
    	SYNTAX              	Counter32
        MAX-ACCESS      	read-only
        STATUS          	current
        DESCRIPTION     	"Display TDM port6 excessive CRC block Counter"
        ::= { tdm_counter6 2 }

tdmPort6CounterFBAErrors      	OBJECT-TYPE
    	SYNTAX              	Counter32
        MAX-ACCESS      	read-only
        STATUS          	current
        DESCRIPTION     	"Display TDM port6 FBA Errors Counter"
        ::= { tdm_counter6 3 }

tdmPort6CounterFEBErrors      	OBJECT-TYPE
    	SYNTAX              	Counter32
        MAX-ACCESS      	read-only
        STATUS          	current
        DESCRIPTION     	"Display TDM port6 FEB Errors Counter"
        ::= { tdm_counter6 4 }

tdmPort6CounterLCViolations    	OBJECT-TYPE
    	SYNTAX              	Counter32
        MAX-ACCESS      	read-only
        STATUS          	current
        DESCRIPTION     	"Display TDM port6 LC Violations Counter"
        ::= { tdm_counter6 5 }

tdm_alarm6             	OBJECT IDENTIFIER ::= { tdm6 3  }

tdmPort6AlarmLOS      		OBJECT-TYPE
    	SYNTAX              	Counter32
        MAX-ACCESS      	read-only
        STATUS          	current
        DESCRIPTION     	"Display TDM port6 LOS alarm"
        ::= { tdm_alarm6 1 }

tdmPort6AlarmLOF      		OBJECT-TYPE
    	SYNTAX              	Counter32
        MAX-ACCESS      	read-only
        STATUS          	current
        DESCRIPTION     	"Display TDM port6 LOF alarm"
        ::= { tdm_alarm6 2 }

tdmPort6AlarmAIS      		OBJECT-TYPE
    	SYNTAX              	Counter32
        MAX-ACCESS      	read-only
        STATUS          	current
        DESCRIPTION     	"Display TDM port6 AIS alarm"
        ::= { tdm_alarm6 3 }

tdmPort6AlarmTS16AIS      	OBJECT-TYPE
    	SYNTAX              	Counter32
        MAX-ACCESS      	read-only
        STATUS          	current
        DESCRIPTION     	"Display TDM port6 TS16AIS alarm"
        ::= { tdm_alarm6 4 }

tdmPort6AlarmRAI      		OBJECT-TYPE
    	SYNTAX              	Counter32
        MAX-ACCESS      	read-only
        STATUS          	current
        DESCRIPTION     	"Display TDM port6 RAI alarm"
        ::= { tdm_alarm6 5 }

tdmPort6AlarmRMA      		OBJECT-TYPE
    	SYNTAX              	Counter32
        MAX-ACCESS      	read-only
        STATUS          	current
        DESCRIPTION     	"Display TDM port6 RMA alarm"
        ::= { tdm_alarm6 6 }

tdmPort6AlarmLCMFA      	OBJECT-TYPE
    	SYNTAX              	Counter32
        MAX-ACCESS      	read-only
        STATUS          	current
        DESCRIPTION     	"Display TDM port6 LCMFA alarm"
        ::= { tdm_alarm6 7 }

tdmPort6AlarmLSMFA      	OBJECT-TYPE
    	SYNTAX              	Counter32
        MAX-ACCESS      	read-only
        STATUS          	current
        DESCRIPTION     	"Display TDM port6 LSMFA alarm"
        ::= { tdm_alarm6 8 }

tdm7             		OBJECT IDENTIFIER ::= { tdm 7  }

tdm_config7             	OBJECT IDENTIFIER ::= { tdm7 1  }

tdmPort7Status      		OBJECT-TYPE
    	SYNTAX              	INTEGER { off(0), on(1) }
        MAX-ACCESS      	read-only
        STATUS          	current
        DESCRIPTION     	"Display TDM port7 status"
        ::= { tdm_config7 1 }

tdmPort7CableConfig      	OBJECT-TYPE
    	SYNTAX              	INTEGER { len0_133(0), len133_266(1), len266_399(2), len399_533(3),
					  len355_655(4) }
        MAX-ACCESS      	read-only
        STATUS          	current
        DESCRIPTION     	"Display TDM port7 cable configuration"
        ::= { tdm_config7 2 }

tdm_counter7             	OBJECT IDENTIFIER ::= { tdm7 2  }

tdmPort7CounterCrcBlockErrors  	OBJECT-TYPE
    	SYNTAX              	Counter32
        MAX-ACCESS      	read-only
        STATUS          	current
        DESCRIPTION     	"Display TDM port7 Crc Block error Counter"
        ::= { tdm_counter7 1 }

tdmPort7CounterExCrcErrors      OBJECT-TYPE
    	SYNTAX              	Counter32
        MAX-ACCESS      	read-only
        STATUS          	current
        DESCRIPTION     	"Display TDM port7 excessive CRC block Counter"
        ::= { tdm_counter7 2 }

tdmPort7CounterFBAErrors      	OBJECT-TYPE
    	SYNTAX              	Counter32
        MAX-ACCESS      	read-only
        STATUS          	current
        DESCRIPTION     	"Display TDM port7 FBA Errors Counter"
        ::= { tdm_counter7 3 }

tdmPort7CounterFEBErrors      	OBJECT-TYPE
    	SYNTAX              	Counter32
        MAX-ACCESS      	read-only
        STATUS          	current
        DESCRIPTION     	"Display TDM port7 FEB Errors Counter"
        ::= { tdm_counter7 4 }

tdmPort7CounterLCViolations    	OBJECT-TYPE
    	SYNTAX              	Counter32
        MAX-ACCESS      	read-only
        STATUS          	current
        DESCRIPTION     	"Display TDM port7 LC Violations Counter"
        ::= { tdm_counter7 5 }

tdm_alarm7             	OBJECT IDENTIFIER ::= { tdm7 3  }

tdmPort7AlarmLOS      		OBJECT-TYPE
    	SYNTAX              	Counter32
        MAX-ACCESS      	read-only
        STATUS          	current
        DESCRIPTION     	"Display TDM port7 LOS alarm"
        ::= { tdm_alarm7 1 }

tdmPort7AlarmLOF      		OBJECT-TYPE
    	SYNTAX              	Counter32
        MAX-ACCESS      	read-only
        STATUS          	current
        DESCRIPTION     	"Display TDM port7 LOF alarm"
        ::= { tdm_alarm7 2 }

tdmPort7AlarmAIS      		OBJECT-TYPE
    	SYNTAX              	Counter32
        MAX-ACCESS      	read-only
        STATUS          	current
        DESCRIPTION     	"Display TDM port7 AIS alarm"
        ::= { tdm_alarm7 3 }

tdmPort7AlarmTS16AIS      	OBJECT-TYPE
    	SYNTAX              	Counter32
        MAX-ACCESS      	read-only
        STATUS          	current
        DESCRIPTION     	"Display TDM port7 TS16AIS alarm"
        ::= { tdm_alarm7 4 }

tdmPort7AlarmRAI      		OBJECT-TYPE
    	SYNTAX              	Counter32
        MAX-ACCESS      	read-only
        STATUS          	current
        DESCRIPTION     	"Display TDM port7 RAI alarm"
        ::= { tdm_alarm7 5 }

tdmPort7AlarmRMA      		OBJECT-TYPE
    	SYNTAX              	Counter32
        MAX-ACCESS      	read-only
        STATUS          	current
        DESCRIPTION     	"Display TDM port7 RMA alarm"
        ::= { tdm_alarm7 6 }

tdmPort7AlarmLCMFA      	OBJECT-TYPE
    	SYNTAX              	Counter32
        MAX-ACCESS      	read-only
        STATUS          	current
        DESCRIPTION     	"Display TDM port7 LCMFA alarm"
        ::= { tdm_alarm7 7 }

tdmPort7AlarmLSMFA      	OBJECT-TYPE
    	SYNTAX              	Counter32
        MAX-ACCESS      	read-only
        STATUS          	current
        DESCRIPTION     	"Display TDM port7 LSMFA alarm"
        ::= { tdm_alarm7 8 }

tdm8             		OBJECT IDENTIFIER ::= { tdm 8  }

tdm_config8             	OBJECT IDENTIFIER ::= { tdm8 1  }

tdmPort8Status      		OBJECT-TYPE
    	SYNTAX              	INTEGER { off(0), on(1) }
        MAX-ACCESS      	read-only
        STATUS          	current
        DESCRIPTION     	"Display TDM port8 status"
        ::= { tdm_config8 1 }

tdmPort8CableConfig      	OBJECT-TYPE
    	SYNTAX              	INTEGER { len0_133(0), len133_266(1), len266_399(2), len399_533(3),
					  len355_655(4) }
        MAX-ACCESS      	read-only
        STATUS          	current
        DESCRIPTION     	"Display TDM port8 cable configuration"
        ::= { tdm_config8 2 }

tdm_counter8             	OBJECT IDENTIFIER ::= { tdm8 2  }

tdmPort8CounterCrcBlockErrors  	OBJECT-TYPE
    	SYNTAX              	Counter32
        MAX-ACCESS      	read-only
        STATUS          	current
        DESCRIPTION     	"Display TDM port8 Crc Block error Counter"
        ::= { tdm_counter8 1 }

tdmPort8CounterExCrcErrors      OBJECT-TYPE
    	SYNTAX              	Counter32
        MAX-ACCESS      	read-only
        STATUS          	current
        DESCRIPTION     	"Display TDM port8 excessive CRC block Counter"
        ::= { tdm_counter8 2 }

tdmPort8CounterFBAErrors      	OBJECT-TYPE
    	SYNTAX              	Counter32
        MAX-ACCESS      	read-only
        STATUS          	current
        DESCRIPTION     	"Display TDM port8 FBA Errors Counter"
        ::= { tdm_counter8 3 }

tdmPort8CounterFEBErrors      	OBJECT-TYPE
    	SYNTAX              	Counter32
        MAX-ACCESS      	read-only
        STATUS          	current
        DESCRIPTION     	"Display TDM port8 FEB Errors Counter"
        ::= { tdm_counter8 4 }

tdmPort8CounterLCViolations    	OBJECT-TYPE
    	SYNTAX              	Counter32
        MAX-ACCESS      	read-only
        STATUS          	current
        DESCRIPTION     	"Display TDM port8 LC Violations Counter"
        ::= { tdm_counter8 5 }

tdm_alarm8             	OBJECT IDENTIFIER ::= { tdm8 3  }

tdmPort8AlarmLOS      		OBJECT-TYPE
    	SYNTAX              	Counter32
        MAX-ACCESS      	read-only
        STATUS          	current
        DESCRIPTION     	"Display TDM port8 LOS alarm"
        ::= { tdm_alarm8 1 }

tdmPort8AlarmLOF      		OBJECT-TYPE
    	SYNTAX              	Counter32
        MAX-ACCESS      	read-only
        STATUS          	current
        DESCRIPTION     	"Display TDM port8 LOF alarm"
        ::= { tdm_alarm8 2 }

tdmPort8AlarmAIS      		OBJECT-TYPE
    	SYNTAX              	Counter32
        MAX-ACCESS      	read-only
        STATUS          	current
        DESCRIPTION     	"Display TDM port8 AIS alarm"
        ::= { tdm_alarm8 3 }

tdmPort8AlarmTS16AIS      	OBJECT-TYPE
    	SYNTAX              	Counter32
        MAX-ACCESS      	read-only
        STATUS          	current
        DESCRIPTION     	"Display TDM port8 TS16AIS alarm"
        ::= { tdm_alarm8 4 }

tdmPort8AlarmRAI      		OBJECT-TYPE
    	SYNTAX              	Counter32
        MAX-ACCESS      	read-only
        STATUS          	current
        DESCRIPTION     	"Display TDM port8 RAI alarm"
        ::= { tdm_alarm8 5 }

tdmPort8AlarmRMA      		OBJECT-TYPE
    	SYNTAX              	Counter32
        MAX-ACCESS      	read-only
        STATUS          	current
        DESCRIPTION     	"Display TDM port8 RMA alarm"
        ::= { tdm_alarm8 6 }

tdmPort8AlarmLCMFA      	OBJECT-TYPE
    	SYNTAX              	Counter32
        MAX-ACCESS      	read-only
        STATUS          	current
        DESCRIPTION     	"Display TDM port8 LCMFA alarm"
        ::= { tdm_alarm8 7 }

tdmPort8AlarmLSMFA      	OBJECT-TYPE
    	SYNTAX              	Counter32
        MAX-ACCESS      	read-only
        STATUS          	current
        DESCRIPTION     	"Display TDM port8 LSMFA alarm"
        ::= { tdm_alarm8 8 }

tdm9             		OBJECT IDENTIFIER ::= { tdm 9  }

tdm_config9             	OBJECT IDENTIFIER ::= { tdm9 1  }

tdmPort9Status      		OBJECT-TYPE
    	SYNTAX              	INTEGER { off(0), on(1) }
        MAX-ACCESS      	read-only
        STATUS          	current
        DESCRIPTION     	"Display TDM port9 status"
        ::= { tdm_config9 1 }

tdmPort9CableConfig      	OBJECT-TYPE
    	SYNTAX              	INTEGER { len0_133(0), len133_266(1), len266_399(2), len399_533(3),
					  len355_655(4) }
        MAX-ACCESS      	read-only
        STATUS          	current
        DESCRIPTION     	"Display TDM port9 cable configuration"
        ::= { tdm_config9 2 }

tdm_counter9             	OBJECT IDENTIFIER ::= { tdm9 2  }

tdmPort9CounterCrcBlockErrors  	OBJECT-TYPE
    	SYNTAX              	Counter32
        MAX-ACCESS      	read-only
        STATUS          	current
        DESCRIPTION     	"Display TDM port9 Crc Block error Counter"
        ::= { tdm_counter9 1 }

tdmPort9CounterExCrcErrors      OBJECT-TYPE
    	SYNTAX              	Counter32
        MAX-ACCESS      	read-only
        STATUS          	current
        DESCRIPTION     	"Display TDM port9 excessive CRC block Counter"
        ::= { tdm_counter9 2 }

tdmPort9CounterFBAErrors      	OBJECT-TYPE
    	SYNTAX              	Counter32
        MAX-ACCESS      	read-only
        STATUS          	current
        DESCRIPTION     	"Display TDM port9 FBA Errors Counter"
        ::= { tdm_counter9 3 }

tdmPort9CounterFEBErrors      	OBJECT-TYPE
    	SYNTAX              	Counter32
        MAX-ACCESS      	read-only
        STATUS          	current
        DESCRIPTION     	"Display TDM port9 FEB Errors Counter"
        ::= { tdm_counter9 4 }

tdmPort9CounterLCViolations    	OBJECT-TYPE
    	SYNTAX              	Counter32
        MAX-ACCESS      	read-only
        STATUS          	current
        DESCRIPTION     	"Display TDM port9 LC Violations Counter"
        ::= { tdm_counter9 5 }

tdm_alarm9             	OBJECT IDENTIFIER ::= { tdm9 3  }

tdmPort9AlarmLOS      		OBJECT-TYPE
    	SYNTAX              	Counter32
        MAX-ACCESS      	read-only
        STATUS          	current
        DESCRIPTION     	"Display TDM port9 LOS alarm"
        ::= { tdm_alarm9 1 }

tdmPort9AlarmLOF      		OBJECT-TYPE
    	SYNTAX              	Counter32
        MAX-ACCESS      	read-only
        STATUS          	current
        DESCRIPTION     	"Display TDM port9 LOF alarm"
        ::= { tdm_alarm9 2 }

tdmPort9AlarmAIS      		OBJECT-TYPE
    	SYNTAX              	Counter32
        MAX-ACCESS      	read-only
        STATUS          	current
        DESCRIPTION     	"Display TDM port9 AIS alarm"
        ::= { tdm_alarm9 3 }

tdmPort9AlarmTS16AIS      	OBJECT-TYPE
    	SYNTAX              	Counter32
        MAX-ACCESS      	read-only
        STATUS          	current
        DESCRIPTION     	"Display TDM port9 TS16AIS alarm"
        ::= { tdm_alarm9 4 }

tdmPort9AlarmRAI      		OBJECT-TYPE
    	SYNTAX              	Counter32
        MAX-ACCESS      	read-only
        STATUS          	current
        DESCRIPTION     	"Display TDM port9 RAI alarm"
        ::= { tdm_alarm9 5 }

tdmPort9AlarmRMA      		OBJECT-TYPE
    	SYNTAX              	Counter32
        MAX-ACCESS      	read-only
        STATUS          	current
        DESCRIPTION     	"Display TDM port9 RMA alarm"
        ::= { tdm_alarm9 6 }

tdmPort9AlarmLCMFA      	OBJECT-TYPE
    	SYNTAX              	Counter32
        MAX-ACCESS      	read-only
        STATUS          	current
        DESCRIPTION     	"Display TDM port9 LCMFA alarm"
        ::= { tdm_alarm9 7 }

tdmPort9AlarmLSMFA      	OBJECT-TYPE
    	SYNTAX              	Counter32
        MAX-ACCESS      	read-only
        STATUS          	current
        DESCRIPTION     	"Display TDM port9 LSMFA alarm"
        ::= { tdm_alarm9 8 }

tdm10             		OBJECT IDENTIFIER ::= { tdm 10  }

tdm_config10             	OBJECT IDENTIFIER ::= { tdm10 1  }

tdmPort10Status      		OBJECT-TYPE
    	SYNTAX              	INTEGER { off(0), on(1) }
        MAX-ACCESS      	read-only
        STATUS          	current
        DESCRIPTION     	"Display TDM port10 status"
        ::= { tdm_config10 1 }

tdmPort10CableConfig      	OBJECT-TYPE
    	SYNTAX              	INTEGER { len0_133(0), len133_266(1), len266_399(2), len399_533(3),
					  len355_655(4) }
        MAX-ACCESS      	read-only
        STATUS          	current
        DESCRIPTION     	"Display TDM port10 cable configuration"
        ::= { tdm_config10 2 }

tdm_counter10            	OBJECT IDENTIFIER ::= { tdm10 2  }

tdmPort10CounterCrcBlockErrors  	OBJECT-TYPE
    	SYNTAX              	Counter32
        MAX-ACCESS      	read-only
        STATUS          	current
        DESCRIPTION     	"Display TDM port10 Crc Block error Counter"
        ::= { tdm_counter10 1 }

tdmPort10CounterExCrcErrors      OBJECT-TYPE
    	SYNTAX              	Counter32
        MAX-ACCESS      	read-only
        STATUS          	current
        DESCRIPTION     	"Display TDM port10 excessive CRC block Counter"
        ::= { tdm_counter10 2 }

tdmPort10CounterFBAErrors      	OBJECT-TYPE
    	SYNTAX              	Counter32
        MAX-ACCESS      	read-only
        STATUS          	current
        DESCRIPTION     	"Display TDM port10 FBA Errors Counter"
        ::= { tdm_counter10 3 }

tdmPort10CounterFEBErrors      	OBJECT-TYPE
    	SYNTAX              	Counter32
        MAX-ACCESS      	read-only
        STATUS          	current
        DESCRIPTION     	"Display TDM port10 FEB Errors Counter"
        ::= { tdm_counter10 4 }

tdmPort10CounterLCViolations    	OBJECT-TYPE
    	SYNTAX              	Counter32
        MAX-ACCESS      	read-only
        STATUS          	current
        DESCRIPTION     	"Display TDM port10 LC Violations Counter"
        ::= { tdm_counter10 5 }

tdm_alarm10             	OBJECT IDENTIFIER ::= { tdm10 3  }

tdmPort10AlarmLOS      		OBJECT-TYPE
    	SYNTAX              	Counter32
        MAX-ACCESS      	read-only
        STATUS          	current
        DESCRIPTION     	"Display TDM port10 LOS alarm"
        ::= { tdm_alarm10 1 }

tdmPort10AlarmLOF      		OBJECT-TYPE
    	SYNTAX              	Counter32
        MAX-ACCESS      	read-only
        STATUS          	current
        DESCRIPTION     	"Display TDM port10 LOF alarm"
        ::= { tdm_alarm10 2 }

tdmPort10AlarmAIS      		OBJECT-TYPE
    	SYNTAX              	Counter32
        MAX-ACCESS      	read-only
        STATUS          	current
        DESCRIPTION     	"Display TDM port10 AIS alarm"
        ::= { tdm_alarm10 3 }

tdmPort10AlarmTS16AIS      	OBJECT-TYPE
    	SYNTAX              	Counter32
        MAX-ACCESS      	read-only
        STATUS          	current
        DESCRIPTION     	"Display TDM port10 TS16AIS alarm"
        ::= { tdm_alarm10 4 }

tdmPort10AlarmRAI      		OBJECT-TYPE
    	SYNTAX              	Counter32
        MAX-ACCESS      	read-only
        STATUS          	current
        DESCRIPTION     	"Display TDM port10 RAI alarm"
        ::= { tdm_alarm10 5 }

tdmPort10AlarmRMA      		OBJECT-TYPE
    	SYNTAX              	Counter32
        MAX-ACCESS      	read-only
        STATUS          	current
        DESCRIPTION     	"Display TDM port10 RMA alarm"
        ::= { tdm_alarm10 6 }

tdmPort10AlarmLCMFA      	OBJECT-TYPE
    	SYNTAX              	Counter32
        MAX-ACCESS      	read-only
        STATUS          	current
        DESCRIPTION     	"Display TDM port10 LCMFA alarm"
        ::= { tdm_alarm10 7 }

tdmPort10AlarmLSMFA      	OBJECT-TYPE
    	SYNTAX              	Counter32
        MAX-ACCESS      	read-only
        STATUS          	current
        DESCRIPTION     	"Display TDM port10 LSMFA alarm"
        ::= { tdm_alarm10 8 }

tdm11             		OBJECT IDENTIFIER ::= { tdm 11  }

tdm_config11             	OBJECT IDENTIFIER ::= { tdm11 1  }

tdmPort11Status      		OBJECT-TYPE
    	SYNTAX              	INTEGER { off(0), on(1) }
        MAX-ACCESS      	read-only
        STATUS          	current
        DESCRIPTION     	"Display TDM port11 status"
        ::= { tdm_config11 1 }

tdmPort11CableConfig      	OBJECT-TYPE
    	SYNTAX              	INTEGER { len0_133(0), len133_266(1), len266_399(2), len399_533(3),
					  len355_655(4) }
        MAX-ACCESS      	read-only
        STATUS          	current
        DESCRIPTION     	"Display TDM port11 cable configuration"
        ::= { tdm_config11 2 }

tdm_counter11             	OBJECT IDENTIFIER ::= { tdm11 2  }

tdmPort11CounterCrcBlockErrors  	OBJECT-TYPE
    	SYNTAX              	Counter32
        MAX-ACCESS      	read-only
        STATUS          	current
        DESCRIPTION     	"Display TDM port11 Crc Block error Counter"
        ::= { tdm_counter11 1 }

tdmPort11CounterExCrcErrors      OBJECT-TYPE
    	SYNTAX              	Counter32
        MAX-ACCESS      	read-only
        STATUS          	current
        DESCRIPTION     	"Display TDM port11 excessive CRC block Counter"
        ::= { tdm_counter11 2 }

tdmPort11CounterFBAErrors      	OBJECT-TYPE
    	SYNTAX              	Counter32
        MAX-ACCESS      	read-only
        STATUS          	current
        DESCRIPTION     	"Display TDM port11 FBA Errors Counter"
        ::= { tdm_counter11 3 }

tdmPort11CounterFEBErrors      	OBJECT-TYPE
    	SYNTAX              	Counter32
        MAX-ACCESS      	read-only
        STATUS          	current
        DESCRIPTION     	"Display TDM port11 FEB Errors Counter"
        ::= { tdm_counter11 4 }

tdmPort11CounterLCViolations    	OBJECT-TYPE
    	SYNTAX              	Counter32
        MAX-ACCESS      	read-only
        STATUS          	current
        DESCRIPTION     	"Display TDM port11 LC Violations Counter"
        ::= { tdm_counter11 5 }

tdm_alarm11             	OBJECT IDENTIFIER ::= { tdm11 3  }

tdmPort11AlarmLOS      		OBJECT-TYPE
    	SYNTAX              	Counter32
        MAX-ACCESS      	read-only
        STATUS          	current
        DESCRIPTION     	"Display TDM port11 LOS alarm"
        ::= { tdm_alarm11 1 }

tdmPort11AlarmLOF      		OBJECT-TYPE
    	SYNTAX              	Counter32
        MAX-ACCESS      	read-only
        STATUS          	current
        DESCRIPTION     	"Display TDM port11 LOF alarm"
        ::= { tdm_alarm11 2 }

tdmPort11AlarmAIS      		OBJECT-TYPE
    	SYNTAX              	Counter32
        MAX-ACCESS      	read-only
        STATUS          	current
        DESCRIPTION     	"Display TDM port11 AIS alarm"
        ::= { tdm_alarm11 3 }

tdmPort11AlarmTS16AIS      	OBJECT-TYPE
    	SYNTAX              	Counter32
        MAX-ACCESS      	read-only
        STATUS          	current
        DESCRIPTION     	"Display TDM port11 TS16AIS alarm"
        ::= { tdm_alarm11 4 }

tdmPort11AlarmRAI      		OBJECT-TYPE
    	SYNTAX              	Counter32
        MAX-ACCESS      	read-only
        STATUS          	current
        DESCRIPTION     	"Display TDM port11 RAI alarm"
        ::= { tdm_alarm11 5 }

tdmPort11AlarmRMA      		OBJECT-TYPE
    	SYNTAX              	Counter32
        MAX-ACCESS      	read-only
        STATUS          	current
        DESCRIPTION     	"Display TDM port11 RMA alarm"
        ::= { tdm_alarm11 6 }

tdmPort11AlarmLCMFA      	OBJECT-TYPE
    	SYNTAX              	Counter32
        MAX-ACCESS      	read-only
        STATUS          	current
        DESCRIPTION     	"Display TDM port11 LCMFA alarm"
        ::= { tdm_alarm11 7 }

tdmPort11AlarmLSMFA      	OBJECT-TYPE
    	SYNTAX              	Counter32
        MAX-ACCESS      	read-only
        STATUS          	current
        DESCRIPTION     	"Display TDM port11 LSMFA alarm"
        ::= { tdm_alarm11 8 }

tdm12             		OBJECT IDENTIFIER ::= { tdm 12  }

tdm_config12             	OBJECT IDENTIFIER ::= { tdm12 1  }

tdmPort12Status      		OBJECT-TYPE
    	SYNTAX              	INTEGER { off(0), on(1) }
        MAX-ACCESS      	read-only
        STATUS          	current
        DESCRIPTION     	"Display TDM port12 status"
        ::= { tdm_config12 1 }

tdmPort12CableConfig      	OBJECT-TYPE
    	SYNTAX              	INTEGER { len0_133(0), len133_266(1), len266_399(2), len399_533(3),
					  len355_655(4) }
        MAX-ACCESS      	read-only
        STATUS          	current
        DESCRIPTION     	"Display TDM port12 cable configuration"
        ::= { tdm_config12 2 }

tdm_counter12             	OBJECT IDENTIFIER ::= { tdm12 2  }

tdmPort12CounterCrcBlockErrors  	OBJECT-TYPE
    	SYNTAX              	Counter32
        MAX-ACCESS      	read-only
        STATUS          	current
        DESCRIPTION     	"Display TDM port12 Crc Block error Counter"
        ::= { tdm_counter12 1 }

tdmPort12CounterExCrcErrors      OBJECT-TYPE
    	SYNTAX              	Counter32
        MAX-ACCESS      	read-only
        STATUS          	current
        DESCRIPTION     	"Display TDM port12 excessive CRC block Counter"
        ::= { tdm_counter12 2 }

tdmPort12CounterFBAErrors      	OBJECT-TYPE
    	SYNTAX              	Counter32
        MAX-ACCESS      	read-only
        STATUS          	current
        DESCRIPTION     	"Display TDM port12 FBA Errors Counter"
        ::= { tdm_counter12 3 }

tdmPort12CounterFEBErrors      	OBJECT-TYPE
    	SYNTAX              	Counter32
        MAX-ACCESS      	read-only
        STATUS          	current
        DESCRIPTION     	"Display TDM port12 FEB Errors Counter"
        ::= { tdm_counter12 4 }

tdmPort12CounterLCViolations    	OBJECT-TYPE
    	SYNTAX              	Counter32
        MAX-ACCESS      	read-only
        STATUS          	current
        DESCRIPTION     	"Display TDM port12 LC Violations Counter"
        ::= { tdm_counter12 5 }

tdm_alarm12             	OBJECT IDENTIFIER ::= { tdm12 3  }

tdmPort12AlarmLOS      		OBJECT-TYPE
    	SYNTAX              	Counter32
        MAX-ACCESS      	read-only
        STATUS          	current
        DESCRIPTION     	"Display TDM port12 LOS alarm"
        ::= { tdm_alarm12 1 }

tdmPort12AlarmLOF      		OBJECT-TYPE
    	SYNTAX              	Counter32
        MAX-ACCESS      	read-only
        STATUS          	current
        DESCRIPTION     	"Display TDM port12 LOF alarm"
        ::= { tdm_alarm12 2 }

tdmPort12AlarmAIS      		OBJECT-TYPE
    	SYNTAX              	Counter32
        MAX-ACCESS      	read-only
        STATUS          	current
        DESCRIPTION     	"Display TDM port12 AIS alarm"
        ::= { tdm_alarm12 3 }

tdmPort12AlarmTS16AIS      	OBJECT-TYPE
    	SYNTAX              	Counter32
        MAX-ACCESS      	read-only
        STATUS          	current
        DESCRIPTION     	"Display TDM port12 TS16AIS alarm"
        ::= { tdm_alarm12 4 }

tdmPort12AlarmRAI      		OBJECT-TYPE
    	SYNTAX              	Counter32
        MAX-ACCESS      	read-only
        STATUS          	current
        DESCRIPTION     	"Display TDM port12 RAI alarm"
        ::= { tdm_alarm12 5 }

tdmPort12AlarmRMA      		OBJECT-TYPE
    	SYNTAX              	Counter32
        MAX-ACCESS      	read-only
        STATUS          	current
        DESCRIPTION     	"Display TDM port12 RMA alarm"
        ::= { tdm_alarm12 6 }

tdmPort12AlarmLCMFA      	OBJECT-TYPE
    	SYNTAX              	Counter32
        MAX-ACCESS      	read-only
        STATUS          	current
        DESCRIPTION     	"Display TDM port12 LCMFA alarm"
        ::= { tdm_alarm12 7 }

tdmPort12AlarmLSMFA      	OBJECT-TYPE
    	SYNTAX              	Counter32
        MAX-ACCESS      	read-only
        STATUS          	current
        DESCRIPTION     	"Display TDM port12 LSMFA alarm"
        ::= { tdm_alarm12 8 }

tdm13             		OBJECT IDENTIFIER ::= { tdm 13  }

tdm_config13             	OBJECT IDENTIFIER ::= { tdm13 1  }

tdmPort13Status      		OBJECT-TYPE
    	SYNTAX              	INTEGER { off(0), on(1) }
        MAX-ACCESS      	read-only
        STATUS          	current
        DESCRIPTION     	"Display TDM port13 status"
        ::= { tdm_config13 1 }

tdmPort13CableConfig      	OBJECT-TYPE
    	SYNTAX              	INTEGER { len0_133(0), len133_266(1), len266_399(2), len399_533(3),
					  len355_655(4) }
        MAX-ACCESS      	read-only
        STATUS          	current
        DESCRIPTION     	"Display TDM port13 cable configuration"
        ::= { tdm_config13 2 }

tdm_counter13             	OBJECT IDENTIFIER ::= { tdm13 2  }

tdmPort13CounterCrcBlockErrors  	OBJECT-TYPE
    	SYNTAX              	Counter32
        MAX-ACCESS      	read-only
        STATUS          	current
        DESCRIPTION     	"Display TDM port13 Crc Block error Counter"
        ::= { tdm_counter13 1 }

tdmPort13CounterExCrcErrors      OBJECT-TYPE
    	SYNTAX              	Counter32
        MAX-ACCESS      	read-only
        STATUS          	current
        DESCRIPTION     	"Display TDM port13 excessive CRC block Counter"
        ::= { tdm_counter13 2 }

tdmPort13CounterFBAErrors      	OBJECT-TYPE
    	SYNTAX              	Counter32
        MAX-ACCESS      	read-only
        STATUS          	current
        DESCRIPTION     	"Display TDM port13 FBA Errors Counter"
        ::= { tdm_counter13 3 }

tdmPort13CounterFEBErrors      	OBJECT-TYPE
    	SYNTAX              	Counter32
        MAX-ACCESS      	read-only
        STATUS          	current
        DESCRIPTION     	"Display TDM port13 FEB Errors Counter"
        ::= { tdm_counter13 4 }

tdmPort13CounterLCViolations    	OBJECT-TYPE
    	SYNTAX              	Counter32
        MAX-ACCESS      	read-only
        STATUS          	current
        DESCRIPTION     	"Display TDM port13 LC Violations Counter"
        ::= { tdm_counter13 5 }

tdm_alarm13             	OBJECT IDENTIFIER ::= { tdm13 3  }

tdmPort13AlarmLOS      		OBJECT-TYPE
    	SYNTAX              	Counter32
        MAX-ACCESS      	read-only
        STATUS          	current
        DESCRIPTION     	"Display TDM port13 LOS alarm"
        ::= { tdm_alarm13 1 }

tdmPort13AlarmLOF      		OBJECT-TYPE
    	SYNTAX              	Counter32
        MAX-ACCESS      	read-only
        STATUS          	current
        DESCRIPTION     	"Display TDM port13 LOF alarm"
        ::= { tdm_alarm13 2 }

tdmPort13AlarmAIS      		OBJECT-TYPE
    	SYNTAX              	Counter32
        MAX-ACCESS      	read-only
        STATUS          	current
        DESCRIPTION     	"Display TDM port13 AIS alarm"
        ::= { tdm_alarm13 3 }

tdmPort13AlarmTS16AIS      	OBJECT-TYPE
    	SYNTAX              	Counter32
        MAX-ACCESS      	read-only
        STATUS          	current
        DESCRIPTION     	"Display TDM port13 TS16AIS alarm"
        ::= { tdm_alarm13 4 }

tdmPort13AlarmRAI      		OBJECT-TYPE
    	SYNTAX              	Counter32
        MAX-ACCESS      	read-only
        STATUS          	current
        DESCRIPTION     	"Display TDM port13 RAI alarm"
        ::= { tdm_alarm13 5 }

tdmPort13AlarmRMA      		OBJECT-TYPE
    	SYNTAX              	Counter32
        MAX-ACCESS      	read-only
        STATUS          	current
        DESCRIPTION     	"Display TDM port13 RMA alarm"
        ::= { tdm_alarm13 6 }

tdmPort13AlarmLCMFA      	OBJECT-TYPE
    	SYNTAX              	Counter32
        MAX-ACCESS      	read-only
        STATUS          	current
        DESCRIPTION     	"Display TDM port13 LCMFA alarm"
        ::= { tdm_alarm13 7 }

tdmPort13AlarmLSMFA      	OBJECT-TYPE
    	SYNTAX              	Counter32
        MAX-ACCESS      	read-only
        STATUS          	current
        DESCRIPTION     	"Display TDM port13 LSMFA alarm"
        ::= { tdm_alarm13 8 }


tdm14             		OBJECT IDENTIFIER ::= { tdm 14  }

tdm_config14             	OBJECT IDENTIFIER ::= { tdm14 1  }

tdmPort14Status      		OBJECT-TYPE
    	SYNTAX              	INTEGER { off(0), on(1) }
        MAX-ACCESS      	read-only
        STATUS          	current
        DESCRIPTION     	"Display TDM port14 status"
        ::= { tdm_config14 1 }

tdmPort14CableConfig      	OBJECT-TYPE
    	SYNTAX              	INTEGER { len0_133(0), len133_266(1), len266_399(2), len399_533(3),
					  len355_655(4) }
        MAX-ACCESS      	read-only
        STATUS          	current
        DESCRIPTION     	"Display TDM port14 cable configuration"
        ::= { tdm_config14 2 }

tdm_counter14             	OBJECT IDENTIFIER ::= { tdm14 2  }

tdmPort14CounterCrcBlockErrors  	OBJECT-TYPE
    	SYNTAX              	Counter32
        MAX-ACCESS      	read-only
        STATUS          	current
        DESCRIPTION     	"Display TDM port14 Crc Block error Counter"
        ::= { tdm_counter14 1 }

tdmPort14CounterExCrcErrors      OBJECT-TYPE
    	SYNTAX              	Counter32
        MAX-ACCESS      	read-only
        STATUS          	current
        DESCRIPTION     	"Display TDM port14 excessive CRC block Counter"
        ::= { tdm_counter14 2 }

tdmPort14CounterFBAErrors      	OBJECT-TYPE
    	SYNTAX              	Counter32
        MAX-ACCESS      	read-only
        STATUS          	current
        DESCRIPTION     	"Display TDM port14 FBA Errors Counter"
        ::= { tdm_counter14 3 }

tdmPort14CounterFEBErrors      	OBJECT-TYPE
    	SYNTAX              	Counter32
        MAX-ACCESS      	read-only
        STATUS          	current
        DESCRIPTION     	"Display TDM port14 FEB Errors Counter"
        ::= { tdm_counter14 4 }

tdmPort14CounterLCViolations    	OBJECT-TYPE
    	SYNTAX              	Counter32
        MAX-ACCESS      	read-only
        STATUS          	current
        DESCRIPTION     	"Display TDM port14 LC Violations Counter"
        ::= { tdm_counter14 5 }

tdm_alarm14             	OBJECT IDENTIFIER ::= { tdm14 3  }

tdmPort14AlarmLOS      		OBJECT-TYPE
    	SYNTAX              	Counter32
        MAX-ACCESS      	read-only
        STATUS          	current
        DESCRIPTION     	"Display TDM port14 LOS alarm"
        ::= { tdm_alarm14 1 }

tdmPort14AlarmLOF      		OBJECT-TYPE
    	SYNTAX              	Counter32
        MAX-ACCESS      	read-only
        STATUS          	current
        DESCRIPTION     	"Display TDM port14 LOF alarm"
        ::= { tdm_alarm14 2 }

tdmPort14AlarmAIS      		OBJECT-TYPE
    	SYNTAX              	Counter32
        MAX-ACCESS      	read-only
        STATUS          	current
        DESCRIPTION     	"Display TDM port14 AIS alarm"
        ::= { tdm_alarm14 3 }

tdmPort14AlarmTS16AIS      	OBJECT-TYPE
    	SYNTAX              	Counter32
        MAX-ACCESS      	read-only
        STATUS          	current
        DESCRIPTION     	"Display TDM port14 TS16AIS alarm"
        ::= { tdm_alarm14 4 }

tdmPort14AlarmRAI      		OBJECT-TYPE
    	SYNTAX              	Counter32
        MAX-ACCESS      	read-only
        STATUS          	current
        DESCRIPTION     	"Display TDM port14 RAI alarm"
        ::= { tdm_alarm14 5 }

tdmPort14AlarmRMA      		OBJECT-TYPE
    	SYNTAX              	Counter32
        MAX-ACCESS      	read-only
        STATUS          	current
        DESCRIPTION     	"Display TDM port14 RMA alarm"
        ::= { tdm_alarm14 6 }

tdmPort14AlarmLCMFA      	OBJECT-TYPE
    	SYNTAX              	Counter32
        MAX-ACCESS      	read-only
        STATUS          	current
        DESCRIPTION     	"Display TDM port14 LCMFA alarm"
        ::= { tdm_alarm14 7 }

tdmPort14AlarmLSMFA      	OBJECT-TYPE
    	SYNTAX              	Counter32
        MAX-ACCESS      	read-only
        STATUS          	current
        DESCRIPTION     	"Display TDM port14 LSMFA alarm"
        ::= { tdm_alarm14 8 }

tdm15             		OBJECT IDENTIFIER ::= { tdm 15  }

tdm_config15             	OBJECT IDENTIFIER ::= { tdm15 1  }

tdmPort15Status      		OBJECT-TYPE
    	SYNTAX              	INTEGER { off(0), on(1) }
        MAX-ACCESS      	read-only
        STATUS          	current
        DESCRIPTION     	"Display TDM port15 status"
        ::= { tdm_config15 1 }

tdmPort15CableConfig      	OBJECT-TYPE
    	SYNTAX              	INTEGER { len0_133(0), len133_266(1), len266_399(2), len399_533(3),
					  len355_655(4) }
        MAX-ACCESS      	read-only
        STATUS          	current
        DESCRIPTION     	"Display TDM port15 cable configuration"
        ::= { tdm_config15 2 }

tdm_counter15             	OBJECT IDENTIFIER ::= { tdm15 2  }

tdmPort15CounterCrcBlockErrors  	OBJECT-TYPE
    	SYNTAX              	Counter32
        MAX-ACCESS      	read-only
        STATUS          	current
        DESCRIPTION     	"Display TDM port15 Crc Block error Counter"
        ::= { tdm_counter15 1 }

tdmPort15CounterExCrcErrors      OBJECT-TYPE
    	SYNTAX              	Counter32
        MAX-ACCESS      	read-only
        STATUS          	current
        DESCRIPTION     	"Display TDM port15 excessive CRC block Counter"
        ::= { tdm_counter15 2 }

tdmPort15CounterFBAErrors      	OBJECT-TYPE
    	SYNTAX              	Counter32
        MAX-ACCESS      	read-only
        STATUS          	current
        DESCRIPTION     	"Display TDM port15 FBA Errors Counter"
        ::= { tdm_counter15 3 }

tdmPort15CounterFEBErrors      	OBJECT-TYPE
    	SYNTAX              	Counter32
        MAX-ACCESS      	read-only
        STATUS          	current
        DESCRIPTION     	"Display TDM port15 FEB Errors Counter"
        ::= { tdm_counter15 4 }

tdmPort15CounterLCViolations    	OBJECT-TYPE
    	SYNTAX              	Counter32
        MAX-ACCESS      	read-only
        STATUS          	current
        DESCRIPTION     	"Display TDM port15 LC Violations Counter"
        ::= { tdm_counter15 5 }

tdm_alarm15             	OBJECT IDENTIFIER ::= { tdm15 3  }

tdmPort15AlarmLOS      		OBJECT-TYPE
    	SYNTAX              	Counter32
        MAX-ACCESS      	read-only
        STATUS          	current
        DESCRIPTION     	"Display TDM port15 LOS alarm"
        ::= { tdm_alarm15 1 }

tdmPort15AlarmLOF      		OBJECT-TYPE
    	SYNTAX              	Counter32
        MAX-ACCESS      	read-only
        STATUS          	current
        DESCRIPTION     	"Display TDM port15 LOF alarm"
        ::= { tdm_alarm15 2 }

tdmPort15AlarmAIS      		OBJECT-TYPE
    	SYNTAX              	Counter32
        MAX-ACCESS      	read-only
        STATUS          	current
        DESCRIPTION     	"Display TDM port15 AIS alarm"
        ::= { tdm_alarm15 3 }

tdmPort15AlarmTS16AIS      	OBJECT-TYPE
    	SYNTAX              	Counter32
        MAX-ACCESS      	read-only
        STATUS          	current
        DESCRIPTION     	"Display TDM port15 TS16AIS alarm"
        ::= { tdm_alarm15 4 }

tdmPort15AlarmRAI      		OBJECT-TYPE
    	SYNTAX              	Counter32
        MAX-ACCESS      	read-only
        STATUS          	current
        DESCRIPTION     	"Display TDM port15 RAI alarm"
        ::= { tdm_alarm15 5 }

tdmPort15AlarmRMA      		OBJECT-TYPE
    	SYNTAX              	Counter32
        MAX-ACCESS      	read-only
        STATUS          	current
        DESCRIPTION     	"Display TDM port15 RMA alarm"
        ::= { tdm_alarm15 6 }

tdmPort15AlarmLCMFA      	OBJECT-TYPE
    	SYNTAX              	Counter32
        MAX-ACCESS      	read-only
        STATUS          	current
        DESCRIPTION     	"Display TDM port15 LCMFA alarm"
        ::= { tdm_alarm15 7 }

tdmPort15AlarmLSMFA      	OBJECT-TYPE
    	SYNTAX              	Counter32
        MAX-ACCESS      	read-only
        STATUS          	current
        DESCRIPTION     	"Display TDM port15 LSMFA alarm"
        ::= { tdm_alarm15 8 }

tdm16             		OBJECT IDENTIFIER ::= { tdm 16  }

tdm_config16             	OBJECT IDENTIFIER ::= { tdm16 1  }

tdmPort16Status      		OBJECT-TYPE
    	SYNTAX              	INTEGER { off(0), on(1) }
        MAX-ACCESS      	read-only
        STATUS          	current
        DESCRIPTION     	"Display TDM port16 status"
        ::= { tdm_config16 1 }

tdmPort16CableConfig      	OBJECT-TYPE
    	SYNTAX              	INTEGER { len0_133(0), len133_266(1), len266_399(2), len399_533(3),
					  len355_655(4) }
        MAX-ACCESS      	read-only
        STATUS          	current
        DESCRIPTION     	"Display TDM port16 cable configuration"
        ::= { tdm_config16 2 }

tdm_counter16             	OBJECT IDENTIFIER ::= { tdm16 2  }

tdmPort16CounterCrcBlockErrors  	OBJECT-TYPE
    	SYNTAX              	Counter32
        MAX-ACCESS      	read-only
        STATUS          	current
        DESCRIPTION     	"Display TDM port16 Crc Block error Counter"
        ::= { tdm_counter16 1 }

tdmPort16CounterExCrcErrors      OBJECT-TYPE
    	SYNTAX              	Counter32
        MAX-ACCESS      	read-only
        STATUS          	current
        DESCRIPTION     	"Display TDM port16 excessive CRC block Counter"
        ::= { tdm_counter16 2 }

tdmPort16CounterFBAErrors      	OBJECT-TYPE
    	SYNTAX              	Counter32
        MAX-ACCESS      	read-only
        STATUS          	current
        DESCRIPTION     	"Display TDM port16 FBA Errors Counter"
        ::= { tdm_counter16 3 }

tdmPort16CounterFEBErrors      	OBJECT-TYPE
    	SYNTAX              	Counter32
        MAX-ACCESS      	read-only
        STATUS          	current
        DESCRIPTION     	"Display TDM port16 FEB Errors Counter"
        ::= { tdm_counter16 4 }

tdmPort16CounterLCViolations    	OBJECT-TYPE
    	SYNTAX              	Counter32
        MAX-ACCESS      	read-only
        STATUS          	current
        DESCRIPTION     	"Display TDM port16 LC Violations Counter"
        ::= { tdm_counter16 5 }

tdm_alarm16             	OBJECT IDENTIFIER ::= { tdm16 3  }

tdmPort16AlarmLOS      		OBJECT-TYPE
    	SYNTAX              	Counter32
        MAX-ACCESS      	read-only
        STATUS          	current
        DESCRIPTION     	"Display TDM port16 LOS alarm"
        ::= { tdm_alarm16 1 }

tdmPort16AlarmLOF      		OBJECT-TYPE
    	SYNTAX              	Counter32
        MAX-ACCESS      	read-only
        STATUS          	current
        DESCRIPTION     	"Display TDM port16 LOF alarm"
        ::= { tdm_alarm16 2 }

tdmPort16AlarmAIS      		OBJECT-TYPE
    	SYNTAX              	Counter32
        MAX-ACCESS      	read-only
        STATUS          	current
        DESCRIPTION     	"Display TDM port16 AIS alarm"
        ::= { tdm_alarm16 3 }

tdmPort16AlarmTS16AIS      	OBJECT-TYPE
    	SYNTAX              	Counter32
        MAX-ACCESS      	read-only
        STATUS          	current
        DESCRIPTION     	"Display TDM port16 TS16AIS alarm"
        ::= { tdm_alarm16 4 }

tdmPort16AlarmRAI      		OBJECT-TYPE
    	SYNTAX              	Counter32
        MAX-ACCESS      	read-only
        STATUS          	current
        DESCRIPTION     	"Display TDM port16 RAI alarm"
        ::= { tdm_alarm16 5 }

tdmPort16AlarmRMA      		OBJECT-TYPE
    	SYNTAX              	Counter32
        MAX-ACCESS      	read-only
        STATUS          	current
        DESCRIPTION     	"Display TDM port16 RMA alarm"
        ::= { tdm_alarm16 6 }

tdmPort16AlarmLCMFA      	OBJECT-TYPE
    	SYNTAX              	Counter32
        MAX-ACCESS      	read-only
        STATUS          	current
        DESCRIPTION     	"Display TDM port16 LCMFA alarm"
        ::= { tdm_alarm16 7 }

tdmPort16AlarmLSMFA      	OBJECT-TYPE
    	SYNTAX              	Counter32
        MAX-ACCESS      	read-only
        STATUS          	current
        DESCRIPTION     	"Display TDM port16 LSMFA alarm"
        ::= { tdm_alarm16 8 }

tdm17             		OBJECT IDENTIFIER ::= { tdm 17  }

tdm_config17             	OBJECT IDENTIFIER ::= { tdm17 1  }

tdmPort17Status      		OBJECT-TYPE
    	SYNTAX              	INTEGER { off(0), on(1) }
        MAX-ACCESS      	read-only
        STATUS          	current
        DESCRIPTION     	"Display TDM port17 status"
        ::= { tdm_config17 1 }

tdmPort17CableConfig      	OBJECT-TYPE
    	SYNTAX              	INTEGER { len0_133(0), len133_266(1), len266_399(2), len399_533(3),
					  len355_655(4) }
        MAX-ACCESS      	read-only
        STATUS          	current
        DESCRIPTION     	"Display TDM port17 cable configuration"
        ::= { tdm_config17 2 }

tdm_counter17             	OBJECT IDENTIFIER ::= { tdm17 2  }

tdmPort17CounterCrcBlockErrors  	OBJECT-TYPE
    	SYNTAX              	Counter32
        MAX-ACCESS      	read-only
        STATUS          	current
        DESCRIPTION     	"Display TDM port17 Crc Block error Counter"
        ::= { tdm_counter17 1 }

tdmPort17CounterExCrcErrors      OBJECT-TYPE
    	SYNTAX              	Counter32
        MAX-ACCESS      	read-only
        STATUS          	current
        DESCRIPTION     	"Display TDM port17 excessive CRC block Counter"
        ::= { tdm_counter17 2 }

tdmPort17CounterFBAErrors      	OBJECT-TYPE
    	SYNTAX              	Counter32
        MAX-ACCESS      	read-only
        STATUS          	current
        DESCRIPTION     	"Display TDM port17 FBA Errors Counter"
        ::= { tdm_counter17 3 }

tdmPort17CounterFEBErrors      	OBJECT-TYPE
    	SYNTAX              	Counter32
        MAX-ACCESS      	read-only
        STATUS          	current
        DESCRIPTION     	"Display TDM port17 FEB Errors Counter"
        ::= { tdm_counter17 4 }

tdmPort17CounterLCViolations    	OBJECT-TYPE
    	SYNTAX              	Counter32
        MAX-ACCESS      	read-only
        STATUS          	current
        DESCRIPTION     	"Display TDM port17 LC Violations Counter"
        ::= { tdm_counter17 5 }

tdm_alarm17             	OBJECT IDENTIFIER ::= { tdm17 3  }

tdmPort17AlarmLOS      		OBJECT-TYPE
    	SYNTAX              	Counter32
        MAX-ACCESS      	read-only
        STATUS          	current
        DESCRIPTION     	"Display TDM port17 LOS alarm"
        ::= { tdm_alarm17 1 }

tdmPort17AlarmLOF      		OBJECT-TYPE
    	SYNTAX              	Counter32
        MAX-ACCESS      	read-only
        STATUS          	current
        DESCRIPTION     	"Display TDM port17 LOF alarm"
        ::= { tdm_alarm17 2 }

tdmPort17AlarmAIS      		OBJECT-TYPE
    	SYNTAX              	Counter32
        MAX-ACCESS      	read-only
        STATUS          	current
        DESCRIPTION     	"Display TDM port17 AIS alarm"
        ::= { tdm_alarm17 3 }

tdmPort17AlarmTS16AIS      	OBJECT-TYPE
    	SYNTAX              	Counter32
        MAX-ACCESS      	read-only
        STATUS          	current
        DESCRIPTION     	"Display TDM port17 TS16AIS alarm"
        ::= { tdm_alarm17 4 }

tdmPort17AlarmRAI      		OBJECT-TYPE
    	SYNTAX              	Counter32
        MAX-ACCESS      	read-only
        STATUS          	current
        DESCRIPTION     	"Display TDM port17 RAI alarm"
        ::= { tdm_alarm17 5 }

tdmPort17AlarmRMA      		OBJECT-TYPE
    	SYNTAX              	Counter32
        MAX-ACCESS      	read-only
        STATUS          	current
        DESCRIPTION     	"Display TDM port17 RMA alarm"
        ::= { tdm_alarm17 6 }

tdmPort17AlarmLCMFA      	OBJECT-TYPE
    	SYNTAX              	Counter32
        MAX-ACCESS      	read-only
        STATUS          	current
        DESCRIPTION     	"Display TDM port17 LCMFA alarm"
        ::= { tdm_alarm17 7 }

tdmPort17AlarmLSMFA      	OBJECT-TYPE
    	SYNTAX              	Counter32
        MAX-ACCESS      	read-only
        STATUS          	current
        DESCRIPTION     	"Display TDM port17 LSMFA alarm"
        ::= { tdm_alarm17 8 }
tdm18             		OBJECT IDENTIFIER ::= { tdm 18  }

tdm_config18             	OBJECT IDENTIFIER ::= { tdm18 1  }

tdmPort18Status      		OBJECT-TYPE
    	SYNTAX              	INTEGER { off(0), on(1) }
        MAX-ACCESS      	read-only
        STATUS          	current
        DESCRIPTION     	"Display TDM port18 status"
        ::= { tdm_config18 1 }

tdmPort18CableConfig      	OBJECT-TYPE
    	SYNTAX              	INTEGER { len0_133(0), len133_266(1), len266_399(2), len399_533(3),
					  len355_655(4) }
        MAX-ACCESS      	read-only
        STATUS          	current
        DESCRIPTION     	"Display TDM port18 cable configuration"
        ::= { tdm_config18 2 }

tdm_counter18             	OBJECT IDENTIFIER ::= { tdm18 2  }

tdmPort18CounterCrcBlockErrors  	OBJECT-TYPE
    	SYNTAX              	Counter32
        MAX-ACCESS      	read-only
        STATUS          	current
        DESCRIPTION     	"Display TDM port18 Crc Block error Counter"
        ::= { tdm_counter18 1 }

tdmPort18CounterExCrcErrors      OBJECT-TYPE
    	SYNTAX              	Counter32
        MAX-ACCESS      	read-only
        STATUS          	current
        DESCRIPTION     	"Display TDM port18 excessive CRC block Counter"
        ::= { tdm_counter18 2 }

tdmPort18CounterFBAErrors      	OBJECT-TYPE
    	SYNTAX              	Counter32
        MAX-ACCESS      	read-only
        STATUS          	current
        DESCRIPTION     	"Display TDM port18 FBA Errors Counter"
        ::= { tdm_counter18 3 }

tdmPort18CounterFEBErrors      	OBJECT-TYPE
    	SYNTAX              	Counter32
        MAX-ACCESS      	read-only
        STATUS          	current
        DESCRIPTION     	"Display TDM port18 FEB Errors Counter"
        ::= { tdm_counter18 4 }

tdmPort18CounterLCViolations    	OBJECT-TYPE
    	SYNTAX              	Counter32
        MAX-ACCESS      	read-only
        STATUS          	current
        DESCRIPTION     	"Display TDM port18 LC Violations Counter"
        ::= { tdm_counter18 5 }

tdm_alarm18             	OBJECT IDENTIFIER ::= { tdm18 3  }

tdmPort18AlarmLOS      		OBJECT-TYPE
    	SYNTAX              	Counter32
        MAX-ACCESS      	read-only
        STATUS          	current
        DESCRIPTION     	"Display TDM port18 LOS alarm"
        ::= { tdm_alarm18 1 }

tdmPort18AlarmLOF      		OBJECT-TYPE
    	SYNTAX              	Counter32
        MAX-ACCESS      	read-only
        STATUS          	current
        DESCRIPTION     	"Display TDM port18 LOF alarm"
        ::= { tdm_alarm18 2 }

tdmPort18AlarmAIS      		OBJECT-TYPE
    	SYNTAX              	Counter32
        MAX-ACCESS      	read-only
        STATUS          	current
        DESCRIPTION     	"Display TDM port18 AIS alarm"
        ::= { tdm_alarm18 3 }

tdmPort18AlarmTS16AIS      	OBJECT-TYPE
    	SYNTAX              	Counter32
        MAX-ACCESS      	read-only
        STATUS          	current
        DESCRIPTION     	"Display TDM port18 TS16AIS alarm"
        ::= { tdm_alarm18 4 }

tdmPort18AlarmRAI      		OBJECT-TYPE
    	SYNTAX              	Counter32
        MAX-ACCESS      	read-only
        STATUS          	current
        DESCRIPTION     	"Display TDM port18 RAI alarm"
        ::= { tdm_alarm18 5 }

tdmPort18AlarmRMA      		OBJECT-TYPE
    	SYNTAX              	Counter32
        MAX-ACCESS      	read-only
        STATUS          	current
        DESCRIPTION     	"Display TDM port18 RMA alarm"
        ::= { tdm_alarm18 6 }

tdmPort18AlarmLCMFA      	OBJECT-TYPE
    	SYNTAX              	Counter32
        MAX-ACCESS      	read-only
        STATUS          	current
        DESCRIPTION     	"Display TDM port18 LCMFA alarm"
        ::= { tdm_alarm18 7 }

tdmPort18AlarmLSMFA      	OBJECT-TYPE
    	SYNTAX              	Counter32
        MAX-ACCESS      	read-only
        STATUS          	current
        DESCRIPTION     	"Display TDM port18 LSMFA alarm"
        ::= { tdm_alarm18 8 }
tdm19             		OBJECT IDENTIFIER ::= { tdm 19  }

tdm_config19             	OBJECT IDENTIFIER ::= { tdm19 1  }

tdmPort19Status      		OBJECT-TYPE
    	SYNTAX              	INTEGER { off(0), on(1) }
        MAX-ACCESS      	read-only
        STATUS          	current
        DESCRIPTION     	"Display TDM port19 status"
        ::= { tdm_config19 1 }

tdmPort19CableConfig      	OBJECT-TYPE
    	SYNTAX              	INTEGER { len0_133(0), len133_266(1), len266_399(2), len399_533(3),
					  len355_655(4) }
        MAX-ACCESS      	read-only
        STATUS          	current
        DESCRIPTION     	"Display TDM port19 cable configuration"
        ::= { tdm_config19 2 }

tdm_counter19             	OBJECT IDENTIFIER ::= { tdm19 2  }

tdmPort19CounterCrcBlockErrors  	OBJECT-TYPE
    	SYNTAX              	Counter32
        MAX-ACCESS      	read-only
        STATUS          	current
        DESCRIPTION     	"Display TDM port19 Crc Block error Counter"
        ::= { tdm_counter19 1 }

tdmPort19CounterExCrcErrors      OBJECT-TYPE
    	SYNTAX              	Counter32
        MAX-ACCESS      	read-only
        STATUS          	current
        DESCRIPTION     	"Display TDM port19 excessive CRC block Counter"
        ::= { tdm_counter19 2 }

tdmPort19CounterFBAErrors      	OBJECT-TYPE
    	SYNTAX              	Counter32
        MAX-ACCESS      	read-only
        STATUS          	current
        DESCRIPTION     	"Display TDM port19 FBA Errors Counter"
        ::= { tdm_counter19 3 }

tdmPort19CounterFEBErrors      	OBJECT-TYPE
    	SYNTAX              	Counter32
        MAX-ACCESS      	read-only
        STATUS          	current
        DESCRIPTION     	"Display TDM port19 FEB Errors Counter"
        ::= { tdm_counter19 4 }

tdmPort19CounterLCViolations    	OBJECT-TYPE
    	SYNTAX              	Counter32
        MAX-ACCESS      	read-only
        STATUS          	current
        DESCRIPTION     	"Display TDM port19 LC Violations Counter"
        ::= { tdm_counter19 5 }

tdm_alarm19             	OBJECT IDENTIFIER ::= { tdm19 3  }

tdmPort19AlarmLOS      		OBJECT-TYPE
    	SYNTAX              	Counter32
        MAX-ACCESS      	read-only
        STATUS          	current
        DESCRIPTION     	"Display TDM port19 LOS alarm"
        ::= { tdm_alarm19 1 }

tdmPort19AlarmLOF      		OBJECT-TYPE
    	SYNTAX              	Counter32
        MAX-ACCESS      	read-only
        STATUS          	current
        DESCRIPTION     	"Display TDM port19 LOF alarm"
        ::= { tdm_alarm19 2 }

tdmPort19AlarmAIS      		OBJECT-TYPE
    	SYNTAX              	Counter32
        MAX-ACCESS      	read-only
        STATUS          	current
        DESCRIPTION     	"Display TDM port19 AIS alarm"
        ::= { tdm_alarm19 3 }

tdmPort19AlarmTS16AIS      	OBJECT-TYPE
    	SYNTAX              	Counter32
        MAX-ACCESS      	read-only
        STATUS          	current
        DESCRIPTION     	"Display TDM port19 TS16AIS alarm"
        ::= { tdm_alarm19 4 }

tdmPort19AlarmRAI      		OBJECT-TYPE
    	SYNTAX              	Counter32
        MAX-ACCESS      	read-only
        STATUS          	current
        DESCRIPTION     	"Display TDM port19 RAI alarm"
        ::= { tdm_alarm19 5 }

tdmPort19AlarmRMA      		OBJECT-TYPE
    	SYNTAX              	Counter32
        MAX-ACCESS      	read-only
        STATUS          	current
        DESCRIPTION     	"Display TDM port19 RMA alarm"
        ::= { tdm_alarm19 6 }

tdmPort19AlarmLCMFA      	OBJECT-TYPE
    	SYNTAX              	Counter32
        MAX-ACCESS      	read-only
        STATUS          	current
        DESCRIPTION     	"Display TDM port19 LCMFA alarm"
        ::= { tdm_alarm19 7 }

tdmPort19AlarmLSMFA      	OBJECT-TYPE
    	SYNTAX              	Counter32
        MAX-ACCESS      	read-only
        STATUS          	current
        DESCRIPTION     	"Display TDM port19 LSMFA alarm"
        ::= { tdm_alarm19 8 }

tdm20             		OBJECT IDENTIFIER ::= { tdm 20  }

tdm_config20             	OBJECT IDENTIFIER ::= { tdm20 1  }

tdmPort20Status      		OBJECT-TYPE
    	SYNTAX              	INTEGER { off(0), on(1) }
        MAX-ACCESS      	read-only
        STATUS          	current
        DESCRIPTION     	"Display TDM port20 status"
        ::= { tdm_config20 1 }

tdmPort20CableConfig      	OBJECT-TYPE
    	SYNTAX              	INTEGER { len0_133(0), len133_266(1), len266_399(2), len399_533(3),
					  len355_655(4) }
        MAX-ACCESS      	read-only
        STATUS          	current
        DESCRIPTION     	"Display TDM port20 cable configuration"
        ::= { tdm_config20 2 }

tdm_counter20             	OBJECT IDENTIFIER ::= { tdm20 2  }

tdmPort20CounterCrcBlockErrors  	OBJECT-TYPE
    	SYNTAX              	Counter32
        MAX-ACCESS      	read-only
        STATUS          	current
        DESCRIPTION     	"Display TDM port20 Crc Block error Counter"
        ::= { tdm_counter20 1 }

tdmPort20CounterExCrcErrors      OBJECT-TYPE
    	SYNTAX              	Counter32
        MAX-ACCESS      	read-only
        STATUS          	current
        DESCRIPTION     	"Display TDM port20 excessive CRC block Counter"
        ::= { tdm_counter20 2 }

tdmPort20CounterFBAErrors      	OBJECT-TYPE
    	SYNTAX              	Counter32
        MAX-ACCESS      	read-only
        STATUS          	current
        DESCRIPTION     	"Display TDM port20 FBA Errors Counter"
        ::= { tdm_counter20 3 }

tdmPort20CounterFEBErrors      	OBJECT-TYPE
    	SYNTAX              	Counter32
        MAX-ACCESS      	read-only
        STATUS          	current
        DESCRIPTION     	"Display TDM port20 FEB Errors Counter"
        ::= { tdm_counter20 4 }

tdmPort20CounterLCViolations    	OBJECT-TYPE
    	SYNTAX              	Counter32
        MAX-ACCESS      	read-only
        STATUS          	current
        DESCRIPTION     	"Display TDM port20 LC Violations Counter"
        ::= { tdm_counter20 5 }

tdm_alarm20             	OBJECT IDENTIFIER ::= { tdm20 3  }

tdmPort20AlarmLOS      		OBJECT-TYPE
    	SYNTAX              	Counter32
        MAX-ACCESS      	read-only
        STATUS          	current
        DESCRIPTION     	"Display TDM port20 LOS alarm"
        ::= { tdm_alarm20 1 }

tdmPort20AlarmLOF      		OBJECT-TYPE
    	SYNTAX              	Counter32
        MAX-ACCESS      	read-only
        STATUS          	current
        DESCRIPTION     	"Display TDM port20 LOF alarm"
        ::= { tdm_alarm20 2 }

tdmPort20AlarmAIS      		OBJECT-TYPE
    	SYNTAX              	Counter32
        MAX-ACCESS      	read-only
        STATUS          	current
        DESCRIPTION     	"Display TDM port20 AIS alarm"
        ::= { tdm_alarm20 3 }

tdmPort20AlarmTS16AIS      	OBJECT-TYPE
    	SYNTAX              	Counter32
        MAX-ACCESS      	read-only
        STATUS          	current
        DESCRIPTION     	"Display TDM port20 TS16AIS alarm"
        ::= { tdm_alarm20 4 }

tdmPort20AlarmRAI      		OBJECT-TYPE
    	SYNTAX              	Counter32
        MAX-ACCESS      	read-only
        STATUS          	current
        DESCRIPTION     	"Display TDM port20 RAI alarm"
        ::= { tdm_alarm20 5 }

tdmPort20AlarmRMA      		OBJECT-TYPE
    	SYNTAX              	Counter32
        MAX-ACCESS      	read-only
        STATUS          	current
        DESCRIPTION     	"Display TDM port20 RMA alarm"
        ::= { tdm_alarm20 6 }

tdmPort20AlarmLCMFA      	OBJECT-TYPE
    	SYNTAX              	Counter32
        MAX-ACCESS      	read-only
        STATUS          	current
        DESCRIPTION     	"Display TDM port20 LCMFA alarm"
        ::= { tdm_alarm20 7 }

tdmPort20AlarmLSMFA      	OBJECT-TYPE
    	SYNTAX              	Counter32
        MAX-ACCESS      	read-only
        STATUS          	current
        DESCRIPTION     	"Display TDM port20 LSMFA alarm"
        ::= { tdm_alarm20 8 }

tdm21             		OBJECT IDENTIFIER ::= { tdm 21  }

tdm_config21             	OBJECT IDENTIFIER ::= { tdm21 1  }

tdmPort21Status      		OBJECT-TYPE
    	SYNTAX              	INTEGER { off(0), on(1) }
        MAX-ACCESS      	read-only
        STATUS          	current
        DESCRIPTION     	"Display TDM port21 status"
        ::= { tdm_config21 1 }

tdmPort21CableConfig      	OBJECT-TYPE
    	SYNTAX              	INTEGER { len0_133(0), len133_266(1), len266_399(2), len399_533(3),
					  len355_655(4) }
        MAX-ACCESS      	read-only
        STATUS          	current
        DESCRIPTION     	"Display TDM port21 cable configuration"
        ::= { tdm_config21 2 }

tdm_counter21             	OBJECT IDENTIFIER ::= { tdm21 2  }

tdmPort21CounterCrcBlockErrors  	OBJECT-TYPE
    	SYNTAX              	Counter32
        MAX-ACCESS      	read-only
        STATUS          	current
        DESCRIPTION     	"Display TDM port21 Crc Block error Counter"
        ::= { tdm_counter21 1 }

tdmPort21CounterExCrcErrors      OBJECT-TYPE
    	SYNTAX              	Counter32
        MAX-ACCESS      	read-only
        STATUS          	current
        DESCRIPTION     	"Display TDM port21 excessive CRC block Counter"
        ::= { tdm_counter21 2 }

tdmPort21CounterFBAErrors      	OBJECT-TYPE
    	SYNTAX              	Counter32
        MAX-ACCESS      	read-only
        STATUS          	current
        DESCRIPTION     	"Display TDM port21 FBA Errors Counter"
        ::= { tdm_counter21 3 }

tdmPort21CounterFEBErrors      	OBJECT-TYPE
    	SYNTAX              	Counter32
        MAX-ACCESS      	read-only
        STATUS          	current
        DESCRIPTION     	"Display TDM port21 FEB Errors Counter"
        ::= { tdm_counter21 4 }

tdmPort21CounterLCViolations    	OBJECT-TYPE
    	SYNTAX              	Counter32
        MAX-ACCESS      	read-only
        STATUS          	current
        DESCRIPTION     	"Display TDM port21 LC Violations Counter"
        ::= { tdm_counter21 5 }

tdm_alarm21             	OBJECT IDENTIFIER ::= { tdm21 3  }

tdmPort21AlarmLOS      		OBJECT-TYPE
    	SYNTAX              	Counter32
        MAX-ACCESS      	read-only
        STATUS          	current
        DESCRIPTION     	"Display TDM port21 LOS alarm"
        ::= { tdm_alarm21 1 }

tdmPort21AlarmLOF      		OBJECT-TYPE
    	SYNTAX              	Counter32
        MAX-ACCESS      	read-only
        STATUS          	current
        DESCRIPTION     	"Display TDM port21 LOF alarm"
        ::= { tdm_alarm21 2 }

tdmPort21AlarmAIS      		OBJECT-TYPE
    	SYNTAX              	Counter32
        MAX-ACCESS      	read-only
        STATUS          	current
        DESCRIPTION     	"Display TDM port21 AIS alarm"
        ::= { tdm_alarm21 3 }

tdmPort21AlarmTS16AIS      	OBJECT-TYPE
    	SYNTAX              	Counter32
        MAX-ACCESS      	read-only
        STATUS          	current
        DESCRIPTION     	"Display TDM port21 TS16AIS alarm"
        ::= { tdm_alarm21 4 }

tdmPort21AlarmRAI      		OBJECT-TYPE
    	SYNTAX              	Counter32
        MAX-ACCESS      	read-only
        STATUS          	current
        DESCRIPTION     	"Display TDM port21 RAI alarm"
        ::= { tdm_alarm21 5 }

tdmPort21AlarmRMA      		OBJECT-TYPE
    	SYNTAX              	Counter32
        MAX-ACCESS      	read-only
        STATUS          	current
        DESCRIPTION     	"Display TDM port21 RMA alarm"
        ::= { tdm_alarm21 6 }

tdmPort21AlarmLCMFA      	OBJECT-TYPE
    	SYNTAX              	Counter32
        MAX-ACCESS      	read-only
        STATUS          	current
        DESCRIPTION     	"Display TDM port21 LCMFA alarm"
        ::= { tdm_alarm21 7 }

tdmPort21AlarmLSMFA      	OBJECT-TYPE
    	SYNTAX              	Counter32
        MAX-ACCESS      	read-only
        STATUS          	current
        DESCRIPTION     	"Display TDM port21 LSMFA alarm"
        ::= { tdm_alarm21 8 }

tdm22             		OBJECT IDENTIFIER ::= { tdm 22  }

tdm_config22             	OBJECT IDENTIFIER ::= { tdm22 1  }

tdmPort22Status      		OBJECT-TYPE
    	SYNTAX              	INTEGER { off(0), on(1) }
        MAX-ACCESS      	read-only
        STATUS          	current
        DESCRIPTION     	"Display TDM port22 status"
        ::= { tdm_config22 1 }

tdmPort22CableConfig      	OBJECT-TYPE
    	SYNTAX              	INTEGER { len0_133(0), len133_266(1), len266_399(2), len399_533(3),
					  len355_655(4) }
        MAX-ACCESS      	read-only
        STATUS          	current
        DESCRIPTION     	"Display TDM port22 cable configuration"
        ::= { tdm_config22 2 }

tdm_counter22             	OBJECT IDENTIFIER ::= { tdm22 2  }

tdmPort22CounterCrcBlockErrors  	OBJECT-TYPE
    	SYNTAX              	Counter32
        MAX-ACCESS      	read-only
        STATUS          	current
        DESCRIPTION     	"Display TDM port22 Crc Block error Counter"
        ::= { tdm_counter22 1 }

tdmPort22CounterExCrcErrors      OBJECT-TYPE
    	SYNTAX              	Counter32
        MAX-ACCESS      	read-only
        STATUS          	current
        DESCRIPTION     	"Display TDM port22 excessive CRC block Counter"
        ::= { tdm_counter22 2 }

tdmPort22CounterFBAErrors      	OBJECT-TYPE
    	SYNTAX              	Counter32
        MAX-ACCESS      	read-only
        STATUS          	current
        DESCRIPTION     	"Display TDM port22 FBA Errors Counter"
        ::= { tdm_counter22 3 }

tdmPort22CounterFEBErrors      	OBJECT-TYPE
    	SYNTAX              	Counter32
        MAX-ACCESS      	read-only
        STATUS          	current
        DESCRIPTION     	"Display TDM port22 FEB Errors Counter"
        ::= { tdm_counter22 4 }

tdmPort22CounterLCViolations    	OBJECT-TYPE
    	SYNTAX              	Counter32
        MAX-ACCESS      	read-only
        STATUS          	current
        DESCRIPTION     	"Display TDM port22 LC Violations Counter"
        ::= { tdm_counter22 5 }

tdm_alarm22             	OBJECT IDENTIFIER ::= { tdm22 3  }

tdmPort22AlarmLOS      		OBJECT-TYPE
    	SYNTAX              	Counter32
        MAX-ACCESS      	read-only
        STATUS          	current
        DESCRIPTION     	"Display TDM port22 LOS alarm"
        ::= { tdm_alarm22 1 }

tdmPort22AlarmLOF      		OBJECT-TYPE
    	SYNTAX              	Counter32
        MAX-ACCESS      	read-only
        STATUS          	current
        DESCRIPTION     	"Display TDM port22 LOF alarm"
        ::= { tdm_alarm22 2 }

tdmPort22AlarmAIS      		OBJECT-TYPE
    	SYNTAX              	Counter32
        MAX-ACCESS      	read-only
        STATUS          	current
        DESCRIPTION     	"Display TDM port22 AIS alarm"
        ::= { tdm_alarm22 3 }

tdmPort22AlarmTS16AIS      	OBJECT-TYPE
    	SYNTAX              	Counter32
        MAX-ACCESS      	read-only
        STATUS          	current
        DESCRIPTION     	"Display TDM port22 TS16AIS alarm"
        ::= { tdm_alarm22 4 }

tdmPort22AlarmRAI      		OBJECT-TYPE
    	SYNTAX              	Counter32
        MAX-ACCESS      	read-only
        STATUS          	current
        DESCRIPTION     	"Display TDM port22 RAI alarm"
        ::= { tdm_alarm22 5 }

tdmPort22AlarmRMA      		OBJECT-TYPE
    	SYNTAX              	Counter32
        MAX-ACCESS      	read-only
        STATUS          	current
        DESCRIPTION     	"Display TDM port22 RMA alarm"
        ::= { tdm_alarm22 6 }

tdmPort22AlarmLCMFA      	OBJECT-TYPE
    	SYNTAX              	Counter32
        MAX-ACCESS      	read-only
        STATUS          	current
        DESCRIPTION     	"Display TDM port22 LCMFA alarm"
        ::= { tdm_alarm22 7 }

tdmPort22AlarmLSMFA      	OBJECT-TYPE
    	SYNTAX              	Counter32
        MAX-ACCESS      	read-only
        STATUS          	current
        DESCRIPTION     	"Display TDM port22 LSMFA alarm"
        ::= { tdm_alarm22 8 }

tdm23             		OBJECT IDENTIFIER ::= { tdm 23  }

tdm_config23             	OBJECT IDENTIFIER ::= { tdm23 1  }

tdmPort23Status      		OBJECT-TYPE
    	SYNTAX              	INTEGER { off(0), on(1) }
        MAX-ACCESS      	read-only
        STATUS          	current
        DESCRIPTION     	"Display TDM port23 status"
        ::= { tdm_config23 1 }

tdmPort23CableConfig      	OBJECT-TYPE
    	SYNTAX              	INTEGER { len0_133(0), len133_266(1), len266_399(2), len399_533(3),
					  len355_655(4) }
        MAX-ACCESS      	read-only
        STATUS          	current
        DESCRIPTION     	"Display TDM port23 cable configuration"
        ::= { tdm_config23 2 }

tdm_counter23             	OBJECT IDENTIFIER ::= { tdm23 2  }

tdmPort23CounterCrcBlockErrors  	OBJECT-TYPE
    	SYNTAX              	Counter32
        MAX-ACCESS      	read-only
        STATUS          	current
        DESCRIPTION     	"Display TDM port23 Crc Block error Counter"
        ::= { tdm_counter23 1 }

tdmPort23CounterExCrcErrors      OBJECT-TYPE
    	SYNTAX              	Counter32
        MAX-ACCESS      	read-only
        STATUS          	current
        DESCRIPTION     	"Display TDM port23 excessive CRC block Counter"
        ::= { tdm_counter23 2 }

tdmPort23CounterFBAErrors      	OBJECT-TYPE
    	SYNTAX              	Counter32
        MAX-ACCESS      	read-only
        STATUS          	current
        DESCRIPTION     	"Display TDM port23 FBA Errors Counter"
        ::= { tdm_counter23 3 }

tdmPort23CounterFEBErrors      	OBJECT-TYPE
    	SYNTAX              	Counter32
        MAX-ACCESS      	read-only
        STATUS          	current
        DESCRIPTION     	"Display TDM port23 FEB Errors Counter"
        ::= { tdm_counter23 4 }

tdmPort23CounterLCViolations    	OBJECT-TYPE
    	SYNTAX              	Counter32
        MAX-ACCESS      	read-only
        STATUS          	current
        DESCRIPTION     	"Display TDM port23 LC Violations Counter"
        ::= { tdm_counter23 5 }

tdm_alarm23             	OBJECT IDENTIFIER ::= { tdm23 3  }

tdmPort23AlarmLOS      		OBJECT-TYPE
    	SYNTAX              	Counter32
        MAX-ACCESS      	read-only
        STATUS          	current
        DESCRIPTION     	"Display TDM port23 LOS alarm"
        ::= { tdm_alarm23 1 }

tdmPort23AlarmLOF      		OBJECT-TYPE
    	SYNTAX              	Counter32
        MAX-ACCESS      	read-only
        STATUS          	current
        DESCRIPTION     	"Display TDM port23 LOF alarm"
        ::= { tdm_alarm23 2 }

tdmPort23AlarmAIS      		OBJECT-TYPE
    	SYNTAX              	Counter32
        MAX-ACCESS      	read-only
        STATUS          	current
        DESCRIPTION     	"Display TDM port23 AIS alarm"
        ::= { tdm_alarm23 3 }

tdmPort23AlarmTS16AIS      	OBJECT-TYPE
    	SYNTAX              	Counter32
        MAX-ACCESS      	read-only
        STATUS          	current
        DESCRIPTION     	"Display TDM port23 TS16AIS alarm"
        ::= { tdm_alarm23 4 }

tdmPort23AlarmRAI      		OBJECT-TYPE
    	SYNTAX              	Counter32
        MAX-ACCESS      	read-only
        STATUS          	current
        DESCRIPTION     	"Display TDM port23 RAI alarm"
        ::= { tdm_alarm23 5 }

tdmPort23AlarmRMA      		OBJECT-TYPE
    	SYNTAX              	Counter32
        MAX-ACCESS      	read-only
        STATUS          	current
        DESCRIPTION     	"Display TDM port23 RMA alarm"
        ::= { tdm_alarm23 6 }

tdmPort23AlarmLCMFA      	OBJECT-TYPE
    	SYNTAX              	Counter32
        MAX-ACCESS      	read-only
        STATUS          	current
        DESCRIPTION     	"Display TDM port23 LCMFA alarm"
        ::= { tdm_alarm23 7 }

tdmPort23AlarmLSMFA      	OBJECT-TYPE
    	SYNTAX              	Counter32
        MAX-ACCESS      	read-only
        STATUS          	current
        DESCRIPTION     	"Display TDM port23 LSMFA alarm"
        ::= { tdm_alarm23 8 }

tdm24             		OBJECT IDENTIFIER ::= { tdm 24  }

tdm_config24             	OBJECT IDENTIFIER ::= { tdm24 1  }

tdmPort24Status      		OBJECT-TYPE
    	SYNTAX              	INTEGER { off(0), on(1) }
        MAX-ACCESS      	read-only
        STATUS          	current
        DESCRIPTION     	"Display TDM port24 status"
        ::= { tdm_config24 1 }

tdmPort24CableConfig      	OBJECT-TYPE
    	SYNTAX              	INTEGER { len0_133(0), len133_266(1), len266_399(2), len399_533(3),
					  len355_655(4) }
        MAX-ACCESS      	read-only
        STATUS          	current
        DESCRIPTION     	"Display TDM port24 cable configuration"
        ::= { tdm_config24 2 }

tdm_counter24             	OBJECT IDENTIFIER ::= { tdm24 2  }

tdmPort24CounterCrcBlockErrors  	OBJECT-TYPE
    	SYNTAX              	Counter32
        MAX-ACCESS      	read-only
        STATUS          	current
        DESCRIPTION     	"Display TDM port24 Crc Block error Counter"
        ::= { tdm_counter24 1 }

tdmPort24CounterExCrcErrors      OBJECT-TYPE
    	SYNTAX              	Counter32
        MAX-ACCESS      	read-only
        STATUS          	current
        DESCRIPTION     	"Display TDM port24 excessive CRC block Counter"
        ::= { tdm_counter24 2 }

tdmPort24CounterFBAErrors      	OBJECT-TYPE
    	SYNTAX              	Counter32
        MAX-ACCESS      	read-only
        STATUS          	current
        DESCRIPTION     	"Display TDM port24 FBA Errors Counter"
        ::= { tdm_counter24 3 }

tdmPort24CounterFEBErrors      	OBJECT-TYPE
    	SYNTAX              	Counter32
        MAX-ACCESS      	read-only
        STATUS          	current
        DESCRIPTION     	"Display TDM port24 FEB Errors Counter"
        ::= { tdm_counter24 4 }

tdmPort24CounterLCViolations    	OBJECT-TYPE
    	SYNTAX              	Counter32
        MAX-ACCESS      	read-only
        STATUS          	current
        DESCRIPTION     	"Display TDM port24 LC Violations Counter"
        ::= { tdm_counter24 5 }

tdm_alarm24             	OBJECT IDENTIFIER ::= { tdm24 3  }

tdmPort24AlarmLOS      		OBJECT-TYPE
    	SYNTAX              	Counter32
        MAX-ACCESS      	read-only
        STATUS          	current
        DESCRIPTION     	"Display TDM port24 LOS alarm"
        ::= { tdm_alarm24 1 }

tdmPort24AlarmLOF      		OBJECT-TYPE
    	SYNTAX              	Counter32
        MAX-ACCESS      	read-only
        STATUS          	current
        DESCRIPTION     	"Display TDM port24 LOF alarm"
        ::= { tdm_alarm24 2 }

tdmPort24AlarmAIS      		OBJECT-TYPE
    	SYNTAX              	Counter32
        MAX-ACCESS      	read-only
        STATUS          	current
        DESCRIPTION     	"Display TDM port24 AIS alarm"
        ::= { tdm_alarm24 3 }

tdmPort24AlarmTS16AIS      	OBJECT-TYPE
    	SYNTAX              	Counter32
        MAX-ACCESS      	read-only
        STATUS          	current
        DESCRIPTION     	"Display TDM port24 TS16AIS alarm"
        ::= { tdm_alarm24 4 }

tdmPort24AlarmRAI      		OBJECT-TYPE
    	SYNTAX              	Counter32
        MAX-ACCESS      	read-only
        STATUS          	current
        DESCRIPTION     	"Display TDM port24 RAI alarm"
        ::= { tdm_alarm24 5 }

tdmPort24AlarmRMA      		OBJECT-TYPE
    	SYNTAX              	Counter32
        MAX-ACCESS      	read-only
        STATUS          	current
        DESCRIPTION     	"Display TDM port24 RMA alarm"
        ::= { tdm_alarm24 6 }

tdmPort24AlarmLCMFA      	OBJECT-TYPE
    	SYNTAX              	Counter32
        MAX-ACCESS      	read-only
        STATUS          	current
        DESCRIPTION     	"Display TDM port24 LCMFA alarm"
        ::= { tdm_alarm24 7 }

tdmPort24AlarmLSMFA      	OBJECT-TYPE
    	SYNTAX              	Counter32
        MAX-ACCESS      	read-only
        STATUS          	current
        DESCRIPTION     	"Display TDM port24 LSMFA alarm"
        ::= { tdm_alarm24 8 }
tdm25             		OBJECT IDENTIFIER ::= { tdm 25  }

tdm_config25             	OBJECT IDENTIFIER ::= { tdm25 1  }

tdmPort25Status      		OBJECT-TYPE
    	SYNTAX              	INTEGER { off(0), on(1) }
        MAX-ACCESS      	read-only
        STATUS          	current
        DESCRIPTION     	"Display TDM port25 status"
        ::= { tdm_config25 1 }

tdmPort25CableConfig      	OBJECT-TYPE
    	SYNTAX              	INTEGER { len0_133(0), len133_266(1), len266_399(2), len399_533(3),
					  len355_655(4) }
        MAX-ACCESS      	read-only
        STATUS          	current
        DESCRIPTION     	"Display TDM port25 cable configuration"
        ::= { tdm_config25 2 }

tdm_counter25             	OBJECT IDENTIFIER ::= { tdm25 2  }

tdmPort25CounterCrcBlockErrors  	OBJECT-TYPE
    	SYNTAX              	Counter32
        MAX-ACCESS      	read-only
        STATUS          	current
        DESCRIPTION     	"Display TDM port25 Crc Block error Counter"
        ::= { tdm_counter25 1 }

tdmPort25CounterExCrcErrors      OBJECT-TYPE
    	SYNTAX              	Counter32
        MAX-ACCESS      	read-only
        STATUS          	current
        DESCRIPTION     	"Display TDM port25 excessive CRC block Counter"
        ::= { tdm_counter25 2 }

tdmPort25CounterFBAErrors      	OBJECT-TYPE
    	SYNTAX              	Counter32
        MAX-ACCESS      	read-only
        STATUS          	current
        DESCRIPTION     	"Display TDM port25 FBA Errors Counter"
        ::= { tdm_counter25 3 }

tdmPort25CounterFEBErrors      	OBJECT-TYPE
    	SYNTAX              	Counter32
        MAX-ACCESS      	read-only
        STATUS          	current
        DESCRIPTION     	"Display TDM port25 FEB Errors Counter"
        ::= { tdm_counter25 4 }

tdmPort25CounterLCViolations    	OBJECT-TYPE
    	SYNTAX              	Counter32
        MAX-ACCESS      	read-only
        STATUS          	current
        DESCRIPTION     	"Display TDM port25 LC Violations Counter"
        ::= { tdm_counter25 5 }

tdm_alarm25             	OBJECT IDENTIFIER ::= { tdm25 3  }

tdmPort25AlarmLOS      		OBJECT-TYPE
    	SYNTAX              	Counter32
        MAX-ACCESS      	read-only
        STATUS          	current
        DESCRIPTION     	"Display TDM port25 LOS alarm"
        ::= { tdm_alarm25 1 }

tdmPort25AlarmLOF      		OBJECT-TYPE
    	SYNTAX              	Counter32
        MAX-ACCESS      	read-only
        STATUS          	current
        DESCRIPTION     	"Display TDM port25 LOF alarm"
        ::= { tdm_alarm25 2 }

tdmPort25AlarmAIS      		OBJECT-TYPE
    	SYNTAX              	Counter32
        MAX-ACCESS      	read-only
        STATUS          	current
        DESCRIPTION     	"Display TDM port25 AIS alarm"
        ::= { tdm_alarm25 3 }

tdmPort25AlarmTS16AIS      	OBJECT-TYPE
    	SYNTAX              	Counter32
        MAX-ACCESS      	read-only
        STATUS          	current
        DESCRIPTION     	"Display TDM port25 TS16AIS alarm"
        ::= { tdm_alarm25 4 }

tdmPort25AlarmRAI      		OBJECT-TYPE
    	SYNTAX              	Counter32
        MAX-ACCESS      	read-only
        STATUS          	current
        DESCRIPTION     	"Display TDM port25 RAI alarm"
        ::= { tdm_alarm25 5 }

tdmPort25AlarmRMA      		OBJECT-TYPE
    	SYNTAX              	Counter32
        MAX-ACCESS      	read-only
        STATUS          	current
        DESCRIPTION     	"Display TDM port23 RMA alarm"
        ::= { tdm_alarm25 6 }

tdmPort25AlarmLCMFA      	OBJECT-TYPE
    	SYNTAX              	Counter32
        MAX-ACCESS      	read-only
        STATUS          	current
        DESCRIPTION     	"Display TDM port25 LCMFA alarm"
        ::= { tdm_alarm25 7 }

tdmPort25AlarmLSMFA      	OBJECT-TYPE
    	SYNTAX              	Counter32
        MAX-ACCESS      	read-only
        STATUS          	current
        DESCRIPTION     	"Display TDM port25 LSMFA alarm"
        ::= { tdm_alarm25 8 }
tdm26             		OBJECT IDENTIFIER ::= { tdm 26  }

tdm_config26             	OBJECT IDENTIFIER ::= { tdm26 1  }

tdmPort26Status      		OBJECT-TYPE
    	SYNTAX              	INTEGER { off(0), on(1) }
        MAX-ACCESS      	read-only
        STATUS          	current
        DESCRIPTION     	"Display TDM port26 status"
        ::= { tdm_config26 1 }

tdmPort26CableConfig      	OBJECT-TYPE
    	SYNTAX              	INTEGER { len0_133(0), len133_266(1), len266_399(2), len399_533(3),
					  len355_655(4) }
        MAX-ACCESS      	read-only
        STATUS          	current
        DESCRIPTION     	"Display TDM port26 cable configuration"
        ::= { tdm_config26 2 }

tdm_counter26             	OBJECT IDENTIFIER ::= { tdm26 2  }

tdmPort26CounterCrcBlockErrors  	OBJECT-TYPE
    	SYNTAX              	Counter32
        MAX-ACCESS      	read-only
        STATUS          	current
        DESCRIPTION     	"Display TDM port26 Crc Block error Counter"
        ::= { tdm_counter26 1 }

tdmPort26CounterExCrcErrors      OBJECT-TYPE
    	SYNTAX              	Counter32
        MAX-ACCESS      	read-only
        STATUS          	current
        DESCRIPTION     	"Display TDM port26 excessive CRC block Counter"
        ::= { tdm_counter26 2 }

tdmPort26CounterFBAErrors      	OBJECT-TYPE
    	SYNTAX              	Counter32
        MAX-ACCESS      	read-only
        STATUS          	current
        DESCRIPTION     	"Display TDM port26 FBA Errors Counter"
        ::= { tdm_counter26 3 }

tdmPort26CounterFEBErrors      	OBJECT-TYPE
    	SYNTAX              	Counter32
        MAX-ACCESS      	read-only
        STATUS          	current
        DESCRIPTION     	"Display TDM port26 FEB Errors Counter"
        ::= { tdm_counter26 4 }

tdmPort26CounterLCViolations    	OBJECT-TYPE
    	SYNTAX              	Counter32
        MAX-ACCESS      	read-only
        STATUS          	current
        DESCRIPTION     	"Display TDM port26 LC Violations Counter"
        ::= { tdm_counter26 5 }

tdm_alarm26             	OBJECT IDENTIFIER ::= { tdm26 3  }

tdmPort26AlarmLOS      		OBJECT-TYPE
    	SYNTAX              	Counter32
        MAX-ACCESS      	read-only
        STATUS          	current
        DESCRIPTION     	"Display TDM port26 LOS alarm"
        ::= { tdm_alarm26 1 }

tdmPort26AlarmLOF      		OBJECT-TYPE
    	SYNTAX              	Counter32
        MAX-ACCESS      	read-only
        STATUS          	current
        DESCRIPTION     	"Display TDM port26 LOF alarm"
        ::= { tdm_alarm26 2 }

tdmPort26AlarmAIS      		OBJECT-TYPE
    	SYNTAX              	Counter32
        MAX-ACCESS      	read-only
        STATUS          	current
        DESCRIPTION     	"Display TDM port26 AIS alarm"
        ::= { tdm_alarm26 3 }

tdmPort26AlarmTS16AIS      	OBJECT-TYPE
    	SYNTAX              	Counter32
        MAX-ACCESS      	read-only
        STATUS          	current
        DESCRIPTION     	"Display TDM port26 TS16AIS alarm"
        ::= { tdm_alarm26 4 }

tdmPort26AlarmRAI      		OBJECT-TYPE
    	SYNTAX              	Counter32
        MAX-ACCESS      	read-only
        STATUS          	current
        DESCRIPTION     	"Display TDM port26 RAI alarm"
        ::= { tdm_alarm26 5 }

tdmPort26AlarmRMA      		OBJECT-TYPE
    	SYNTAX              	Counter32
        MAX-ACCESS      	read-only
        STATUS          	current
        DESCRIPTION     	"Display TDM port26 RMA alarm"
        ::= { tdm_alarm26 6 }

tdmPort26AlarmLCMFA      	OBJECT-TYPE
    	SYNTAX              	Counter32
        MAX-ACCESS      	read-only
        STATUS          	current
        DESCRIPTION     	"Display TDM port26 LCMFA alarm"
        ::= { tdm_alarm26 7 }

tdmPort26AlarmLSMFA      	OBJECT-TYPE
    	SYNTAX              	Counter32
        MAX-ACCESS      	read-only
        STATUS          	current
        DESCRIPTION     	"Display TDM port26 LSMFA alarm"
        ::= { tdm_alarm26 8 }

tdm27             		OBJECT IDENTIFIER ::= { tdm 27  }

tdm_config27             	OBJECT IDENTIFIER ::= { tdm27 1  }

tdmPort27Status      		OBJECT-TYPE
    	SYNTAX              	INTEGER { off(0), on(1) }
        MAX-ACCESS      	read-only
        STATUS          	current
        DESCRIPTION     	"Display TDM port27 status"
        ::= { tdm_config27 1 }

tdmPort27CableConfig      	OBJECT-TYPE
    	SYNTAX              	INTEGER { len0_133(0), len133_266(1), len266_399(2), len399_533(3),
					  len355_655(4) }
        MAX-ACCESS      	read-only
        STATUS          	current
        DESCRIPTION     	"Display TDM port27 cable configuration"
        ::= { tdm_config27 2 }

tdm_counter27             	OBJECT IDENTIFIER ::= { tdm27 2  }

tdmPort27CounterCrcBlockErrors  	OBJECT-TYPE
    	SYNTAX              	Counter32
        MAX-ACCESS      	read-only
        STATUS          	current
        DESCRIPTION     	"Display TDM port27 Crc Block error Counter"
        ::= { tdm_counter27 1 }

tdmPort27CounterExCrcErrors      OBJECT-TYPE
    	SYNTAX              	Counter32
        MAX-ACCESS      	read-only
        STATUS          	current
        DESCRIPTION     	"Display TDM port27 excessive CRC block Counter"
        ::= { tdm_counter27 2 }

tdmPort27CounterFBAErrors      	OBJECT-TYPE
    	SYNTAX              	Counter32
        MAX-ACCESS      	read-only
        STATUS          	current
        DESCRIPTION     	"Display TDM port27 FBA Errors Counter"
        ::= { tdm_counter27 3 }

tdmPort27CounterFEBErrors      	OBJECT-TYPE
    	SYNTAX              	Counter32
        MAX-ACCESS      	read-only
        STATUS          	current
        DESCRIPTION     	"Display TDM port27 FEB Errors Counter"
        ::= { tdm_counter27 4 }

tdmPort27CounterLCViolations    	OBJECT-TYPE
    	SYNTAX              	Counter32
        MAX-ACCESS      	read-only
        STATUS          	current
        DESCRIPTION     	"Display TDM port27 LC Violations Counter"
        ::= { tdm_counter27 5 }

tdm_alarm27             	OBJECT IDENTIFIER ::= { tdm27 3  }

tdmPort27AlarmLOS      		OBJECT-TYPE
    	SYNTAX              	Counter32
        MAX-ACCESS      	read-only
        STATUS          	current
        DESCRIPTION     	"Display TDM port27 LOS alarm"
        ::= { tdm_alarm27 1 }

tdmPort27AlarmLOF      		OBJECT-TYPE
    	SYNTAX              	Counter32
        MAX-ACCESS      	read-only
        STATUS          	current
        DESCRIPTION     	"Display TDM port27 LOF alarm"
        ::= { tdm_alarm27 2 }

tdmPort27AlarmAIS      		OBJECT-TYPE
    	SYNTAX              	Counter32
        MAX-ACCESS      	read-only
        STATUS          	current
        DESCRIPTION     	"Display TDM port27 AIS alarm"
        ::= { tdm_alarm27 3 }

tdmPort27AlarmTS16AIS      	OBJECT-TYPE
    	SYNTAX              	Counter32
        MAX-ACCESS      	read-only
        STATUS          	current
        DESCRIPTION     	"Display TDM port27 TS16AIS alarm"
        ::= { tdm_alarm27 4 }

tdmPort27AlarmRAI      		OBJECT-TYPE
    	SYNTAX              	Counter32
        MAX-ACCESS      	read-only
        STATUS          	current
        DESCRIPTION     	"Display TDM port27 RAI alarm"
        ::= { tdm_alarm27 5 }

tdmPort27AlarmRMA      		OBJECT-TYPE
    	SYNTAX              	Counter32
        MAX-ACCESS      	read-only
        STATUS          	current
        DESCRIPTION     	"Display TDM port27 RMA alarm"
        ::= { tdm_alarm27 6 }

tdmPort27AlarmLCMFA      	OBJECT-TYPE
    	SYNTAX              	Counter32
        MAX-ACCESS      	read-only
        STATUS          	current
        DESCRIPTION     	"Display TDM port27 LCMFA alarm"
        ::= { tdm_alarm27 7 }

tdmPort27AlarmLSMFA      	OBJECT-TYPE
    	SYNTAX              	Counter32
        MAX-ACCESS      	read-only
        STATUS          	current
        DESCRIPTION     	"Display TDM port27 LSMFA alarm"
        ::= { tdm_alarm27 8 }
tdm28             		OBJECT IDENTIFIER ::= { tdm 28  }

tdm_config28             	OBJECT IDENTIFIER ::= { tdm28 1  }

tdmPort28Status      		OBJECT-TYPE
    	SYNTAX              	INTEGER { off(0), on(1) }
        MAX-ACCESS      	read-only
        STATUS          	current
        DESCRIPTION     	"Display TDM port28 status"
        ::= { tdm_config28 1 }

tdmPort28CableConfig      	OBJECT-TYPE
    	SYNTAX              	INTEGER { len0_133(0), len133_266(1), len266_399(2), len399_533(3),
					  len355_655(4) }
        MAX-ACCESS      	read-only
        STATUS          	current
        DESCRIPTION     	"Display TDM port28 cable configuration"
        ::= { tdm_config28 2 }

tdm_counter28             	OBJECT IDENTIFIER ::= { tdm28 2  }

tdmPort28CounterCrcBlockErrors  	OBJECT-TYPE
    	SYNTAX              	Counter32
        MAX-ACCESS      	read-only
        STATUS          	current
        DESCRIPTION     	"Display TDM port28 Crc Block error Counter"
        ::= { tdm_counter28 1 }

tdmPort28CounterExCrcErrors      OBJECT-TYPE
    	SYNTAX              	Counter32
        MAX-ACCESS      	read-only
        STATUS          	current
        DESCRIPTION     	"Display TDM port28 excessive CRC block Counter"
        ::= { tdm_counter28 2 }

tdmPort28CounterFBAErrors      	OBJECT-TYPE
    	SYNTAX              	Counter32
        MAX-ACCESS      	read-only
        STATUS          	current
        DESCRIPTION     	"Display TDM port28 FBA Errors Counter"
        ::= { tdm_counter28 3 }

tdmPort28CounterFEBErrors      	OBJECT-TYPE
    	SYNTAX              	Counter32
        MAX-ACCESS      	read-only
        STATUS          	current
        DESCRIPTION     	"Display TDM port28 FEB Errors Counter"
        ::= { tdm_counter28 4 }

tdmPort28CounterLCViolations    	OBJECT-TYPE
    	SYNTAX              	Counter32
        MAX-ACCESS      	read-only
        STATUS          	current
        DESCRIPTION     	"Display TDM port28 LC Violations Counter"
        ::= { tdm_counter28 5 }

tdm_alarm28             	OBJECT IDENTIFIER ::= { tdm28 3  }

tdmPort28AlarmLOS      		OBJECT-TYPE
    	SYNTAX              	Counter32
        MAX-ACCESS      	read-only
        STATUS          	current
        DESCRIPTION     	"Display TDM port28 LOS alarm"
        ::= { tdm_alarm28 1 }

tdmPort28AlarmLOF      		OBJECT-TYPE
    	SYNTAX              	Counter32
        MAX-ACCESS      	read-only
        STATUS          	current
        DESCRIPTION     	"Display TDM port28 LOF alarm"
        ::= { tdm_alarm28 2 }

tdmPort28AlarmAIS      		OBJECT-TYPE
    	SYNTAX              	Counter32
        MAX-ACCESS      	read-only
        STATUS          	current
        DESCRIPTION     	"Display TDM port28 AIS alarm"
        ::= { tdm_alarm28 3 }

tdmPort28AlarmTS16AIS      	OBJECT-TYPE
    	SYNTAX              	Counter32
        MAX-ACCESS      	read-only
        STATUS          	current
        DESCRIPTION     	"Display TDM port228 TS16AIS alarm"
        ::= { tdm_alarm28 4 }

tdmPort28AlarmRAI      		OBJECT-TYPE
    	SYNTAX              	Counter32
        MAX-ACCESS      	read-only
        STATUS          	current
        DESCRIPTION     	"Display TDM port28 RAI alarm"
        ::= { tdm_alarm28 5 }

tdmPort28AlarmRMA      		OBJECT-TYPE
    	SYNTAX              	Counter32
        MAX-ACCESS      	read-only
        STATUS          	current
        DESCRIPTION     	"Display TDM port28 RMA alarm"
        ::= { tdm_alarm28 6 }

tdmPort28AlarmLCMFA      	OBJECT-TYPE
    	SYNTAX              	Counter32
        MAX-ACCESS      	read-only
        STATUS          	current
        DESCRIPTION     	"Display TDM port28 LCMFA alarm"
        ::= { tdm_alarm28 7 }

tdmPort28AlarmLSMFA      	OBJECT-TYPE
    	SYNTAX              	Counter32
        MAX-ACCESS      	read-only
        STATUS          	current
        DESCRIPTION     	"Display TDM port28 LSMFA alarm"
        ::= { tdm_alarm28 8 }

tdm29             		OBJECT IDENTIFIER ::= { tdm 29  }

tdm_config29             	OBJECT IDENTIFIER ::= { tdm29 1  }

tdmPort29Status      		OBJECT-TYPE
    	SYNTAX              	INTEGER { off(0), on(1) }
        MAX-ACCESS      	read-only
        STATUS          	current
        DESCRIPTION     	"Display TDM port29 status"
        ::= { tdm_config29 1 }

tdmPort29CableConfig      	OBJECT-TYPE
    	SYNTAX              	INTEGER { len0_133(0), len133_266(1), len266_399(2), len399_533(3),
					  len355_655(4) }
        MAX-ACCESS      	read-only
        STATUS          	current
        DESCRIPTION     	"Display TDM port29 cable configuration"
        ::= { tdm_config29 2 }

tdm_counter29             	OBJECT IDENTIFIER ::= { tdm29 2  }

tdmPort29CounterCrcBlockErrors  	OBJECT-TYPE
    	SYNTAX              	Counter32
        MAX-ACCESS      	read-only
        STATUS          	current
        DESCRIPTION     	"Display TDM port29 Crc Block error Counter"
        ::= { tdm_counter29 1 }

tdmPort29CounterExCrcErrors      OBJECT-TYPE
    	SYNTAX              	Counter32
        MAX-ACCESS      	read-only
        STATUS          	current
        DESCRIPTION     	"Display TDM port29 excessive CRC block Counter"
        ::= { tdm_counter29 2 }

tdmPort29CounterFBAErrors      	OBJECT-TYPE
    	SYNTAX              	Counter32
        MAX-ACCESS      	read-only
        STATUS          	current
        DESCRIPTION     	"Display TDM port29 FBA Errors Counter"
        ::= { tdm_counter29 3 }

tdmPort29CounterFEBErrors      	OBJECT-TYPE
    	SYNTAX              	Counter32
        MAX-ACCESS      	read-only
        STATUS          	current
        DESCRIPTION     	"Display TDM port29 FEB Errors Counter"
        ::= { tdm_counter29 4 }

tdmPort29CounterLCViolations    	OBJECT-TYPE
    	SYNTAX              	Counter32
        MAX-ACCESS      	read-only
        STATUS          	current
        DESCRIPTION     	"Display TDM port29 LC Violations Counter"
        ::= { tdm_counter29 5 }

tdm_alarm29             	OBJECT IDENTIFIER ::= { tdm29 3  }

tdmPort29AlarmLOS      		OBJECT-TYPE
    	SYNTAX              	Counter32
        MAX-ACCESS      	read-only
        STATUS          	current
        DESCRIPTION     	"Display TDM port29 LOS alarm"
        ::= { tdm_alarm29 1 }

tdmPort29AlarmLOF      		OBJECT-TYPE
    	SYNTAX              	Counter32
        MAX-ACCESS      	read-only
        STATUS          	current
        DESCRIPTION     	"Display TDM port29 LOF alarm"
        ::= { tdm_alarm29 2 }

tdmPort29AlarmAIS      		OBJECT-TYPE
    	SYNTAX              	Counter32
        MAX-ACCESS      	read-only
        STATUS          	current
        DESCRIPTION     	"Display TDM port29 AIS alarm"
        ::= { tdm_alarm29 3 }

tdmPort29AlarmTS16AIS      	OBJECT-TYPE
    	SYNTAX              	Counter32
        MAX-ACCESS      	read-only
        STATUS          	current
        DESCRIPTION     	"Display TDM port29 TS16AIS alarm"
        ::= { tdm_alarm29 4 }

tdmPort29AlarmRAI      		OBJECT-TYPE
    	SYNTAX              	Counter32
        MAX-ACCESS      	read-only
        STATUS          	current
        DESCRIPTION     	"Display TDM port29 RAI alarm"
        ::= { tdm_alarm29 5 }

tdmPort29AlarmRMA      		OBJECT-TYPE
    	SYNTAX              	Counter32
        MAX-ACCESS      	read-only
        STATUS          	current
        DESCRIPTION     	"Display TDM port29 RMA alarm"
        ::= { tdm_alarm29 6 }

tdmPort29AlarmLCMFA      	OBJECT-TYPE
    	SYNTAX              	Counter32
        MAX-ACCESS      	read-only
        STATUS          	current
        DESCRIPTION     	"Display TDM port29 LCMFA alarm"
        ::= { tdm_alarm29 7 }

tdmPort29AlarmLSMFA      	OBJECT-TYPE
    	SYNTAX              	Counter32
        MAX-ACCESS      	read-only
        STATUS          	current
        DESCRIPTION     	"Display TDM port29 LSMFA alarm"
        ::= { tdm_alarm29 8 }

tdm30             		OBJECT IDENTIFIER ::= { tdm 30  }

tdm_config30             	OBJECT IDENTIFIER ::= { tdm30 1  }

tdmPort30Status      		OBJECT-TYPE
    	SYNTAX              	INTEGER { off(0), on(1) }
        MAX-ACCESS      	read-only
        STATUS          	current
        DESCRIPTION     	"Display TDM port30 status"
        ::= { tdm_config30 1 }

tdmPort30CableConfig      	OBJECT-TYPE
    	SYNTAX              	INTEGER { len0_133(0), len133_266(1), len266_399(2), len399_533(3),
					  len355_655(4) }
        MAX-ACCESS      	read-only
        STATUS          	current
        DESCRIPTION     	"Display TDM port30 cable configuration"
        ::= { tdm_config30 2 }

tdm_counter30             	OBJECT IDENTIFIER ::= { tdm30 2  }

tdmPort30CounterCrcBlockErrors  	OBJECT-TYPE
    	SYNTAX              	Counter32
        MAX-ACCESS      	read-only
        STATUS          	current
        DESCRIPTION     	"Display TDM port30 Crc Block error Counter"
        ::= { tdm_counter30 1 }

tdmPort30CounterExCrcErrors      OBJECT-TYPE
    	SYNTAX              	Counter32
        MAX-ACCESS      	read-only
        STATUS          	current
        DESCRIPTION     	"Display TDM port30 excessive CRC block Counter"
        ::= { tdm_counter30 2 }

tdmPort30CounterFBAErrors      	OBJECT-TYPE
    	SYNTAX              	Counter32
        MAX-ACCESS      	read-only
        STATUS          	current
        DESCRIPTION     	"Display TDM port30 FBA Errors Counter"
        ::= { tdm_counter30 3 }

tdmPort30CounterFEBErrors      	OBJECT-TYPE
    	SYNTAX              	Counter32
        MAX-ACCESS      	read-only
        STATUS          	current
        DESCRIPTION     	"Display TDM port30 FEB Errors Counter"
        ::= { tdm_counter30 4 }

tdmPort30CounterLCViolations    	OBJECT-TYPE
    	SYNTAX              	Counter32
        MAX-ACCESS      	read-only
        STATUS          	current
        DESCRIPTION     	"Display TDM port30 LC Violations Counter"
        ::= { tdm_counter30 5 }

tdm_alarm30             	OBJECT IDENTIFIER ::= { tdm30 3  }

tdmPort30AlarmLOS      		OBJECT-TYPE
    	SYNTAX              	Counter32
        MAX-ACCESS      	read-only
        STATUS          	current
        DESCRIPTION     	"Display TDM port30 LOS alarm"
        ::= { tdm_alarm30 1 }

tdmPort30AlarmLOF      		OBJECT-TYPE
    	SYNTAX              	Counter32
        MAX-ACCESS      	read-only
        STATUS          	current
        DESCRIPTION     	"Display TDM port30 LOF alarm"
        ::= { tdm_alarm30 2 }

tdmPort30AlarmAIS      		OBJECT-TYPE
    	SYNTAX              	Counter32
        MAX-ACCESS      	read-only
        STATUS          	current
        DESCRIPTION     	"Display TDM port30 AIS alarm"
        ::= { tdm_alarm30 3 }

tdmPort30AlarmTS16AIS      	OBJECT-TYPE
    	SYNTAX              	Counter32
        MAX-ACCESS      	read-only
        STATUS          	current
        DESCRIPTION     	"Display TDM port30 TS16AIS alarm"
        ::= { tdm_alarm30 4 }

tdmPort30AlarmRAI      		OBJECT-TYPE
    	SYNTAX              	Counter32
        MAX-ACCESS      	read-only
        STATUS          	current
        DESCRIPTION     	"Display TDM port30 RAI alarm"
        ::= { tdm_alarm30 5 }

tdmPort30AlarmRMA      		OBJECT-TYPE
    	SYNTAX              	Counter32
        MAX-ACCESS      	read-only
        STATUS          	current
        DESCRIPTION     	"Display TDM port30 RMA alarm"
        ::= { tdm_alarm30 6 }

tdmPort30AlarmLCMFA      	OBJECT-TYPE
    	SYNTAX              	Counter32
        MAX-ACCESS      	read-only
        STATUS          	current
        DESCRIPTION     	"Display TDM port30 LCMFA alarm"
        ::= { tdm_alarm30 7 }

tdmPort30AlarmLSMFA      	OBJECT-TYPE
    	SYNTAX              	Counter32
        MAX-ACCESS      	read-only
        STATUS          	current
        DESCRIPTION     	"Display TDM port30 LSMFA alarm"
        ::= { tdm_alarm30 8 }

tdm31             		OBJECT IDENTIFIER ::= { tdm 31  }

tdm_config31             	OBJECT IDENTIFIER ::= { tdm31 1  }

tdmPort31Status      		OBJECT-TYPE
    	SYNTAX              	INTEGER { off(0), on(1) }
        MAX-ACCESS      	read-only
        STATUS          	current
        DESCRIPTION     	"Display TDM port31 status"
        ::= { tdm_config31 1 }

tdmPort31CableConfig      	OBJECT-TYPE
    	SYNTAX              	INTEGER { len0_133(0), len133_266(1), len266_399(2), len399_533(3),
					  len355_655(4) }
        MAX-ACCESS      	read-only
        STATUS          	current
        DESCRIPTION     	"Display TDM port31 cable configuration"
        ::= { tdm_config31 2 }

tdm_counter31             	OBJECT IDENTIFIER ::= { tdm31 2  }

tdmPort31CounterCrcBlockErrors  	OBJECT-TYPE
    	SYNTAX              	Counter32
        MAX-ACCESS      	read-only
        STATUS          	current
        DESCRIPTION     	"Display TDM port31 Crc Block error Counter"
        ::= { tdm_counter31 1 }

tdmPort31CounterExCrcErrors      OBJECT-TYPE
    	SYNTAX              	Counter32
        MAX-ACCESS      	read-only
        STATUS          	current
        DESCRIPTION     	"Display TDM port31 excessive CRC block Counter"
        ::= { tdm_counter31 2 }

tdmPort31CounterFBAErrors      	OBJECT-TYPE
    	SYNTAX              	Counter32
        MAX-ACCESS      	read-only
        STATUS          	current
        DESCRIPTION     	"Display TDM port31 FBA Errors Counter"
        ::= { tdm_counter31 3 }

tdmPort31CounterFEBErrors      	OBJECT-TYPE
    	SYNTAX              	Counter32
        MAX-ACCESS      	read-only
        STATUS          	current
        DESCRIPTION     	"Display TDM port31 FEB Errors Counter"
        ::= { tdm_counter31 4 }

tdmPort31CounterLCViolations    	OBJECT-TYPE
    	SYNTAX              	Counter32
        MAX-ACCESS      	read-only
        STATUS          	current
        DESCRIPTION     	"Display TDM port31 LC Violations Counter"
        ::= { tdm_counter31 5 }

tdm_alarm31             	OBJECT IDENTIFIER ::= { tdm31 3  }

tdmPort31AlarmLOS      		OBJECT-TYPE
    	SYNTAX              	Counter32
        MAX-ACCESS      	read-only
        STATUS          	current
        DESCRIPTION     	"Display TDM port31 LOS alarm"
        ::= { tdm_alarm31 1 }

tdmPort31AlarmLOF      		OBJECT-TYPE
    	SYNTAX              	Counter32
        MAX-ACCESS      	read-only
        STATUS          	current
        DESCRIPTION     	"Display TDM port31 LOF alarm"
        ::= { tdm_alarm31 2 }

tdmPort31AlarmAIS      		OBJECT-TYPE
    	SYNTAX              	Counter32
        MAX-ACCESS      	read-only
        STATUS          	current
        DESCRIPTION     	"Display TDM port31 AIS alarm"
        ::= { tdm_alarm31 3 }

tdmPort31AlarmTS16AIS      	OBJECT-TYPE
    	SYNTAX              	Counter32
        MAX-ACCESS      	read-only
        STATUS          	current
        DESCRIPTION     	"Display TDM port31 TS16AIS alarm"
        ::= { tdm_alarm31 4 }

tdmPort31AlarmRAI      		OBJECT-TYPE
    	SYNTAX              	Counter32
        MAX-ACCESS      	read-only
        STATUS          	current
        DESCRIPTION     	"Display TDM port31 RAI alarm"
        ::= { tdm_alarm31 5 }

tdmPort31AlarmRMA      		OBJECT-TYPE
    	SYNTAX              	Counter32
        MAX-ACCESS      	read-only
        STATUS          	current
        DESCRIPTION     	"Display TDM port31 RMA alarm"
        ::= { tdm_alarm31 6 }

tdmPort31AlarmLCMFA      	OBJECT-TYPE
    	SYNTAX              	Counter32
        MAX-ACCESS      	read-only
        STATUS          	current
        DESCRIPTION     	"Display TDM port31 LCMFA alarm"
        ::= { tdm_alarm31 7 }

tdmPort31AlarmLSMFA      	OBJECT-TYPE
    	SYNTAX              	Counter32
        MAX-ACCESS      	read-only
        STATUS          	current
        DESCRIPTION     	"Display TDM port31 LSMFA alarm"
        ::= { tdm_alarm31 8 }
tdm32             		OBJECT IDENTIFIER ::= { tdm 32  }

tdm_config32             	OBJECT IDENTIFIER ::= { tdm32 1  }

tdmPort32Status      		OBJECT-TYPE
    	SYNTAX              	INTEGER { off(0), on(1) }
        MAX-ACCESS      	read-only
        STATUS          	current
        DESCRIPTION     	"Display TDM port32 status"
        ::= { tdm_config32 1 }

tdmPort32CableConfig      	OBJECT-TYPE
    	SYNTAX              	INTEGER { len0_133(0), len133_266(1), len266_399(2), len399_533(3),
					  len355_655(4) }
        MAX-ACCESS      	read-only
        STATUS          	current
        DESCRIPTION     	"Display TDM port32 cable configuration"
        ::= { tdm_config32 2 }

tdm_counter32             	OBJECT IDENTIFIER ::= { tdm32 2  }

tdmPort32CounterCrcBlockErrors  	OBJECT-TYPE
    	SYNTAX              	Counter32
        MAX-ACCESS      	read-only
        STATUS          	current
        DESCRIPTION     	"Display TDM port32 Crc Block error Counter"
        ::= { tdm_counter32 1 }

tdmPort32CounterExCrcErrors      OBJECT-TYPE
    	SYNTAX              	Counter32
        MAX-ACCESS      	read-only
        STATUS          	current
        DESCRIPTION     	"Display TDM port32 excessive CRC block Counter"
        ::= { tdm_counter32 2 }

tdmPort32CounterFBAErrors      	OBJECT-TYPE
    	SYNTAX              	Counter32
        MAX-ACCESS      	read-only
        STATUS          	current
        DESCRIPTION     	"Display TDM port32 FBA Errors Counter"
        ::= { tdm_counter32 3 }

tdmPort32CounterFEBErrors      	OBJECT-TYPE
    	SYNTAX              	Counter32
        MAX-ACCESS      	read-only
        STATUS          	current
        DESCRIPTION     	"Display TDM port32 FEB Errors Counter"
        ::= { tdm_counter32 4 }

tdmPort32CounterLCViolations    	OBJECT-TYPE
    	SYNTAX              	Counter32
        MAX-ACCESS      	read-only
        STATUS          	current
        DESCRIPTION     	"Display TDM port32 LC Violations Counter"
        ::= { tdm_counter32 5 }

tdm_alarm32             	OBJECT IDENTIFIER ::= { tdm32 3  }

tdmPort32AlarmLOS      		OBJECT-TYPE
    	SYNTAX              	Counter32
        MAX-ACCESS      	read-only
        STATUS          	current
        DESCRIPTION     	"Display TDM port32 LOS alarm"
        ::= { tdm_alarm32 1 }

tdmPort32AlarmLOF      		OBJECT-TYPE
    	SYNTAX              	Counter32
        MAX-ACCESS      	read-only
        STATUS          	current
        DESCRIPTION     	"Display TDM port32 LOF alarm"
        ::= { tdm_alarm32 2 }

tdmPort32AlarmAIS      		OBJECT-TYPE
    	SYNTAX              	Counter32
        MAX-ACCESS      	read-only
        STATUS          	current
        DESCRIPTION     	"Display TDM port32 AIS alarm"
        ::= { tdm_alarm32 3 }

tdmPort32AlarmTS16AIS      	OBJECT-TYPE
    	SYNTAX              	Counter32
        MAX-ACCESS      	read-only
        STATUS          	current
        DESCRIPTION     	"Display TDM port32 TS16AIS alarm"
        ::= { tdm_alarm32 4 }

tdmPort32AlarmRAI      		OBJECT-TYPE
    	SYNTAX              	Counter32
        MAX-ACCESS      	read-only
        STATUS          	current
        DESCRIPTION     	"Display TDM port32 RAI alarm"
        ::= { tdm_alarm32 5 }

tdmPort32AlarmRMA      		OBJECT-TYPE
    	SYNTAX              	Counter32
        MAX-ACCESS      	read-only
        STATUS          	current
        DESCRIPTION     	"Display TDM port32 RMA alarm"
        ::= { tdm_alarm32 6 }

tdmPort32AlarmLCMFA      	OBJECT-TYPE
    	SYNTAX              	Counter32
        MAX-ACCESS      	read-only
        STATUS          	current
        DESCRIPTION     	"Display TDM port32 LCMFA alarm"
        ::= { tdm_alarm32 7 }

tdmPort32AlarmLSMFA      	OBJECT-TYPE
    	SYNTAX              	Counter32
        MAX-ACCESS      	read-only
        STATUS          	current
        DESCRIPTION     	"Display TDM port32 LSMFA alarm"
        ::= { tdm_alarm32 8 }


trapStartUp             	NOTIFICATION-TYPE
        STATUS          	current
        DESCRIPTION     	"send traps when the system starts up"
        ::= { trangotrap 1 }

trapReboot              	NOTIFICATION-TYPE
        STATUS          	current
        DESCRIPTION     	"send traps when the system reboots"
        ::= { trangotrap 2 }

traprps         		OBJECT IDENTIFIER ::= { trangotrap 3 }

trapRPSPortDown   		NOTIFICATION-TYPE
        STATUS          	current
        DESCRIPTION     	"send traps when the rapid port shutdown occurs"
        ::= { traprps 1 }

trapRPSPortUp   		NOTIFICATION-TYPE
        STATUS          	current
        DESCRIPTION     	"send traps when the rapid port up occurs"
        ::= { traprps 2 }

trapProtectionModeSwitch        NOTIFICATION-TYPE
        STATUS          	current
        DESCRIPTION     	"send traps when protection switch occurs"
        ::= { trangotrap 4 }

trapeth         		OBJECT IDENTIFIER ::= { trangotrap 5 }

trapEth1StatusUpdate    	NOTIFICATION-TYPE
        STATUS          	current
        DESCRIPTION     	"send traps when ethernet port 1 status changed"
        ::= { trapeth 1 }

trapEth2StatusUpdate    	NOTIFICATION-TYPE
        STATUS          	current
        DESCRIPTION     	"send traps when ethernet port 2 status changed"
        ::= { trapeth 2 }

trapEth3StatusUpdate    	NOTIFICATION-TYPE
        STATUS          	current
        DESCRIPTION     	"send traps when ethernet port 3 status changed"
        ::= { trapeth 3 }

trapEth4StatusUpdate    	NOTIFICATION-TYPE
        STATUS          	current
        DESCRIPTION     	"send traps when ethernet port 4 status changed"
        ::= { trapeth 4 }

trapEth5StatusUpdate    	NOTIFICATION-TYPE
        STATUS          	current
        DESCRIPTION     	"send traps when ethernet port 5 status changed"
        ::= { trapeth 5 }

trapEth6StatusUpdate    	NOTIFICATION-TYPE
        STATUS          	current
        DESCRIPTION     	"send traps when ethernet port 6 status changed"
        ::= { trapeth 6 }

link         			OBJECT IDENTIFIER ::= { trangotrap 6 }

trapLinkLock1          		NOTIFICATION-TYPE
        STATUS          	current
        DESCRIPTION     	"send traps when the system lose modem lock"
        ::= { link 1 }

trapLinkLock2           	NOTIFICATION-TYPE
        STATUS          	current
        DESCRIPTION     	"send traps when the system lose modem lock"
        ::= { link 2 }

trapAcmTxProfileUpdate1        	NOTIFICATION-TYPE
        STATUS          	current
        DESCRIPTION     	"send traps when the modem 1 change tx profile"
        ::= { link 3 }

trapAcmTxProfileUpdate2        	NOTIFICATION-TYPE
        STATUS          	current
        DESCRIPTION     	"send traps when the modem 2 change tx profile"
        ::= { link 4 }

trapAcmRxProfileUpdate1        	NOTIFICATION-TYPE
        STATUS          	current
        DESCRIPTION     	"send traps when the modem 1 change rx profile"
        ::= { link 5 }

trapAcmRxProfileUpdate2        	NOTIFICATION-TYPE
        STATUS          	current
        DESCRIPTION     	"send traps when the modem 2 change rx profile"
        ::= { link 6 }


END
