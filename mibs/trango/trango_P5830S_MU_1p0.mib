-- Private MIB definition for Trango Systems
-- Access 58xx series wireless broadband Master Unit P5830S
-- Version: 1.0
-- Date: June 10, 2003
--
-- Copyright 2003: Trango Systems, Inc. All Rights Reserved.
-- Trango Systems, Inc. 15070 Avenue Of Science Suite 200 San Diego CA 92128 USA.
--
-- Reproduction of this document is authorized on condition that the
-- foregoing copyright notice is included.

TRANGOP5830S-MU-MIB DEFINITIONS ::= BEGIN

-- MIB module for enterprise trango wireless broadband
-- of management of P5830S master unit

    	IMPORTS
            enterprises, IpAddress, Counter
        	FROM RFC1155-SMI
        OBJECT-TYPE
            FROM RFC-1212;

        -- textual conventions

        DisplayString ::=
            OCTET STRING
        -- This data type is used to model textual information taken
        -- from the NVT ASCII character set.  By convention, objects
        -- with this syntax are declared as having
        --
        -- SIZE (0..255)


	-- trango wireless broadband MIB registration id assigned to 5454.
        -- customer needs to change this value based on their OEM value.
	trango	    	OBJECT IDENTIFIER ::= { enterprises 5454 }
	tbw	    	OBJECT IDENTIFIER ::= { trango 1 }
	p5830smu    OBJECT IDENTIFIER ::= { tbw 22 }

	-- modules branched from p5830smu
	musys       OBJECT IDENTIFIER ::= { p5830smu 1 }
	murf        OBJECT IDENTIFIER ::= { p5830smu 2 }
	ru 	    OBJECT IDENTIFIER ::= { p5830smu 3 }
	trapconfig  OBJECT IDENTIFIER ::= { p5830smu 4 }
	mibinfo     OBJECT IDENTIFIER ::= { p5830smu 5 }
    
	muversion   OBJECT IDENTIFIER ::= { musys 1 }
	muswitches  OBJECT IDENTIFIER ::= { musys 8}
	mutraffic   OBJECT IDENTIFIER ::= { musys 9}
	muipconfig  OBJECT IDENTIFIER ::= { musys 13}
	murftable   OBJECT IDENTIFIER ::= { murf 4 }
	muism       OBJECT IDENTIFIER ::= { murf 5 }
	muunii      OBJECT IDENTIFIER ::= { murf 6 }

	-- MIB objects defined below

	-- master unit system objects
	muversionHW OBJECT-TYPE
    	    SYNTAX  OCTET STRING (SIZE(2))
            ACCESS  read-only
            STATUS  mandatory
            DESCRIPTION
	       	"Hardware version."
            ::= { muversion 1 }

	muversionFW OBJECT-TYPE
            SYNTAX  DisplayString (SIZE (0..80))
            ACCESS  read-only
            STATUS  mandatory
            DESCRIPTION
	       	"Main firmware version.
                 Format: <code version>H<hardware version>D<date>."
            ::= { muversion 2 }

	muversionFPGA OBJECT-TYPE
    	    SYNTAX  OCTET STRING (SIZE(4))
            ACCESS  read-only
            STATUS  mandatory
            DESCRIPTION
	       	"FPGA firmware version."
            ::= { muversion 3 }

	muversionFWChecksum OBJECT-TYPE
    	    SYNTAX  OCTET STRING (SIZE(4))
            ACCESS  read-only
            STATUS  mandatory
            DESCRIPTION
	       	"Master unit firmware checksum."
            ::= { muversion 4 }

	muversionFPGAChecksum OBJECT-TYPE
    	    SYNTAX  OCTET STRING (SIZE(4))
            ACCESS  read-only
            STATUS  mandatory
            DESCRIPTION
	       	"Master unit FPGA checksum."
            ::= { muversion 5 }

	musysDeviceId OBJECT-TYPE
	    SYNTAX  OCTET STRING (SIZE(6))
	    ACCESS  read-only
	    STATUS  mandatory
	    DESCRIPTION
	        "Master unit device Id. Each master unit in a cluster shall have unique ID."
	    ::= { musys 2 }

	musysDefOpMode OBJECT-TYPE
	    SYNTAX  INTEGER {
                        on(16),
                        off(0)
                    }
            ACCESS  read-write
	    STATUS  mandatory
	    DESCRIPTION
	        "The operation mode (on or off) the master unit is on after reboot/power cycle."
	    ::= { musys 3 }

	musysCurOpMode OBJECT-TYPE
	    SYNTAX  INTEGER {
                        on(16),
                        off(0)
                    }
	    ACCESS  read-only
	    STATUS  mandatory
	    DESCRIPTION
	        "Master unit's current operation mode."
	    ::= { musys 4 }
        
        musysActivateOpmode OBJECT-TYPE
            SYNTAX  INTEGER {
                        deactivated(0),
                        activated(1)
                    }
            ACCESS  read-write
            STATUS  mandatory
            DESCRIPTION
                "Engage master unit to on operation mode."
            DEFVAL { deactivated }
            ::= { musys 5 }

	musysReadCommStr OBJECT-TYPE
            SYNTAX  DisplayString (SIZE (0..32))
	    ACCESS  read-write
	    STATUS  mandatory
	    DESCRIPTION
		"SNMP agent read community string. It is used for authentication 		                 purpose."
 	    ::= { musys 6 }

	musysWriteCommStr OBJECT-TYPE
            SYNTAX  DisplayString (SIZE (0..32))
	    ACCESS  read-write
	    STATUS  mandatory
	    DESCRIPTION
	        "SNMP agent write community string. It is used for authentication                            purpose."
	    ::= { musys 7 }

	muswitchesBlockBroadcastMulticast OBJECT-TYPE
	    SYNTAX  INTEGER {
                        passed(0),
                        blocked(1)
                    }
	    ACCESS  read-write
	    STATUS  mandatory
	    DESCRIPTION
		"This switch enables or disables the blocking of Ethernet
                 control packet except ICMP and ARP to reduce the amount
                 of uneccessary overhead introduced to the wireless link."
	    ::= { muswitches 1 }

	muswitchesHTTPD OBJECT-TYPE
	    SYNTAX  INTEGER {
                        disabled(0),
                        enabled(1)
                    }
	    ACCESS  read-write
	    STATUS  mandatory
	    DESCRIPTION
		"When it is turned on, then the master unit is accessible
		 for configuring via web browser (e.g. IE or Nescape)."
	    ::= { muswitches 5 }

	muswitchesAutoPowerLevelRemoteUnit OBJECT-TYPE
	    SYNTAX  INTEGER {
                        disabled(0),
                        enabled(1)
                    }
	    ACCESS  read-write
	    STATUS  mandatory
	    DESCRIPTION
		"When it is turned on, then the master unit will
		 command the remote unit to do power leveling."
	    ::= { muswitches 7 }

	mutrafficEthInOctets OBJECT-TYPE
	    SYNTAX  Counter
	    ACCESS  read-only
	    STATUS  mandatory
	    DESCRIPTION
		"Number of payload octets received on Ethernet port."
            ::= { mutraffic 1 }

	mutrafficEthOutOctets OBJECT-TYPE
	    SYNTAX  Counter
	    ACCESS  read-only
	    STATUS  mandatory
	    DESCRIPTION
		"Number of payload octets transmitted on Ethernet port."
	    ::= { mutraffic 2 }

	mutrafficRfInOctets OBJECT-TYPE
	    SYNTAX  Counter
	    ACCESS  read-only
	    STATUS  mandatory
	    DESCRIPTION
		"Number of octets of remote's payload received from RF port."
	    ::= { mutraffic 3 }

	mutrafficRfOutOctets OBJECT-TYPE
	    SYNTAX  Counter
	    ACCESS  read-only
	    STATUS  mandatory
	    DESCRIPTION
		"Number of octets of remote's payload transmitted to RF port."
            ::= { mutraffic 4 }

        musysTemperature OBJECT-TYPE
            SYNTAX  INTEGER (-128..127)
            ACCESS  read-only
            STATUS  mandatory
            DESCRIPTION
                "Current master unit's temperature value (in Celsius)."
            ::= { musys 10 }

	musysUpdateFlashAndActivate OBJECT-TYPE
	    SYNTAX  INTEGER {
                        no(0),
                        yes(1)
                    }
	    ACCESS  read-write
	    STATUS  mandatory
	    DESCRIPTION
	        "Save system setting values to Flash and activate the settings."
            DEFVAL  {no}
	    ::= { musys 11 }

	musysReboot OBJECT-TYPE
	    SYNTAX  INTEGER {
                        deactivated(0),
                        activated(1)
                    }
	    ACCESS  read-write
	    STATUS  mandatory
	    DESCRIPTION
	        "Reboot the master unit."
            DEFVAL { deactivated }
	    ::= { musys 12 }

	muipconfigIpAddress OBJECT-TYPE
	    SYNTAX  IpAddress
	    ACCESS  read-write
	    STATUS  mandatory
	    DESCRIPTION
	        "New IP address. It will be saved to
                 non-volatile memory and activated in 5 secs."
	    ::= { muipconfig 1 }

    	muipconfigSubnet OBJECT-TYPE
	    SYNTAX  IpAddress
	    ACCESS  read-write
	    STATUS  mandatory
	    DESCRIPTION
		"New Subnet mask. It will be saved to
                 non-volatile memory and activated in 5 secs."
	    ::= { muipconfig 2 }

    	muipconfigDefaultGateway OBJECT-TYPE
	    SYNTAX  IpAddress
	    ACCESS  read-write
	    STATUS  mandatory
	    DESCRIPTION
		"New Default gateway. It will be saved to
                 non-volatile memory and activated in 5 secs."
	    ::= { muipconfig 3 }

	-- master unit rf objects
	murfRSSI OBJECT-TYPE
	    SYNTAX  INTEGER (-128..127)
	    ACCESS  read-only
	    STATUS  mandatory
	    DESCRIPTION
		"Remote unit RSSI (in dBm)."
	    ::= { murf 1 }

	murfActiveChannel OBJECT-TYPE
	    SYNTAX  INTEGER (1..30)
	    ACCESS  read-write
	    STATUS  mandatory
	    DESCRIPTION
		"It specifies the current channel number the master unit operates on."
	    ::= { murf 2 }

	murfActivePolarization OBJECT-TYPE
            SYNTAX  DisplayString (SIZE (1))
	    ACCESS  read-write
	    STATUS  mandatory
	    DESCRIPTION
	        "It specifies the current polarization the master unit operates on."
	    ::= { murf 3 }

	murftableChannel1 OBJECT-TYPE
	    SYNTAX  INTEGER (5260..5340 | 5736..5836)
	    ACCESS  read-write
	    STATUS  mandatory
	    DESCRIPTION
	        "RF channel 1 frequency (in MHz). It allows you to create your
                 own channel instead of the manufacturing defaults in the master unit.
                 Keep in mind that channel width is 20MHz, and the frequency
                 specified here is the center frequency.
                 Frequency (5260MHz - 5340MHz) is only applicable to M5830S/P5830S radio."
	    ::= { murftable 1 }

	murftableChannel2 OBJECT-TYPE
	    SYNTAX  INTEGER (5260..5340 | 5736..5836)
	    ACCESS  read-write
	    STATUS  mandatory
	    DESCRIPTION
	        "RF channel 2 frequency (in MHz). It allows you to create your
                 own channel instead of the manufacturing defaults in the master unit.
                 Keep in mind that channel width is 20MHz, and the frequency
                 specified here is the center frequency.
                 Frequency (5260MHz - 5340MHz) is only applicable to M5830S/P5830S radio."
	    ::= { murftable 2 }

	murftableChannel3 OBJECT-TYPE
	    SYNTAX  INTEGER (5260..5340 | 5736..5836)
            ACCESS  read-write
	    STATUS  mandatory
	    DESCRIPTION
		"RF channel 3 frequency (in MHz). It allows you to create your
                 own channel instead of the manufacturing defaults in the master unit.
                 Keep in mind that channel width is 20MHz, and the frequency
                 specified here is the center frequency.
                 Frequency (5260MHz - 5340MHz) is only applicable to M5830S/P5830S radio."
	    ::= { murftable 3 }

	murftableChannel4 OBJECT-TYPE
	    SYNTAX  INTEGER (5260..5340 | 5736..5836)
	    ACCESS  read-write
	    STATUS  mandatory
	    DESCRIPTION
		"RF channel 4 frequency (in MHz). It allows you to create your
                 own channel instead of the manufacturing defaults in the master unit.
                 Keep in mind that channel width is 20MHz, and the frequency
                 specified here is the center frequency.
                 Frequency (5260MHz - 5340MHz) is only applicable to M5830S/P5830S radio."
	    ::= { murftable 4 }

	murftableChannel5 OBJECT-TYPE
	    SYNTAX  INTEGER (5260..5340 | 5736..5836)
	    ACCESS  read-write
	    STATUS  mandatory
	    DESCRIPTION
	 	"RF channel 5 frequency (in MHz). It allows you to create your
                 own channel instead of the manufacturing defaults in the master unit.
                 Keep in mind that channel width is 20MHz, and the frequency
                 specified here is the center frequency.
                 Frequency (5260MHz - 5340MHz) is only applicable to M5830S/P5830S radio."
	    ::= { murftable 5 }

	murftableChannel6 OBJECT-TYPE
	    SYNTAX  INTEGER (5260..5340 | 5736..5836)
	    ACCESS  read-write
	    STATUS  mandatory
	    DESCRIPTION
	        "RF channel 6 frequency (in MHz). It allows you to create your
                 own channel instead of the manufacturing defaults in the master unit.
                 Keep in mind that channel width is 20MHz, and the frequency
                 specified here is the center frequency.
                 Frequency (5260MHz - 5340MHz) is only applicable to M5830S/P5830S radio."
	    ::= { murftable 6 }

	murftableChannel7 OBJECT-TYPE
	    SYNTAX  INTEGER (5260..5340 | 5736..5836)
	    ACCESS  read-write
	    STATUS  mandatory
	    DESCRIPTION
	        "RF channel 7 frequency (in MHz). It allows you to create your
                 own channel instead of the manufacturing defaults in the master unit.
                 Keep in mind that channel width is 20MHz, and the frequency
                 specified here is the center frequency.
                 Frequency (5260MHz - 5340MHz) is only applicable to M5830S/P5830S radio."
	    ::= { murftable 7 }

	murftableChannel8 OBJECT-TYPE
	    SYNTAX  INTEGER (5260..5340 | 5736..5836)
	    ACCESS  read-write
	    STATUS  mandatory
	    DESCRIPTION
		"RF channel 8 frequency (in MHz). It allows you to create your
                 own channel instead of the manufacturing defaults in the master unit.
                 Keep in mind that channel width is 20MHz, and the frequency
                 specified here is the center frequency.
                 Frequency (5260MHz - 5340MHz) is only applicable to M5830S/P5830S radio."
	    ::= { murftable 8 }

	murftableChannel9 OBJECT-TYPE
	    SYNTAX  INTEGER (5260..5340 | 5736..5836)
	    ACCESS  read-write
	    STATUS  mandatory
	    DESCRIPTION
	        "RF channel 9 frequency (in MHz). It allows you to create your
                 own channel instead of the manufacturing defaults in the master unit.
                 Keep in mind that channel width is 20MHz, and the frequency
                 specified here is the center frequency.
                 Frequency (5260MHz - 5340MHz) is only applicable to M5830S/P5830S radio."
	    ::= { murftable 9 }

	murftableChannel10 OBJECT-TYPE
	    SYNTAX  INTEGER (5260..5340 | 5736..5836)
	    ACCESS  read-write
	    STATUS  mandatory
	    DESCRIPTION
		"RF channel 10 frequency (in MHz). It allows you to create your
                 own channel instead of the manufacturing defaults in the master unit.
                 Keep in mind that channel width is 20MHz, and the frequency
                 specified here is the center frequency.
                 Frequency (5260MHz - 5340MHz) is only applicable to M5830S/P5830S radio."
	    ::= { murftable 10 }

	murftableChannel11 OBJECT-TYPE
            SYNTAX  INTEGER (5260..5340 | 5736..5836)
	    ACCESS  read-write
	    STATUS  mandatory
	    DESCRIPTION
		"RF channel 11 frequency (in MHz). It allows you to create your
                 own channel instead of the manufacturing defaults in the master unit.
                 Keep in mind that channel width is 20MHz, and the frequency
                 specified here is the center frequency.
                 Frequency (5260MHz - 5340MHz) is only applicable to M5830S/P5830S radio."
	    ::= { murftable 11 }

	murftableChannel12 OBJECT-TYPE
	    SYNTAX  INTEGER (5260..5340 | 5736..5836)
	    ACCESS  read-write
	    STATUS  mandatory
	    DESCRIPTION
	   	"RF channel 12 frequency (in MHz). It allows you to create your
                 own channel instead of the manufacturing defaults in the master unit.
                 Keep in mind that channel width is 20MHz, and the frequency
                 specified here is the center frequency.
                 Frequency (5260MHz - 5340MHz) is only applicable to M5830S/P5830S radio."
	    ::= { murftable 12 }

	murftableChannel13 OBJECT-TYPE
	    SYNTAX  INTEGER (5260..5340 | 5736..5836)
	    ACCESS  read-write
	    STATUS  mandatory
	    DESCRIPTION
		"RF channel 13 frequency (in MHz). It allows you to create your
                 own channel instead of the manufacturing defaults in the master unit.
                 Keep in mind that channel width is 20MHz, and the frequency
                 specified here is the center frequency.
                 Frequency (5260MHz - 5340MHz) is only applicable to M5830S/P5830S radio."
	    ::= { murftable 13 }

	murftableChannel14 OBJECT-TYPE
	    SYNTAX  INTEGER (5260..5340 | 5736..5836)
	    ACCESS  read-write
	    STATUS  mandatory
	    DESCRIPTION
		"RF channel 14 frequency (in MHz). It allows you to create your
                 own channel instead of the manufacturing defaults in the master unit.
                 Keep in mind that channel width is 20MHz, and the frequency
                 specified here is the center frequency.
                 Frequency (5260MHz - 5340MHz) is only applicable to M5830S/P5830S radio."
	    ::= { murftable 14 }

	murftableChannel15 OBJECT-TYPE
	    SYNTAX  INTEGER (5260..5340 | 5736..5836)
	    ACCESS  read-write
	    STATUS  mandatory
	    DESCRIPTION
		"RF channel 15 frequency (in MHz). It allows you to create your
                 own channel instead of the manufacturing defaults in the master unit.
                 Keep in mind that channel width is 20MHz, and the frequency
                 specified here is the center frequency.
                 Frequency (5260MHz - 5340MHz) is only applicable to M5830S/P5830S radio."
	    ::= { murftable 15 }

	murftableChannel16 OBJECT-TYPE
	    SYNTAX  INTEGER (5260..5340 | 5736..5836)
	    ACCESS  read-write
	    STATUS  mandatory
	    DESCRIPTION
		"RF channel 16 frequency (in MHz). It allows you to create your
                 own channel instead of the manufacturing defaults in the master unit.
                 Keep in mind that channel width is 20MHz, and the frequency
                 specified here is the center frequency.
                 Frequency (5260MHz - 5340MHz) is only applicable to M5830S/P5830S radio."
	    ::= { murftable 16 }

	murftableChannel17 OBJECT-TYPE
	    SYNTAX  INTEGER (5260..5340 | 5736..5836)
	    ACCESS  read-write
	    STATUS  mandatory
	    DESCRIPTION
		"RF channel 17 frequency (in MHz). It allows you to create your
                 own channel instead of the manufacturing defaults in the master unit.
                 Keep in mind that channel width is 20MHz, and the frequency
                 specified here is the center frequency.
                 Frequency (5260MHz - 5340MHz) is only applicable to M5830S/P5830S radio."
	    ::= { murftable 17 }

	murftableChannel18 OBJECT-TYPE
	    SYNTAX  INTEGER (5260..5340 | 5736..5836)
	    ACCESS  read-write
	    STATUS  mandatory
	    DESCRIPTION
		"RF channel 18 frequency (in MHz). It allows you to create your
                 own channel instead of the manufacturing defaults in the master unit.
                 Keep in mind that channel width is 20MHz, and the frequency
                 specified here is the center frequency.
                 Frequency (5260MHz - 5340MHz) is only applicable to M5830S/P5830S radio."
	    ::= { murftable 18 }

	murftableChannel19 OBJECT-TYPE
	    SYNTAX  INTEGER (5260..5340 | 5736..5836)
	    ACCESS  read-write
	    STATUS  mandatory
	    DESCRIPTION
		"RF channel 19 frequency (in MHz). It allows you to create your
                 own channel instead of the manufacturing defaults in the master unit.
                 Keep in mind that channel width is 20MHz, and the frequency
                 specified here is the center frequency.
                 Frequency (5260MHz - 5340MHz) is only applicable to M5830S/P5830S radio."
	    ::= { murftable 19 }

	murftableChannel20 OBJECT-TYPE
	    SYNTAX  INTEGER (5260..5340 | 5736..5836)
	    ACCESS  read-write
	    STATUS  mandatory
	    DESCRIPTION
		"RF channel 20 frequency (in MHz). It allows you to create your
                 own channel instead of the manufacturing defaults in the master unit.
                 Keep in mind that channel width is 20MHz, and the frequency
                 specified here is the center frequency.
                 Frequency (5260MHz - 5340MHz) is only applicable to M5830S/P5830S radio."
	    ::= { murftable 20 }

	murftableChannel21 OBJECT-TYPE
	    SYNTAX  INTEGER (5260..5340 | 5736..5836)
	    ACCESS  read-write
	    STATUS  mandatory
	    DESCRIPTION
		"RF channel 21 frequency (in MHz). It allows you to create your
                 own channel instead of the manufacturing defaults in the master unit.
                 Keep in mind that channel width is 20MHz, and the frequency
                 specified here is the center frequency.
                 Frequency (5260MHz - 5340MHz) is only applicable to M5830S/P5830S radio."
	    ::= { murftable 21 }

	murftableChannel22 OBJECT-TYPE
	    SYNTAX  INTEGER (5260..5340 | 5736..5836)
	    ACCESS  read-write
	    STATUS  mandatory
	    DESCRIPTION
		"RF channel 22 frequency (in MHz). It allows you to create your
                 own channel instead of the manufacturing defaults in the master unit.
                 Keep in mind that channel width is 20MHz, and the frequency
                 specified here is the center frequency.
                 Frequency (5260MHz - 5340MHz) is only applicable to M5830S/P5830S radio."
	    ::= { murftable 22 }

	murftableChannel23 OBJECT-TYPE
	    SYNTAX  INTEGER (5260..5340 | 5736..5836)
	    ACCESS  read-write
	    STATUS  mandatory
	    DESCRIPTION
	    	"RF channel 23 frequency (in MHz). It allows you to create your
                 own channel instead of the manufacturing defaults in the master unit.
                 Keep in mind that channel width is 20MHz, and the frequency
                 specified here is the center frequency.
                 Frequency (5260MHz - 5340MHz) is only applicable to M5830S/P5830S radio."
	    ::= { murftable 23 }

	murftableChannel24 OBJECT-TYPE
	    SYNTAX  INTEGER (5260..5340 | 5736..5836)
	    ACCESS  read-write
	    STATUS  mandatory
	    DESCRIPTION
		"RF channel 24 frequency (in MHz). It allows you to create your
                 own channel instead of the manufacturing defaults in the master unit.
                 Keep in mind that channel width is 20MHz, and the frequency
                 specified here is the center frequency.
                 Frequency (5260MHz - 5340MHz) is only applicable to M5830S/P5830S radio."
	    ::= { murftable 24 }

	murftableChannel25 OBJECT-TYPE
	    SYNTAX  INTEGER (5260..5340 | 5736..5836)
	    ACCESS  read-write
	    STATUS  mandatory
	    DESCRIPTION
		"RF channel 25 frequency (in MHz). It allows you to create your
                 own channel instead of the manufacturing defaults in the master unit.
                 Keep in mind that channel width is 20MHz, and the frequency
                 specified here is the center frequency.
                 Frequency (5260MHz - 5340MHz) is only applicable to M5830S/P5830S radio."
	    ::= { murftable 25 }

	murftableChannel26 OBJECT-TYPE
	    SYNTAX  INTEGER (5260..5340 | 5736..5836)
	    ACCESS  read-write
	    STATUS  mandatory
	    DESCRIPTION
		"RF channel 26 frequency (in MHz). It allows you to create your
                 own channel instead of the manufacturing defaults in the master unit.
                 Keep in mind that channel width is 20MHz, and the frequency
                 specified here is the center frequency.
                 Frequency (5260MHz - 5340MHz) is only applicable to M5830S/P5830S radio."
	    ::= { murftable 26 }

	murftableChannel27 OBJECT-TYPE
	    SYNTAX  INTEGER (5260..5340 | 5736..5836)
	    ACCESS  read-write
	    STATUS  mandatory
	    DESCRIPTION
		"RF channel 27 frequency (in MHz). It allows you to create your
                 own channel instead of the manufacturing defaults in the master unit.
                 Keep in mind that channel width is 20MHz, and the frequency
                 specified here is the center frequency.
                 Frequency (5260MHz - 5340MHz) is only applicable to M5830S/P5830S radio."
	    ::= { murftable 27 }

	murftableChannel28 OBJECT-TYPE
	    SYNTAX  INTEGER (5260..5340 | 5736..5836)
	    ACCESS  read-write
	    STATUS  mandatory
	    DESCRIPTION
		"RF channel 28 frequency (in MHz). It allows you to create your
                 own channel instead of the manufacturing defaults in the master unit.
                 Keep in mind that channel width is 20MHz, and the frequency
                 specified here is the center frequency.
                 Frequency (5260MHz - 5340MHz) is only applicable to M5830S/P5830S radio."
	    ::= { murftable 28 }

	murftableChannel29 OBJECT-TYPE
	    SYNTAX  INTEGER (5260..5340 | 5736..5836)
	    ACCESS  read-write
	    STATUS  mandatory
	    DESCRIPTION
		"RF channel 29 frequency (in MHz). It allows you to create your
                 own channel instead of the manufacturing defaults in the master unit.
                 Keep in mind that channel width is 20MHz, and the frequency
                 specified here is the center frequency.
                 Frequency (5260MHz - 5340MHz) is only applicable to M5830S/P5830S radio."
	    ::= { murftable 29 }

	murftableChannel30 OBJECT-TYPE
	    SYNTAX  INTEGER (5260..5340 | 5736..5836)
	    ACCESS  read-write
	    STATUS  mandatory
	    DESCRIPTION
		"RF channel 30 frequency (in MHz). It allows you to create your
                 own channel instead of the manufacturing defaults in the master unit.
                 Keep in mind that channel width is 20MHz, and the frequency
                 specified here is the center frequency.
                 Frequency (5260MHz - 5340MHz) is only applicable to M5830S/P5830S radio."
	    ::= { murftable 30 }

	muismTxPowerMax OBJECT-TYPE
            SYNTAX  INTEGER (-128..127)
	    ACCESS  read-only
	    STATUS  mandatory
	    DESCRIPTION
            	"The maximum ISM Tx power value can be set (in dBm)."
            ::= { muism 1 }
    
	muismTxPowerMin OBJECT-TYPE
	    SYNTAX  INTEGER (-128..127)
	    ACCESS  read-only
	    STATUS  mandatory
	    DESCRIPTION
            	"The minimum ISM Tx power value can be set (in dBm)."
            ::= { muism 2 }
    
	muismTxPower OBJECT-TYPE
	    SYNTAX  INTEGER (-128..127)
	    ACCESS  read-write
	    STATUS  mandatory
	    DESCRIPTION
		"ISM RF tx power (in dBm). It specifies the power output
                 of the radio, excluding the antenna gain. Check parameters
                 muismTxPowerMax and masterismTxPowerMin for power setting range."
	    ::= { muism 3 }

	muismRxThreshold OBJECT-TYPE
	    SYNTAX  INTEGER (-90 | -85 | -80 | -75 | -70 | -65)
	    ACCESS  read-write
	    STATUS  mandatory
	    DESCRIPTION
		"ISM RF rx threshold (in dBm). It specifies the receiver                                     
		 sensitivity of the master. By default, the radio's sensitivity is -82dBm.
                 The higher the threshold is, the less sensitive the radio will be.
                 In M5800S, the value -90 represents the rfrxthreshold is disabled."
	    ::= { muism 4 }

	muismTargetRSSI OBJECT-TYPE
	    SYNTAX  INTEGER (-85..-45)
	    ACCESS  read-write
	    STATUS  mandatory
	    DESCRIPTION
		"ISM RF RSSI (in dBm). It specifies the target RSSI from the remote unit
                 to the master unit. Based on this parameter, the master unit can power level
                 the remote unit so that it receives same level of signal strength from
                 the remote unit, regardless far or near. Note that when you set the Target RSSI
                 from the remote unit, you need to consider master unit's RF Rx Threshold value.
                 The Target RSSI from the remote unit must be 5dB higher than the RF Rx
	         Threshold. When the RF Rx Threshold is disabled, the setting of the Target
                 RSSI from remote unit shall be no less than -75dBm."
	    ::= { muism 5 }

	muuniiTxPowerMax OBJECT-TYPE
	    SYNTAX  INTEGER (-128..127)
	    ACCESS  read-only
	    STATUS  mandatory
	    DESCRIPTION
            	"This object is only applicable to M5830S/P5830S radio.
                 The maximum UNII Tx power value can be set (in dBm)."
        ::= { muunii 1 }
    
	muuniiTxPowerMin OBJECT-TYPE
	    SYNTAX  INTEGER (-128..127)
	    ACCESS  read-only
	    STATUS  mandatory
	    DESCRIPTION
            	"This object is only applicable to M5830S/P5830S radio.
                 The minimum UNII Tx power value can be set (in dBm)."
            ::= { muunii 2 }
        
 	muuniiTxPower OBJECT-TYPE
	    SYNTAX  INTEGER (-128..127)
	    ACCESS  read-write
	    STATUS  mandatory
	    DESCRIPTION
            	"This object is only applicable to M5830S/P5830S radio.
		 UNII RF tx power (in dBm). It specifies the power output
                 of the radio, excluding the antenna gain. Check parameters
                 apuniiTxPowerMax and apuniiTxPowerMin for power setting range."
	    ::= { muunii 3 }

	muuniiRxThreshold OBJECT-TYPE
	    SYNTAX  INTEGER (-90 | -85 | -80 | -75 | -70 | -65)
	    ACCESS  read-write
	    STATUS  mandatory
	    DESCRIPTION
            	"This object is only applicable to M5830S/P5830S radio.
                 UNII RF rx threshold (in dBm). It specifies the receiver sensitivity of the  master."
	    ::= { muunii 4 }

	muuniiTargetRSSI OBJECT-TYPE
	    SYNTAX  INTEGER (-85..-45)
	    ACCESS  read-write
	    STATUS  mandatory
	    DESCRIPTION
            	"This object is only applicable to M5830S/P5830S radio.
		 UNII RF target RSSI (in dBm). It specifies the target RSSI from
                 remote unit to the master unit. Based on this parameter, the master can power
                 level the remote unit so that it receives same level of signal strength from
                 the remote unit, regardless far or near. Note that when you set the Target RSSI
                 from the remote unit, you need to consider remote unit's RF Rx Threshold value.
                 The Target RSSI from the remote unit must be 5dB higher than the RF Rx Threshold."
	    ::= { muunii 5 }

	-- remote unit objects
	ruDeviceId OBJECT-TYPE
    	    SYNTAX  OCTET STRING (SIZE(4))
	    ACCESS  read-write
	    STATUS  mandatory
	    DESCRIPTION
		"Remote unit device ID."
	    ::= { ru 1 }

	ruUpstreamMIR OBJECT-TYPE
	    SYNTAX  INTEGER (100..10000)
	    ACCESS  read-write
	    STATUS  mandatory
	    DESCRIPTION
		"It is the Maximum Information Rate (in Kbps)
                 the master unit allocates to remote unit."
            DEFVAL { 128 }
	    ::= { ru 2 }

	remoteDownstreamMIR OBJECT-TYPE
	    SYNTAX  INTEGER (100..10000)
	    ACCESS  read-write
	    STATUS  mandatory
	    DESCRIPTION
		"It is the Maximum Information Rate (in Kbps)
                 the master unit allocates to the remote unit."
            DEFVAL { 9999 }
	    ::= { ru 3 }

	ruPowerLvl OBJECT-TYPE
	    SYNTAX  INTEGER {
                        deactivated(0),
                        activated(1)
                    }
	    ACCESS  read-write
	    STATUS  mandatory
	    DESCRIPTION
		"It is a feature that is typically found in more
                 elaborate mobile systems such as cellular CDMA
                 networks. Using this feature, the remote unit have its
                 RF power output adjusted until its signal strength
                 received in the master unit is roughly the same."
            DEFVAL  {deactivated}
	    ::= { ru 4 }

	ruReboot OBJECT-TYPE
            SYNTAX  INTEGER {
                        deactivated(0),
                        activated(1)
                    }
            ACCESS  read-write
            STATUS  mandatory
            DESCRIPTION
            	"Master unit issues reboot command to remote unit."
            DEFVAL { deactivated }
            ::= { ru 5 }

	ruAssociation OBJECT-TYPE
            SYNTAX  INTEGER {
                        associated(1),
                        notAssociated(0)
                    }
	    ACCESS  read-only
	    STATUS  mandatory
	    DESCRIPTION
		"Remote unit association status."
	    ::= { ru 6 }

	ruDistance OBJECT-TYPE
	    SYNTAX  INTEGER (0..40)
	    ACCESS  read-only
	    STATUS  mandatory
	    DESCRIPTION
		"Distance of remote unit (in mile)."
	    ::= { ru 7 }

	-- trapconfig objects
    	trapconfigDest1IPAddress OBJECT-TYPE
	    SYNTAX  IpAddress
	    ACCESS  read-write
	    STATUS  mandatory
	    DESCRIPTION
		"Trap destination 1 IP address."
	    ::= { trapconfig 2 }
         
    	trapconfigDest2IPAddress OBJECT-TYPE
	    SYNTAX  IpAddress
	    ACCESS  read-write
	    STATUS  mandatory
	    DESCRIPTION
		"Trap destination 2 IP address."
	    ::= { trapconfig 3 }
 
	
	-- MIB version object
	mibinfoVersion OBJECT-TYPE
            SYNTAX  DisplayString (SIZE (0..32))
	    ACCESS  read-only
	    STATUS  mandatory
	    DESCRIPTION
		"Trango master unit MIB Version."
	    ::= { mibinfo 1 }

	-- Trap objects

-- End of file <trango_P5830S_MU_1p0.mib>
END
