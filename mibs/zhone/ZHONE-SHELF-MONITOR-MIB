--
-- genShelfMonitor.mib
-- MIB generated by MG-SOFT Visual MIB Builder Version 3.0 Build 285
-- Friday, December 02, 2011 at 11:16:05
--

    ZHONE-SHELF-MONITOR-MIB DEFINITIONS ::= BEGIN
 
        IMPORTS
            OBJECT-GROUP, NOTIFICATION-GROUP            
                FROM SNMPv2-CONF            
            Integer32, Gauge32, OBJECT-TYPE, MODULE-IDENTITY, OBJECT-IDENTITY, 
            NOTIFICATION-TYPE            
                FROM SNMPv2-SMI            
            TimeStamp, TruthValue            
                FROM SNMPv2-TC            
            zhoneShelf, zhoneShelfIndex, zhoneSlotIndex, zhoneModules, zhoneShelfIndex, 
            zhoneSlotIndex            
                FROM Zhone            
            ZhoneAdminString, ZhoneCardType, ZhoneCardLineType            
                FROM Zhone-TC;
    
    
-- 
-- Overview of Zhone Shelf Monitor mib
-- 
-- The Zhone Shelf Monitor mib provides status information on system-level
-- devices such as alarm, fan tray, power supply, etc.
-- The following tables are described in this mib
-- 
-- 
-- shelfDataTable
-- shelfStatusTable
-- shelfFanTable
-- shelfTeperatureTable
-- shelfCardTable
-- 
-- This table provides status information on the power, temperature and fan-tray.
-- 
-- 
-- 
-- 
--     
-- 
-- 
--  
--  
        -- 1.3.6.1.4.1.5504.6.7
        zhoneShelfMonitorModule MODULE-IDENTITY 
			LAST-UPDATED "201112021020Z"		-- December 02, 2011 at 10:20 GMT
            ORGANIZATION 
                "Zhone Technologies, Inc"
            CONTACT-INFO 
                "  Postal: 
                           Zhone Technologies, Inc.
                           @ Zhone Way
                           7001 Oakport Street
                           Oakland, CA  94621
                           USA
                Toll-Free: +1 877-ZHONE20 (+1 877-946-6320)
                      Tel: +1-510-777-7000
                      Fax: +1-510-777-7001
                   E-mail: support@zhone.com"
            DESCRIPTION 
                "Contains the elements that are monitored on a per
                shelf basis in the PLS."
			REVISION "201112021114Z"		-- December 02, 2011 at 11:14 GMT
			DESCRIPTION 
				"Add shelf I/O alarm board present"
            REVISION "201105241025Z"		-- May 24, 2011 at 10:25 GMT
            DESCRIPTION 
                "V01.01.15 - Update shelfCardStatus with new
                card states (15, 16) for concurrent uplink.  Also added
                missing states."
            REVISION "201008101508Z"		-- August 10, 2010 at 15:08 GMT
            DESCRIPTION 
                "V01.01.14 - Added Battery A, B and Battery return voltages.
                          - Added shelfFanTrayType"
            REVISION "200608311058Z"		-- August 31, 2006 at 10:58 GMT
            DESCRIPTION 
                "V01.01.13 - Added fan C/D/E status. 
                          - Added missing power C/D status . "
            REVISION "200405112203Z"		-- May 11, 2004 at 22:03 GMT
            DESCRIPTION 
                "V01.01.12 - Added power supply C status"
            REVISION "200310281531Z"		-- October 28, 2003 at 15:31 GMT
            DESCRIPTION 
                "V01.01.11 - Added FlashCardStatus Trap"
            REVISION "200309171856Z"		-- September 17, 2003 at 18:56 GMT
            DESCRIPTION 
                "V01.01.10 - Added fan A/B status "
            REVISION "200307161630Z"		-- July 16, 2003 at 16:30 GMT
            DESCRIPTION 
                "V01.01.09 - added zhoneTrapCardVersionCheck trap."
            REVISION "200208191002Z"		-- August 19, 2002 at 10:02 GMT
            DESCRIPTION 
                "V01.01.08 - added cardReboot"
            REVISION "200207091036Z"		-- July 09, 2002 at 10:36 GMT
            DESCRIPTION 
                "Added NotProvisioned State to cardState
                Added FanTrayOK type to shelfTrap list"
            REVISION "200205281808Z"		-- May 28, 2002 at 18:08 GMT
            DESCRIPTION 
                "Moved shelfDataTable from 3.2.4 to 3.2.1
                Renamed shelfEnvironTable to shelfStatusTable and moved from 3.2.5 to 3.2.2
                Added shelfFanTable, shelfTemperatureTable, and shelfCardTable 
                Moved zhoneStatusChangeGroup"
            REVISION "200202120954Z"		-- February 12, 2002 at 09:54 GMT
            DESCRIPTION 
                "V01.01.05 -
                Added markup for environmental status fields."
            REVISION "200109101834Z"		-- September 10, 2001 at 18:34 GMT
            DESCRIPTION 
                "V01.01.04 - 
                Added tempOverLimit, tempUnderLimit, tempNormal, fanPowerSupplyAFailure, fanPowerSupplyAOK, fanPowerSupplyBFailure, fanPowerSupplyBOK, fanTrayAdded, and fanTrayRemoved to the zhoneShelfStatus OID."
            REVISION "200109101616Z"		-- September 10, 2001 at 16:16 GMT
            DESCRIPTION 
                "V01.01.03 - 
                Added the cardReset and cardRunning to the zhoneCardStatus Object Type.
                "
            REVISION "200010241618Z"		-- October 24, 2000 at 16:18 GMT
            DESCRIPTION 
                "V01.01.02 - 
                Added Revision descriptions
                to this mib."
            REVISION "200010131642Z"		-- October 13, 2000 at 16:42 GMT
            DESCRIPTION 
                "V01.01.01 - 
                Added the shelfControllerFault
                to the zhoneShelfStatus Object Type.
                Added the cardFaultError to
                the zhoneCardStatus Object Type.
                "
            REVISION "200009271625Z"		-- September 27, 2000 at 16:25 GMT
            DESCRIPTION 
                "V01.01.00 - 
                Added zhoneShelfStatus Object Type.
                Added zhoneCardStatus Object Type.
                Added zhoneShelfStatusLastChange Object Type.
                Added zhoneCardStatusLastChange Object Type.
                Imported TimeStamp from rfc1907.mib
                All changes for the shelfCtrl task.
                "
            REVISION "200009121126Z"		-- September 12, 2000 at 11:26 GMT
            DESCRIPTION 
                "V01.00.00 - Initial Release"
            ::= { zhoneModules 7 }

        
    
    
--
-- Node definitions
--
    
        -- 1.3.6.1.4.1.5504.3.2.1
        shelfDataTable OBJECT-TYPE
            SYNTAX SEQUENCE OF ShelfDataEntry
            MAX-ACCESS not-accessible
            STATUS current
            DESCRIPTION
                "A table of shelf information and status for each shelf 
                in a PLS system. The table includes revision level, 
                general shelf status, and enviromental monitoring.
                
                The maximum number of shelves in a system is 255. Shelf
                0 is an invalid entry."
            ::= { zhoneShelf 1 }

        
        -- 1.3.6.1.4.1.5504.3.2.4.1
        shelfDataEntry OBJECT-TYPE
            SYNTAX ShelfDataEntry
            MAX-ACCESS not-accessible
            STATUS current
            DESCRIPTION
                "An entry per shelf in a PLS system.  The entries are 
                indexed by zhoneShelfIndex or the shelf number which
                has a value of 1 to 255.  Shelf 0 is not valid.  
                zhoneShelfIndex is a column in the zhoneShelfSlotTable,
                defined in the zhone MIB (Zhone.mib).
                
                An Entry in the table is automatically created when
                a new shelf is added to a PLS and detected by the 
                operating software of the system"
            INDEX { zhoneShelfIndex }
            ::= { shelfDataTable 1 }

        
        ShelfDataEntry ::=
            SEQUENCE { 
                shelfMfgCLEICode
                    ZhoneAdminString,
                shelfMonitorSerialNumber
                    ZhoneAdminString,
                shelfMonitorRevisionCode
                    ZhoneAdminString,
                shelfBkplaneSerialNumber
                    ZhoneAdminString,
                shelfBkplaneRevisionCode
                    ZhoneAdminString,
                shelfFanTraySerialNumber
                    ZhoneAdminString,
                shelfFanTrayRevisionCode
                    ZhoneAdminString,
                shelfSlotCount
                    Integer32,
                shelfFeatureBits
                    OCTET STRING,
                shelfFanTrayType
					ZhoneCardType,
				shelfIOAlarmBoardPresent
					TruthValue
             }

-- 
        -- 1.3.6.1.4.1.5504.3.2.4.1.1
        shelfMfgCLEICode OBJECT-TYPE
            SYNTAX ZhoneAdminString
            MAX-ACCESS read-only
            STATUS current
            DESCRIPTION
                "CLEI (Common Language Equipment Identifier) code of the 
                shelf assembly as stored in the EEPROM of the unit if 
                defined otherwise the value will be set to NULL (0-length
                string) by the shelf monitor card.
                
                Note: CLEI codes for individual assemblies of the shelf
                such as monitor card or backplane assembly are not 
                supported."
            ::= { shelfDataEntry 1 }

        
-- 
        -- 1.3.6.1.4.1.5504.3.2.4.1.2
        shelfMonitorSerialNumber OBJECT-TYPE
            SYNTAX ZhoneAdminString
            MAX-ACCESS read-only
            STATUS current
            DESCRIPTION
                "The manufacturing serial number for the shelf monitor
                card of this shelf assembly."
            ::= { shelfDataEntry 2 }

        
-- 
        -- 1.3.6.1.4.1.5504.3.2.4.1.3
        shelfMonitorRevisionCode OBJECT-TYPE
            SYNTAX ZhoneAdminString
            MAX-ACCESS read-only
            STATUS current
            DESCRIPTION
                "Manufacturing hardware revision code for the shelf 
                monitoring card of this shelf assembly"
            ::= { shelfDataEntry 3 }

        
-- 
        -- 1.3.6.1.4.1.5504.3.2.4.1.4
        shelfBkplaneSerialNumber OBJECT-TYPE
            SYNTAX ZhoneAdminString
            MAX-ACCESS read-only
            STATUS current
            DESCRIPTION
                "The manufacturing serial number of the backplane in this
                shelf assembly."
            ::= { shelfDataEntry 4 }

        
-- 
        -- 1.3.6.1.4.1.5504.3.2.4.1.5
        shelfBkplaneRevisionCode OBJECT-TYPE
            SYNTAX ZhoneAdminString
            MAX-ACCESS read-only
            STATUS current
            DESCRIPTION
                "The manufacturing hardware revision code for the back-
                plane in this shelf assembly."
            ::= { shelfDataEntry 5 }

        
-- 
        -- 1.3.6.1.4.1.5504.3.2.4.1.6
        shelfFanTraySerialNumber OBJECT-TYPE
            SYNTAX ZhoneAdminString
            MAX-ACCESS read-only
            STATUS current
            DESCRIPTION
                "The manufacturing serial number for the fan tray assembly
                in this shelf assembly."
            ::= { shelfDataEntry 6 }

        
-- 
        -- 1.3.6.1.4.1.5504.3.2.4.1.7
        shelfFanTrayRevisionCode OBJECT-TYPE
            SYNTAX ZhoneAdminString
            MAX-ACCESS read-only
            STATUS current
            DESCRIPTION
                "The hardware revision code for the fan tray assembly in
                this shelf assembly."
            ::= { shelfDataEntry 7 }

        
-- 
        -- 1.3.6.1.4.1.5504.3.2.4.1.8
        shelfSlotCount OBJECT-TYPE
            SYNTAX Integer32
            MAX-ACCESS read-only
            STATUS current
            DESCRIPTION
                "The number of slots in this shelf"
            ::= { shelfDataEntry 8 }

        
-- 
        -- 1.3.6.1.4.1.5504.3.2.4.1.9
        shelfFeatureBits OBJECT-TYPE
            SYNTAX OCTET STRING (SIZE (8))
            MAX-ACCESS read-only
            STATUS current
            DESCRIPTION
                "A string of 8 octets indicating the setting of the feature BITS.
                "
            ::= { shelfDataEntry 9 }

        
-- This value represents the fan tray controller card type.
        -- 1.3.6.1.4.1.5504.3.2.4.1.10
        shelfFanTrayType OBJECT-TYPE
            SYNTAX ZhoneCardType
            MAX-ACCESS read-only
            STATUS current
            DESCRIPTION
                "Description."
            ::= { shelfDataEntry 10 }

        
		-- 1.3.6.1.4.1.5504.3.2.4.1.11
		shelfIOAlarmBoardPresent OBJECT-TYPE
			SYNTAX TruthValue
			MAX-ACCESS read-only
			STATUS current
			DESCRIPTION
				"Indicates that MXK I/O Alarm Board hardware
				is present and supported. Not used in systems
				other than MXK."
			::= { shelfDataEntry 11 }

		
        -- 1.3.6.1.4.1.5504.3.2.2
        shelfStatusTable OBJECT-TYPE
            SYNTAX SEQUENCE OF ShelfStatusEntry
            MAX-ACCESS not-accessible
            STATUS current
            DESCRIPTION
                "environmental status table - this table contains the 
                environmental monitoring data for each shelf in a PLS."
            ::= { zhoneShelf 2 }

        
        -- 1.3.6.1.4.1.5504.3.2.5.1
        shelfStatusEntry OBJECT-TYPE
            SYNTAX ShelfStatusEntry
            MAX-ACCESS not-accessible
            STATUS current
            DESCRIPTION
                "This table augments the shelfDataTable.  Each entry in
                the table contains the status of the environmental 
                monitoring sensors on the shelf monitor card."
            INDEX { zhoneShelfIndex }
            ::= { shelfStatusTable 1 }

        
        ShelfStatusEntry ::=
            SEQUENCE { 
                shelfAPowerStatus
                    INTEGER,
                shelfBPowerStatus
                    INTEGER,
                shelfTemperatureStatus
                    INTEGER,
                shelfFanTrayStatus
                    INTEGER,
                shelfAlarmContactsStatus
                    BITS,
                shelfCardStatus
                    OCTET STRING,
                shelfLedStatus
                    BITS,
                shelfAdminResets
                    Gauge32,
                shelfFaultResets
                    Gauge32,
                shelfPowerResets
                    Gauge32,
                shelfCPowerStatus
                    INTEGER,
                shelfDPowerStatus
                    INTEGER,
                shelfBatteryAVoltage
                    ZhoneAdminString,
                shelfBatteryBVoltage
                    ZhoneAdminString,
                shelfChassisReturnVoltage
                    ZhoneAdminString
             }

-- 
        -- 1.3.6.1.4.1.5504.3.2.5.1.1
        shelfAPowerStatus OBJECT-TYPE
            SYNTAX INTEGER
                {
                powerOk(1),
                powerNotOk(2)
                }
            MAX-ACCESS read-only
            STATUS current
            DESCRIPTION
                "Status of the A power to the shelf.  On systems with 
                multiple power sources, this entry represents the
                AC power-supply status.
                
                On systems with line-power, this entry represents 
                the status of power-line 1.
                
                The status of the power is indicated as follows:
                
                powerOk: the shelf is receiving a normal (in-range) 
                voltage.
                
                powerNotOk: the shelf is not receiving voltage or 
                the voltage is outside of the usable range.
                
                A trap is generated with the loss of A power."
            ::= { shelfStatusEntry 1 }

        
-- 
        -- 1.3.6.1.4.1.5504.3.2.5.1.2
        shelfBPowerStatus OBJECT-TYPE
            SYNTAX INTEGER
                {
                powerOk(1),
                powerNotOk(2)
                }
            MAX-ACCESS read-only
            STATUS current
            DESCRIPTION
                "Status of the B power to the shelf.  
                On systems with 
                multiple power sources, this entry represents the
                -48 Volt DC power-supply status.
                
                On systems with line-power, this entry represents 
                the status of power-line 2.
                
                The status of the power is indicated as follows:
                
                powerOk: the shelf is receiving a normal (in-range) 
                voltage.
                
                powerNotOk: the shelf is not receiving voltage or 
                the voltage is outside of the usable range.
                
                A trap is generated with the loss of A power."
            ::= { shelfStatusEntry 2 }

        
-- 
        -- 1.3.6.1.4.1.5504.3.2.5.1.3
        shelfTemperatureStatus OBJECT-TYPE
            SYNTAX INTEGER
                {
                normal(1),
                aboveNormal(2),
                belowNormal(3)
                }
            MAX-ACCESS read-only
            STATUS current
            DESCRIPTION
                "Outlet or exhaust air temperature as status.
                
                A trap is generated if temperature leaves the normal opertioning range."
            ::= { shelfStatusEntry 3 }

        
-- 
        -- 1.3.6.1.4.1.5504.3.2.5.1.4
        shelfFanTrayStatus OBJECT-TYPE
            SYNTAX INTEGER
                {
                operational(1),
                partiallyOperational(2),
                notOperational(3)
                }
            MAX-ACCESS read-only
            STATUS current
            DESCRIPTION
                "The operational status of the shelf fan tray assembly as
                follows:
                
                Operational: the fan tray is fully operational with
                all fans running.  
                
                notOperational: the fan tray assembly has failed.  A high severity trap
                is generated when the status is set to notOperational."
            ::= { shelfStatusEntry 4 }

        
-- 
        -- 1.3.6.1.4.1.5504.3.2.5.1.5
        shelfAlarmContactsStatus OBJECT-TYPE
            SYNTAX BITS
                {
                contactAlarm0(0),
                contactAlarm1(1),
                contactAlarm2(2),
                contactAlarm3(3)
                }
            MAX-ACCESS read-only
            STATUS current
            DESCRIPTION
                "A BIT field of two (2) BITs indicating larm status of the dry contact alarm on
                the chassis/shelf:
                
                A value of zero(0) is returned in each BIT if the contact is open
                A value of one(1) is returned if the contack is closed
                "
            ::= { shelfStatusEntry 5 }

        
-- 
        -- 1.3.6.1.4.1.5504.3.2.5.1.6
        shelfCardStatus OBJECT-TYPE
            SYNTAX OCTET STRING
            MAX-ACCESS read-only
            STATUS current
            DESCRIPTION
                "A string of octets, with one octet per card slot on
                the shelf assembly.  The string of octets indicates the
                status of each slot in sequence with the first octet 
                describing first slot.  The encoding of each octet is as 
                follows:
                
                1:  card is booting from eeprom
                2:  card is performing post tests
                3:  card is loading code from code loader
                4:  card is configuing
                5:  card is running      
                6:  card is blocked from booting
                7:  card is dumping fatal data
                8:  card is in faulted
                9:  card is reseting
                10: slot is empty
                11: slot is not provisioned
                12: card is disabled
                13: card is powered down
                14: card is powered up
                15: card is uplink with active traffic
                16: card is uplink without active traffic
                "
            ::= { shelfStatusEntry 6 }

        
-- 
-- 
        -- 1.3.6.1.4.1.5504.3.2.5.1.7
        shelfLedStatus OBJECT-TYPE
            SYNTAX BITS
                {
                battAPower(0),
                battBPower(1),
                fanAlarm(2),
                minorAlarm(3),
                majorAlarm(4),
                criticalAlarm(5)
                }
            MAX-ACCESS read-only
            STATUS current
            DESCRIPTION
                "A BIT field of six(6) BITs indicating the status of the
                LEDs on the chassis bezel.  A value of zero(0) is 
                returned in each BIT if the LED is off, a value of one(1)
                is returned if the LED is lit."
            ::= { shelfStatusEntry 7 }

        
-- 
        -- 1.3.6.1.4.1.5504.3.2.5.1.8
        shelfAdminResets OBJECT-TYPE
            SYNTAX Gauge32
            MAX-ACCESS read-only
            STATUS current
            DESCRIPTION
                "Count of the number of administration resets
                to a shelf such as systemreboot."
            ::= { shelfStatusEntry 8 }

        
-- 
        -- 1.3.6.1.4.1.5504.3.2.5.1.9
        shelfFaultResets OBJECT-TYPE
            SYNTAX Gauge32
            MAX-ACCESS read-only
            STATUS current
            DESCRIPTION
                "Count of the number of shelf resets due to faults."
            ::= { shelfStatusEntry 9 }

        
        -- 1.3.6.1.4.1.5504.3.2.5.1.10
        shelfPowerResets OBJECT-TYPE
            SYNTAX Gauge32
            MAX-ACCESS read-only
            STATUS current
            DESCRIPTION
                "Count of the number of shelf resets due to power 
                failure or power cycle."
            ::= { shelfStatusEntry 10 }

        
-- 
        -- 1.3.6.1.4.1.5504.3.2.5.1.11
        shelfCPowerStatus OBJECT-TYPE
            SYNTAX INTEGER
                {
                powerOk(1),
                powerNotOk(2)
                }
            MAX-ACCESS read-only
            STATUS current
            DESCRIPTION
                "Status of the C power to the shelf.  On systems with 
                multiple power sources, this entry represents the
                line-power power-supply status.
                
                On systems with line-power, this entry represents 
                the status of power-line 3.
                
                The status of the power is indicated as follows:
                
                powerOk: the shelf is receiving a normal (in-range) 
                voltage.
                
                powerNotOk: the shelf is not receiving voltage or 
                the voltage is outside of the usable range.
                
                A trap is generated with the loss of A power."
            ::= { shelfStatusEntry 11 }

        
-- 
        -- 1.3.6.1.4.1.5504.3.2.5.1.12
        shelfDPowerStatus OBJECT-TYPE
            SYNTAX INTEGER
                {
                powerOk(1),
                powerNotOk(2)
                }
            MAX-ACCESS read-only
            STATUS current
            DESCRIPTION
                "Status of the D power to the shelf.  
                
                On systems with line-power, this entry represents 
                the status of power-line 4.
                
                The status of the power is indicated as follows:
                
                powerOk: the shelf is receiving a normal (in-range) 
                voltage.
                
                powerNotOk: the shelf is not receiving voltage or 
                the voltage is outside of the usable range.
                
                A trap is generated with the loss of A power."
            ::= { shelfStatusEntry 12 }

        
        -- 1.3.6.1.4.1.5504.3.2.5.1.13
        shelfBatteryAVoltage OBJECT-TYPE
            SYNTAX ZhoneAdminString
            MAX-ACCESS read-only
            STATUS current
            DESCRIPTION
                "Battery A voltage measurement."
            ::= { shelfStatusEntry 13 }

        
        -- 1.3.6.1.4.1.5504.3.2.5.1.14
        shelfBatteryBVoltage OBJECT-TYPE
            SYNTAX ZhoneAdminString
            MAX-ACCESS read-only
            STATUS current
            DESCRIPTION
                "Battery B voltage measurement."
            ::= { shelfStatusEntry 14 }

        
        -- 1.3.6.1.4.1.5504.3.2.5.1.15
        shelfChassisReturnVoltage OBJECT-TYPE
            SYNTAX ZhoneAdminString
            MAX-ACCESS read-only
            STATUS current
            DESCRIPTION
                "Chassis return voltage."
            ::= { shelfStatusEntry 15 }

        
        -- 1.3.6.1.4.1.5504.3.2.3
        shelfFanTable OBJECT-TYPE
            SYNTAX SEQUENCE OF ShelfFanEntry
            MAX-ACCESS not-accessible
            STATUS current
            DESCRIPTION
                "A table of information about the fans on the shelf.
                Currently a BAN has 8 fans and a MALC has 3 fans."
            ::= { zhoneShelf 3 }

        
        -- 1.3.6.1.4.1.5504.3.2.6.1
        shelfFanEntry OBJECT-TYPE
            SYNTAX ShelfFanEntry
            MAX-ACCESS not-accessible
            STATUS current
            DESCRIPTION
                "Description."
            INDEX { zhoneShelfIndex, shelfFanIndex }
            ::= { shelfFanTable 1 }

        
        ShelfFanEntry ::=
            SEQUENCE { 
                shelfFanIndex
                    Integer32,
                shelfFanSpeed
                    Integer32,
                shelfFanLocation
                    ZhoneAdminString,
                shelfFanLowSpeedThreshold
                    Integer32
             }

        -- 1.3.6.1.4.1.5504.3.2.6.1.1
        shelfFanIndex OBJECT-TYPE
            SYNTAX Integer32 (1..100)
            MAX-ACCESS not-accessible
            STATUS current
            DESCRIPTION
                "An index into the fan table.  It is index from
                1..Number of fans with no missing indicies."
            ::= { shelfFanEntry 1 }

        
        -- 1.3.6.1.4.1.5504.3.2.6.1.2
        shelfFanSpeed OBJECT-TYPE
            SYNTAX Integer32
            MAX-ACCESS read-only
            STATUS current
            DESCRIPTION
                "Fan speed of the fan in RPM"
            ::= { shelfFanEntry 2 }

        
        -- 1.3.6.1.4.1.5504.3.2.6.1.3
        shelfFanLocation OBJECT-TYPE
            SYNTAX ZhoneAdminString
            MAX-ACCESS read-only
            STATUS current
            DESCRIPTION
                "Description of the location of the fan in the fan tray"
            ::= { shelfFanEntry 3 }

        
        -- 1.3.6.1.4.1.5504.3.2.6.1.4
        shelfFanLowSpeedThreshold OBJECT-TYPE
            SYNTAX Integer32
            MAX-ACCESS read-only
            STATUS current
            DESCRIPTION
                "The lower speed allowed for a fan before it is considered failed."
            ::= { shelfFanEntry 4 }

        
        -- 1.3.6.1.4.1.5504.3.2.4
        shelfTemperatureTable OBJECT-TYPE
            SYNTAX SEQUENCE OF ShelfTemperatureEntry
            MAX-ACCESS not-accessible
            STATUS current
            DESCRIPTION
                "A table of information about the temperature sensors
                in the shelf."
            ::= { zhoneShelf 4 }

        
        -- 1.3.6.1.4.1.5504.3.2.7.1
        shelfTemperatureEntry OBJECT-TYPE
            SYNTAX ShelfTemperatureEntry
            MAX-ACCESS not-accessible
            STATUS current
            DESCRIPTION
                "Description."
            INDEX { zhoneShelfIndex, shelfTemperatureIndex }
            ::= { shelfTemperatureTable 1 }

        
        ShelfTemperatureEntry ::=
            SEQUENCE { 
                shelfTemperatureIndex
                    Integer32,
                shelfTemperature
                    Integer32,
                shelfTemperatureLocation
                    ZhoneAdminString,
                shelfTemperatureHighThreshold
                    Integer32,
                shelfTemperatureLowThreshold
                    Integer32
             }

        -- 1.3.6.1.4.1.5504.3.2.7.1.1
        shelfTemperatureIndex OBJECT-TYPE
            SYNTAX Integer32 (1..100)
            MAX-ACCESS not-accessible
            STATUS current
            DESCRIPTION
                "An index into the temperature table.  It is index
                1..Number of temperature sensors with no missing indicies."
            ::= { shelfTemperatureEntry 1 }

        
        -- 1.3.6.1.4.1.5504.3.2.7.1.2
        shelfTemperature OBJECT-TYPE
            SYNTAX Integer32
            MAX-ACCESS read-only
            STATUS current
            DESCRIPTION
                "The temperature of a shelf at this position."
            ::= { shelfTemperatureEntry 2 }

        
        -- 1.3.6.1.4.1.5504.3.2.7.1.3
        shelfTemperatureLocation OBJECT-TYPE
            SYNTAX ZhoneAdminString
            MAX-ACCESS read-only
            STATUS current
            DESCRIPTION
                "The location of the this temperature sensors."
            ::= { shelfTemperatureEntry 3 }

        
        -- 1.3.6.1.4.1.5504.3.2.7.1.4
        shelfTemperatureHighThreshold OBJECT-TYPE
            SYNTAX Integer32
            MAX-ACCESS read-only
            STATUS current
            DESCRIPTION
                "The upper temperature when an alarm will be sent."
            ::= { shelfTemperatureEntry 4 }

        
        -- 1.3.6.1.4.1.5504.3.2.7.1.5
        shelfTemperatureLowThreshold OBJECT-TYPE
            SYNTAX Integer32
            MAX-ACCESS read-only
            STATUS current
            DESCRIPTION
                "The lower temperature that an alarm will be sent."
            ::= { shelfTemperatureEntry 5 }

        
        -- 1.3.6.1.4.1.5504.3.2.5
        shelfCardTable OBJECT-TYPE
            SYNTAX SEQUENCE OF ShelfCardEntry
            MAX-ACCESS not-accessible
            STATUS current
            DESCRIPTION
                "A table of card information for each shelf in a PLS
                system. The includes different counts of resets for
                each card and the card type for each slot."
            ::= { zhoneShelf 5 }

        
        -- 1.3.6.1.4.1.5504.3.2.5.1
        shelfCardEntry OBJECT-TYPE
            SYNTAX ShelfCardEntry
            MAX-ACCESS not-accessible
            STATUS current
            DESCRIPTION
                "An entry per slot and shelf in a PLS system. 
                The entries are indexed by zhoneShelfIndex/zhoneSlotIndex."
            INDEX { zhoneShelfIndex, zhoneSlotIndex }
            ::= { shelfCardTable 1 }

        
        ShelfCardEntry ::=
            SEQUENCE { 
                cardType
                    ZhoneCardType,
                cardSubType
                    ZhoneCardType,
                cardLineType
                    ZhoneCardLineType,
                cardVersion
                    ZhoneAdminString,
                cardEepromVersion
                    ZhoneAdminString,
                cardSerialNumber
                    ZhoneAdminString,
                cardCLEICode
                    ZhoneAdminString,
                cardFeatureBits
                    OCTET STRING,
                cardState
                    INTEGER,
                cardAdminResets
                    Gauge32,
                cardFaultResets
                    Gauge32,
                cardReboot
                    TruthValue
             }

-- 
        -- 1.3.6.1.4.1.5504.3.2.5.1.1
        cardType OBJECT-TYPE
            SYNTAX ZhoneCardType
            MAX-ACCESS read-only
            STATUS current
            DESCRIPTION
                "The card type for the card in this slot."
            ::= { shelfCardEntry 1 }

        
-- 
        -- 1.3.6.1.4.1.5504.3.2.5.1.2
        cardSubType OBJECT-TYPE
            SYNTAX ZhoneCardType
            MAX-ACCESS read-only
            STATUS current
            DESCRIPTION
                "The card sub type for this slot"
            ::= { shelfCardEntry 2 }

        
-- 
        -- 1.3.6.1.4.1.5504.3.2.5.1.3
        cardLineType OBJECT-TYPE
            SYNTAX ZhoneCardLineType
            MAX-ACCESS read-only
            STATUS current
            DESCRIPTION
                "The card line type for this slot.  This is only valid if the slot is provisioned."
            ::= { shelfCardEntry 3 }

        
-- 
        -- 1.3.6.1.4.1.5504.3.2.5.1.4
        cardVersion OBJECT-TYPE
            SYNTAX ZhoneAdminString
            MAX-ACCESS read-only
            STATUS current
            DESCRIPTION
                "The card version for the card in this slot."
            ::= { shelfCardEntry 4 }

        
-- 
-- 
        -- 1.3.6.1.4.1.5504.3.2.5.1.5
        cardEepromVersion OBJECT-TYPE
            SYNTAX ZhoneAdminString
            MAX-ACCESS read-only
            STATUS current
            DESCRIPTION
                "The eeprom version for the card in this slot."
            ::= { shelfCardEntry 5 }

        
-- 
        -- 1.3.6.1.4.1.5504.3.2.5.1.6
        cardSerialNumber OBJECT-TYPE
            SYNTAX ZhoneAdminString
            MAX-ACCESS read-only
            STATUS current
            DESCRIPTION
                "The serial number for the card in this slot."
            ::= { shelfCardEntry 6 }

        
-- 
-- 
        -- 1.3.6.1.4.1.5504.3.2.5.1.7
        cardCLEICode OBJECT-TYPE
            SYNTAX ZhoneAdminString
            MAX-ACCESS read-only
            STATUS current
            DESCRIPTION
                "CLEI (Common Language Equipment Identifier) code of the 
                shelf assembly as stored in the EEPROM of the unit if 
                defined otherwise the value will be set to NULL (0-length
                string) by the shelf monitor card."
            ::= { shelfCardEntry 7 }

        
-- 
        -- 1.3.6.1.4.1.5504.3.2.5.1.8
        cardFeatureBits OBJECT-TYPE
            SYNTAX OCTET STRING (SIZE (8))
            MAX-ACCESS read-only
            STATUS current
            DESCRIPTION
                "A string of 8 octets indicating the setting of the feature BITS.
                "
            ::= { shelfCardEntry 8 }

        
-- 
        -- 1.3.6.1.4.1.5504.3.2.5.1.9
        cardState OBJECT-TYPE
            SYNTAX INTEGER
                {
                cardStateNone(0),
                cardStateBooting(1),
                cardStatePost(2),
                cardStateLoading(3),
                cardStateConfiguring(4),
                cardStateRunning(5),
                cardStateResetHold(6),
                cardStateDumping(7),
                cardStateFault(8),
                cardStateReset(9),
                cardNotPresent(10),
                cardNotProvisioned(11)
                }
            MAX-ACCESS read-only
            STATUS current
            DESCRIPTION
                "The card state for the card in this slot.
                
                cardStateBooting      card is booting from eeprom
                cardStatePost         card is performing post tests
                cardStateLoading      card is loading code from code loader
                cardStateConfiguring  card is configuing
                cardStateRunning      card is running      
                cardStateResetHold    card is blocked from booting
                cardStateDumping     
                cardStateFault        card is in faulted
                cardStateReset        card is reseting
                cardNotPresent        card is not present in slot
                cardNotProvisioned    card in slot is not provisioned
                "
            ::= { shelfCardEntry 9 }

        
-- 
        -- 1.3.6.1.4.1.5504.3.2.5.1.10
        cardAdminResets OBJECT-TYPE
            SYNTAX Gauge32
            MAX-ACCESS read-only
            STATUS current
            DESCRIPTION
                "Count of the number of administration resets to this 
                card."
            ::= { shelfCardEntry 10 }

        
-- 
        -- 1.3.6.1.4.1.5504.3.2.5.1.11
        cardFaultResets OBJECT-TYPE
            SYNTAX Gauge32
            MAX-ACCESS read-only
            STATUS current
            DESCRIPTION
                "Count of number of fault resets to this card."
            ::= { shelfCardEntry 11 }

        
        -- 1.3.6.1.4.1.5504.3.2.5.1.12
        cardReboot OBJECT-TYPE
            SYNTAX TruthValue
            MAX-ACCESS read-write
            STATUS current
            DESCRIPTION
                "When set to true, this card will be rebooted.
                Error cases:
                (a) If the card is not present, a set results in an 
                    INCONSISTENT_VALUE error.
                (b) An attempt to set to false results in a 
                    WRONG_VALUE error.
                 
                All gets will return a value of false.
                
                This is supported only on systems with a supervisory 
                bus, such as BAN & MALC."
            ::= { shelfCardEntry 12 }

        
-- 
        -- 1.3.6.1.4.1.5504.3.2.7
        zhoneShelfStatus OBJECT-TYPE
            SYNTAX INTEGER
                {
                leftOutletTempOverLimit(1),
                leftOutletTempNormal(2),
                rightOutletTempOverLimit(3),
                rightOutletTempNormal(4),
                powerSupplyAFailure(5),
                powerSupplyAOK(6),
                powerSupplyBFailure(7),
                powerSupplyBOK(8),
                fanSpeedError(9),
                shelfControllerFault(10),
                tempOverLimit(11),
                tempUnderLimit(12),
                tempNormal(13),
                fanPowerSupplyAFailure(14),
                fanPowerSupplyAOK(15),
                fanPowerSupplyBFailure(16),
                fanPowerSupplyBOK(17),
                fanTrayAdded(18),
                fanTrayRemoved(19),
                fanSpeedOK(20),
                fanAFailure(21),
                fanAOK(22),
                fanBFailure(23),
                fanBOK(24),
                fanPowerSupplyCFailure(25),
                fanPowerSupplyCOK(26),
                fanPowerSupplyDFailure(27),
                fanPowerSupplyDOK(28),
                shelfControllerCleared(29),
                fanCFailure(30),
                fanCOK(31),
                fanDFailure(32),
                fanDOK(33),
                fanEFailure(34),
                fanEOK(35)
                }
            MAX-ACCESS read-only
            STATUS current
            DESCRIPTION
                "This variable is set by the ShelfMonitor when the
                shelf state changes."
            ::= { zhoneShelf 7 }

        
-- 
        -- 1.3.6.1.4.1.5504.3.2.8
        zhoneCardStatus OBJECT-TYPE
            SYNTAX INTEGER
                {
                cardRemoved(1),
                cardAdded(2),
                cardTimeoutError(3),
                cardFaultError(4),
                cardReset(5),
                cardRunning(6)
                }
            MAX-ACCESS read-only
            STATUS current
            DESCRIPTION
                "This variable is set by the ShelfMonitor whenever the
                card state changes."
            ::= { zhoneShelf 8 }

        
-- 
        -- 1.3.6.1.4.1.5504.3.2.10
        zhoneShelfStatusLastChange OBJECT-TYPE
            SYNTAX TimeStamp
            MAX-ACCESS read-only
            STATUS current
            DESCRIPTION
                "The time the shelf status changed."
            ::= { zhoneShelf 10 }

        
-- 
        -- 1.3.6.1.4.1.5504.3.2.11
        zhoneCardStatusLastChange OBJECT-TYPE
            SYNTAX TimeStamp
            MAX-ACCESS read-only
            STATUS current
            DESCRIPTION
                "The time the card status last changed."
            ::= { zhoneShelf 11 }

        
        -- 1.3.6.1.4.1.5504.3.2.12
        zhoneTrapShelfMonitorV2Traps OBJECT-IDENTITY
            STATUS current
            DESCRIPTION 
                "ShelfMonitor Trap."
            ::= { zhoneShelf 12 }

        
        -- 1.3.6.1.4.1.5504.3.2.12.1
        zhoneTrapShelfMonitorGroup NOTIFICATION-GROUP
            NOTIFICATIONS { zhoneTrapShelfStatusChange, zhoneTrapCardStatusChange, zhoneTrapCardVersionCheck, zhoneTrapFlashCardStatusChange }
            STATUS current
            DESCRIPTION 
                "Description."
            ::= { zhoneTrapShelfMonitorV2Traps 1 }

        
        -- 1.3.6.1.4.1.5504.3.2.12.2
        zhoneTrapShelfStatusChange NOTIFICATION-TYPE
            OBJECTS { zhoneShelfStatus }
            STATUS current
            DESCRIPTION 
                "Shelf status reported by the ShelfMonitor."
            ::= { zhoneTrapShelfMonitorV2Traps 2 }

        
        -- 1.3.6.1.4.1.5504.3.2.12.3
        zhoneTrapCardStatusChange NOTIFICATION-TYPE
            OBJECTS { zhoneCardStatus }
            STATUS current
            DESCRIPTION 
                "Card status reported by the ShelfMonitor."
            ::= { zhoneTrapShelfMonitorV2Traps 3 }

        
        -- 1.3.6.1.4.1.5504.3.2.12.4
        zhoneTrapCardVersionCheck NOTIFICATION-TYPE
            OBJECTS { cardVersion }
            STATUS current
            DESCRIPTION 
                "When the cardVersion of a card is incompatible with that
                of active InfoServ card, this trap is generated. Currently,
                this is only supported on BAN platform and its card versions
                are described as follows:
                
                The revision number of the newer 40 Mhz cards is in the range
                of 'BA' to 'CV'. 
                
                Older card version either does not display in this format or
                the revision number is not in this range.
                
                For example, for a card with cardVersion '840-29496-72-CR',
                the revision number is 'CR' and is a new 40 Mhz card."
            ::= { zhoneTrapShelfMonitorV2Traps 4 }

        
--  1.3.6.1.4.1.5504.3.2.12.5
        -- 1.3.6.1.4.1.5504.3.2.12.5
        zhoneTrapFlashCardStatusChange NOTIFICATION-TYPE
            OBJECTS { zhoneFlashCardStatusChange }
            STATUS current
            DESCRIPTION 
                "This Trap reports the FlashCard status change for the InfoServ slots 
                flash cards within BAN shelf."
            ::= { zhoneTrapShelfMonitorV2Traps 5 }

        
-- 1.3.6.1.4.1.5504.3.2.12.6
        -- 1.3.6.1.4.1.5504.3.2.12.6
        zhoneTrapCardToBkplaneStatusChange NOTIFICATION-TYPE
            OBJECTS { zhoneCardLinkToBkplaneStatus }
            STATUS current
            DESCRIPTION 
                "Mxk line card link to backplane status."
            ::= { zhoneTrapShelfMonitorV2Traps 6 }

        
        -- 1.3.6.1.4.1.5504.3.2.13
        zhoneShelfStatusGroup OBJECT-GROUP
            OBJECTS { shelfMfgCLEICode, shelfMonitorSerialNumber, shelfMonitorRevisionCode, shelfBkplaneSerialNumber, shelfBkplaneRevisionCode, 
                shelfFanTraySerialNumber, shelfFanTrayRevisionCode, shelfSlotCount, shelfFeatureBits, shelfAPowerStatus, 
                shelfBPowerStatus, shelfFanTrayStatus, shelfAlarmContactsStatus, shelfCardStatus, shelfLedStatus, 
                shelfAdminResets, shelfFaultResets, shelfPowerResets, zhoneShelfStatus, zhoneCardStatus, 
                zhoneShelfStatusLastChange, zhoneCardStatusLastChange, shelfFanSpeed, shelfFanLocation, shelfFanLowSpeedThreshold, 
                shelfTemperature, shelfTemperatureLocation, shelfTemperatureHighThreshold, zhoneFlashCardStatusChange, shelfTemperatureLowThreshold, 
                shelfTemperatureStatus }
            STATUS current
            DESCRIPTION 
                "These objects are used to identify the status change
                of the trap."
            ::= { zhoneShelf 13 }

        
        -- 1.3.6.1.4.1.5504.3.2.14
        zhoneStatusLastChangeGroup OBJECT-GROUP
            OBJECTS { zhoneShelfStatusLastChange, zhoneCardStatusLastChange }
            STATUS current
            DESCRIPTION 
                "Description."
            ::= { zhoneShelf 14 }

        
        -- 1.3.6.1.4.1.5504.3.2.15
        zhoneCardStatusGroup OBJECT-GROUP
            OBJECTS { cardType, cardSubType, cardLineType, cardVersion, cardEepromVersion, 
                cardSerialNumber, cardCLEICode, cardFeatureBits, cardState, cardAdminResets, 
                cardFaultResets, cardReboot }
            STATUS current
            DESCRIPTION 
                "Description."
            ::= { zhoneShelf 15 }

        
--  1.3.6.1.4.1.5504.3.2.16
        -- 1.3.6.1.4.1.5504.3.2.16
        zhoneFlashCardStatusChange OBJECT-TYPE
            SYNTAX INTEGER
                {
                flashCardPort1Installed(1),
                flashCardPort1Removed(2),
                flashCardPort2Installed(3),
                flashCardPort2Removed(4)
                }
            MAX-ACCESS accessible-for-notify
            STATUS current
            DESCRIPTION
                "The FlashCardStatus reports the status of the flash card ports on the 
                InfoServe cards within BAN shelf.  
                1 : FlashCard Port 1 is Installed
                2 : FlashCard Port 1 is Removed
                3 : FlashCard Port 2 is Installed
                4 : FlashCard Port 2 is Removed"
            ::= { zhoneShelf 16 }

        
        -- 1.3.6.1.4.1.5504.3.2.17
        zhoneCardLinkToBkplaneStatus OBJECT-TYPE
            SYNTAX INTEGER
                {
                cardToBkpLinkNotPresent(1),
                cardToBkpLinkPresent(2)
                }
            MAX-ACCESS accessible-for-notify
            STATUS current
            DESCRIPTION
                "Mxk linecard Link To Backplane status."
            ::= { zhoneShelf 17 }

        
    
    END

--
-- genShelfMonitor.mib
--
