--
-- phyWtnRadio.mib
-- MIB generated by MG-SOFT Visual MIB Builder Version 2.1 Build 205
-- Wednesday, August 22, 2001 at 02:16:01
--

    ZHONE-PHY-WTN-RADIO-MIB DEFINITIONS ::= BEGIN

        IMPORTS 
            InterfaceIndex            
                FROM IF-MIB            
            SnmpAdminString            
                FROM SNMP-FRAMEWORK-MIB            
            Integer32, Gauge32, OBJECT-TYPE, MODULE-IDENTITY, NOTIFICATION-TYPE            
                FROM SNMPv2-SMI            
            TruthValue, TimeStamp            
                FROM SNMPv2-TC            
            SkyZhoneScientificNotation, SkyZhoneRadioChannelNumber            
                FROM ZHONE-RADIO-TC-MIB            
            zhoneRadio, zhoneModules            
                FROM Zhone            
            ZhoneAdminString            
                FROM Zhone-TC;
    
    
-- 
-- 
        zhonePhyWtnRadio MODULE-IDENTITY
            LAST-UPDATED "190011031129Z"
            ORGANIZATION
                "Zhone Technologies, Inc."
            CONTACT-INFO
                "  Postal: 
                Zhone Technologies, Inc.
                @ Zhone Way
                7001 Oakport Street
                Oakland, CA  94621
                USA
                Toll-Free: +1 877-ZHONE20 (+1 877-946-6320)
                Tel: +1-510-777-7000
                Fax: +1-510-777-7001
                E-mail: support@zhone.com
                
                Zhone Technologies, Inc.
                Wireless Group
                120 Stony Point Rd
                Suite 140
                Santa Rosa, CA  95401
                707 206 3600"
            DESCRIPTION
                "Module for radio provisioning and status."
            REVISION "200107111300Z"
            DESCRIPTION
                "V01.04.01 - Use SkyZhoneScientificNotation rather 
                than SinglePrecision Floating point
                format."
            REVISION "200106071414Z"
            DESCRIPTION
                "V01.03.01 - add ODU loopback"
            REVISION "200105181002Z"
            DESCRIPTION
                "V01.03.00 - Generalize for all SkyZhone products."
            REVISION "200011240818Z"
            DESCRIPTION
                "V01.02.00 - Support traps."
            REVISION "200011211535Z"
            DESCRIPTION
                "V01.00.01 - Add DDL markups."
            REVISION "200011030944Z"
            DESCRIPTION
                "V01.00.00 - Initial Revision"
            ::= { zhoneModules 106 }
        
    
    
--
-- Node definitions
--
    
-- For use of radio interface regarding the ifTable, 
-- see the zhoneRadio-TC.mib.
        wtnConfigTable OBJECT-TYPE
            SYNTAX SEQUENCE OF WtnConfigEntry
            MAX-ACCESS not-accessible
            STATUS current
            DESCRIPTION
                "Radio, modem and ODU configuration information.  An entry 
                is automatically created for each radio/modem/ODU 
                interface."
            ::= { zhoneRadio 1 }
        
        wtnConfigEntry OBJECT-TYPE
            SYNTAX WtnConfigEntry
            MAX-ACCESS not-accessible
            STATUS current
            DESCRIPTION
                "Configuration entries"
            INDEX { wtnRadioIfIndex }
            ::= { wtnConfigTable 1 }
        
        WtnConfigEntry ::=
            SEQUENCE { 
                wtnRadioIfIndex
                    InterfaceIndex,
                wtnActiveChannelNumber
                    SkyZhoneRadioChannelNumber,
                wtnActiveTransmitFrequency
                    SkyZhoneScientificNotation,
                wtnStandbyChannelNumber
                    SkyZhoneRadioChannelNumber,
                wtnStandbyTransmitFrequency
                    SkyZhoneScientificNotation,
                wtnAutoChannelSwitchEnable
                    TruthValue,
                wtnChannelSeparation
                    INTEGER,
                wtnRadioAmplifiersEnable
                    TruthValue,
                wtnRxBERThresh
                    SkyZhoneScientificNotation,
                wtnRxBERHysteresisWindow
                    SkyZhoneScientificNotation,
                wtnAntennaSize
                    INTEGER,
                wtnIduOduCableLength
                    Integer32,
                wtnRssiThresh
                    Integer32,
                wtnRssiHysteresisWindow
                    Integer32,
                wtnTrapsEnable
                    TruthValue,
                wtnOduLoopback
                    INTEGER,
                wtnOduIdentifier
                    SnmpAdminString,
                wtnTxLevel
                    Integer32
             }

        wtnRadioIfIndex OBJECT-TYPE
            SYNTAX InterfaceIndex
            MAX-ACCESS not-accessible
            STATUS current
            DESCRIPTION
                "This object should be made equal to the Ifindex used for
                the radio interface."
            ::= { wtnConfigEntry 1 }
        
-- 
        wtnActiveChannelNumber OBJECT-TYPE
            SYNTAX SkyZhoneRadioChannelNumber
            MAX-ACCESS read-write
            STATUS current
            DESCRIPTION
                "Assigns one of N allowed frequency pairs for the radio 
                transmitter and reciever as described in zhoneRadio-TC.mib.
                
                5.7Ghz family (sysObjId) systems:
                ---------------------------------
                Writing to this value will change the current operating frequency.
                The active channel is the default channel used on power up. 
                
                The channel is switched at the near end, and if possible, also at
                the far end, towards minimizing link down time.  
                
                Every time the active channel number changes BITS WILL BE DROPPED.  
                In poor conditions there is a risk that the new frequency assignment 
                will fare more poorly.  The user should expect alarms where the facility 
                is terminated until the nodes re-sync.
                
                If a new active channel number is equal to the current value of
                active channel, the command will have no effect and no error message will result. 
                
                
                Allowed range of allowed values:   0 - 17
                
                This value will read back the current active channel.
                
                Note:  if this value is changed to a new active channel number,
                and the system can not establish a radio link at this channel,
                the system may automatically switch to the standby channel, if
                wtnAutoChannelSwitchEnable is true(1), and the value of 
                wtnStandbyChannelNumber is neither the same channel number nor zero.
                
                23Ghz family (sysObjId) systems: 
                -------------------------------
                This variable is not used and so should not be presented to user.
                Use direct frequency assignments instead.   
                See wtnActiveTransmitFrequency."
            ::= { wtnConfigEntry 2 }
        
        wtnActiveTransmitFrequency OBJECT-TYPE
            SYNTAX SkyZhoneScientificNotation
            UNITS "Hz"
            MAX-ACCESS read-write
            STATUS current
            DESCRIPTION
                "Current transmit frequency. As described in zhoneRadio-TC.mib.
                
                
                23Ghz family:  ( according to sysObjId )
                -------------------------------------------   
                The transmit frequency is entered as a floating point number in Mhz,
                for example, 23565.5 for 23.5655Ghz.
                Note:  receive frequency will also be affected by this parameter.
                
                The resulting receive frequency will be simultaneously set to 
                this value +/- wtnChannelSeparation  (plus or minus depending upon
                whether the unit is an A or B type ODU.)
                
                If the frequency entered or the calulated receive frequency
                outside the range of the unit, an error will be returned and the
                value left unchanged.
                
                If a new active frequency is equal to the current value frequency,
                the command will have no effect and no error message will result. 
                
                Every time the active frequency changes BITS WILL BE DROPPED.  
                In poor conditions there is a risk that the new frequency assignment 
                will fare more poorly.  The user should expect alarms where the facility 
                is terminated until the nodes re-sync.
                
                If the link is operational, the new frequencies will be changed
                at the opposite end before the values at the local end are changed
                in an attempt to minimize payload data loss.
                
                5.7Ghz family of systems (according to sysObjId )
                -------------------------------------------------
                Value will reflect the frequency of the currently
                active channel (wtnActiveChannelNumber).
                Writing to this variable will have no effect."
            ::= { wtnConfigEntry 3 }
        
-- 
        wtnStandbyChannelNumber OBJECT-TYPE
            SYNTAX SkyZhoneRadioChannelNumber
            MAX-ACCESS read-write
            STATUS current
            DESCRIPTION
                "Assigns one of N allowed standby frequency pairs to the radio 
                transmitter and reciever as described in zhoneRadio-TC.mib.
                
                5.7Ghz family (sysObjId) systems:
                ---------------------------------
                Selection of one of N possible frequency pairs for the 
                standby radio transmitter reciever.  
                
                The Standby channel is the channel automatically switched to
                in the event of failure of the current active channel, for example,
                due to radio inteference. Automatic Switching must be enabled for
                the standby channel to be switched to by setting wtnAutoChannelSwitchEnable
                to true.
                
                If the standby channel is assigned a value of zero (0), the automatic
                switch to standby feature is effectively disabled, regardless of
                the value of wtnAutoChannelSwitchEnable.
                
                The channel is switched at the near end, and if possible, also at
                the far end, towards minimizing link down time.  
                
                
                Allowed range of allowed values (see zhoneRadio-TC.mib ): 0 - 17
                
                This value will read back the current standby channel.
                
                Operation - 
                If a switch-to-standby channel event occurs, the active channel
                number and the standby channel number swap values.  For example, 
                
                before a radio failure:  active channel = 1, 
                                         standby channel = 7, and 
                                         automatic channel switching is enabled.
                
                After a radio failure on channel 1:
                                         active channel = 7,
                                         standby channel = 1, and
                                         automatic channel switching is enabled.
                
                If both channels fail to operate, the system will bounce back
                and forth between the active and standby channels until the radio
                link is re-established.
                
                
                23Ghz family sysObjId systems: 
                -------------------------------
                This variable is not used and so should not be presented to user.
                Use direct frequency assignments instead.   
                See wtnStandbyTransmitFrequency.
                "
            ::= { wtnConfigEntry 4 }
        
        wtnStandbyTransmitFrequency OBJECT-TYPE
            SYNTAX SkyZhoneScientificNotation
            UNITS "Hz"
            MAX-ACCESS read-write
            STATUS current
            DESCRIPTION
                "Standby Transmit frequency as described in zhoneRadio-TC.mib.
                
                
                23Ghz family:  ( according to sysObjId )
                -------------------------------------------   
                If auto-switching is enabled, the
                frequency shown will be used in the event the currently active
                frequency fails due to low RSSI, or high BER.  Note the switch
                will occur only if wtnAutoChannelSwitchEnable is true(1).
                
                The transmit frequency is entered as a floating point number in Mhz,
                for example, 23565.5 for 23.5655Ghz.
                
                If the frequency entered or the calulated receive frequency
                outside the range of the unit, an error will be returned and the
                value left unchanged.
                
                If the link is operational, the new standby frequencies will be changed
                at the opposite end before the values at the local end are changed.
                
                
                5.7Ghz family: (according to sysObjId )
                -----------------------------------------
                Value will reflect the frequency of the currently
                active channel (wtnStandbyChannelNumber).
                Writing to this variable will have no effect."
            ::= { wtnConfigEntry 5 }
        
-- 
        wtnAutoChannelSwitchEnable OBJECT-TYPE
            SYNTAX TruthValue
            MAX-ACCESS read-write
            STATUS current
            DESCRIPTION
                "true(1) - allows radio to automatically switch 
                to the standby channel in case of active channel 
                interference.
                
                false(2) - inhibits radio from automatically 
                switching to the standby channel.
                
                The default value is false(2)."
            ::= { wtnConfigEntry 6 }
        
        wtnChannelSeparation OBJECT-TYPE
            SYNTAX INTEGER
                {
                na(0),
                s1232MHz(1),
                s1200MHz(2),
                s1008MHz(3)
                }
            MAX-ACCESS read-write
            STATUS current
            DESCRIPTION
                "23Ghz family (sysObjId) systems:
                ---------------------------------
                Channel separation - the fixed difference between transmit 
                and receive frequency.
                
                Only three values are allowed: s1232MHz(1), s1200MHz,
                and s1008MHz.  
                
                This value is used to automatically calculate the receive 
                frequency, when the transmit frequency is entered.
                
                Default value:  s1232Mhz(1)
                
                
                5.7Ghz family (sysObjId) systems:
                ---------------------------------
                Not used.  ( Internally fixed at 475MHz fixed ).
                
                Default value:  na(0)"
            ::= { wtnConfigEntry 7 }
        
-- 
        wtnRadioAmplifiersEnable OBJECT-TYPE
            SYNTAX TruthValue
            MAX-ACCESS read-write
            STATUS current
            DESCRIPTION
                "true(1) - Enables amplifiers for transmitter and receiver.
                The radio will begin transmitting and receiving data.  If the ODU
                is looped back, unable to lock onto a signal, or the ODU equipment 
                has failed, the enable command will return an error trap and 
                the amplifier enable state will transition to disableAmplifiers(2).
                
                
                false(2) - shuts down the transmit and receive amplifiers of the ODU.
                This will cause the link to go down.  Payload will be dropped.
                
                
                When the amplifiers are turned off, the active and standby 
                channel assignments may be freely changed, if necessary, 
                but notification of such changes to the far end will not be done 
                automatically.  That is, channel assignments made when the 
                amplifiers are disabled must be done manually at each node - 
                near end and far end.
                
                Default value after power up is false(2).
                
                "
            ::= { wtnConfigEntry 8 }
        
-- 
        wtnRxBERThresh OBJECT-TYPE
            SYNTAX SkyZhoneScientificNotation
            MAX-ACCESS read-write
            STATUS current
            DESCRIPTION
                "Set point of BER alarm.  When the modem BER estimate
                is higher than this value, a modem BER alarm will occur.
                The BER over threshold Causes trap wtnBerAlarm to be emitted.
                The alarm will stay present until the modem BER estimate
                is lower than this set point less the hysteresis window
                wtnMdmRxBERHysteresisWindow.
                
                A value of 0 disables the BER threshold alarm.
                
                Allowed range is 1.0e-1 to 1.0e-12.
                
                
                BER is assumed accumulated over a second."
            ::= { wtnConfigEntry 9 }
        
-- 
        wtnRxBERHysteresisWindow OBJECT-TYPE
            SYNTAX SkyZhoneScientificNotation
            MAX-ACCESS read-write
            STATUS current
            DESCRIPTION
                "After a wtnBerAlarm trap is sent, it is revoked using the same trap with
                the condition flag set to false when the modem BER estimate is lower 
                than the set point wtnModemRxBERThresh less this value.
                
                Valid values are 0, and the range from 1.0e-1 to 1.0e-12.
                
                A value of 0 indicates no hysteresis.
                
                BER is assumed accumulated over the last second."
            ::= { wtnConfigEntry 10 }
        
-- 
        wtnAntennaSize OBJECT-TYPE
            SYNTAX INTEGER
                {
                oneFoot(1),
                twoFeet(2),
                fourFeet(4),
                sixFeet(6)
                }
            UNITS "feet"
            MAX-ACCESS read-write
            STATUS current
            DESCRIPTION
                "Initial power of transmitter is based upon antenna diameter.
                
                oneFoot(1) - a one foot dish
                twoFeet(2) - a two foot dish
                fourFeet(4) - a four foot dish
                sixFeet(6) - a six foot dish
                
                FCC mandates a maximimum EIRP (Effective Isotropic
                Radiated Power) level, which is directly dependent
                upon antenna size.
                
                The system will use antenna size to determine a 
                power level in accordance to maxmimum EIRP.
                
                5.7Ghz family
                -------------------
                The equipment is shipped with a dish that
                is one of 3 sizes:
                
                twoFeet(2) - a two foot dish
                fourFeet(4) - a four foot dish
                sixFeet(6) - a six foot dish
                
                Default value sixFeet(3).
                
                
                23Ghz family
                -------------------
                The equipment is shipped with a dish that
                is one of 2 sizes:
                
                oneFoot(1) - a one foot dish
                twoFeet(2) - a two foot dish
                
                Default value: twoFeet(2).
                
                "
            DEFVAL { sixFeet }
            ::= { wtnConfigEntry 11 }
        
-- 
        wtnIduOduCableLength OBJECT-TYPE
            SYNTAX Integer32 (0..300)
            UNITS "feet"
            MAX-ACCESS read-write
            STATUS current
            DESCRIPTION
                "The length of the coaxial cable between the Indoor
                Unit and the Outdoor Unit.
                
                Used internally to compensate for the coaxial cable's
                natural attenuation of the signal.
                
                This cable is cut to its appropriate length when the system 
                is installed.
                
                Default value:  0 feet."
            DEFVAL { 0 }
            ::= { wtnConfigEntry 12 }
        
        wtnRssiThresh OBJECT-TYPE
            SYNTAX Integer32 (-99..-30)
            UNITS "dB"
            MAX-ACCESS read-write
            STATUS current
            DESCRIPTION
                "Set point of RSSI thresholdalarm.  When the ODU RSSI estimate
                is lower than this value, a wtnRssiDeviation trap will be emitted.
                When the ODU RSSI estimate is higher than this set point 
                plus the hysteresis window wtnOduRxRSSIHysteresisWindow, the same
                trap will be re-emitted with condition = false..
                
                
                Receive signal strength (RSSI) reported by near end 
                ODU.
                
                Typical values range from -95dB to -30dB.
                Tyipcal nominal value is -60dB."
            DEFVAL { -80 }
            ::= { wtnConfigEntry 13 }
        
-- 
        wtnRssiHysteresisWindow OBJECT-TYPE
            SYNTAX Integer32
            UNITS "dB"
            MAX-ACCESS read-write
            STATUS current
            DESCRIPTION
                "After a wtnRssiDeviation Trap is sent, an the trap is re-emitted
                with the condition flag set to false when the ODU RSSI 
                estimate is higher than the set point wtnOduRxRSSIThresh plus this value.
                
                Typical value of window size is 10dB."
            DEFVAL { 10 }
            ::= { wtnConfigEntry 14 }
        
-- 
        wtnTrapsEnable OBJECT-TYPE
            SYNTAX TruthValue
            MAX-ACCESS read-write
            STATUS current
            DESCRIPTION
                "When true(1), radio traps may be emitted.
                When false(2), radio traps will be absorbed.
                
                Default value is true(1) = enabled."
            ::= { wtnConfigEntry 15 }
        
        wtnOduLoopback OBJECT-TYPE
            SYNTAX INTEGER
                {
                loopbackOn(1),
                loopbackOff(2)
                }
            MAX-ACCESS read-write
            STATUS current
            DESCRIPTION
                "loopbackOn(1) - engages the loopback function at the ODU (outdoor unit).
                Data normally transmitted by the radio is instead returned to the IDU
                (indoor unit).  This is useful to check the integrity of the IDU, the
                integrity of the cable connecting IDU to ODU, and of some portions
                of ODU circuitry.  
                ifAdminStatus must be in 'testing' mode for loopbackOn to be accepted.
                Once the loopback is turned on verify that there is no radio alarm
                condition.  Also, any line data received on the line interface 
                (DS3, STM-1, E1, etc) will be looped back and transmitted to it.
                
                
                loopbackOff(2) - disengages the loopback function at the ODU.
                Causes the radio to re-acquire the signal from the far end, if any."
            ::= { wtnConfigEntry 16 }
        
-- 
        wtnOduIdentifier OBJECT-TYPE
            SYNTAX SnmpAdminString
            MAX-ACCESS read-write
            STATUS current
            DESCRIPTION
                "Textual description of ODU.
                This string typically identifies the location of antenna."
            ::= { wtnConfigEntry 17 }
        
-- 
        wtnTxLevel OBJECT-TYPE
            SYNTAX Integer32 (0..45)
            UNITS "dB"
            MAX-ACCESS read-write
            STATUS current
            DESCRIPTION
                "Desired transmitter signal strength (TSSI) at antenna.
                Note:  Accuracy decreases as power levels decrease below 20dBm.
                FCC maximum power allowed is +30dBm. "
            DEFVAL { 0 }
            ::= { wtnConfigEntry 18 }
        
        wtnStatusTable OBJECT-TYPE
            SYNTAX SEQUENCE OF WtnStatusEntry
            MAX-ACCESS not-accessible
            STATUS current
            DESCRIPTION
                "Contains the status of the Radio, ODU and Modem."
            ::= { zhoneRadio 2 }
        
        wtnStatusEntry OBJECT-TYPE
            SYNTAX WtnStatusEntry
            MAX-ACCESS not-accessible
            STATUS current
            DESCRIPTION
                "Entries for radio, ODU and modem status."
            AUGMENTS { wtnConfigEntry }
            ::= { wtnStatusTable 1 }
        
        WtnStatusEntry ::=
            SEQUENCE { 
                wtnCriticalAlarmStatus
                    BITS,
                wtnCriticalAlarmStatusLastChange
                    TimeStamp,
                wtnMinorAlarmStatus
                    BITS,
                wtnMinorAlarmStatusLastChange
                    TimeStamp,
                wtnOduTemperature
                    Integer32,
                wtnReceiveFrequency
                    SkyZhoneScientificNotation
             }

-- 
        wtnCriticalAlarmStatus OBJECT-TYPE
            SYNTAX BITS
                {
                rssiDeviation(0),
                iduOOL(1),
                oduTempAlert(2),
                rxBerAlarm(3),
                rxEbnoAlarm(4),
                unused5(5),
                unused6(6),
                unused7(7),
                iduEquipFail(8),
                oduEquipFail(9),
                iduOduLinkFail(10),
                mcChannelFail(11),
                unused12(12),
                unused13(13),
                unused14(14),
                serviceAffected(15)
                }
            MAX-ACCESS read-only
            STATUS current
            DESCRIPTION
                "Current radio alarm status details.  
                
                
                BIT     Hex     Decimal BIT NAME
                Number  Value   Value	
                ------  ------  ------- ----------------------
                0       0x01    1       RSSI_DEVIATION
                1       0x02    2       IDU_OOL
                2       0x04    4       ODU_TEMP_ALERT
                3       0x08    8       RX_BER_ALARM
                4       0x10    16      RX_EBNO_ALARM
                5       0x20    32      (reserved)
                6       0x40    64      (reserved)
                7       0x80    128     (reserved)
                8       0x100   256     IDU_EQUIP_FAIL
                9       0x200   512     ODU_EQUIP_FAIL
                10      0x400   1024    IDU_ODU_LINK_FAIL
                11      0x800   2048    MC_CHANNEL_FAIL
                12      0x1000  4096    (reserved)
                13      0x2000  8192    (reserved)
                14      0x4000  16384   (reserved)
                15      0x8000  32768   SERVICE_AFFECTED
                
                IDU_EQUIP_FAIL - can be caused by:
                power supply failure, watchdog timeout, or other internal
                failure on indoor unit.
                
                IDU_ODU_LINK_FAIL - can be caused by:
                IDU/ODU cable failure, bad connection, or equipment failure
                
                IDU_OOL - can be caused by:
                intermittent loss of lock of internal clocks
                
                MC_CHANNEL_FAIL - can be caused by:
                Signal path (air) degradation, or internal equipment failure 
                on near end or far end node.
                
                ODU_EQUIP_FAIL - can be caused by:
                Loss of frequency lock, loss of clock reference, power fault, 
                excessive transmitter power, signal path degradation, 
                frequency drift, or internal failure of equipment in outdoor
                unit.
                
                ODU_TEMP_ALERT - can be caused by:
                Operating temperature too high or too low.   Allowable range
                of operating temperatures ( in ODU ) are -40C to +65C.
                
                RSSI_DEVIATION - can be caused by:
                signal path (air) degradation, excessive heat buildup at ODU,
                or frequency drift.
                
                RX_BER_ALARM - can be caused by:
                RF noise burst, fade burst, interference, or internal equipment 
                failure.
                
                RX_EBNO_ALARM - can be caused by:
                Fade, noise burst, or internal equipment stress.
                
                SERVICE_AFFECTED - indicates a predicted loss of data 
                or quality of service in transport due to any of the 
                above conditions."
            ::= { wtnStatusEntry 1 }
        
        wtnCriticalAlarmStatusLastChange OBJECT-TYPE
            SYNTAX TimeStamp
            MAX-ACCESS read-only
            STATUS current
            DESCRIPTION
                "Time Stamp of last change of critical alarm status
                wtnRadioCriticalAlmStatus.  "
            ::= { wtnStatusEntry 2 }
        
        wtnMinorAlarmStatus OBJECT-TYPE
            SYNTAX BITS
                {
                rssiDeviation(0),
                iduOOL(1),
                oduTempAlert(2),
                rxBerAlarm(3),
                rxEbnoAlarm(4),
                unused5(5),
                unused6(6),
                unused7(7),
                iduEquipFail(8),
                oduEquipFail(9),
                iduOduLinkFail(10),
                mcChannelFail(11),
                unused12(12),
                unused13(13),
                unused14(14),
                serviceAffected(15)
                }
            MAX-ACCESS read-only
            STATUS current
            DESCRIPTION
                "Current radio alarm status details.  
                
                BIT     Hex     Decimal BIT NAME
                Number  Value   Value	
                ------  ------  ------- ----------------------
                0       0x01    1       RSSI_DEVIATION
                1       0x02    2       IDU_OOL
                2       0x04    4       ODU_TEMP_ALERT
                3       0x08    8       RX_BER_ALARM
                4       0x10    16      RX_EBNO_ALARM
                5       0x20    32      (reserved)
                6       0x40    64      (reserved)
                7       0x80    128     (reserved)
                8       0x100   256     IDU_EQUIP_FAIL
                9       0x200   512     ODU_EQUIP_FAIL
                10      0x400   1024    IDU_ODU_LINK_FAIL
                11      0x800   2048    MC_CHANNEL_FAIL
                12      0x1000  4096    (reserved)
                13      0x2000  8192    (reserved)
                14      0x4000  16384   (reserved)
                15      0x8000  32768   SERVICE_AFFECTED
                
                IDU_EQUIP_FAIL - can be caused by:
                power supply failure, watchdog timeout, or other internal
                failure on indoor unit.
                
                IDU_ODU_LINK_FAIL - can be caused by:
                IDU/ODU cable failure, bad connection, or equipment failure
                
                IDU_OOL - can be caused by:
                intermittent loss of lock of internal clocks
                
                MC_CHANNEL_FAIL - can be caused by:
                Signal path (air) degradation, or internal equipment failure 
                on near end or far end node.
                
                ODU_EQUIP_FAIL - can be caused by:
                Loss of frequency lock, loss of clock reference, power fault, 
                excessive transmitter power, signal path degradation, 
                frequency drift, or internal failure of equipment in outdoor
                unit.
                
                ODU_TEMP_ALERT - can be caused by:
                Operating temperature too high or too low.   Allowable range
                of operating temperatures ( in ODU ) are -40C to +65C.
                
                RSSI_DEVIATION - can be caused by:
                signal path (air) degradation, excessive heat buildup at ODU,
                or frequency drift.
                
                RX_BER_ALARM - can be caused by:
                RF noise burst, fade burst, interference, or internal equipment 
                failure.
                
                RX_EBNO_ALARM - can be caused by:
                Fade, noise burst, or internal equipment stress.
                
                
                The SERVICE_AFFECTING bit should always = 0 on this variable
                because, by definition, minor alarms may not affect service.
                "
            ::= { wtnStatusEntry 3 }
        
        wtnMinorAlarmStatusLastChange OBJECT-TYPE
            SYNTAX TimeStamp
            MAX-ACCESS read-only
            STATUS current
            DESCRIPTION
                "Time Stamp of last change of minor alarm status 
                wtnRadioMinorAlmStatus."
            ::= { wtnStatusEntry 4 }
        
-- 
        wtnOduTemperature OBJECT-TYPE
            SYNTAX Integer32
            MAX-ACCESS read-only
            STATUS current
            DESCRIPTION
                "Current temperature measured at local outdoor unit, in 
                degrees Celsius (Centigrade)."
            ::= { wtnStatusEntry 5 }
        
        wtnReceiveFrequency OBJECT-TYPE
            SYNTAX SkyZhoneScientificNotation
            UNITS "Hz"
            MAX-ACCESS read-only
            STATUS current
            DESCRIPTION
                "Current frequency at which radio receiver is set."
            ::= { wtnStatusEntry 6 }
        
        wtnInfoTable OBJECT-TYPE
            SYNTAX SEQUENCE OF WtnInfoEntry
            MAX-ACCESS not-accessible
            STATUS current
            DESCRIPTION
                "Table augments the wtnConfigTable"
            ::= { zhoneRadio 3 }
        
        wtnInfoEntry OBJECT-TYPE
            SYNTAX WtnInfoEntry
            MAX-ACCESS not-accessible
            STATUS current
            DESCRIPTION
                "Device information entries for the radio, modem and ODU."
            AUGMENTS { wtnConfigEntry }
            ::= { wtnInfoTable 1 }
        
        WtnInfoEntry ::=
            SEQUENCE { 
                wtnOduSerialNumber
                    ZhoneAdminString,
                wtnOduMfgCLEICode
                    ZhoneAdminString
             }

-- 
        wtnOduSerialNumber OBJECT-TYPE
            SYNTAX ZhoneAdminString
            MAX-ACCESS read-only
            STATUS current
            DESCRIPTION
                "Manufacturing Serial Number for Outdoor Unit.
                Format of the serial number is XXXXX, where X = 0 to F."
            ::= { wtnInfoEntry 1 }
        
-- 
        wtnOduMfgCLEICode OBJECT-TYPE
            SYNTAX ZhoneAdminString
            MAX-ACCESS read-only
            STATUS current
            DESCRIPTION
                "CLEI code for Outdoor Unit."
            ::= { wtnInfoEntry 2 }
        
        wtnSnapshotTable OBJECT-TYPE
            SYNTAX SEQUENCE OF WtnSnapshotEntry
            MAX-ACCESS not-accessible
            STATUS current
            DESCRIPTION
                "Table to collect statistics at radio demodulator of 
                wireless transport node."
            ::= { zhoneRadio 4 }
        
        wtnSnapshotEntry OBJECT-TYPE
            SYNTAX WtnSnapshotEntry
            MAX-ACCESS not-accessible
            STATUS current
            DESCRIPTION
                "Entry into wireless transport local radio status table.
                No rows may be added to this table."
            AUGMENTS { wtnConfigEntry }
            ::= { wtnSnapshotTable 1 }
        
        WtnSnapshotEntry ::=
            SEQUENCE { 
                wtnRSSI
                    Integer32,
                wtnTSSI
                    Integer32,
                wtnRxBerFloat
                    SkyZhoneScientificNotation,
                wtnRcvEbNoFloat
                    SkyZhoneScientificNotation
             }

-- 
        wtnRSSI OBJECT-TYPE
            SYNTAX Integer32 (-90..0)
            UNITS "dBm"
            MAX-ACCESS read-only
            STATUS current
            DESCRIPTION
                "Current Received Signal Strength in dB as registered at 
                the near end Outdoor Unit.  This number is updated about once per 
                second.
                
                Typical values range from -95dB to -30dB.
                Tyipcal nominal value is -60dB."
            ::= { wtnSnapshotEntry 1 }
        
        wtnTSSI OBJECT-TYPE
            SYNTAX Integer32 (0..45)
            UNITS "dBm"
            MAX-ACCESS read-only
            STATUS current
            DESCRIPTION
                "Estimated transmitter signal strength (TSSI) at antenna.
                Note: maximum level allowed by FCC is 30dBm."
            ::= { wtnSnapshotEntry 2 }
        
-- 
        wtnRxBerFloat OBJECT-TYPE
            SYNTAX SkyZhoneScientificNotation
            MAX-ACCESS read-only
            STATUS current
            DESCRIPTION
                "Current received BER at local Indoor Unit demodulator over 
                the previous 250ms."
            ::= { wtnSnapshotEntry 3 }
        
-- 
        wtnRcvEbNoFloat OBJECT-TYPE
            SYNTAX SkyZhoneScientificNotation
            MAX-ACCESS read-only
            STATUS current
            DESCRIPTION
                "Current local demodulator (rcvd) Energy-bit per noise.  
                Conveys energy in each bit as compared to energy in noise."
            ::= { wtnSnapshotEntry 4 }
        
        wtnTrapData OBJECT IDENTIFIER ::= { zhoneRadio 5 }
        
        wtnTraps OBJECT IDENTIFIER ::= { wtnTrapData 0 }
        
        wtnIduEquipFailCritical NOTIFICATION-TYPE
            OBJECTS { wtnTrapCondition, wtnServiceAffected }
            STATUS current
            DESCRIPTION
                "Critical indoor equipment failure trap.
                Can be caused by:
                power supply failure, watchdog timeout, or other internal
                failure on indoor unit."
            ::= { wtnTraps 1 }
        
        wtnIduEquipFail NOTIFICATION-TYPE
            OBJECTS { wtnTrapCondition, wtnServiceAffected }
            STATUS current
            DESCRIPTION
                "Non-critical indoor equipment failure trap.
                Can be caused by:
                spurious power supply failure, 
                or other temporary internal failure on indoor unit."
            ::= { wtnTraps 2 }
        
        wtnIduOduLinkFailCritical  NOTIFICATION-TYPE
            OBJECTS { wtnTrapCondition, wtnServiceAffected }
            STATUS current
            DESCRIPTION
                "Critical failure of IDU to ODU communications link trap.
                can be caused by:
                IDU/ODU cable failure, 
                bad connection, or 
                equipment failure."
            ::= { wtnTraps 3 }
        
        wtnIduOduLinkFail  NOTIFICATION-TYPE
            OBJECTS { wtnTrapCondition, wtnServiceAffected }
            STATUS current
            DESCRIPTION
                "Intermittent failure of IDU to ODU communications link trap.
                can be caused by:
                IDU/ODU cable failure, 
                bad connection, 
                or spurious equipment failure."
            ::= { wtnTraps 4 }
        
        wtnIduOutOfLockCritical  NOTIFICATION-TYPE
            OBJECTS { wtnTrapCondition, wtnServiceAffected }
            STATUS current
            DESCRIPTION
                "Permanent or persistant loss of lock of internal clocks 
                in indoor unit."
            ::= { wtnTraps 5 }
        
        wtnIduOutOfLock NOTIFICATION-TYPE
            OBJECTS { wtnTrapCondition, wtnServiceAffected }
            STATUS current
            DESCRIPTION
                "Spurious or intermittant loss of lock of internal 
                clocks in indoor unit."
            ::= { wtnTraps 6 }
        
        wtnMcChannelFailCritical  NOTIFICATION-TYPE
            OBJECTS { wtnTrapCondition, wtnServiceAffected }
            STATUS current
            DESCRIPTION
                "Radio overhead channel failure trap. May be caused by 
                signal path degradation, or equipment failure on local or
                far end node."
            ::= { wtnTraps 7 }
        
        wtnMcChannelFail  NOTIFICATION-TYPE
            OBJECTS { wtnTrapCondition, wtnServiceAffected }
            STATUS current
            DESCRIPTION
                "Spurious or intermittant radio overhead channel failure trap.  
                May be caused by signal path degradation
                or equipment failure on local or
                far end node."
            ::= { wtnTraps 8 }
        
        wtnOduEquipFailCritical NOTIFICATION-TYPE
            OBJECTS { wtnTrapCondition, wtnServiceAffected }
            STATUS current
            DESCRIPTION
                "Critical ODU hardware failure trap.  Possible causes:
                Synthesizer has lost desired frequency.
                Could be loss of reference signal from IDU or hardware error.  
                Synthesizer hardware fault.
                Possible component fault."
            ::= { wtnTraps 9 }
        
        wtnOduEquipFail NOTIFICATION-TYPE
            OBJECTS { wtnTrapCondition, wtnServiceAffected }
            STATUS current
            DESCRIPTION
                "Spurious or intermittant ODU hardware failure trap.  
                Could be loss of reference signal from IDU or hardware error.  "
            ::= { wtnTraps 10 }
        
        wtnOduTempAlertCritical  NOTIFICATION-TYPE
            OBJECTS { wtnTrapCondition, wtnServiceAffected }
            STATUS current
            DESCRIPTION
                "Significant deviation of ODU temperature from specified limits  
                May be power amp heating up or environment heat buildup, or
                environment ice or frost."
            ::= { wtnTraps 11 }
        
        wtnOduTempAlert NOTIFICATION-TYPE
            OBJECTS { wtnTrapCondition, wtnServiceAffected }
            STATUS current
            DESCRIPTION
                "Warning to indicate that ODU is approaching a significant 
                deviation of ODU temperature from specified limits. 
                May be power amp heating up or environment heat buildup, or
                environment ice or frost."
            ::= { wtnTraps 12 }
        
        wtnRSSIDeviation  NOTIFICATION-TYPE
            OBJECTS { wtnTrapCondition, wtnServiceAffected }
            STATUS current
            DESCRIPTION
                "Receive signal strength at the odu is lower (in dB) than wtnOduRxRSSIThresh.  
                This alarm will persist until the RSSI rises above wtnOduRxRSSIThresh - wtnOduRxRssiHysteresisWindow.
                
                May be from signal path degradation.  
                May be power amp heating up or environment heat buildup. "
            ::= { wtnTraps 13 }
        
        wtnBerAlarm NOTIFICATION-TYPE
            OBJECTS { wtnTrapCondition, wtnServiceAffected }
            STATUS current
            DESCRIPTION
                "Modem reports temporary BER > threshold alarm. 
                Condition is true when current BER > wtnMdmRxBERThresh.
                Condition will persist until current BER < ( wtnMdmRxBERThresh - wtnMdmRxBERHysteresisWindow ).
                
                Probable fade burst.  
                Could be interference.  
                Could be incipient hardware fault"
            ::= { wtnTraps 14 }
        
        wtnEbNoAlarm NOTIFICATION-TYPE
            OBJECTS { wtnTrapCondition, wtnServiceAffected }
            STATUS current
            DESCRIPTION
                "Modem reports temporary post-detection signal to noise ratio 
                below preset threshold   wtnMdmRxEbNoThresh.
                
                This condition will persist until the radio signal quality
                rises above wtnMdmRxEbNoThresh - wtnMdmRxEbnoHysteresisWindow.
                
                Probable fade or noise burst."
            ::= { wtnTraps 15 }
        
        wtnTrapCondition OBJECT-TYPE
            SYNTAX INTEGER
                {
                conditionPresent(1),
                conditionCleared(2)
                }
            MAX-ACCESS accessible-for-notify
            STATUS current
            DESCRIPTION
                "Sent with wireless traps to indicate whether condition has 
                arrived or has gone away."
            ::= { wtnTrapData 1 }
        
        wtnServiceAffected OBJECT-TYPE
            SYNTAX INTEGER
                {
                serviceAffected(1),
                serviceNotAffected(2)
                }
            MAX-ACCESS accessible-for-notify
            STATUS current
            DESCRIPTION
                "Flag sent with each trap to indicate whether service may be 
                affected by this particular trap condition.
                
                Service affecting means that payload data (DS3, etc)
                MAY be affected.  Since a node does not have visibility
                into the payloads this flag is determined by contingencies 
                such as signal quality measurements and introspective
                hardware.
                
                
                This flag should be ignored when the trap is sent to indicate the 
                trap condition has gone away."
            ::= { wtnTrapData 2 }
        
        radioTotalTable OBJECT-TYPE
            SYNTAX SEQUENCE OF RadioTotalEntry
            MAX-ACCESS not-accessible
            STATUS current
            DESCRIPTION
                "Table of current statistics in the style of rfc2493 current table."
            ::= { zhoneRadio 6 }
        
        radioTotalEntry OBJECT-TYPE
            SYNTAX RadioTotalEntry
            MAX-ACCESS not-accessible
            STATUS current
            DESCRIPTION
                "Set of basic statistics for radio interface."
            AUGMENTS { wtnConfigEntry }
            ::= { radioTotalTable 1 }
        
        RadioTotalEntry ::=
            SEQUENCE { 
                radioTotalES
                    Gauge32,
                radioTotalSES
                    Gauge32,
                radioTotalUAS
                    Gauge32
             }

        radioTotalES OBJECT-TYPE
            SYNTAX Gauge32
            MAX-ACCESS read-write
            STATUS current
            DESCRIPTION
                "Number of seconds the radio link detected bit errors since
                the system has been up, or since last reset.   
                
                If the BER is above the 
                user set threshhold then the readioCurrentSES count will be 
                incremented instead of this one.  If the radio link is down
                or a loss of signal is declared this count will not be
                incremented.
                
                Writing any value to this counter will reset the count."
            ::= { radioTotalEntry 1 }
        
        radioTotalSES OBJECT-TYPE
            SYNTAX Gauge32
            MAX-ACCESS read-write
            STATUS current
            DESCRIPTION
                "Count of the number of seconds the radio endured severe conditions 
                since system came up or value was reset.  
                
                A severe condition occurs if:
                1 - received BER is greater exceeds the BER threshold and has not yet 
                dropped below the BER hysteresis window.
                2-  radio link failure.  Radio signal cannot be detected.
                
                Writing any value to this counter will reset the count."
            ::= { radioTotalEntry 2 }
        
        radioTotalUAS OBJECT-TYPE
            SYNTAX Gauge32
            MAX-ACCESS read-write
            STATUS current
            DESCRIPTION
                "Unavailable seconds.  This value is incremented once per second after
                ten consecutive radioCurrentSES (severe-error seconds) are counted.  
                An equipment failure will also increment this value.
                
                Writing any value will cause the count to be reset."
            ::= { radioTotalEntry 3 }
        
    
    END

--
-- phyWtnRadio.mib
--
