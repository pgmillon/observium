NTNTECH-NMS-TRAPS-V1-MIB DEFINITIONS ::= BEGIN    

--	**************************************************************   
--  Enterprise:
--   	Paradyne Corporation.    
--
--  ContactInfo:
--    	Paradyne Corporation
--     	8545 126th Avenue North
--     	Largo, FL 33773
--     	phone: +1 (727) 530 2000
--     	email: support@paradyne.com 
--		www:   http://www.nettonet.com/support/
--
--  Description:
--    	ntntech-nms-traps-MIB.my
--    	Revision: 1.02.02
--    	Part Number: xx-xxxx-xx
--    	Date: November 17, 2004

--    
--    	This module provides explicit definitions for the Net to
--		Net Technologies naming	tree below:
--    
--    	nettonettech { enterprises 8059 }
--    
--    	This module will be extended, as additional sub-sections
--    	of this naming tree are defined.
--
--  Disclaimer:
--	   	This is an extremely preliminary MIB module and is subject
--		to change at any time therefore, use at your own risk.
--    
-- 	Copyright (c) 2000 - 2004 by Paradyne Corporation.
-- 	All rights reserved.          

-- **************************************************************
IMPORTS  
	ntntechNMSTraps						FROM NTNTECH-ROOT-MIB 	
	mumStaFanState					  	FROM NTNTECH-CHASSIS-STATUS-MIB  
	ifStaSlotIndex, ifStaType 			FROM NTNTECH-INTERFACE-MODULE-STATUS-MIB     
   	OBJECT-TYPE		 					FROM RFC-1212
   	TRAP-TYPE			    			FROM RFC-1215;
-- **************************************************************        
          
    envFanTrap-v1      TRAP-TYPE
          ENTERPRISE ntntechNMSTraps
          VARIABLES { mumStaFanState }
          DESCRIPTION
          "There has been a change in the Fan state." 
      	  ::= 1001
      	  
    envTempNormal-v1 TRAP-TYPE
          ENTERPRISE ntntechNMSTraps
          DESCRIPTION
          "The normal operating temperature inside the chassis has returned.
        
          Note: This trap applies to the micro DSLAMs only."
          ::= 1002
     	  
    envTempExceeded-v1 TRAP-TYPE
          ENTERPRISE ntntechNMSTraps
          DESCRIPTION
          "The normal operating temperature inside the chassis has been exceeded.
        
          Note: This trap applies to the micro DSLAMs only."
          ::= 1003

    invIfModPresentTrap-v1     TRAP-TYPE
          ENTERPRISE ntntechNMSTraps
          VARIABLES { ifStaSlotIndex, ifStaType }
          DESCRIPTION
          "A change was detected related to the population state of a chassis slot. This
          trap will be triggered when the population state of a slot makes the transition
          from vacant to present, where present is any valid interface module type as
          defined by 'ifStaType'."
      	  ::= 2001
      	  
    invIfModRemovedTrap-v1      TRAP-TYPE
          ENTERPRISE ntntechNMSTraps
          VARIABLES { ifStaSlotIndex, ifStaType }
          DESCRIPTION
          "A change was detected related to the population state of a chassis slot. This
          trap will be triggered when the population state of a slot makes the transition
          from present, to vacant. In otherwords, this trap will be triggered if an interface
          module of type 'a' is immediately replaced with one of type 'b' or 40 seconds after
          an interface module is removed leaving the slot vacant."
      	  ::= 2002
      	  
END
