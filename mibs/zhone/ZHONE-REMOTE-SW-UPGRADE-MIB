--
-- remoteSwUpgrade.mib
-- MIB generated by MG-SOFT Visual MIB Builder Version 3.0 Build 285
-- Wednesday, July 01, 2009 at 07:45:52
--

	ZHONE-REMOTE-SW-UPGRADE-MIB DEFINITIONS ::= BEGIN
 
		IMPORTS
			OBJECT-GROUP			
				FROM SNMPv2-CONF			
			Integer32, Unsigned32, OBJECT-TYPE, MODULE-IDENTITY			
				FROM SNMPv2-SMI			
			TruthValue			
				FROM SNMPv2-TC			
			zhone, zhoneModules			
				FROM Zhone			
			ZhoneRowStatus			
				FROM Zhone-TC;
	
	
-- The markup shown in this mib was used to generate the Remote Software
-- Upgrade profile and the supporting PL code. 
--  
-- CFG -----------------------------------------------------------------
-- 
-- BUILD --------------------------------------------------------------
-- 
-- To generate MIB handler:
-- /vob/EPILOGUE/binaries/emissary/solaris/mibcomp rfc1907.mib iftype.mib rfc2233.mib Zhone.mib Zhone-TC.mib -stub -o remoteSwUpgradeProfileMibHdlr.c remoteSwUpgrade.mib
-- 
-- To generate .c, .h, and CSS files:
-- /vob/zhonetools/bin/pahrser.pl -css rfc2233.mib Zhone.mib Zhone-TC.mib remoteSwUpgrade.mib
--  
		-- 1.3.6.1.4.1.5504.6.117
		zhoneRemoteSwUpgrade MODULE-IDENTITY 
			LAST-UPDATED "200808081113Z"		-- August 08, 2008 at 11:13 GMT
			ORGANIZATION 
				"Zhone Technologies, Inc."
			CONTACT-INFO 
				"Postal: 
				    Zhone Technologies, Inc.
				    @ Zhone Way
				    7001 Oakport Street
				    Oakland, CA  94621
				    USA
				Toll-Free: +1 877-ZHONE20 (+1 877-946-6320)
				      Tel: +1-510-777-7000
				      Fax: +1-510-777-7001
				   E-mail: support@zhone.com"
			DESCRIPTION 
				"This is the Zhone module identifier for the Zhone Auto Upgrade definition."
			REVISION "200907010745Z"		-- July 01, 2009 at 07:45 GMT
			DESCRIPTION 
				"Add zhoneRemoteSwUpgradeIndexNext object"
			REVISION "200906090833Z"		-- June 09, 2009 at 08:33 GMT
			DESCRIPTION 
				"Created"
			::= { zhoneModules 117 }

		
	
	
--
-- Node definitions
--
	
		-- 1.3.6.1.4.1.5504.6.117.1
		zhoneRemoteSwUpgradeTable OBJECT-TYPE
			SYNTAX SEQUENCE OF ZhoneRemoteSwUpgradeEntry
			MAX-ACCESS not-accessible
			STATUS current
			DESCRIPTION
				"Zhone extension table for Remote Software Upgrade configuration."
			::= { zhoneRemoteSwUpgrade 1 }

		
		-- 1.3.6.1.4.1.5504.6.117.1.1
		zhoneRemoteSwUpgradeEntry OBJECT-TYPE
			SYNTAX ZhoneRemoteSwUpgradeEntry
			MAX-ACCESS not-accessible
			STATUS current
			DESCRIPTION
				"Zhone extension entry Remote Software Upgrade configuration."
			INDEX { zhoneRemoteSwUpgradeIndex }
			::= { zhoneRemoteSwUpgradeTable 1 }

		
		ZhoneRemoteSwUpgradeEntry ::=
			SEQUENCE { 
				zhoneRemoteSwUpgradeIndex
					Integer32,
				zhoneRemoteSwUpgradeRowStatus
					ZhoneRowStatus,
				zhoneRemoteSwUpgradeEnabled
					TruthValue,
				zhoneRemoteSwUpgradeModel
					OCTET STRING,
				zhoneRemoteSwUpgradeSwVersion
					OCTET STRING,
				zhoneRemoteSwUpgradeFileName
					OCTET STRING
			 }

		-- 1.3.6.1.4.1.5504.6.117.1.1.1
		zhoneRemoteSwUpgradeIndex OBJECT-TYPE
			SYNTAX Integer32 (1..2147483647)
			MAX-ACCESS not-accessible
			STATUS current
			DESCRIPTION
				"Index for the conceptual row associating an entry from
				this table to a unique remote software upgrade instance."
			::= { zhoneRemoteSwUpgradeEntry 1 }

		
		-- 1.3.6.1.4.1.5504.6.117.1.1.2
		zhoneRemoteSwUpgradeRowStatus OBJECT-TYPE
			SYNTAX ZhoneRowStatus
			MAX-ACCESS read-write
			STATUS current
			DESCRIPTION
				"The row status for the port config table. "
			::= { zhoneRemoteSwUpgradeEntry 2 }

		
-- 
		-- 1.3.6.1.4.1.5504.6.117.1.1.3
		zhoneRemoteSwUpgradeEnabled OBJECT-TYPE
			SYNTAX TruthValue
			MAX-ACCESS read-write
			STATUS current
			DESCRIPTION
				"This object is used to enable or disable the profile.  When
				the profile is disabled all pending remote software upgrade
				operations will be cancelled but remote software operations
				in progress will continue."
			DEFVAL { true }
			::= { zhoneRemoteSwUpgradeEntry 3 }

		
-- 
		-- 1.3.6.1.4.1.5504.6.117.1.1.4
		zhoneRemoteSwUpgradeModel OBJECT-TYPE
			SYNTAX OCTET STRING (SIZE (0..31))
			MAX-ACCESS read-write
			STATUS current
			DESCRIPTION
				"Model number of device to upgrade.  This object is only
				writeable when the profile is created. "
			::= { zhoneRemoteSwUpgradeEntry 4 }

		
-- 
		-- 1.3.6.1.4.1.5504.6.117.1.1.5
		zhoneRemoteSwUpgradeSwVersion OBJECT-TYPE
			SYNTAX OCTET STRING (SIZE (0..31))
			MAX-ACCESS read-write
			STATUS current
			DESCRIPTION
				"Software version.  The software version of the model is 
				compared against this value during the upgrade process.
				Leading zeros and trailing spaces are ignored in the 
				upgrade process."
			::= { zhoneRemoteSwUpgradeEntry 5 }

		
		-- 1.3.6.1.4.1.5504.6.117.1.1.6
		zhoneRemoteSwUpgradeFileName OBJECT-TYPE
			SYNTAX OCTET STRING (SIZE (0..127))
			MAX-ACCESS read-write
			STATUS current
			DESCRIPTION
				"Name of file to download if the remote unit needs to
				be upgraded."
			::= { zhoneRemoteSwUpgradeEntry 6 }

		
		-- 1.3.6.1.4.1.5504.6.117.2
		zhoneRemoteSwUpgradeIndexNext OBJECT-TYPE
			SYNTAX Unsigned32
			MAX-ACCESS read-only
			STATUS current
			DESCRIPTION
				"Index of the next available Remote Software Upgrade profile."
			DEFVAL { 1 }
			::= { zhoneRemoteSwUpgrade 2 }

		
		-- 1.3.6.1.4.1.5504.9
		zhoneCompliances OBJECT IDENTIFIER ::= { zhone 9 }

		
		-- 1.3.6.1.4.1.5504.9.1
		zhoneGroups OBJECT IDENTIFIER ::= { zhoneCompliances 1 }

		
		-- 1.3.6.1.4.1.5504.9.1.30
		zhoneAutoUpgradeGroup OBJECT-GROUP
			OBJECTS { zhoneRemoteSwUpgradeModel, zhoneRemoteSwUpgradeSwVersion, zhoneRemoteSwUpgradeRowStatus, zhoneRemoteSwUpgradeIndexNext, zhoneRemoteSwUpgradeFileName, 
				zhoneRemoteSwUpgradeEnabled }
			STATUS current
			DESCRIPTION 
				"A collection of objects from zhoneRemoteSwUpgrade"
			::= { zhoneGroups 30 }

		
	
	END

--
-- remoteSwUpgrade.mib
--
