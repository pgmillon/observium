-- extracted from draft-ietf-ipcdn-pktc-signaling-06.txt

   PKTC-IETF-SIG-MIB DEFINITIONS ::= BEGIN 
    
   IMPORTS 
       MODULE-IDENTITY,  
       OBJECT-TYPE,  
       Integer32, 
       Unsigned32, 
       mib-2  
             FROM SNMPv2-SMI  
       InetAddressType, 
       InetAddress, 
       InetPortNumber  
             FROM INET-ADDRESS-MIB  
       TEXTUAL-CONVENTION,  
       RowStatus,  
       TruthValue  
             FROM SNMPv2-TC  
       OBJECT-GROUP,  
       MODULE-COMPLIANCE  
             FROM SNMPv2-CONF  
       SnmpAdminString  
             FROM SNMP-FRAMEWORK-MIB  
       ifIndex   
             FROM IF-MIB 
       Dscp 
             FROM DIFFSERV-DSCP-TC
       ietfDrafts                        
             FROM Zhone;
    
-- /vob/EPILOGUE/binaries/emissary/solaris/mibcomp rfc1907.mib iftype.mib rfc2233.mib 
--      rfc1213.mib -stub -o pktcSigMibHdlrs.c PKTC-SIG-MIB.mib
-- /vob/EPILOGUE/binaries/emissary/solaris/mibcomp rfc1907.mib iftype.mib rfc2233.mib 
--      rfc1213.mib -skel.h -o pktcSigMibHdlrs.h PKTC-SIG-MIB.mib
-- /vob/EPILOGUE/binaries/emissary/solaris/mibcomp rfc1907.mib iftype.mib rfc2233.mib 
--      rfc1213.mib -leaf -o pktcSigMibHdlrsLeaf.h PKTC-SIG-MIB.mib
--
-- /vob/zhonetools/bin/pahrser.pl INET-ADDRESS-MIB.mib rfc2571.mib rfc2233.mib 
--              rfc3289.mib Zhone.mib PKTC-SIG-MIB.mib
--
-- 
-- 
-- 
-- 
-- 
-- 
-- 
   pktcIetfSigMib MODULE-IDENTITY  
       LAST-UPDATED    "200409030000Z" -- September 3, 2004  
       ORGANIZATION    "IETF IPCDN Working Group"  
       CONTACT-INFO  
           "Gordon Beacham  
            Motorola Inc.  
            6450 Sequence Drive, Bldg. 1  
            San Diego, CA 92121, USA  
            Phone: +1 858-404-2335  
            Email: gordon.beacham@motorola.com  
    
            Sumanth Channabasappa 
            Alopa Networks Inc.  
            248, McCaslin Bvld #101,  
            Louisville, CO 80027, USA  
            Phone: +1 303-604-6595  
            Email: Sumanth@alopa.com  
    
            Satish Kumar Mudugere Eswaraiah  
            Texas Instruments India (P) Ltd.,  
            Golf view, Wind Tunnel Road   
            Murugesh Palya  
            Bangalore 560 017, INDIA  
            Phone:   +91 80 5269451  
            Email:  satish.kumar@ti.com  
    
       IETF IPCDN Working Group  
            General Discussion: ipcdn@ietf.org  
            Subscribe: http://www.ietf.org/mailman/listinfo/ipcdn  
            Archive: ftp://ftp.ietf.org/ietf-mail-archive/ipcdn  
            Co-Chair: Jean-Francois Mule, jf.mule@cablelabs.com 
            Co-Chair: Richard Woundy, Richard_Woundy@cable.comcast.com" 
    
       DESCRIPTION  
          "This MIB module supplies the basic management  
           object for the PacketCable and IPCablecom Signaling  
           protocols. This version of the MIB includes  
           common signaling and Network Call Signaling  
           (NCS) related signaling objects. 
    
           Copyright (C) The Internet Society (2004). This version of 
           this MIB module is part of RFC yyyy; see the RFC itself for 
           full legal notices." 
   -- RFC Ed: replace yyyy with actual RFC number and remove this note 
    
       REVISION                "200409030000Z" 
    
       DESCRIPTION 
          "Initial version, published as RFC yyyy." 
   -- RFC Ed: replace yyyy with actual RFC number and remove this note 
    
   ::= { ietfDrafts 5 }
   -- XXXXXXXXXXXXXXXXXXXXXXXXXXXXXXXXXXXXXXXXXXXXXXXXXXXXXXXXXXXX
   -- XXXXXXXXXXXX PLEASE READ THE FOLLOWING COMMENT XXXXXXXXXXXXX
   -- XXXXXXXXXXXXXXXXXXXXXXXXXXXXXXXXXXXXXXXXXXXXXXXXXXXXXXXXXXXX
   -- The previous line has to be deleted and the next line has to uncommented
   -- when PKTC-SIG-MIB becomes a standard.
   -- ::=  { mib-2 XXX } 
   --
   -- RFC Ed: replace XXX with IANA-assigned number and remove this 
   -- note 
    
   -- Textual Conventions 
    
   TenthdBm ::= TEXTUAL-CONVENTION 
       DISPLAY-HINT "d-1" 
       STATUS       current 
       DESCRIPTION 
           "This textual convention represents power levels that are 
            normally expressed in dBm. Units are in tenths of a dBm; 
            for example, -13.5 dBm will be represented as -135." 
       SYNTAX       Integer32 
    
   PktcCodecType ::= TEXTUAL-CONVENTION  
       STATUS       current  
       DESCRIPTION    
           " This textual convention defines various types of codecs 
             that MAY be supported. The description for each 
             enumeration is listed below: 
             Enumeration     Description 
             other           a defined codec not in the enumeration 
             unknown         a codec not defined in PacketCable 
             g729            ITU-T Recommendation G.722 
             reserved        for future use 
             g729E           ITU-T Recommendation G.729E 
             pcmu            Pulse Code Modulation u-law (PCMU) 
             g726at32        ITU-T Recommendation G.726-32 (32 kbit/s) 
             g728            ITU-T Recommendation G.728 
             pcma            Pulse Code Modulation a-law (PCMA) 
             g726at16        ITU-T Recommendation G.726-16 (16 kbit/s) 
             g726at24        ITU-T Recommendation G.726-24 (24 kbit/s) 
             g726at40        ITU-T Recommendation G.726-40 (40 kbit/s) 
             ilbc            internet low bit rate codec 
             bv16            BroadVoice16 
           . The list of codecs is consistent with the IETF 
             Real Time Transport Protocol (RTP) Profile registry and 
             the RTP Map Parameters Table in [PKT-SP-CODEC]. The 
             literal codec name for each codec is listed below: 
             Codec     Literal Codec Name 
             g729              G729 
             g729E             G729E 
             pcmu              PCMU 
             g726at32          G726-32 
             g728              G728 
             pcma              PCMA 
             g726at16          G726-16 
             g726at24          G726-24 
             g726at40          G726-40 
             ilbc              iLBC 
             bv16              BV16 
             The literal codec name is the second column of the table 
             with codec RTP Map Parameters. Literal Codec Name Column 
             contains the codec name used in the local connection 
             descriptor (LCD) of the NCS messages create connection 
             (CRCX)/modify connection (MDCX) and is also used to 
             identify the codec in the Call Management System (CMS) 
             Provisioning Specification. RTP Map Parameter Column of 
             the Table contains the string used in the media attribute 
             line (a=) of the session description protocol (SDP) 
             parameters in NCS messages." 
       SYNTAX INTEGER { 
                  other     (1), 
                  unknown   (2), 
                  g729      (3), 
                  reserved  (4), 
                  g729E     (5), 
                  pcmu      (6), 
                  g726at32  (7), 
                  g728      (8), 
                  pcma      (9), 
                  g726at16  (10), 
                  g726at24  (11), 
                  g726at40  (12), 
                  ilbc      (13), 
                  bv16      (14) 
       } 
    
   PktcRingCadence   ::= TEXTUAL-CONVENTION 
       STATUS        current 
       DESCRIPTION 
           "This object represents a ring cadence and repeatable 
            characteristics in a bit string format. The first two 
            octets of the bit string represent the length in bits of 
            the duration of the cadence (i.e., the number of bits that 
            follow the third octet). The first two octets MUST 
            represent a value between 1 and 264. Any other values MUST 
            be rejected. The bit count needs to be consistent with the 
            OCTET STRING's length. If there are unused octets, the SNMP 
            set MUST be rejected. If the length implied by the bit 
            count is greater than the OCTET STRING's length the SNMP 
            set MUST be rejected. The third octet is used to 
            represent repeatable characteristics. 00000000 means 
            repeatable, and 10000000 means non repeatable. The value of 
            the repeatable field MUST be 0x00 or 0x80. Each bit 
            after the third octet corresponds to 50 ms where 1 
            represents ring and 0 represents silence. The first bit of 
            the fourth octet is the first bit of the ring cadence. All 
            bits are counted in network order such that the octet with 
            only the first bit set will look like 10000000 bit 
            sequence. A total of 264 bits can be set to represent 
            13200 ms of total cadence cycle. There will be at most 3 
            on/off transitions per cadence cycle. If there are more 
            than three on-to-off transitions, the SNMP set MUST be 
            rejected." 
       SYNTAX  OCTET STRING (SIZE(4..36)) 
    
   PktcSigType     ::= TEXTUAL-CONVENTION 
       STATUS       current 
       DESCRIPTION 
           " This object lists the various types of signaling that may 
             be supported: 
             other û set when signaling other than ncs is used 
             reserved û for future use 
             ncs - Network call signaling is a derivation of MGCP 
                   (Media Gateway Control Protocol) defined for 
                   IPCablecom/PacketCable MTAs." 
       SYNTAX INTEGER {  
                      other(1), 
                      reserved(2), 
                      ncs(3) 
       }  
    
   pktcSigMibObjects OBJECT IDENTIFIER ::= { pktcIetfSigMib 1 } 
   pktcSigDevConfigObjects OBJECT IDENTIFIER ::= 
                                           { pktcSigMibObjects 1 } 
   pktcNcsEndPntConfigObjects OBJECT IDENTIFIER ::= 
                                           { pktcSigMibObjects 2 } 
   -- 
   -- The codec table (pktcSigDevCodecTable) defines all combinations 
   -- of codecs supported by the Multimedia Terminal Adapter (MTA). 
   -- 
   pktcSigDevCodecTable OBJECT-TYPE 
       SYNTAX      SEQUENCE OF PktcSigDevCodecEntry 
       MAX-ACCESS  not-accessible  
       STATUS      current  
       DESCRIPTION  
           " This table describes the MTA supported codec types. A MTA 
             MUST populate this table with all possible combinations of 
             codecs it supports for simultaneous operation. For 
             example, a MTA with two endpoints may be designed with a 
             particular DSP and memory architecture that allows it to 
             support the following fixed combinations of codecs for 
             simultaneous operation: 
    
             Codec Type     Maximum Number of Simultaneous Codecs 
             PCMA                             3 
    
             PCMA                             2 
             PCMU                             1 
    
             PCMA                             1 
             PCMU                             2 
    
             PCMU                             3 
    
             PCMA                             1 
             G729                             1 
    
             G729                             2 
    
             PCMU                             1 
             G729                             1 
    
             Based on this example, the entries in the codec table 
             would be: 
    
             CodecComboIndex pktcSigDevCodecType pktcSigDevCodecMax 
                    1               pcma                3 
                    2               pcma                2 
                    2               pcmu                1 
                    3               pcma                1 
                    3               pcmu                2 
                    4               pcmu                3 
                    5               pcma                1 
                    5               g729                1 
                    6               g729                2 
                    7               pcmu                1 
                    7               g729                1 
    
             An operator querying this table is able to determine all 
             possible codec combinations the MTA is capable of 
             simultaneously supporting." 
       ::= { pktcSigDevConfigObjects 1 } 
    
   pktcSigDevCodecEntry  OBJECT-TYPE  
       SYNTAX      PktcSigDevCodecEntry  
       MAX-ACCESS  not-accessible  
       STATUS      current  
       DESCRIPTION  
           "Each entry represents the maximum number of active 
            connections with a particular codec the MTA is capable of 
            supporting. Each row is indexed by a composite key 
            consisting of a number enumerating the particular codec 
            combination and the codec type."  
       INDEX { pktcSigDevCodecComboIndex, pktcSigDevCodecType }  
       ::= { pktcSigDevCodecTable 1 } 
    
   PktcSigDevCodecEntry  ::= SEQUENCE {  
       pktcSigDevCodecComboIndex    Unsigned32,  
       pktcSigDevCodecType     PktcCodecType,  
       pktcSigDevCodecMax      Unsigned32  
       }  
    
   pktcSigDevCodecComboIndex  OBJECT-TYPE  
       SYNTAX      Unsigned32 (1..255)  
       MAX-ACCESS  not-accessible  
       STATUS      current  
       DESCRIPTION  
           " The index value which enumerates a  particular codec 
             combination in the pktcSigDevCodecTable." 
       ::= { pktcSigDevCodecEntry 1 } 
    
   pktcSigDevCodecType  OBJECT-TYPE  
       SYNTAX       PktcCodecType       
       MAX-ACCESS   not-accessible  
       STATUS       current  
       DESCRIPTION  
           " A codec type supported by this MTA."  
       ::= { pktcSigDevCodecEntry 2 } 
    
   pktcSigDevCodecMax  OBJECT-TYPE  
       SYNTAX      Unsigned32(1..255)  
       MAX-ACCESS  read-only  
       STATUS      current  
       DESCRIPTION 
           " The maximum number of simultaneous sessions of a 
             particular codec that the MTA can support." 
       ::= { pktcSigDevCodecEntry 3 }  
    
   -- 
   -- These are the common signaling related definitions that affect 
   -- the entire MTA device. 
   -- 
    
   pktcSigDevEchoCancellation  OBJECT-TYPE  
       SYNTAX       TruthValue  
       MAX-ACCESS   read-only  
       STATUS       current  
       DESCRIPTION  
           " This object specifies if the device is capable of echo 
             cancellation."  
       ::= { pktcSigDevConfigObjects 2 }  
    
   pktcSigDevSilenceSuppression  OBJECT-TYPE  
       SYNTAX       TruthValue  
       MAX-ACCESS   read-only  
       STATUS       current  
       DESCRIPTION  
           " This object specifies if the device is capable of 
             silence suppression (Voice Activity Detection)." 
   ::= { pktcSigDevConfigObjects 3 }  
    
   pktcSigDevCallerIdSigProtocol  OBJECT-TYPE  
       SYNTAX       INTEGER { 
                            fsk  (1), 
                            dtmf (2) 
       } 
       MAX-ACCESS   read-write  
       STATUS       current  
       DESCRIPTION  
           "This object identifies the subscriber line protocol used 
            for signaling on-hook caller id information. Different 
            countries define different caller id signaling protocols to 
            support caller identification. Frequency shift keying (FSK) 
            is most commonly used. Dual tone multi-frequency (DTMF) 
            is an alternative." 
        REFERENCE  
           "EN 300 659-1 Specification" 
        DEFVAL { fsk } 
   ::= { pktcSigDevConfigObjects 4 }  
    
   pktcSigDevR0Cadence     OBJECT-TYPE  
       SYNTAX      PktcRingCadence  
       MAX-ACCESS  read-write  
       STATUS      current  
       DESCRIPTION  
           " This object specifies ring cadence 0 (a user defined 
             field). This object is required for the L line package." 
       ::= { pktcSigDevConfigObjects 5 } 
    
   pktcSigDevR1Cadence     OBJECT-TYPE  
       SYNTAX      PktcRingCadence  
       MAX-ACCESS  read-write  
       STATUS      current  
       DESCRIPTION  
           " This object specifies ring cadence 1 (a user defined 
             field). This object is required for the L line package." 
       ::= { pktcSigDevConfigObjects 6 }  
    
   pktcSigDevR2Cadence     OBJECT-TYPE  
       SYNTAX       PktcRingCadence  
       MAX-ACCESS    read-write  
       STATUS        current  
       DESCRIPTION  
           " This object specifies ring cadence 2 (a user defined 
             field). This object is required for the L line package."  
       ::= { pktcSigDevConfigObjects 7 }  
    
   pktcSigDevR3Cadence     OBJECT-TYPE  
       SYNTAX       PktcRingCadence  
       MAX-ACCESS   read-write  
       STATUS       current  
       DESCRIPTION  
           " This object specifies ring cadence 3 (a user defined 
             field). This object is required for the L line package." 
       ::= { pktcSigDevConfigObjects 8 }  
    
   pktcSigDevR4Cadence     OBJECT-TYPE  
       SYNTAX       PktcRingCadence  
       MAX-ACCESS   read-write  
       STATUS       current  
       DESCRIPTION  
           " This object specifies ring cadence 4 (a user defined 
             field). This object is required for the L line package." 
       ::= { pktcSigDevConfigObjects 9 }  
    
   pktcSigDevR5Cadence     OBJECT-TYPE  
       SYNTAX       PktcRingCadence  
       MAX-ACCESS   read-write  
       STATUS       current  
       DESCRIPTION  
           " This object specifies ring cadence 5 (a user defined 
             field). This object is required for the L line package." 
       ::= { pktcSigDevConfigObjects 10 }  
    
   pktcSigDevR6Cadence     OBJECT-TYPE  
       SYNTAX      PktcRingCadence  
       MAX-ACCESS  read-write  
       STATUS      current  
       DESCRIPTION  
           " This object specifies ring cadence 6 (a user defined 
             field). This object is required for the L line package." 
       ::= { pktcSigDevConfigObjects 11 }  
    
   pktcSigDevR7Cadence     OBJECT-TYPE  
       SYNTAX       PktcRingCadence  
       MAX-ACCESS   read-write  
       STATUS       current  
       DESCRIPTION  
           " This object specifies ring cadence 7 (a user defined 
             field). This object is required for the L line package."  
       ::= { pktcSigDevConfigObjects 12 }  
    
   pktcSigDevRgCadence     OBJECT-TYPE  
       SYNTAX       PktcRingCadence  
       MAX-ACCESS   read-write  
       STATUS       current  
       DESCRIPTION  
           " This object specifies ring cadence rg (a user defined 
             field). This object is required for the L line package." 
       ::= { pktcSigDevConfigObjects 13 }  
    
   pktcSigDevRsCadence     OBJECT-TYPE  
       SYNTAX       PktcRingCadence  
       MAX-ACCESS   read-write  
       STATUS       current  
       DESCRIPTION  
           " This object specifies ring cadence rs (a user defined 
             field) The MTA MUST reject any attempt to make this object 
             repeatable. This object is required for the L line 
             package." 
       ::= { pktcSigDevConfigObjects 14 }  
    
   pktcSigDefCallSigDscp  OBJECT-TYPE  
       SYNTAX      Dscp  -- RFC 3289: DIFFSERV-DSCP-TC 
       MAX-ACCESS  read-write      
       STATUS      current      
       DESCRIPTION  
           " The default value used in the IP header for setting the 
             Differentiated Services Code Point (DSCP) value for call 
             signaling." 
       DEFVAL { 0 }  
       ::= { pktcSigDevConfigObjects 15 }  
    
   pktcSigDefMediaStreamDscp  OBJECT-TYPE  
       SYNTAX      Dscp  -- RFC 3289: DIFFSERV-DSCP-TC  
       MAX-ACCESS  read-write  
       STATUS      current  
       DESCRIPTION  
           " This object contains the default value used in the IP 
             header for setting the Differentiated Services Code Point 
             (DSCP) value for media stream packets. The MTA MUST NOT 
             update this object with the value supplied by the CMS in 
             the NCS messages (if present). Any currently active 
             connections are not affected by updates to this object. 
             When the value of this object is updated by SNMP, the MTA 
             MUST use the new value as a default starting only from 
             new connections." 
       DEFVAL { 0 }            
       ::= { pktcSigDevConfigObjects 16 }  
    
   -- 
   -- pktcSigCapabilityTable - This table defines the valid signaling  
   -- types supported by this MTA. 
   -- 
    
   pktcSigCapabilityTable    OBJECT-TYPE  
       SYNTAX        SEQUENCE OF PktcSigCapabilityEntry  
       MAX-ACCESS    not-accessible  
       STATUS        current  
       DESCRIPTION     
           " This table describes the signaling types supported by this 
             MTA."  
       ::= { pktcSigDevConfigObjects 17 }  
    
   pktcSigCapabilityEntry    OBJECT-TYPE  
       SYNTAX        PktcSigCapabilityEntry     
       MAX-ACCESS    not-accessible  
       STATUS        current  
       DESCRIPTION     
           " Entries in pktcMtaDevSigCapabilityTable - List of 
             supported signaling types, versions and vendor extensions 
             for this MTA. Each entry in the list provides for one 
             signaling type and version combination. If the device 
             supports multiple versions of the same signaling type it 
             will require multiple entries." 
       INDEX { pktcSignalingIndex }  
       ::= { pktcSigCapabilityTable 1 }  
          
   PktcSigCapabilityEntry  ::= SEQUENCE {  
       pktcSignalingIndex             Unsigned32,  
       pktcSignalingType              PktcSigType,  
       pktcSignalingVersion           SnmpAdminString,  
       pktcSignalingVendorExtension   SnmpAdminString  
       }  
    
   pktcSignalingIndex       OBJECT-TYPE  
       SYNTAX        Unsigned32 (1..255)  
       MAX-ACCESS    not-accessible  
       STATUS        current  
       DESCRIPTION     
           " The index value which uniquely identifies an entry in the 
             pktcSigCapabilityTable." 
       ::= { pktcSigCapabilityEntry 1 } 
    
   pktcSignalingType      OBJECT-TYPE  
       SYNTAX        PktcSigType  
       MAX-ACCESS    read-only  
       STATUS        current  
       DESCRIPTION     
           " This object identifies the type of signaling used. This 
             value has to be associated with a single signaling 
             version." 
       ::= { pktcSigCapabilityEntry 2 } 
    
   pktcSignalingVersion      OBJECT-TYPE  
       SYNTAX        SnmpAdminString  
       MAX-ACCESS    read-only  
       STATUS        current  
       DESCRIPTION     
           " Provides the version of the signaling type - reference 
             pktcSignalingType. Examples would be 1.0 or 2.33 etc." 
       ::= { pktcSigCapabilityEntry 3 }  
    
   pktcSignalingVendorExtension      OBJECT-TYPE  
       SYNTAX        SnmpAdminString  
       MAX-ACCESS    read-only  
       STATUS        current  
       DESCRIPTION    
           " The vendor extension allows vendors to provide a list of 
             additional capabilities, vendors can decide how to encode 
             these extensions, although space separated text is 
             suggested." 
       ::= { pktcSigCapabilityEntry 4 } 
    
   pktcSigDefNcsReceiveUdpPort  OBJECT-TYPE  
       SYNTAX      InetPortNumber (1025..65535) 
       MAX-ACCESS  read-only  
       STATUS      current  
       DESCRIPTION  
           " This object contains the MTA User Datagram Protocol (UDP) 
             receive port that is being used for NCS call signaling. 
             This object should only be changed by the configuration 
             file." 
       REFERENCE  
           "PacketCable NCS Specification"  
       DEFVAL { 2427 }  
       ::= { pktcSigDevConfigObjects 18 }  
    
   pktcSigPowerRingFrequency    OBJECT-TYPE  
       SYNTAX       INTEGER {  
                    f20Hz(1), 
                    f25Hz(2), 
                    f33Point33Hz(3), 
                    f50Hz(4), 
                    f15Hz(5), 
                    f16Hz(6), 
                    f22Hz(7), 
                    f23Hz(8), 
                    f45Hz(9) 
       }  
       UNITS "Hertz"  
       MAX-ACCESS   read-only  
       STATUS       current  
       DESCRIPTION  
           " This object must only be set via the configuration file 
             during the provisioning process. The power ring frequency 
             is the frequency at which the sinusoidal voltage must 
             travel down the twisted pair to make terminal equipment 
             ring. Different countries define different electrical 
             characteristics to make terminal equipment ring. The f20Hz 
             setting corresponds to a power ring frequency of 20 Hertz. 
             The f25Hz setting corresponds to a power ring frequency of 
             25 Hertz. The f33Point33Hz setting corresponds to a power 
             ring frequency of 33.33 Hertz. The f50Hz setting 
             corresponds to a power ring frequency of 50 Hertz. The 
             f15Hz setting corresponds to a power ring frequency of 15 
             Hertz. The f16Hz setting corresponds to a power ring 
             frequency of 16 Hertz. The f22Hz setting corresponds to a 
             power ring frequency of 22 Hertz. The f23Hz setting 
             corresponds to a power ring frequency of 23 Hertz. The 
             f45Hz setting corresponds to a power ring frequency of 45 
             Hertz. 
   "  
       REFERENCE  
             "EN 300 001 contains a list of frequency ranges that 
              are defined for each country." 
       DEFVAL { f20Hz } 
       ::= { pktcSigDevConfigObjects 19 }  
    
   pktcSigPulseSignalTable    OBJECT-TYPE  
       SYNTAX       SEQUENCE OF PktcSigPulseSignalEntry  
       MAX-ACCESS   not-accessible  
       STATUS       current  
       DESCRIPTION  
           " The Pulse signal table defines the pulse signal operation. 
             There are nine types of international pulse signals, 
             with each signal having a set of provisionable parameters. 
             The values of the MIB objects in this table take effect 
             only if these parameters are not defined via signaling, in 
             which case the latter determines the values of the 
             parameters. This object is required for the E line 
             package. Signals defined in this table are triggered using 
             the E line package. 
             Objects in this table do not persist across MTA reboots." 
       REFERENCE  
           "TS 101 909-4 Specification"  
       ::= { pktcSigDevConfigObjects 20 }  
    
   pktcSigPulseSignalEntry    OBJECT-TYPE  
       SYNTAX       PktcSigPulseSignalEntry  
       MAX-ACCESS   not-accessible  
       STATUS       current  
       DESCRIPTION  
           " This object defines the set of parameters associated with 
             each particular value of pktcSigPulseSignalType. Each 
             entry in the pktcSigPulseSignalTable is indexed by the 
             pktcSigPulseSignalType object." 
       INDEX { pktcSigPulseSignalType } 
       ::= { pktcSigPulseSignalTable 1 }  
    
   PktcSigPulseSignalEntry ::= SEQUENCE {  
           pktcSigPulseSignalType              INTEGER, 
           pktcSigPulseSignalFrequency         INTEGER,  
           pktcSigPulseSignalDbLevel           TenthdBm, 
           pktcSigPulseSignalDuration          Unsigned32, 
           pktcSigPulseSignalPulseInterval     Unsigned32, 
           pktcSigPulseSignalRepeatCount       Unsigned32  
   } 
    
   pktcSigPulseSignalType    OBJECT-TYPE  
       SYNTAX       INTEGER  
                    {  
                        initialRing(1),  
                        pulseLoopClose(2), 
                        pulseLoopOpen(3), 
                        enableMeterPulse(4), 
                        meterPulseBurst(5), 
                        pulseNoBattery(6), 
                        pulseNormalPolarity(7), 
                        pulseReducedBattery(8),  
                        pulseReversePolarity(9)  
                    }  
       MAX-ACCESS   not-accessible  
       STATUS       current  
       DESCRIPTION  
           "There are nine types of international pulse signals. These 
            signals are defined as follows: 
            initial ring 
            pulse loop close 
            pulse loop open 
            enable meter pulse 
            meter pulse burst 
            pulse no battery 
            pulse normal polarity 
            pulse reduced battery 
            pulse reverse polarity"  
       REFERENCE  
           "EN 300 324-1 Specification"  
    
       ::= { pktcSigPulseSignalEntry 1 } 
    
   pktcSigPulseSignalFrequency    OBJECT-TYPE  
       SYNTAX       INTEGER {  
                    twentyfive (1),  
                    twelvethousand(2),  
                    sixteenthousand(3)  
       }  
       UNITS        "Hertz"  
       MAX-ACCESS   read-write  
       STATUS       current  
       DESCRIPTION  
           " This object is only applicable to the initialRing, 
             enableMeterPulse, and meterPulseBurst signal type. This 
             object identifies the frequency of the generated signal. 
             The following table defines the default values for this 
             object depending on signal type: 
             pktcSigPulseSignalType     Default 
             initialRing                25 
             enableMeterPulse           16000 
             meterPulseBurst            16000 
             The value of twentyfive MUST only be used for the 
             initialRing signal type. The values of twelvethousand and 
             sixteenthousand MUST only be used for enableMeterPulse and 
             meterPulseBurst signal types. An attempt to set this 
             object while the value of pktcSigPulseSignalType is not 
             initialRing,enableMeterPulse, or meterPulseBurst will 
             result in an inconsistentValue error." 
       REFERENCE  
           "EN 300 001 Specification" 
            ::= { pktcSigPulseSignalEntry 2} 
    
   pktcSigPulseSignalDbLevel    OBJECT-TYPE  
       SYNTAX       TenthdBm (-350..0)  
       UNITS        "dBm"  
       MAX-ACCESS   read-write  
       STATUS       current  
       DESCRIPTION  
           " This object is only applicable to the enableMeterPulse and 
             meterPulseBurst signal types. This is the decibel level 
             for each frequency at which tones could be generated at 
             the a and b terminals (TE connection point). An attempt to 
             set this object while the value of pktcSigPulseSignalType 
             is not enableMeterPulse, or meterPulseBurst will result in 
             an inconsistentValue error." 
       REFERENCE  
           "EN 300 001 Specification" 
       DEFVAL { -135 }  
       ::={pktcSigPulseSignalEntry 3 } 
    
   pktcSigPulseSignalDuration    OBJECT-TYPE  
       SYNTAX       Unsigned32 (0..5000)  
       UNITS        "Milliseconds"  
       MAX-ACCESS   read-write  
       STATUS       current  
       DESCRIPTION   
           " This object specifies the pulse duration for each 
             signal type. In addition, the MTA must accept the values 
             in the incremental steps specific for each signal type. 
             The following table defines the default values and the 
             incremental steps for this object depending on the signal 
             type. 
             pktcSigPulseSignaltype  Default (ms)   Increment (ms) 
             initialRing                 200             50 
             pulseLoopClose              200             10 
             pulseLoopOpen               200             10 
             enableMeterPulse            150             10 
             meterPulseBurst             150             10 
             pulseNoBattery              200             10 
             pulseNormalPolarity         200             10 
             pulseReducedBattery         200             10 
             pulseReversePolarity        200             10 
             An attempt to set this object to a value that does not 
             fall on one of the increment boundaries, or on the wrong 
             increment boundary for the specific signal type will 
             result in an inconsistentValue error." 
       REFERENCE  
           "EN 300 324-1 Specification"  
            ::= {pktcSigPulseSignalEntry 4 }  
    
   pktcSigPulseSignalPulseInterval     OBJECT-TYPE 
       SYNTAX       Unsigned32 (0..5000) 
       UNITS        "Milliseconds"  
       MAX-ACCESS   read-write  
       STATUS       current  
       DESCRIPTION 
           " This object specifies the repeat interval, or the period 
             for each signal type. In addition, the MTA must accept 
             the values in the incremental steps specific for each 
             signal type. The following table defines the default 
             values and the incremental steps for this object depending 
             on the signal type. 
             pktcSigPulseSignaltype  Default (ms)   Increment (ms) 
             initialRing                 200             50 
             pulseLoopClose             1000             10 
             pulseLoopOpen              1000             10 
             enableMeterPulse           1000             10 
             meterPulseBurst            1000             10 
             pulseNoBattery             1000             10 
             pulseNormalPolarity        1000             10 
             pulseReducedBattery        1000             10 
             pulseReversePolarity       1000             10 
             An attempt to set this object to a value that does not 
             fall on one of the increment boundaries, or on the wrong 
             increment boundary for the specific signal type will 
             result in an inconsistentValue error." 
       REFERENCE  
           "EN 300 324-1 Specification" 
            ::= { pktcSigPulseSignalEntry 5} 
    
   pktcSigPulseSignalRepeatCount    OBJECT-TYPE  
       SYNTAX       Unsigned32  
       MAX-ACCESS   read-write  
       STATUS       current  
       DESCRIPTION  
           " This object specifies how many times to repeat a pulse. 
             This object is not used by the enableMeterPulse signal 
             type and as such must have a value of zero. The following 
             table defines the default values and the valid ranges for 
             this object depending on the signal type. 
             pktcSigPulseSignaltype  Default   Range 
             initialRing                1       1-5 
             pulseLoopClose             1       1-50 
             pulseLoopOpen              1       1-50 
             enableMeterPulse           0       Not Used 
             meterPulseBurst            1       1-50 
             pulseNoBattery             1       1-50 
             pulseNormalPolarity        1       1-50 
             pulseReducedBattery        1       1-50 
             pulseReversePolarity       1       1-50 
             An attempt to set this object to a value that does not 
             fall within the range (or is not used) for the specific 
             signal type will result in an inconsistentValue error."  
       ::={ pktcSigPulseSignalEntry 6 }  
    
   pktcSigDevCIDMode    OBJECT-TYPE  
       SYNTAX       INTEGER { 
                    duringRingingETS(1), 
                    dtAsETS(2), 
                    rpAsETS(3), 
                    lrAsETS(4) 
                    } 
       MAX-ACCESS read-write 
       STATUS current  
       DESCRIPTION  
           " This object is required for the E line package. 
             For on-hook Caller ID, pktcSigDevCIDMode selects the 
             method of Caller ID. For the duringRingingETS method, the 
             Frequency Shift Keying (FSK) containing the Caller ID 
             information is sent between the first and second ring 
             pattern. For the dtAsETS,rpAsETS, and lrAsETS methods, the 
             FSK containing the Caller ID information is sent before 
             the first ring pattern. For the dtAsETS method, the FSK is 
             sent after the Dual Tone Alert Signal. For the rpAsETS 
             method, the FSK is sent after a Ring Pulse. For the 
             lrAsETS method, the Line Reversal occurs first, then the 
             Dual Tone Alert Signal, and finally the FSK is sent." 
       DEFVAL { dtAsETS }  
       ::= {pktcSigDevConfigObjects 21 }  
    
   pktcSigDevCIDFskAfterRing    OBJECT-TYPE 
       SYNTAX       Unsigned32 (50..2000) 
       UNITS        "Milliseconds" 
       MAX-ACCESS   read-write 
       STATUS       current 
       DESCRIPTION 
           " This object is required for the E line package. This 
             object specifies the delay between the end of first 
             ringing pattern and the start of the transmission of the 
             FSK containing the Caller ID information. It is only used 
             when pktcSigDevCIDMode is duringRingingETS. The following 
             table defines the default values for this object depending 
             on signal type: 
             pktcSigDevCIDMode     Default 
             duringringingETS      550 ms 
             dtAsETS               not used 
             rpAsETS               not used 
             lrAsETS               not used 
             An attempt to set this object while the value of 
             pktcSigDevCIDMode is not duringringingETS will result in 
             an inconsistentValue error." 
       REFERENCE  
           "EN 300 659-1 Specification" 
       DEFVAL { 550 } 
       ::= {pktcSigDevConfigObjects 22 } 
          
   pktcSigDevCIDFskAfterDTAS    OBJECT-TYPE 
       SYNTAX       Unsigned32 (45..500) 
       UNITS        "Milliseconds" 
       MAX-ACCESS   read-write 
       STATUS       current 
       DESCRIPTION 
           " This object is required for the E line package. This 
             object specifies the delay between the end of the Dual 
             Tone Alert Signal (DT-AS) and the start of the 
             transmission of the FSK containing the Caller ID 
             information. This object is only used when 
             pktcSigDevCIDMode is dtAsETS or lrAsETS. The following 
             table defines the default values for this object depending 
             on signal type: 
             pktcSigDevCIDMode     Default 
             duringringingETS      not used 
             dtAsETS               50 ms 
             rpAsETS               not used 
             lrAsETS               50 ms 
             An attempt to set this object while the value of 
             pktcSigDevCIDMode is not dtAsETS or lrAsETS will result in 
             an inconsistentValue error." 
       REFERENCE  
           "EN 300 659-1 Specification" 
       DEFVAL { 50 } 
       ::= {pktcSigDevConfigObjects 23 } 
          
   pktcSigDevCIDFskAfterRPAS    OBJECT-TYPE 
       SYNTAX       Unsigned32 (500..800) 
       UNITS        "Milliseconds" 
       MAX-ACCESS   read-write 
       STATUS       current 
       DESCRIPTION 
           " This object is required for the E line package. This 
             object specifies the delay between the end of the Ring 
             Pulse Alert Signal (RP-AS) and the start of the 
             transmission of the FSK containing the Caller ID 
             information. This object is only used when 
             pktcSigDevCIDMode is rpAsETS. The following table defines 
             the default values for this object depending on signal 
             type: 
             pktcSigDevCIDMode     Default 
             duringringingETS      not used 
             dtAsETS               not used 
             rpAsETS               650 ms 
             lrAsETS               not used 
             An attempt to set this object while the value of 
             pktcSigDevCIDMode is not rpAsETS will result in an 
             inconsistentValue error." 
       REFERENCE  
           "EN 300 659-1 Specification" 
       DEFVAL { 650 } 
       ::= {pktcSigDevConfigObjects 24 } 
          
   pktcSigDevCIDRingAfterFSK    OBJECT-TYPE  
       SYNTAX       Unsigned32 (50..500)  
       UNITS        "Milliseconds"  
       MAX-ACCESS   read-write  
       STATUS       current  
       DESCRIPTION  
           " This object is required for the E line package. This 
             object specifies the delay between the end of the complete 
             transmission of the FSK containing the Caller ID 
             information and the start of the first ring pattern. It is 
             only used when pktcSigDevCIDMode is dtAsETS, rpAsETS or 
             lrAsETS. The following table defines the default values 
             for this object depending on signal type: 
             pktcSigDevCIDMode     Default 
             duringringingETS      not used 
             dtAsETS               250 ms 
             rpAsETS               250 ms 
             lrAsETS               250 ms 
             An attempt to set this object while the value of 
             pktcSigDevCIDMode is not dtAsETS, rpAsETS, or lrAsETS will 
             result in an inconsistentValue error." 
       REFERENCE  
           "EN 300 659-1 Specification" 
       DEFVAL { 250 } 
       ::= {pktcSigDevConfigObjects 25 }  
    
   pktcSigDevCIDDTASAfterLR    OBJECT-TYPE  
       SYNTAX       Unsigned32 (50..655)  
       UNITS        "Milliseconds"  
       MAX-ACCESS   read-write  
       STATUS       current  
       DESCRIPTION  
           " This object is required for the E line package. This 
             object specifies the delay between the end of the Line 
             Reversal and the start of the Dual Tone Alert Signal 
             (DT-AS). This object is only used when pktcSigDevCIDMode 
             is lrAsETS. The following table defines the default values 
             for this object depending on signal type: 
             pktcSigDevCIDMode     Default 
             duringringingETS      not used 
             dtAsETS               not used 
             rpAsETS               not used 
             lrAsETS               250 ms 
             An attempt to set this object while the value of 
             pktcSigDevCIDMode is not lrAsETS will result in an 
             inconsistentValue error." 
       REFERENCE  
           "EN 300 659-1 Specification" 
       DEFVAL { 250 } 
    
       ::= {pktcSigDevConfigObjects 26 }  
    
   pktcSigDevVmwiMode    OBJECT-TYPE  
       SYNTAX       INTEGER { 
                    dtAsETS(1), 
                    rpAsETS(2), 
                    lrAsETS(3), 
                    osi(4) 
                    } 
       MAX-ACCESS read-write 
       STATUS current  
       DESCRIPTION  
           " For visual message waiting indicator (VMWI), 
             pktcSigDevVmwiMode selects the alerting signal method. For 
             the dtAsETS, rpAsETS, lrAsETS, and OSI methods, 
             the FSK containing the VMWI information is sent after an 
             alerting signal. For the dtAsETS method, the FSK is sent 
             after the Dual Tone Alert Signal. For the rpAsETS method, 
             the FSK is sent after a Ring Pulse. For the lrAsETS 
             method, the Line Reversal occurs first, then the Dual Tone 
             Alert Signal, and finally the FSK is sent. For the OSI 
             method, the FSK is sent after the Open Switching 
             Interval." 
       DEFVAL { dtAsETS }  
       ::= {pktcSigDevConfigObjects 27 }  
    
   pktcSigDevVmwiFskAfterDTAS    OBJECT-TYPE 
       SYNTAX       Unsigned32 (45..500) 
       UNITS        "Milliseconds" 
       MAX-ACCESS   read-write 
       STATUS       current 
       DESCRIPTION 
           " This object is required for the E line package. This 
             object specifies the delay between the end of the Dual 
             Tone Alert Signal (DT-AS) and the start of the 
             transmission of the FSK containing the VMWI information. 
             This object is only used when pktcSigDevVmwiMode is 
             dtAsETS or lrAsETS. The following table defines the 
             default values for this object depending on signal type: 
             pktcSigDevVmwiMode     Default 
             dtAsETS                50 ms 
             rpAsETS                not used 
             lrAsETS                50 ms 
             An attempt to set this object while the value of 
             pktcSigDevVmwiMode is not dtAsETS or lrAsETS will result 
             in an inconsistentValue error." 
       REFERENCE  
           "EN 300 659-1 Specification" 
       DEFVAL { 50 } 
       ::= {pktcSigDevConfigObjects 28 } 
          
    
   pktcSigDevVmwiFskAfterRPAS    OBJECT-TYPE 
       SYNTAX       Unsigned32 (500..800) 
       UNITS        "Milliseconds" 
       MAX-ACCESS   read-write 
       STATUS       current 
       DESCRIPTION 
           " This object is required for the E line package. This 
             object specifies the delay between the end of the Ring 
             Pulse Alert Signal (RP-AS) and the start of the 
             transmission of the FSK containing the VMWI information. 
             This object is only used when pktcSigDevVmwiMode is 
             rpAsETS. The following table defines the default values 
             for this object depending on signal type: 
             pktcSigDevVmwiMode     Default 
             dtAsETS                not used 
             rpAsETS                650 ms 
             lrAsETS                not used 
             An attempt to set this object while the value of 
             pktcSigDevVmwiMode is not rpAsETS will result in an 
             inconsistentValue error." 
       REFERENCE  
           "EN 300 659-1 Specification" 
       DEFVAL { 650 } 
       ::= {pktcSigDevConfigObjects 29 } 
    
   pktcSigDevVmwiDTASAfterLR    OBJECT-TYPE 
       SYNTAX       Unsigned32 (50..655) 
       UNITS        "Milliseconds" 
       MAX-ACCESS   read-write 
       STATUS       current 
       DESCRIPTION 
           " This object is required for the E line package. This 
             object specifies the delay between the end of the Line 
             Reversal and the start of the Dual Tone Alert Signal 
             (DT-AS) for VMWI information. This object is only used 
             when pktcSigDevVmwiMode is lrAsETS. The following table 
             defines the default values for this object depending on 
             signal type: 
             pktcSigDevVmwiMode     Default 
             dtAsETS                not used 
             rpAsETS                not used 
             lrAsETS                250 ms 
             An attempt to set this object while the value of 
             pktcSigDevVmwiMode is not lrAsETS will result in an 
             inconsistentValue error." 
       REFERENCE  
           "EN 300 659-1 Specification" 
       DEFVAL { 250 } 
       ::= {pktcSigDevConfigObjects 30 } 
    
   pktcSigDevRingCadenceTable    OBJECT-TYPE  
       SYNTAX       SEQUENCE OF PktcSigDevRingCadenceEntry  
       MAX-ACCESS   not-accessible  
       STATUS       current  
       DESCRIPTION  
           "Cadence rings are defined by the telco governing 
            body for each country. The MTA must be able to support 
            various ranges of cadence patterns and cadence periods. 
            The MTA will be able to support country specific 
            provisioning of the cadence and idle period. Each 
            cadence pattern will be assigned a unique value ranging 
            from 0-127 (inclusive) corresponding to the value of x, 
            where x is the value sent in the cadence ringing (cr) 
            signal cr(x), requested per the appropriate NCS 
            message, and defined in the E package. The MTA will derive 
            the cadence periods from the ring cadence table entry as 
            provisioned by the customer. The MTA is allowed to provide 
            appropriate default values for each of the ring cadences. 
            This table only needs to be supported when the MTA 
            implements the E package. Objects in this table do not 
            persist across MTA reboots." 
       REFERENCE  
           "TS 101 909-4 Specification" 
       ::= { pktcSigDevConfigObjects 31 }  
    
   pktcSigDevRingCadenceEntry    OBJECT-TYPE  
       SYNTAX       PktcSigDevRingCadenceEntry  
       MAX-ACCESS   not-accessible  
       STATUS       current  
       DESCRIPTION  
           " Unique value ranging from 0 to 127 that will correspond to 
             the different ring cadences that are being supported by 
             the device." 
       INDEX { pktcSigDevRingCadenceIndex }  
       ::= { pktcSigDevRingCadenceTable 1 }  
    
   PktcSigDevRingCadenceEntry ::= SEQUENCE {  
           pktcSigDevRingCadenceIndex       Unsigned32,  
           pktcSigDevRingCadence            PktcRingCadence  
       }  
    
   pktcSigDevRingCadenceIndex    OBJECT-TYPE  
       SYNTAX       Unsigned32 (0..127)  
       MAX-ACCESS   not-accessible  
       STATUS       current  
       DESCRIPTION   
           " Unique value ranging from 0 to 127 that corresponds to the 
             value sent by the LE based on country specific cadences, 
             one row per cadence cycle. In any given system 
             implementation for a particular country, it is anticipated 
             that a small number of ring cadences will be in use. Thus, 
             this table most likely will not be populated to its full 
             size."  
       ::= { pktcSigDevRingCadenceEntry 1 }  
    
   pktcSigDevRingCadence    OBJECT-TYPE  
       SYNTAX       PktcRingCadence 
       MAX-ACCESS   read-write  
       STATUS       current  
       DESCRIPTION  
           "This is the Ring Cadence. This object is required for the 
            E line package." 
       ::= { pktcSigDevRingCadenceEntry 2 }  
    
   pktcSigDevToneTable    OBJECT-TYPE  
       SYNTAX       SEQUENCE OF PktcSigDevToneEntry  
       MAX-ACCESS   not-accessible  
       STATUS       current  
       DESCRIPTION  
           " The Tone Table defines the various tone operations. Any 
             definition of the tones callWaiting1-4 in this table 
             should just contain the audible tone itself and NOT 
             contain the delay between tones or the tone repeat count. 
             The delay between tones or the repeat count is controlled 
             by the objects pktcNcsEndPntConfigCallWaitingDelay, and 
             pktcNcsEndPntConfigCallWaitingMaxRep. If the 
             pktcSigDevToneType is callWaiting1-4, the 
             pktcSigDevToneWholeToneRepeatCount does not apply and MUST 
             be ignored on SNMP get/set operations. The MTA MUST 
             make sure that, after the provisioning cycle, the table is 
             fully populated (i.e., for each possible index, an entry 
             MUST be defined) using reasonable defaults for each row 
             that was not defined by the provisioning information. 
             Objects in this table do not persist across MTA reboots." 
       REFERENCE  
           "NCS Specification, TS 101 909-4 Specification" 
       ::= { pktcSigDevConfigObjects 32 }  
    
   pktcSigDevToneEntry    OBJECT-TYPE  
       SYNTAX       PktcSigDevToneEntry  
       MAX-ACCESS   not-accessible  
       STATUS       current  
       DESCRIPTION  
           " The different tone types that can be provisioned based on 
             country specific needs." 
       INDEX { pktcSigDevToneType }  
       ::= { pktcSigDevToneTable 1 }  
    
   PktcSigDevToneEntry ::= SEQUENCE {  
       pktcSigDevToneType                      INTEGER,  
       pktcSigDevToneDbLevel                   TenthdBm,  
       pktcSigDevToneFreqType                  INTEGER,  
       pktcSigDevToneNumFrequencies            Unsigned32,  
       pktcSigDevToneFirstFrequency            Unsigned32,  
       pktcSigDevToneSecondFrequency           Unsigned32,  
       pktcSigDevToneThirdFrequency            Unsigned32,  
       pktcSigDevToneFourthFrequency           Unsigned32,  
       pktcSigDevToneNumOnOffTimes             Unsigned32,  
       pktcSigDevToneFirstToneOn               Unsigned32,  
       pktcSigDevToneFirstToneOff              Unsigned32,  
       pktcSigDevToneSecondToneOn              Unsigned32,  
       pktcSigDevToneSecondToneOff             Unsigned32,  
       pktcSigDevToneThirdToneOn               Unsigned32,  
       pktcSigDevToneThirdToneOff              Unsigned32,  
       pktcSigDevToneFourthToneOn              Unsigned32,  
       pktcSigDevToneFourthToneOff             Unsigned32,  
       pktcSigDevToneWholeToneRepeatCount      Unsigned32,  
       pktcSigDevToneSteady                    TruthValue  
       }  
    
   pktcSigDevToneType        OBJECT-TYPE  
       SYNTAX       INTEGER {  
                    busy(1),  
                    confirmation(2),  
                    dial(3),  
                    messageWaiting(4),  
                    offHookWarning(5),  
                    ringBack(6),  
                    reOrder(7),  
                    stutterdial(8),  
                    callWaiting1(9),  
                    callWaiting2(10),  
                    callWaiting3(11),  
                    callWaiting4(12), 
                    alertingSignal(13), 
                    specialDial(14), 
                    specialInfo(15), 
                    release(16), 
                    congestion(17), 
                    userDefined1(18), 
                    userDefined2(19), 
                    userDefined3(20), 
                    userDefined4(21) 
                    }  
       MAX-ACCESS   not-accessible 
       STATUS       current  
       DESCRIPTION  
           "Unique value ranging from 1 to 21 that will correspond to 
            the different tone types. These tones can be provisioned 
            based on country specific needs. This object defines the 
            type of tone being accessed. The alertingSignal, 
            specialDial, specialInfo, release, congestion and 
            userDefined1-4 tone types are used in the E line package." 
       ::={pktcSigDevToneEntry 1 }  
    
   pktcSigDevToneDbLevel    OBJECT-TYPE 
       SYNTAX       TenthdBm (-250..-30) 
       UNITS        "dBm"  
       MAX-ACCESS   read-write  
       STATUS       current  
       DESCRIPTION  
           "This is the decibel level for each frequency at which 
            tones could be generated at the a and b terminals (TE 
            connection point)." 
       DEFVAL { -40 }  
       ::={pktcSigDevToneEntry 2 }  
    
   pktcSigDevToneFreqType    OBJECT-TYPE  
       SYNTAX      INTEGER {  
                   allFrequencies (1),  
                   singleFrequencySequence (2),  
                   dualFrequencySequence (3),  
                   allFrequenciesModulated (4)  
       }  
       MAX-ACCESS   read-write  
       STATUS       current  
       DESCRIPTION  
           "This object describes how the frequencies are applied.  
            allFrequencies indicates all frequencies specifed by 
            pktcSigDevToneNumFrequencies are mixed to form a single 
            tone. The tone is then applied in sequence using the 
            number of on/off times specified in 
            pktcSigDevToneNumOnOffTimes. SingleFrequecySequence 
            indicates all frequencies specified by 
            pktcSigDevToneNumFrequencies are applied in sequence 
            using the corresponding frequency number on/off time 
            (e.g., pktcSigDevToneFirstFrequency uses 
            pktcSigDevToneFirstToneOn and pktcSigDevToneFirstToneOff, 
            pktcSigDevToneSecondFrequency uses 
            pktcSigDevToneSecondToneOn and 
            pktcSigDevToneSecondToneOff). For this tone type 
            pktcSigDevToneNumFrequencies MUST equal 
            pktcSigDevToneNumOnOffTimes. DualFrequencySequence 
            indicates two pairs of frequencies are added to form two 
            sequenced tones. The first and second frequency are added 
            to form tone one and are applied using 
            pktcSigDevToneFirstToneOn and pktcSigDevToneFirstToneOff. 
            The third and forth frequency are added to form tone two 
            and are applied using pktcSigDevToneSecondToneOn and 
            pktcSigDevToneSecondToneOff. For this tone type 
            pktcSigDevToneNumFrequencies MUST equal 4 and 
            pktcSigDevToneNumOnOffTimes MUST equal 2. 
            allFrequenciesModulated indicates all frequencies 
            specified by pktcSigDevToneNumFrequencies are modulated to 
            form a single tone. The tone is then applied in sequence 
            using the number of on/off times specified in 
            pktcSigDevToneNumOnOffTimes. For allFrequenciesModulated, 
            the pktcSigDevToneNumFrequencies MUST equal 2, and the 
            frequency in pktcSigDevToneFirstFrequency modulates the 
            frequency in pktcSigDevToneSecondFrequency." 
       REFERENCE  
           "ITU-T E.180"  
       DEFVAL { allFrequencies }  
       ::={ pktcSigDevToneEntry 3 }  
    
   pktcSigDevToneNumFrequencies    OBJECT-TYPE  
       SYNTAX       Unsigned32 (1..4)  
       MAX-ACCESS   read-write  
       STATUS       current  
       DESCRIPTION  
           "Specifies the number of frequencies specified in the table 
            entry."  
       DEFVAL { 1 }  
       ::={pktcSigDevToneEntry 4}  
    
   pktcSigDevToneFirstFrequency    OBJECT-TYPE  
       SYNTAX       Unsigned32 (0..4000)  
       UNITS        "Hertz"  
       MAX-ACCESS   read-write  
       STATUS       current  
       DESCRIPTION  
           "This is the first frequency at which the tones are 
            generated in a multiple frequency tone."  
       ::={pktcSigDevToneEntry 5}  
    
   pktcSigDevToneSecondFrequency    OBJECT-TYPE  
       SYNTAX       Unsigned32 (0..4000)  
       UNITS        "Hertz"  
       MAX-ACCESS   read-write  
       STATUS       current  
       DESCRIPTION  
           "This is the second frequency at which the tones are 
            generated in a multiple frequency tone."  
       ::={pktcSigDevToneEntry 6}  
    
   pktcSigDevToneThirdFrequency    OBJECT-TYPE  
       SYNTAX       Unsigned32 (0..4000)  
       UNITS        "Hertz"  
       MAX-ACCESS   read-write  
       STATUS       current  
       DESCRIPTION  
           "This is the third frequency at which the tones are 
            generated."  
       ::={pktcSigDevToneEntry 7}  
    
   pktcSigDevToneFourthFrequency    OBJECT-TYPE  
       SYNTAX       Unsigned32 (0..4000)  
       UNITS        "Hertz"  
       MAX-ACCESS   read-write  
       STATUS       current  
       DESCRIPTION  
           "This is the fourth frequency at which the tones are 
            generated."  
       ::={pktcSigDevToneEntry 8}  
    
   pktcSigDevToneNumOnOffTimes    OBJECT-TYPE  
       SYNTAX       Unsigned32 (1..4)  
       MAX-ACCESS   read-write  
       STATUS       current  
       DESCRIPTION  
           "Specifies the number of on/off times specified in the  
            table entry."  
       DEFVAL { 1 }  
       ::={pktcSigDevToneEntry 9}  
    
   pktcSigDevToneFirstToneOn    OBJECT-TYPE  
       SYNTAX       Unsigned32 (0..5000)  
       UNITS        "Milliseconds"  
       MAX-ACCESS   read-write  
       STATUS       current  
       DESCRIPTION  
           "This is the first tone interval. This object represents 
            the length of time the tone is on."  
       ::={ pktcSigDevToneEntry 10}  
    
   pktcSigDevToneFirstToneOff    OBJECT-TYPE  
       SYNTAX       Unsigned32 (0..5000)  
       UNITS        "Milliseconds"  
       MAX-ACCESS   read-write  
       STATUS       current  
       DESCRIPTION  
           "This is the first idle interval. This object represents 
            the length of time the tone is off."  
        ::={ pktcSigDevToneEntry 11 }  
    
   pktcSigDevToneSecondToneOn    OBJECT-TYPE  
       SYNTAX       Unsigned32 (0..5000)  
       UNITS        "Milliseconds"  
       MAX-ACCESS   read-write  
       STATUS       current  
       DESCRIPTION  
           "This is the second tone interval. This object represents 
            the length of time the tone is on."  
       ::={ pktcSigDevToneEntry 12 }  
    
   pktcSigDevToneSecondToneOff    OBJECT-TYPE  
       SYNTAX       Unsigned32 (0..5000)  
       UNITS        "Milliseconds"  
       MAX-ACCESS   read-write  
       STATUS       current  
       DESCRIPTION  
           "This is the second idle interval. This object represents 
            the length of time the tone is off."  
       ::={ pktcSigDevToneEntry 13 }  
    
   pktcSigDevToneThirdToneOn    OBJECT-TYPE  
       SYNTAX       Unsigned32 (0..5000)  
       UNITS        "Milliseconds"  
       MAX-ACCESS   read-write  
       STATUS       current  
       DESCRIPTION  
           "This is the third tone interval. This object represents 
            the length of time the tone is on."  
       ::={ pktcSigDevToneEntry 14 }  
    
   pktcSigDevToneThirdToneOff    OBJECT-TYPE  
       SYNTAX       Unsigned32 (0..5000)  
       UNITS        "Milliseconds"  
       MAX-ACCESS   read-write  
       STATUS       current  
       DESCRIPTION  
           "This is the third idle interval. This object represents 
            the length of time the tone is off."  
       ::={ pktcSigDevToneEntry 15 }  
          
   pktcSigDevToneFourthToneOn    OBJECT-TYPE  
       SYNTAX       Unsigned32 (0..5000)  
       UNITS        "Milliseconds"  
       MAX-ACCESS   read-write  
       STATUS       current  
       DESCRIPTION  
           "This is the fourth tone interval. This object represents 
            the length of time the tone is on."  
       ::={ pktcSigDevToneEntry 16 }  
    
   pktcSigDevToneFourthToneOff    OBJECT-TYPE  
       SYNTAX       Unsigned32 (0..5000)  
       UNITS        "Milliseconds"  
       MAX-ACCESS   read-write  
       STATUS       current  
       DESCRIPTION  
           "This is the Fourth idle interval. This object represents 
            the length of time the tone is off."  
       ::={ pktcSigDevToneEntry 17 }  
    
   pktcSigDevToneWholeToneRepeatCount      OBJECT-TYPE  
       SYNTAX       Unsigned32 (0..5000)  
       MAX-ACCESS   read-write  
       STATUS       current  
       DESCRIPTION  
           "This is the repeat count, which signifies how many times 
            to repeat the entire on-off sequence. Setting this object 
            may result in a tone duration longer than the overall 
            signal duration specified by the time out (TO) object for a 
            particular signal. In this case, the tone duration defined 
            by the TO object for a particular signal always represents 
            the overall signal duration for a tone." 
       ::={ pktcSigDevToneEntry 18 }  
    
   pktcSigDevToneSteady    OBJECT-TYPE  
       SYNTAX       TruthValue  
       MAX-ACCESS   read-write  
       STATUS       current  
       DESCRIPTION  
           "This is the steady tone. Device must play out the on-off 
            sequence for pktcSigDevToneWholeRepeatCount times and 
            then apply the last tone forever. Setting this object 
            may result in a tone duration longer than the overall 
            signal duration specified by the time out (TO) object for a 
            particular signal. In this case, the tone duration defined 
            by the TO object for a particular signal always represents 
            the overall signal duration for a tone."  
       ::={ pktcSigDevToneEntry 19 }  
    
   --  
   -- The NCS End Point Config Table is used to define attributes that 
   -- are specific to connection EndPoints. 
   --  
    
   pktcNcsEndPntConfigTable  OBJECT-TYPE  
       SYNTAX        SEQUENCE OF PktcNcsEndPntConfigEntry  
       MAX-ACCESS    not-accessible  
       STATUS        current  
       DESCRIPTION     
           " This table describes the information pertaining to each 
             endpoint of the MTA. All entries in this table represent 
             the provisioned endpoints provisioned with the information 
             required by the MTA to maintain the NCS signaling protocol 
             communication with the CMS. Each endpoint can be assigned 
             to its own CMS. If the specific endpoint does not have 
             the corresponding CMS information in this table, the 
             endpoint is considered as not provisioned with voice 
             services. Objects in this table do not persist across 
             MTA reboots." 
      ::=  { pktcNcsEndPntConfigObjects 1 }  
    
   pktcNcsEndPntConfigEntry  OBJECT-TYPE  
       SYNTAX        PktcNcsEndPntConfigEntry  
       MAX-ACCESS    not-accessible  
       STATUS        current  
       DESCRIPTION     
           "Each entry in the pktcNcsEndPntConfigTable represents  
            required signaling parameters for the specific endpoint 
            provisioned with voice services." 
       INDEX { ifIndex }  
       ::= { pktcNcsEndPntConfigTable 1 }  
    
   PktcNcsEndPntConfigEntry  ::= SEQUENCE {  
       pktcNcsEndPntConfigCallAgentId             SnmpAdminString,  
       pktcNcsEndPntConfigCallAgentUdpPort        InetPortNumber,  
       pktcNcsEndPntConfigPartialDialTO           Unsigned32,  
       pktcNcsEndPntConfigCriticalDialTO          Unsigned32,  
       pktcNcsEndPntConfigBusyToneTO              Unsigned32,  
       pktcNcsEndPntConfigDialToneTO              Unsigned32,  
       pktcNcsEndPntConfigMessageWaitingTO        Unsigned32,  
       pktcNcsEndPntConfigOffHookWarnToneTO       Unsigned32,  
       pktcNcsEndPntConfigRingingTO               Unsigned32,  
       pktcNcsEndPntConfigRingBackTO              Unsigned32,  
       pktcNcsEndPntConfigReorderToneTO           Unsigned32,  
       pktcNcsEndPntConfigStutterDialToneTO       Unsigned32,  
       pktcNcsEndPntConfigTSMax                   Unsigned32,  
       pktcNcsEndPntConfigMax1                    Unsigned32,  
       pktcNcsEndPntConfigMax2                    Unsigned32,  
       pktcNcsEndPntConfigMax1QEnable             TruthValue,  
       pktcNcsEndPntConfigMax2QEnable             TruthValue,  
       pktcNcsEndPntConfigMWD                     Unsigned32,  
       pktcNcsEndPntConfigTdinit                  Unsigned32,  
       pktcNcsEndPntConfigTdmin                   Unsigned32,  
       pktcNcsEndPntConfigTdmax                   Unsigned32,  
       pktcNcsEndPntConfigRtoMax                  Unsigned32,  
       pktcNcsEndPntConfigRtoInit                 Unsigned32,  
       pktcNcsEndPntConfigLongDurationKeepAlive   Unsigned32,  
       pktcNcsEndPntConfigThist                   Unsigned32,  
       pktcNcsEndPntConfigStatus                  RowStatus,  
       pktcNcsEndPntConfigCallWaitingMaxRep       Unsigned32,  
       pktcNcsEndPntConfigCallWaitingDelay        Unsigned32,  
       pktcNcsEndPntStatusCallIpAddressType       InetAddressType, 
       pktcNcsEndPntStatusCallIpAddress           InetAddress,  
       pktcNcsEndPntStatusError                   INTEGER,  
       pktcNcsEndPntConfigMinHookFlash            Unsigned32,  
       pktcNcsEndPntConfigMaxHookFlash            Unsigned32,  
       pktcNcsEndPntConfigPulseDialInterdigitTime Unsigned32,  
       pktcNcsEndPntConfigPulseDialMinMakeTime    Unsigned32,  
       pktcNcsEndPntConfigPulseDialMaxMakeTime    Unsigned32,  
       pktcNcsEndPntConfigPulseDialMinBreakTime   Unsigned32,  
       pktcNcsEndPntConfigPulseDialMaxBreakTime   Unsigned32 
       }  
    
   pktcNcsEndPntConfigCallAgentId     OBJECT-TYPE  
       SYNTAX      SnmpAdminString(SIZE (3..255))  
       MAX-ACCESS  read-create  
       STATUS      current  
       DESCRIPTION  
           " This object contains a string indicating the call agent 
             name (e.g.: ca@example.com). The call agent name, after 
             the character '@', MUST be a fully qualified domain name 
             (FQDN) and MUST have a corresponding pktcMtaDevCmsFqdn 
             entry in the pktcMtaDevCmsTable. The object 
             pktcMtaDevCmsFqdn is defined in the PacketCable MIBMTA 
             Specification. For each particular endpoint, the MTA MUST 
             use the current value of this object to communicate with 
             the corresponding CMS. The MTA MUST update this object 
             with the value of the 'Notified Entity' parameter of the 
             NCS message. Because of the high importance of this object 
             to the ability of the MTA to maintain reliable NCS 
             communication with the CMS, it is highly recommended not 
             to change this object's value using SNMP during normal 
             operation."  
       ::= {  pktcNcsEndPntConfigEntry 1 }  
    
   pktcNcsEndPntConfigCallAgentUdpPort    OBJECT-TYPE  
       SYNTAX      InetPortNumber (1025..65535)  
       MAX-ACCESS  read-create   
       STATUS      current  
       DESCRIPTION  
           " This object contains the current value of the User 
             Datagram Protocol (UDP) receive port on which the 
             call agent will receive NCS signaling from the endpoint. 
             For each particular endpoint, the MTA MUST use the current 
             value of this object to communicate with the corresponding 
             CMS. The MTA MUST update this object with the value of the 
             'Notified Entity' parameter of the NCS message. If the 
             Notified Entity parameter does not contain a CallAgent 
             port, the MTA MUST update this object with the default 
             value of 2727. Because of the high importance of this 
             object to the ability of the MTA to maintain reliable NCS 
             communication with the CMS, it is highly recommended not 
             to change this object's value using SNMP during normal 
             operation."  
       REFERENCE  
           "PacketCable NCS Specification"  
       DEFVAL    { 2727 }  
       ::= { pktcNcsEndPntConfigEntry 2 }  
    
   pktcNcsEndPntConfigPartialDialTO     OBJECT-TYPE  
       SYNTAX       Unsigned32  
       UNITS        "seconds"  
       MAX-ACCESS   read-create  
       STATUS       current  
       DESCRIPTION  
           "This object contains the maximum value of the partial dial 
            time out." 
       REFERENCE  
           "PacketCable NCS Specification"  
       DEFVAL { 16 }  
       ::= { pktcNcsEndPntConfigEntry 3 }  
    
   pktcNcsEndPntConfigCriticalDialTO     OBJECT-TYPE  
       SYNTAX       Unsigned32  
       UNITS        "seconds"  
       MAX-ACCESS   read-create  
       STATUS       current  
       DESCRIPTION  
           "This object contains the maximum value of the critical 
            dial time out." 
       REFERENCE  
           "PacketCable NCS Specification"  
       DEFVAL { 4 }  
       ::= { pktcNcsEndPntConfigEntry 4 }  
    
   pktcNcsEndPntConfigBusyToneTO     OBJECT-TYPE  
       SYNTAX       Unsigned32  
       UNITS        "seconds"  
       MAX-ACCESS   read-create  
       STATUS       current  
       DESCRIPTION  
           " This object contains the default timeout value for busy 
             tone. The MTA MUST NOT update this object with the 
             value provided in the NCS message (if present). If 
             the value of the object is modified by the SNMP Management 
             Station, the MTA MUST use the new value as a default only 
             for a new signal requested by the NCS message."  
       REFERENCE  
           "PacketCable NCS Specification"  
       DEFVAL    { 30 }  
       ::= { pktcNcsEndPntConfigEntry 5 }  
    
   pktcNcsEndPntConfigDialToneTO     OBJECT-TYPE  
       SYNTAX       Unsigned32  
       UNITS        "seconds"  
       MAX-ACCESS   read-create  
       STATUS       current  
       DESCRIPTION  
           " This object contains the default timeout value for dial 
             tone. The MTA MUST NOT update this object with the 
             value provided in the NCS message (if present). If 
             the value of the object is modified by the SNMP Management 
             Station, the MTA MUST use the new value as a default only 
             for a new signal requested by the NCS message."  
       REFERENCE  
           "PacketCable NCS Specification"  
       DEFVAL    { 16 }  
       ::= { pktcNcsEndPntConfigEntry 6 }  
    
   pktcNcsEndPntConfigMessageWaitingTO     OBJECT-TYPE  
       SYNTAX       Unsigned32  
       UNITS        "seconds"  
       MAX-ACCESS   read-create  
       STATUS       current  
       DESCRIPTION  
           " This object contains the default timeout value for message 
             waiting indicator. The MTA MUST NOT update this object 
             with the value provided in the NCS message (if 
             present). If the value of the object is modified by the 
             SNMP Management Station, the MTA MUST use the new value as 
             a default only for a new signal requested by the NCS 
             message."  
       REFERENCE  
           "PacketCable NCS Specification"  
       DEFVAL    { 16 }  
       ::= { pktcNcsEndPntConfigEntry 7 }  
    
   pktcNcsEndPntConfigOffHookWarnToneTO     OBJECT-TYPE  
       SYNTAX       Unsigned32  
       UNITS        "seconds"  
       MAX-ACCESS   read-create  
       STATUS       current  
       DESCRIPTION  
           " This object contains the default timeout value for the off 
             hook Warning tone. The MTA MUST NOT update this object 
             with the value provided in the NCS message (if 
             present). If the value of the object is modified by the 
             SNMP Management Station, the MTA MUST use the new value as 
             a default only for a new signal requested by the NCS 
             message."  
       REFERENCE  
           "PacketCable NCS Specification"  
       DEFVAL { 0 }  
       ::= { pktcNcsEndPntConfigEntry 8 }  
    
   pktcNcsEndPntConfigRingingTO     OBJECT-TYPE  
       SYNTAX       Unsigned32  
       UNITS        "seconds"  
       MAX-ACCESS   read-create  
       STATUS       current  
       DESCRIPTION  
           " This object contains the default timeout value for 
             ringing. The MTA MUST NOT update this object with the 
             value provided in the NCS message (if present). If 
             the value of the object is modified by the SNMP Management 
             Station, the MTA MUST use the new value as a default only 
             for a new signal requested by the NCS message."  
       REFERENCE  
           "PacketCable NCS Specification"  
       DEFVAL    { 180 }  
       ::= { pktcNcsEndPntConfigEntry 9 }  
    
   pktcNcsEndPntConfigRingBackTO     OBJECT-TYPE  
       SYNTAX       Unsigned32  
       UNITS        "seconds"  
       MAX-ACCESS   read-create  
       STATUS       current  
       DESCRIPTION  
           " This object contains the default timeout value for ring 
             back. The MTA MUST NOT update this object with the 
             value provided in the NCS message (if present). If 
             the value of the object is modified by the SNMP Management 
             Station, the MTA MUST use the new value as a default only 
             for a new signal requested by the NCS message."  
       REFERENCE  
           "PacketCable NCS Specification"  
       DEFVAL    { 180 }  
       ::= { pktcNcsEndPntConfigEntry 10 }  
    
   pktcNcsEndPntConfigReorderToneTO     OBJECT-TYPE  
       SYNTAX       Unsigned32  
       UNITS        "seconds"  
       MAX-ACCESS   read-create  
       STATUS       current  
       DESCRIPTION  
           " This object contains the default timeout value for reorder 
             tone. The MTA MUST NOT update this object with the 
             value provided in the NCS message (if present). If 
             the value of the object is modified by the SNMP Management 
             Station, the MTA MUST use the new value as a default only 
             for a new signal requested by the NCS message."  
       REFERENCE  
           "PacketCable NCS Specification"  
       DEFVAL    { 30 }  
       ::= { pktcNcsEndPntConfigEntry 11 }  
    
   pktcNcsEndPntConfigStutterDialToneTO     OBJECT-TYPE  
       SYNTAX       Unsigned32  
       UNITS        "seconds"  
       MAX-ACCESS   read-create  
       STATUS       current  
       DESCRIPTION  
           " This object contains the default timeout value for stutter 
             dial tone. The MTA MUST NOT update this object with the 
             value provided in the NCS message (if present). If 
             the value of the object is modified by the SNMP Management 
             Station, the MTA MUST use the new value as a default only 
             for a new signal requested by the NCS message."  
       REFERENCE  
             "PacketCable NCS Specification"  
       DEFVAL    { 16 }  
       ::= { pktcNcsEndPntConfigEntry 12 }  
    
   pktcNcsEndPntConfigTSMax     OBJECT-TYPE  
       SYNTAX      Unsigned32  
       MAX-ACCESS  read-create  
       STATUS      current  
       DESCRIPTION  
           "This object is used as part of a MTA retransmission 
            algorithm when communicating with a call agent. This object 
            contains the maximum time in seconds since the sending of 
            the initial datagram to a call agent. If more than 
            pktcNcsEndPntConfigTSMax time has elapsed, the endpoint 
            becomes disconnected." 
       REFERENCE  
           "PacketCable NCS Specification"  
       DEFVAL { 20 }  
       ::= { pktcNcsEndPntConfigEntry 13 }  
    
   pktcNcsEndPntConfigMax1     OBJECT-TYPE  
       SYNTAX      Unsigned32  
       MAX-ACCESS  read-create  
       STATUS      current  
       DESCRIPTION  
           "This object contains the suspicious error threshold for 
            signaling messages. The pktcNcsEndPntConfigMax1 object 
            indicates the retransmission threshold at which the MTA MAY 
            actively query the domain name server (DNS) in order to 
            detect the possible change of call agent interfaces." 
       REFERENCE  
           "PacketCable NCS Specification"  
       DEFVAL { 5 }  
       ::= { pktcNcsEndPntConfigEntry 14 }  
    
   pktcNcsEndPntConfigMax2     OBJECT-TYPE  
       SYNTAX      Unsigned32  
       MAX-ACCESS  read-create  
       STATUS      current  
       DESCRIPTION  
           "This object contains the disconnect error threshold for 
            signaling messages. The pktcNcsEndPntConfigMax2 object 
            indicates the retransmission threshold at which the MTA 
            SHOULD contact the DNS one more time to see if any other 
            interfaces to the call agent have become available." 
       REFERENCE  
           "PacketCable NCS Specification"  
       DEFVAL { 7 }  
       ::= { pktcNcsEndPntConfigEntry 15 }  
    
   pktcNcsEndPntConfigMax1QEnable     OBJECT-TYPE  
       SYNTAX      TruthValue  
       MAX-ACCESS  read-create  
       STATUS      current  
       DESCRIPTION  
           "This object enables/disables the Max1 domain name server 
            (DNS) query operation when the pktcNcsEndPntConfigMax1 
            threshold has been reached." 
       DEFVAL { true }  
       ::= { pktcNcsEndPntConfigEntry 16 }  
    
   pktcNcsEndPntConfigMax2QEnable     OBJECT-TYPE  
       SYNTAX      TruthValue  
       MAX-ACCESS  read-create  
       STATUS      current  
       DESCRIPTION  
           "This object enables/disables the Max2 domain name server 
            (DNS) query operation when the pktcNcsEndPntConfigMax2 
            threshold has been reached." 
       DEFVAL { true }  
       ::= { pktcNcsEndPntConfigEntry 17 }  
    
   pktcNcsEndPntConfigMWD     OBJECT-TYPE  
       SYNTAX      Unsigned32  
       UNITS       "seconds"  
       MAX-ACCESS  read-create  
       STATUS      current  
       DESCRIPTION  
           "Maximum Waiting Delay (MWD) contains the maximum number of 
            seconds a MTA waits after powering on, before initiating 
            the restart procedure with the call agent." 
       REFERENCE  
           "PacketCable NCS Specification"  
       DEFVAL { 600 }  
       ::= { pktcNcsEndPntConfigEntry 18 }  
    
   pktcNcsEndPntConfigTdinit     OBJECT-TYPE  
       SYNTAX      Unsigned32  
       UNITS       "seconds"  
       MAX-ACCESS  read-create  
       STATUS      current  
       DESCRIPTION  
           "This object contains the initial number of seconds the MTA  
            waits after a disconnect, before initiating the 
            disconnected procedure with the call agent." 
       REFERENCE  
           "PacketCable NCS Specification"  
       DEFVAL { 15 }  
       ::= { pktcNcsEndPntConfigEntry 19 }  
    
   pktcNcsEndPntConfigTdmin     OBJECT-TYPE  
       SYNTAX      Unsigned32  
       UNITS       "seconds"  
       MAX-ACCESS  read-create  
       STATUS      current  
       DESCRIPTION  
           " This object contains the minimum number of seconds the MTA  
             waits after a disconnect, before initiating the 
             disconnected procedure with the call agent."  
       REFERENCE  
           "PacketCable NCS Specification"  
       DEFVAL { 15 }  
       ::= { pktcNcsEndPntConfigEntry 20 }  
    
   pktcNcsEndPntConfigTdmax     OBJECT-TYPE  
       SYNTAX      Unsigned32  
       UNITS       "seconds"  
       MAX-ACCESS  read-create  
       STATUS      current  
       DESCRIPTION  
           " This object contains the maximum number of seconds the MTA  
             waits after a disconnect, before initiating the 
             disconnected procedure with the call agent. 
              "  
       REFERENCE  
           "PacketCable NCS Specification"  
       DEFVAL { 600 }  
       ::= { pktcNcsEndPntConfigEntry 21 }  
    
   pktcNcsEndPntConfigRtoMax     OBJECT-TYPE  
       SYNTAX      Unsigned32  
       UNITS       "seconds"  
       MAX-ACCESS  read-create  
       STATUS      current  
       DESCRIPTION  
           " This object contains the maximum number of seconds for the 
             retransmission timer. When this timer expires the MTA  
             retransmits the message."  
       REFERENCE  
           "PacketCable NCS Specification"  
       DEFVAL { 4 }  
       ::= { pktcNcsEndPntConfigEntry 22 }  
    
   pktcNcsEndPntConfigRtoInit     OBJECT-TYPE  
       SYNTAX      Unsigned32  
       UNITS       "milliseconds"  
       MAX-ACCESS  read-create  
       STATUS      current  
       DESCRIPTION  
           " This object contains the initial number of seconds for the 
             retransmission timer."  
       REFERENCE  
           "PacketCable NCS Specification"  
       DEFVAL { 200 }  
       ::= { pktcNcsEndPntConfigEntry 23 }  
    
   pktcNcsEndPntConfigLongDurationKeepAlive     OBJECT-TYPE  
       SYNTAX      Unsigned32  
       UNITS       "minutes"  
       MAX-ACCESS  read-create  
       STATUS      current  
       DESCRIPTION  
           " Specifies a timeout value in minutes for sending long 
             duration call notification message."  
       REFERENCE  
           "PacketCable NCS Specification"  
       DEFVAL { 60 }  
       ::= { pktcNcsEndPntConfigEntry 24 }  
    
   pktcNcsEndPntConfigThist  OBJECT-TYPE  
       SYNTAX      Unsigned32  
       UNITS       "seconds"  
       MAX-ACCESS  read-create  
       STATUS      current  
       DESCRIPTION  
           " Timeout period in seconds before no response is declared."  
       REFERENCE  
           "PacketCable NCS Specification"  
       DEFVAL { 30 } 
       ::= { pktcNcsEndPntConfigEntry 25 }  
    
   pktcNcsEndPntConfigStatus     OBJECT-TYPE  
       SYNTAX      RowStatus  
       MAX-ACCESS  read-create  
       STATUS      current  
       DESCRIPTION  
           " This object contains the Row Status associated with the 
             pktcNcsEndPntConfigTable. "  
       ::= { pktcNcsEndPntConfigEntry 26 }  
    
   pktcNcsEndPntConfigCallWaitingMaxRep     OBJECT-TYPE  
       SYNTAX      Unsigned32 (0..10)  
       MAX-ACCESS  read-create  
       STATUS      current  
       DESCRIPTION  
           " This object contains the default value of the maximum 
             number of repetitions of the call waiting tone that the 
             MTA will play from a single CMS request. The MTA MUST NOT 
             update this object with the information provided in the 
             NCS message (if present). If the value of the object is 
             modified by the SNMP Management Station, the MTA MUST use 
             the new value as a default only for a new signal 
             requested by the NCS message."  
       DEFVAL    { 1 }  
       ::= { pktcNcsEndPntConfigEntry 27 }  
    
   pktcNcsEndPntConfigCallWaitingDelay     OBJECT-TYPE  
       SYNTAX       Unsigned32 (1..100)  
       UNITS        "seconds"  
       MAX-ACCESS   read-create  
       STATUS       current  
       DESCRIPTION  
           " This object contains the delay between repetitions of the 
             call waiting tone that the MTA will play from a single CMS 
             request."  
       DEFVAL    { 10 }  
       ::= { pktcNcsEndPntConfigEntry 28 }  
    
   pktcNcsEndPntStatusCallIpAddressType  OBJECT-TYPE  
       SYNTAX      InetAddressType      
       MAX-ACCESS  read-only      
       STATUS      current      
       DESCRIPTION      
          " This object contains the type of Internet address of the 
            CMS currently being used for this endpoint."  
       ::= { pktcNcsEndPntConfigEntry 29 }  
    
   pktcNcsEndPntStatusCallIpAddress  OBJECT-TYPE  
       SYNTAX      InetAddress      
       MAX-ACCESS  read-only      
       STATUS      current      
       DESCRIPTION      
          " This object contains the Internet address of the CMS 
            currently being used for this endpoint. This Internet 
            address is used to create the appropriate security 
            association. The type of this IP address is determined by 
            the value of the pktcNcsEndPntStatusCallIpAddressType 
            object."  
   ::= { pktcNcsEndPntConfigEntry 30 }  
    
   pktcNcsEndPntStatusError  OBJECT-TYPE      
       SYNTAX INTEGER {  
                  operational (1), 
                  noSecurityAssociation (2), 
                  disconnected (3) 
                }      
       MAX-ACCESS   read-only      
       STATUS  current      
       DESCRIPTION  
          " This object contains the error status for this interface. 
            The operational status indicates that all operations 
            necessary to put the line in service have occurred, and the 
            CMS has acknowledged the Restart In Progress (RSIP) 
            message successfully. If pktcMtaDevCmsIpsecCtrl is enabled 
            for the associated Call Agent, the noSecurityAssociation 
            status indicates that no Security Association (SA) yet 
            exists for this endpoint. If pktcMtaDevCmsIpsecCtrl is 
            disabled for the associated Call Agent, the 
            noSecurityAssociation status is not applicable and should 
            not be used by the MTA. The disconnected status indicates 
            one of the following two: 
            If pktcMtaDevCmsIpsecCtrl is disabled, then no security 
            association is involved with this endpoint. The NCS 
            signaling software is in process of establishing the NCS 
            signaling link via an RSIP exchange. 
            Otherwise, when pktcMtaDevCmsIpsecCtrl is enabled,  
            security Association has been established, and the NCS 
            signaling software is in process of establishing the NCS 
            signaling link via an RSIP exchange." 
       ::= { pktcNcsEndPntConfigEntry 31 }  
    
   pktcNcsEndPntConfigMinHookFlash    OBJECT-TYPE  
       SYNTAX       Unsigned32 (20..1000)  
       UNITS        "Milliseconds"  
       MAX-ACCESS   read-only  
       STATUS       current  
       DESCRIPTION  
           " This is the minimum time a line needs to be on hook for a 
             valid hook flash. The value of this object MUST be 
             greater than the value of 
             pktcNcsEndPntConfigPulseDialMaxBreakTime. The value of 
             pktcNcsEndPntConfigMinHookFlash MUST be less than 
             pktcNcsEndPntConfigMaxHookFlash. This object MUST only be 
             set via the configuration file during the provisioning 
             process." 
       DEFVAL { 300 }  
       ::= { pktcNcsEndPntConfigEntry 32 }  
    
   pktcNcsEndPntConfigMaxHookFlash    OBJECT-TYPE  
       SYNTAX       Unsigned32 (20..1000)  
       UNITS        "Milliseconds"  
       MAX-ACCESS   read-only  
       STATUS       current  
       DESCRIPTION  
           " This is the maximum time a line needs to be on hook for a 
             valid hook flash. The value of 
             pktcNcsEndPntConfigMaxHookFlash MUST be greater than 
             pktcNcsEndPntConfigMinHookFlash. This object MUST only be 
             set via the configuration file during the provisioning 
             process." 
       DEFVAL { 800 }  
       ::= { pktcNcsEndPntConfigEntry 33 }  
    
   pktcNcsEndPntConfigPulseDialInterdigitTime    OBJECT-TYPE  
       SYNTAX       Unsigned32 (100..1500)  
       UNITS        "Milliseconds"  
       MAX-ACCESS   read-only  
       STATUS       current  
       DESCRIPTION  
           " This is the pulse dial inter-digit timeout. This object 
             MUST only be set via the configuration file during the 
             provisioning process."  
       DEFVAL { 100 }  
       ::= { pktcNcsEndPntConfigEntry 34 }  
    
   pktcNcsEndPntConfigPulseDialMinMakeTime    OBJECT-TYPE  
       SYNTAX       Unsigned32 (20..200)  
       UNITS        "Milliseconds"  
       MAX-ACCESS   read-only  
       STATUS       current  
       DESCRIPTION  
           " This is the minimum make pulse width for the dial pulse. 
             The value of pktcNcsEndPntConfigPulseDialMinMakeTime MUST 
             be less than pktcNcsEndPntConfigPulseDialMaxMakeTime. This 
             object MUST only be set via the configuration file during 
             the provisioning process."  
       DEFVAL { 25 }  
       ::= { pktcNcsEndPntConfigEntry 35 }  
    
   pktcNcsEndPntConfigPulseDialMaxMakeTime    OBJECT-TYPE  
       SYNTAX       Unsigned32 (20..200)  
       UNITS        "Milliseconds"  
       MAX-ACCESS   read-only  
       STATUS       current  
       DESCRIPTION  
           " This is the maximum make pulse width for the dial pulse. 
             The value of pktcNcsEndPntConfigPulseDialMaxMakeTime MUST 
             be greater than pktcNcsEndPntConfigPulseDialMinMakeTime. 
             This object MUST only be set via the configuration file 
             during the provisioning process."  
       DEFVAL { 55 }  
       ::= { pktcNcsEndPntConfigEntry 36 }  
    
   pktcNcsEndPntConfigPulseDialMinBreakTime    OBJECT-TYPE  
       SYNTAX       Unsigned32 (20..200)  
       UNITS        "Milliseconds"  
       MAX-ACCESS   read-only  
       STATUS       current  
       DESCRIPTION  
           " This is the minimum break pulse width for the dial pulse. 
             The value of pktcNcsEndPntConfigPulseDialMinBreakTime MUST 
             be less than pktcNcsEndPntConfigPulseDialMaxBreakTime. 
             This object must only be set via the configuration file 
             during the provisioning process."  
       DEFVAL { 45 }  
       ::= { pktcNcsEndPntConfigEntry 37 }  
    
   pktcNcsEndPntConfigPulseDialMaxBreakTime    OBJECT-TYPE  
       SYNTAX       Unsigned32 (20..200)  
       UNITS        "Milliseconds"  
       MAX-ACCESS   read-only  
       STATUS       current  
       DESCRIPTION  
           " This is the maximum break pulse width for the dial pulse. 
             The value of pktcNcsEndPntConfigPulseDialMaxBreakTime MUST 
             be greater than pktcNcsEndPntConfigPulseDialMinBreakTime. 
             This object MUST only be set via the configuration file 
             during the provisioning process."  
       DEFVAL { 75 }  
       ::= { pktcNcsEndPntConfigEntry 38 } 
    
   --  
   -- notification group is for future extension.  
   --   
   pktcSigNotification  OBJECT IDENTIFIER ::= { pktcIetfSigMib 0 }  
   pktcSigConformance   OBJECT IDENTIFIER ::= { pktcIetfSigMib 2 }  
   pktcSigCompliances   OBJECT IDENTIFIER ::= { pktcSigConformance 1 }  
   pktcSigGroups        OBJECT IDENTIFIER ::= { pktcSigConformance 2 }  
    
   --  
   -- compliance statements  
   --  
    
   pktcSigBasicCompliance  MODULE-COMPLIANCE  
       STATUS     current  
       DESCRIPTION  
           " The compliance statement for devices that implement 
             Signaling on the MTA." 
    
   MODULE  -- pktcIetfSigMib 
    
   --  
   --  unconditionally mandatory groups 
   --  
    
   MANDATORY-GROUPS {  
       pktcSigGroup  
   } 
    
   GROUP pktcNcsGroup  
       DESCRIPTION   
           " This group is mandatory for any MTA implementing NCS 
             signaling"  
    
   GROUP pktcInternationalGroup  
       DESCRIPTION   
           " This group is mandatory for any MTA implementing 
             international telephony features. In such cases, it is 
             left to manufacturers to determine whether to support both 
             PacketCable and IPCablecom objects in the same MTA." 
       ::={ pktcSigCompliances 1 } 
    
   --  
   -- units of conformance  
   --  
    
   pktcSigGroup  OBJECT-GROUP  
       OBJECTS {  
       pktcSigDevCodecMax,  
       pktcSigDevEchoCancellation,  
       pktcSigDevSilenceSuppression,  
       pktcSigDevR0Cadence,  
       pktcSigDevR1Cadence,  
       pktcSigDevR2Cadence,  
       pktcSigDevR3Cadence,  
       pktcSigDevR4Cadence,  
       pktcSigDevR5Cadence,  
       pktcSigDevR6Cadence,  
       pktcSigDevR7Cadence,  
       pktcSigDevRgCadence,  
       pktcSigDevRsCadence,  
       pktcSigDefCallSigDscp,  
       pktcSigDefMediaStreamDscp, 
       pktcSigDevVmwiMode,  
       pktcSignalingType,  
       pktcSignalingVersion,  
       pktcSignalingVendorExtension,  
       pktcSigDefNcsReceiveUdpPort  
       }  
       STATUS current  
       DESCRIPTION  
             "Group of objects for the common portion of the 
              PacketCable Signaling MIB."  
       ::= { pktcSigGroups 1 }   
    
   pktcNcsGroup  OBJECT-GROUP  
       OBJECTS {  
       pktcNcsEndPntConfigCallAgentId,  
       pktcNcsEndPntConfigCallAgentUdpPort,  
       pktcNcsEndPntConfigPartialDialTO,  
       pktcNcsEndPntConfigCriticalDialTO,  
       pktcNcsEndPntConfigBusyToneTO,  
       pktcNcsEndPntConfigDialToneTO,  
       pktcNcsEndPntConfigMessageWaitingTO,  
       pktcNcsEndPntConfigOffHookWarnToneTO,  
       pktcNcsEndPntConfigRingingTO,  
       pktcNcsEndPntConfigRingBackTO,  
       pktcNcsEndPntConfigReorderToneTO,  
       pktcNcsEndPntConfigStutterDialToneTO,  
       pktcNcsEndPntConfigTSMax,  
       pktcNcsEndPntConfigMax1,  
       pktcNcsEndPntConfigMax2,  
       pktcNcsEndPntConfigMax1QEnable,  
       pktcNcsEndPntConfigMax2QEnable,  
       pktcNcsEndPntConfigMWD,  
       pktcNcsEndPntConfigTdinit,  
       pktcNcsEndPntConfigTdmin,  
       pktcNcsEndPntConfigTdmax,  
       pktcNcsEndPntConfigRtoMax,  
       pktcNcsEndPntConfigRtoInit,  
       pktcNcsEndPntConfigLongDurationKeepAlive,  
       pktcNcsEndPntConfigThist,  
       pktcNcsEndPntConfigStatus,  
       pktcNcsEndPntConfigCallWaitingMaxRep,  
       pktcNcsEndPntConfigCallWaitingDelay,  
       pktcNcsEndPntStatusCallIpAddressType,  
       pktcNcsEndPntStatusCallIpAddress,  
       pktcNcsEndPntStatusError      
       }  
       STATUS current  
       DESCRIPTION  
             "Group of objects for the NCS portion of the PacketCable 
              Signaling MIB. This is mandatory for NCS signaling."  
       ::= { pktcSigGroups 2 }   
    
   pktcInternationalGroup    OBJECT-GROUP  
       OBJECTS {  
       pktcNcsEndPntConfigMinHookFlash,  
       pktcNcsEndPntConfigMaxHookFlash,  
       pktcNcsEndPntConfigPulseDialInterdigitTime,  
       pktcNcsEndPntConfigPulseDialMinMakeTime,  
       pktcNcsEndPntConfigPulseDialMaxMakeTime,  
       pktcNcsEndPntConfigPulseDialMinBreakTime,  
       pktcNcsEndPntConfigPulseDialMaxBreakTime,  
       pktcSigDevRingCadence,  
       pktcSigDevCallerIdSigProtocol,  
       pktcSigDevCIDMode,  
       pktcSigDevCIDFskAfterRing,  
       pktcSigDevCIDFskAfterDTAS,  
       pktcSigDevCIDFskAfterRPAS,  
       pktcSigDevCIDRingAfterFSK,  
       pktcSigDevCIDDTASAfterLR,  
       pktcSigDevVmwiFskAfterDTAS,  
       pktcSigDevVmwiFskAfterRPAS,  
       pktcSigDevVmwiDTASAfterLR,  
       pktcSigPowerRingFrequency,  
       pktcSigPulseSignalFrequency,   
       pktcSigPulseSignalDbLevel, 
       pktcSigPulseSignalDuration,  
       pktcSigPulseSignalPulseInterval, 
       pktcSigPulseSignalRepeatCount,  
       pktcSigDevToneDbLevel,  
       pktcSigDevToneFreqType,  
       pktcSigDevToneNumFrequencies,  
       pktcSigDevToneFirstFrequency,  
       pktcSigDevToneSecondFrequency,  
       pktcSigDevToneThirdFrequency,  
       pktcSigDevToneFourthFrequency,  
       pktcSigDevToneNumOnOffTimes,  
       pktcSigDevToneFirstToneOn,  
       pktcSigDevToneFirstToneOff,  
       pktcSigDevToneSecondToneOn,  
       pktcSigDevToneSecondToneOff,  
       pktcSigDevToneThirdToneOn,  
       pktcSigDevToneThirdToneOff,  
       pktcSigDevToneFourthToneOn,  
       pktcSigDevToneFourthToneOff,  
       pktcSigDevToneWholeToneRepeatCount,  
       pktcSigDevToneSteady  
       }  
       STATUS current  
       DESCRIPTION  
           " Group of objects that extend the behavior of existing  
             objects to support operations in the widest possible set 
             of international marketplaces.  Note that many of these 
             objects represent a superset of behaviors described in 
             other objects within this MIB Module."  
       ::= { pktcSigGroups 3 }  
    
   END
