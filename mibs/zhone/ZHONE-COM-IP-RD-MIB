--
-- comIpRD.mib
-- MIB generated by MG-SOFT Visual MIB Builder Version 2.0 Build 187
-- Tuesday, September 12, 2000 at 10:03:18
--

	ZHONE-COM-IP-RD-MIB DEFINITIONS ::= BEGIN

		IMPORTS 
			Integer32, OBJECT-TYPE, MODULE-IDENTITY, OBJECT-IDENTITY			
				FROM SNMPv2-SMI			
			TEXTUAL-CONVENTION			
				FROM SNMPv2-TC			
			zhoneIp, zhoneModules			
				FROM Zhone			
			ZhoneRowStatus			
				FROM Zhone-TC;
	
	
		comIpRd MODULE-IDENTITY
			LAST-UPDATED "200009111700Z"
			ORGANIZATION
				"Zhone Technologies, Inc."
			CONTACT-INFO
				"   Postal: 
				           Zhone Technologies, Inc.
				           @ Zhone Way
				           7001 Oakport Street
				           Oakland, CA  94621
				           USA
				Toll-Free: +1 877-ZHONE20 (+1 877-946-6320)
				      Tel: +1-510-777-7000
				      Fax: +1-510-777-7001
				   E-mail: support@zhone.com"
			DESCRIPTION
				"IP Routing Domain MIB
				IP Software
				Minneapolis, MN"
			REVISION "200009121002Z"
			DESCRIPTION
				"V01.00.00 - Initial Release"
			::= { zhoneModules 53 }
		
	
--
-- Textual conventions
--
	
		ZhoneRDIndex ::= TEXTUAL-CONVENTION
			STATUS current
			DESCRIPTION
				"Zhone Routing Domain Index.  A unique identifier for
				routing domains."
			SYNTAX Integer32 (0..2147483647)
			
	
--
-- Node definitions
--
	
		rd OBJECT-IDENTITY
			STATUS current
			DESCRIPTION
				"The MIB module representing Routing Domains (RD) in Zhone
				Technologies products.  A Routing Domain is an instance
				of a routing table."
			::= { zhoneIp 3 }
		
		rdTable OBJECT-TYPE
			SYNTAX SEQUENCE OF RdEntry
			MAX-ACCESS not-accessible
			STATUS current
			DESCRIPTION
				"The Routing Domain table contains top-level information
				on a Routing Domain.  Other tables should use the Routing
				Domain table index (rdIndex) rather than define their own.
				Rows are added by assigning rdIndex and setting rdRowStatus
				to createAndGo.  Rows are removed by setting rdRowStatus
				to destroy."
			::= { rd 1 }
		
		rdEntry OBJECT-TYPE
			SYNTAX RdEntry
			MAX-ACCESS not-accessible
			STATUS current
			DESCRIPTION
				"An entry in the Routing Domain table."
			INDEX { rdIndex }
			::= { rdTable 1 }
		
		RdEntry ::=
			SEQUENCE { 
				rdIndex
					ZhoneRDIndex,
				rdRowStatus
					ZhoneRowStatus
			 }

		rdIndex OBJECT-TYPE
			SYNTAX ZhoneRDIndex
			MAX-ACCESS not-accessible
			STATUS current
			DESCRIPTION
				"The Routing Domain (RD) table index."
			::= { rdEntry 1 }
		
		rdRowStatus OBJECT-TYPE
			SYNTAX ZhoneRowStatus
			MAX-ACCESS read-create
			STATUS current
			DESCRIPTION
				"The status of a Routing Domain entry."
			::= { rdEntry 2 }
		
	
	END

--
-- comIpRD.mib
--
