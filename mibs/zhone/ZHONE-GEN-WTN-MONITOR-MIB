--
-- genWtnMonitor.mib
-- MIB generated by MG-SOFT Visual MIB Builder Version 2.1 Build 205
-- Tuesday, June 12, 2001 at 09:35:59
--

    ZHONE-GEN-WTN-MONITOR-MIB DEFINITIONS ::= BEGIN

        IMPORTS 
            SnmpAdminString            
                FROM SNMP-FRAMEWORK-MIB            
            OBJECT-TYPE, MODULE-IDENTITY, OBJECT-IDENTITY            
                FROM SNMPv2-SMI            
            zhoneGenWtn, zhoneModules            
                FROM Zhone;
    
    
-- 
        zhoneGenWtnMonitorModule MODULE-IDENTITY
            LAST-UPDATED "0009281216Z"
            ORGANIZATION
                "Zhone Technologies, Inc."
            CONTACT-INFO
                "  Postal: 
                Zhone Technologies, Inc.
                @ Zhone Way
                7001 Oakport Street
                Oakland, CA  94621
                USA
                Toll-Free: +1 877-ZHONE20 (+1 877-946-6320)
                Tel: +1-510-777-7000
                Fax: +1-510-777-7001
                E-mail: support@zhone.com"
            DESCRIPTION
                "Module for wireless transport node (ZWT)
                variables which report general system status."
            REVISION "0105252136Z"
            DESCRIPTION
                "V01.01.00 - Removed ACO related objects.
                   Using SkyZhone_Stats_Profile."
            ::= { zhoneModules 102 }
        
    
    
--
-- Node definitions
--
    
        wtnMonitor OBJECT-IDENTITY
            STATUS current
            DESCRIPTION
                "Collection of monitored elements for each wireless transport node."
            ::= { zhoneGenWtn 1 }
        
        wtnLedStatus OBJECT-TYPE
            SYNTAX BITS
                {
                diag(0),
                operational(1),
                lineInterface(2),
                radio(3),
                local(4),
                remote(5)
                }
            MAX-ACCESS read-only
            STATUS current
            DESCRIPTION
                "Reflects current state of LEDs of indoor unit.
                A bit value of 1 indicates the LED is ON.
                A bit value of 0 indicates the LED of OFF.
                
                Meaning of LEDs:
                ===========================================
                diag -
                  Upon power up the LED is turned on.  If the unit
                successfully passes diagnostics, the LED is turned off.
                  When operational, the LED is turned on when diagnostics
                are performed or when the system detects an alarm.       
                
                operational -
                   Upon power up the LED is off.  When the system is
                operating it is turned on.
                   The actual LED is blinked when the ZMS link is down 
                or during software download.
                
                lineInterface -
                   This LED is turned on when there are no wire-line alarms.
                   For SkyZhone45 - this refers to the DS3 line.
                   For SkyZhone155 - this refers to the fiber.
                   For SkyZhone8e - this refers to the set of T1/E1 lines.
                
                radio -
                   This LED is turned on when there are no radio receive alarms. 
                
                local- 
                   This LED is turned on when there are not alarms present
                on the Near End indoor or outdoor units.
                
                remote -
                   This LED is turned on when there are not alarms present
                on the Far End indoor or outdoor units."
            ::= { wtnMonitor 1 }
        
        wtnAlarmStatus OBJECT-TYPE
            SYNTAX BITS
                {
                minorAlarm(0),
                criticalAlarm(1)
                }
            MAX-ACCESS read-only
            STATUS current
            DESCRIPTION
                "Alarm Contact Status.  
                   minorAlarm(0) - when active, a minor alarm condition is present
                   criticalAlarm(1) - when active, a critical alarm condition is present.
                
                On power up all alarms contacts are open/inactive (0)."
            ::= { wtnMonitor 2 }
        
        radioLinkConfiguration OBJECT-IDENTITY
            STATUS current
            DESCRIPTION
                "Description."
            ::= { zhoneGenWtn 2 }
        
        wtnLinkName OBJECT-TYPE
            SYNTAX SnmpAdminString
            MAX-ACCESS read-write
            STATUS current
            DESCRIPTION
                "Textual description which identifies link.
                A link is comprised of this and another SkyZhone
                node at the far end."
            ::= { radioLinkConfiguration 1 }
        
    
    END

--
-- genWtnMonitor.mib
--
