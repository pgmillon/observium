--
-- comVideo.mib
-- MIB generated by MG-SOFT Visual MIB Builder Version 3.0 Build 271
-- Friday, October 31, 2003 at 15:46:17
--

        ZHONE-COM-VIDEO-MIB DEFINITIONS ::= BEGIN
 
                IMPORTS
                        ifIndex                        
                                FROM IF-MIB                        
                        ifPhysAddress                        
                                FROM RFC1213-MIB                        
                        OBJECT-GROUP                        
                                FROM SNMPv2-CONF                        
                        IpAddress, Integer32, OBJECT-TYPE, MODULE-IDENTITY                        
                                FROM SNMPv2-SMI                        
                        zhoneVideo, zhoneModules                        
                                FROM Zhone                        
                        ZhoneRowStatus                        
                                FROM Zhone-TC;
        
        
-- To create generated mib handler: 
-- /vob/EPILOGUE/binaries/emissary/solaris/mibcomp iftype.mib Zhone.mib Zhone-TC.mib rfc1907.mib rfc2233.mib rfc2514.mib rfc1213.mib -stub -o videoHdlr.c comVideo.mib
-- 
-- To create generated protection layer:
--  /vob/zhonetools/bin/pahrser.pl iftype.mib Zhone.mib Zhone-TC.mib rfc2514.mib rfc2233.mib comVideo.mib
-- 
-- 
-- 
-- 
                comVideo MODULE-IDENTITY 
                        LAST-UPDATED "200310281012Z"		-- October 28, 2003 at 10:12 GMT
                        ORGANIZATION 
                                "Zhone Technologies, Inc."
                        CONTACT-INFO 
                                "  Postal: 
                                Zhone Technologies, Inc.
                                @ Zhone Way
                                7001 Oakport Street
                                Oakland, CA  94621
                                USA
                                Toll-Free: +1 877-ZHONE20 (+1 877-946-6320)
                                Tel: +1-510-777-7000
                                Fax: +1-510-777-7001
                                E-mail: support@zhone.com"
                        DESCRIPTION 
                                "Zhone Video MIB.
                                "
                        REVISION "200310281100Z"		-- October 28, 2003 at 11:00 GMT
                        DESCRIPTION
                                "V01.00.00 - Initial Release"
                        ::= { zhoneModules 78 }
                
        
        
        
--
-- Node definitions
--
        
                -- 1.3.6.1.4.1.5504.4.8.1
                videoGroup OBJECT-GROUP
                        OBJECTS { videoInterfaceRowStatus, videoInterfaceType, videoMulticastSourceRowStatus, videoMulticastSourceIpAddress, videoMulticastSourceNetMask, 
                                videoMulticastSourceIndexNext }
                        STATUS current
                        DESCRIPTION 
                                "Description."
                        ::= { zhoneVideo 1 }
                
                -- 1.3.6.1.4.1.5504.4.8.2
                videoInterfaceTable OBJECT-TYPE
                        SYNTAX SEQUENCE OF VideoInterfaceEntry
                        MAX-ACCESS not-accessible
                        STATUS current
                        DESCRIPTION
                                "Used to provision management, stream and client
                                interfaces.  This table resides on the Zhone
                                Residential Gateway (ZRG) and is a CPE device.
                                
                                Each entry in this table is indexed by an IP
                                interface, and subsequently points to an
                                IP interface record.  The videoInterfaceType
                                can be either management, stream or client,
                                and depending upon which it is, various fields
                                within the IP interface are used as follows:
                                
                                managment: ip address.
                                stream: ip address, netmask, vpi, vci.
                                client: ip address, netmask.
                                
                                Management interface is used to send an IGMP
                                request from the CPE to the upstream head-end 
                                video gateway or other device which interacts with
                                the video gateway.
                                
                                Stream interface is used to associate an ip address
                                to a vpi/vci (VCL).
                                 
                                Client interface is used to define the netmask for
                                a given ip address."
                        ::= { zhoneVideo 2 }
                
                -- 1.3.6.1.4.1.5504.4.8.2.1
                videoInterfaceEntry OBJECT-TYPE
                        SYNTAX VideoInterfaceEntry
                        MAX-ACCESS not-accessible
                        STATUS current
                        DESCRIPTION
                                "See Table description above."
                        INDEX { ifIndex }
                        ::= { videoInterfaceTable 1 }
                
                VideoInterfaceEntry ::=
                        SEQUENCE { 
                                videoInterfaceRowStatus
                                        ZhoneRowStatus,
                                videoInterfaceType
                                        INTEGER
                         }

                -- 1.3.6.1.4.1.5504.4.8.2.1.1
                videoInterfaceRowStatus OBJECT-TYPE
                        SYNTAX ZhoneRowStatus
                        MAX-ACCESS read-create
                        STATUS current
                        DESCRIPTION
                                "Row Status used to create, delete or modify a row."
                        ::= { videoInterfaceEntry 1 }
                
                -- 1.3.6.1.4.1.5504.4.8.2.1.2
                videoInterfaceType OBJECT-TYPE
                        SYNTAX INTEGER
                                {
                                management(1),
                                stream(2),
                                client(3)
                                }
                        MAX-ACCESS read-create
                        STATUS current
                        DESCRIPTION
                                "Defines which type of video interface this row
                                represents.  Either management, stream or client."
                        DEFVAL { management }
                        ::= { videoInterfaceEntry 2 }
                
                -- 1.3.6.1.4.1.5504.4.8.3
                videoMulticastSourceTable OBJECT-TYPE
                        SYNTAX SEQUENCE OF VideoMulticastSourceEntry
                        MAX-ACCESS not-accessible
                        STATUS current
                        DESCRIPTION
                                "Used to provision multicast source addresses used by
                                the Zhone Residential Gateway."
                        ::= { zhoneVideo 3 }
                
                -- 1.3.6.1.4.1.5504.4.8.3.1
                videoMulticastSourceEntry OBJECT-TYPE
                        SYNTAX VideoMulticastSourceEntry
                        MAX-ACCESS not-accessible
                        STATUS current
                        DESCRIPTION
                                "See Table description above."
                        INDEX { videoMulticastSourceIndex }
                        ::= { videoMulticastSourceTable 1 }
                
                VideoMulticastSourceEntry ::=
                        SEQUENCE { 
                                videoMulticastSourceIndex
                                        Integer32,
                                videoMulticastSourceRowStatus
                                        ZhoneRowStatus,
                                videoMulticastSourceIpAddress
                                        IpAddress,
                                videoMulticastSourceNetMask
                                        IpAddress
                         }

                -- 1.3.6.1.4.1.5504.4.8.3.1.1
                videoMulticastSourceIndex OBJECT-TYPE
                        SYNTAX Integer32 (1..2147483647)
                        MAX-ACCESS not-accessible
                        STATUS current
                        DESCRIPTION
                                "Index value for this entry.
                                
                                videoMulticastSourceIndexNext must be queried first,
                                and the result used to create an entry in this table."
                        ::= { videoMulticastSourceEntry 1 }
                
                -- 1.3.6.1.4.1.5504.4.8.3.1.2
                videoMulticastSourceRowStatus OBJECT-TYPE
                        SYNTAX ZhoneRowStatus
                        MAX-ACCESS read-write
                        STATUS current
                        DESCRIPTION
                                "Row Status used to create, delete or modify a row."
                        ::= { videoMulticastSourceEntry 2 }
                
                -- 1.3.6.1.4.1.5504.4.8.3.1.3
                videoMulticastSourceIpAddress OBJECT-TYPE
                        SYNTAX IpAddress
                        MAX-ACCESS read-write
                        STATUS current
                        DESCRIPTION
                                "Multicast source address."
                        ::= { videoMulticastSourceEntry 3 }
                
                -- 1.3.6.1.4.1.5504.4.8.3.1.4
                videoMulticastSourceNetMask OBJECT-TYPE
                        SYNTAX IpAddress
                        MAX-ACCESS read-write
                        STATUS current
                        DESCRIPTION
                                "Multicast source netmask value."
                        ::= { videoMulticastSourceEntry 4 }
                
                -- 1.3.6.1.4.1.5504.4.8.4
                videoMulticastSourceIndexNext OBJECT-TYPE
                        SYNTAX Integer32 (1..2147483647)
                        MAX-ACCESS read-only
                        STATUS current
                        DESCRIPTION
                                "This value is read in order to get the next
                                available index to be used to create a new
                                entry within the videoMulticastSourceTable."
                        ::= { zhoneVideo 4 }
                
        
        END

--
-- comVideo.mib
--
