-- ===================================================================
-- == Copyright (C) 2004 Paradyne Corporation.                      ==
-- ===================================================================

PDN-HDLC-MIB DEFINITIONS ::= BEGIN

IMPORTS
   MODULE-IDENTITY, OBJECT-TYPE, Counter32
      FROM SNMPv2-SMI
   OBJECT-GROUP, MODULE-COMPLIANCE
      FROM SNMPv2-CONF
   ifIndex
      FROM IF-MIB
   pdn-interfaces
      FROM PDN-HEADER-MIB;
        
pdnHdlcMIB MODULE-IDENTITY
   LAST-UPDATED "200409100000Z"  -- September 10, 2004
   ORGANIZATION "Paradyne Networks
                 MIB Working Group
                 Other information about group editing the MIB"
   CONTACT-INFO "Paradyne Networks, Inc.
                 8545 126th Avenue North
                 Largo, FL 33733
                 www.paradyne.com
        
                 General Comments to: mibwg_team@paradyne.com

                 Editor
                    Clay Sikes"

   DESCRIPTION  "The MIB module provides objects to manage an 
                 interface's High-level Data Link Control (HDLC)
                 protocol."

   REVISION     "200409100000Z"  -- September 10, 2004
   DESCRIPTION  "Initial release."

::=  { pdn-interfaces 26 }



-- ====================================================================
-- == Define groups for Notifications, MIB Objects, Accessible for   ==
-- == Notifications (AFNs), and Conformance.                         ==
-- == These may just be place holders.                               ==
-- ====================================================================
pdnHdlcNotifications OBJECT IDENTIFIER ::= { pdnHdlcMIB 0 }
pdnHdlcObjects       OBJECT IDENTIFIER ::= { pdnHdlcMIB 1 }
pdnHdlcAFNs          OBJECT IDENTIFIER ::= { pdnHdlcMIB 2 } 
pdnHdlcConformance   OBJECT IDENTIFIER ::= { pdnHdlcMIB 3 }




-- ====================================================================
-- ==                  Textual Conventions                           ==
-- ====================================================================
-- None defined.




-- ====================================================================
-- ==                  MIB Objects                                   ==
-- ====================================================================




-- ===================================================================
-- == pdnHdlcStatsTotalTable                                        ==
-- ===================================================================
pdnHdlcStatsTotalTable  OBJECT-TYPE
   SYNTAX      SEQUENCE OF PdnHdlcStatsTotalEntry
   MAX-ACCESS  not-accessible
   STATUS      current
   DESCRIPTION "The HDLC Total Statistics Table.  This table contains 
                counters for statistics.  Counters in this group 
                contain `total' counts which are marked from the time 
                the system was last re-initialized."
   ::= { pdnHdlcObjects 1 }

pdnHdlcStatsTotalEntry  OBJECT-TYPE
   SYNTAX      PdnHdlcStatsTotalEntry
   MAX-ACCESS  not-accessible
   STATUS      current
   DESCRIPTION "An entry in the HDLC Total Statistics Table."
   INDEX       { ifIndex }
   ::= { pdnHdlcStatsTotalTable 1 }

PdnHdlcStatsTotalEntry ::=
   SEQUENCE {
      pdnHdlcStatsTotalRxGood              Counter32,
      pdnHdlcStatsTotalRxCRCErrors         Counter32,
      pdnHdlcStatsTotalRxAborts            Counter32,
      pdnHdlcStatsTotalRxBadAddress        Counter32,
      pdnHdlcStatsTotalRxNoBufAvail        Counter32,
      pdnHdlcStatsTotalReceiverOverrun     Counter32,
      pdnHdlcStatsTotalRxMaxSizeExceeded   Counter32,
      pdnHdlcStatsTotalTx                  Counter32,
      pdnHdlcStatsTotalTxBufUnderrun       Counter32
   }

pdnHdlcStatsTotalRxGood  OBJECT-TYPE
   SYNTAX      Counter32
   MAX-ACCESS  read-only
   STATUS      current
   DESCRIPTION "The number of HDLC frames that were received without
                any errors."
   ::= { pdnHdlcStatsTotalEntry 1 }

pdnHdlcStatsTotalRxCRCErrors  OBJECT-TYPE
   SYNTAX      Counter32
   MAX-ACCESS  read-only
   STATUS      current
   DESCRIPTION "The number of HDLC frames that were received with 
                CRC errors."
   ::= { pdnHdlcStatsTotalEntry 2 }

pdnHdlcStatsTotalRxAborts  OBJECT-TYPE
   SYNTAX      Counter32
   MAX-ACCESS  read-only
   STATUS      current
   DESCRIPTION "The number of HDLC frames that were aborted during
                receive."
   ::= { pdnHdlcStatsTotalEntry 3 }

pdnHdlcStatsTotalRxBadAddress  OBJECT-TYPE
   SYNTAX      Counter32
   MAX-ACCESS  read-only
   STATUS      current
   DESCRIPTION "The number of HDLC frames that were discarded due
                to a bad address."
   ::= { pdnHdlcStatsTotalEntry 4 }

pdnHdlcStatsTotalRxNoBufAvail  OBJECT-TYPE
   SYNTAX      Counter32
   MAX-ACCESS  read-only
   STATUS      current
   DESCRIPTION "The number of HDLC frames that were discarded because
                no receive buffers were available."
   ::= { pdnHdlcStatsTotalEntry 5 }

pdnHdlcStatsTotalReceiverOverrun  OBJECT-TYPE
   SYNTAX      Counter32
   MAX-ACCESS  read-only
   STATUS      current
   DESCRIPTION "The number of times a receiver overrun occurred."
   ::= { pdnHdlcStatsTotalEntry 6 }

pdnHdlcStatsTotalRxMaxSizeExceeded  OBJECT-TYPE
   SYNTAX      Counter32
   MAX-ACCESS  read-only
   STATUS      current
   DESCRIPTION "The number of times a frame was received which was 
                discarded due to the frame size exceeding the maximum
                frame size for the receiver."
   ::= { pdnHdlcStatsTotalEntry 7 }

pdnHdlcStatsTotalTx  OBJECT-TYPE
   SYNTAX      Counter32
   MAX-ACCESS  read-only
   STATUS      current
   DESCRIPTION "The number of HDLC frames transmitted."
   ::= { pdnHdlcStatsTotalEntry 8 }

pdnHdlcStatsTotalTxBufUnderrun  OBJECT-TYPE
   SYNTAX      Counter32
   MAX-ACCESS  read-only
   STATUS      current
   DESCRIPTION "The number of times a transmitter underrun occurred."
   ::= { pdnHdlcStatsTotalEntry 9 }



-- ====================================================================
-- ==                  Accessible for Notifications (AFNs)           ==
-- ====================================================================
-- None defined



-- ===================================================================
-- ==                  Traps/Notifications                          ==
-- ===================================================================
-- None defined



-- ====================================================================
-- ==                  Conformance Information                       ==
-- ====================================================================

pdnHdlcCompliances  OBJECT IDENTIFIER ::= { pdnHdlcConformance 1 }
pdnHdlcGroups       OBJECT IDENTIFIER ::= { pdnHdlcConformance 2 }


-- ===========================
-- == Compliance Statements ==
-- ===========================


pdnHdlcCompliance  MODULE-COMPLIANCE
   STATUS      current
   DESCRIPTION "The compliance statement for network elements 
                implementing HDLC Protocol."
   MODULE      -- this module
   -- No mandatory groups are specified.  
   
   GROUP       pdnHdlcStatsTotalGroup
   DESCRIPTION "This group is only required for implementations that
                need to display total HDLC statistics."
    ::= { pdnHdlcCompliances 1 }


-- ==========================
-- == Units of Conformance ==
-- ==========================

pdnHdlcObjGroups   OBJECT IDENTIFIER ::= { pdnHdlcGroups 1 }
pdnHdlcAfnGroups   OBJECT IDENTIFIER ::= { pdnHdlcGroups 2 }
pdnHdlcNtfyGroups  OBJECT IDENTIFIER ::= { pdnHdlcGroups 3 }


-- ===================
-- == Object Groups ==
-- ===================


pdnHdlcStatsTotalGroup  OBJECT-GROUP
   OBJECTS {
      pdnHdlcStatsTotalRxGood,
      pdnHdlcStatsTotalRxCRCErrors,
      pdnHdlcStatsTotalRxAborts,
      pdnHdlcStatsTotalRxBadAddress,
      pdnHdlcStatsTotalRxNoBufAvail,
      pdnHdlcStatsTotalReceiverOverrun,
      pdnHdlcStatsTotalRxMaxSizeExceeded,
      pdnHdlcStatsTotalTx,
      pdnHdlcStatsTotalTxBufUnderrun
   }
   STATUS      current
   DESCRIPTION "Displays various HDLC related total counters."
   ::= { pdnHdlcObjGroups 1 }



-- =========================================
-- == Accessible for Notifications Groups ==
-- =========================================
-- None defined



-- =========================
-- == Notification Groups ==
-- =========================
-- None defined




-- =========
-- == END ==
-- =========
END
