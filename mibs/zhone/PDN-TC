PDN-TC DEFINITIONS ::=  BEGIN

-- Copyright (C) 2002 Paradyne Corporation.
-- Enterprise Textual Convention MIB
-- Version : 0.2 DRAFT 

-- Last Updated Sue Alfano 08/13/2002
-- Last Updated Sue Alfano 05/7/2002
-- Last Updated Wayne Jadoo 10/7/1999
-- Last Updated Wayne Jadoo 10/4/1999
-- Last Update Wayne Jadoo 09/28/1999
-- Last Updated Wayne Jadoo 09/27/1999
-- Last Updated : Wayne Jadoo 08/31/99

-- The textual Conversion MIB contains the definitions of objects that  are used
-- for defining  objects in other MIBs. This file can be imported by the other  
-- MIBs in order to use the pre-defined objects. Textual conventions for new  
-- objects can  be added to this file.

-- History
-- 08/25/1999  Wayne Jadoo
--   Initial Version.
-- 09/27/1999  Wayne Jadoo
--   Commented out textual conventions so 
--   to be compatible to SNMP-V1 
-- 09/28/99 Wayne Jadoo
--   Added TC for TAddress , MacAddress and TruthValue
-- 10/04/99 Wayne Jadoo
--   Removed TC for Tadddress, MacAddress and TruthValue 
--   DateAndTime and SnmpAdminString and moved to rfc1901v1.mi
-- Wayne Jadoo 10/7/99
--   Imported PDN-HEADER-HEADER mib 
--   and added TC for SnmpAdminString.
-- Kevin Baughman 10/27/99
--   Converted back to smiv2
-- Rajesh Raghavan 9/21/2000
--   Added TC for TimeOfDay
-- Sue Alfano 5/7/2002
--   Added new enum to NTPMode, removed reference to DisplayString
--   (MIB compile doesn't allow definition in TC to use syntax
--   from another TC)
-- 
-- Jesus Pinto 8/13/2002
--   Added TC for ContactState. 
-- 

IMPORTS 

TEXTUAL-CONVENTION
  FROM SNMPv2-TC 
enterprises
  FROM RFC1155-SMI;

-- Not having an object defined causes errors for HP OpenView
pdyn           OBJECT IDENTIFIER ::= { enterprises 1795 }

-- ==========================================================

VnidMode ::= TEXTUAL-CONVENTION
     STATUS       current
     DESCRIPTION
	"This object describes the configuration mode
  	for VNIDs and ports. "

     SYNTAX INTEGER { implicit(1), explicit(2), notagging(3) }

ClientState ::= TEXTUAL-CONVENTION
     STATUS current
     DESCRIPTION
       " The configuration type for a client."
     SYNTAX INTEGER { static(1), dynamic(2)}

VnidTaggingState ::=  TEXTUAL-CONVENTION
     STATUS current
     DESCRIPTION
        " This object indicates whether VNID tagging 
        is activated or de-activated."
     SYNTAX	INTEGER { enabled(1), disabled(2)}

VnidRange ::= TEXTUAL-CONVENTION
     STATUS current
     DESCRIPTION
        " The valid range for VNID IDs"
     SYNTAX INTEGER ( 2..4000 )

SwitchState ::= TEXTUAL-CONVENTION
     STATUS current
     DESCRIPTION
        " This object indicates whether an object state is 
        in the enabled or disabled state "
     SYNTAX INTEGER { enabled(1), disabled(2)}

ResetStates ::= TEXTUAL-CONVENTION
     STATUS current
     DESCRIPTION
        "This object defines the enumerations
        of values that can be applied to the reset
        object"
     SYNTAX INTEGER { 
                      noOp(1), 
		      reset(2), 
		      resetToFactoryDefaults(3), 
		      resetToNewActiveConfig(4) 
     }

ResultTypes ::=  TEXTUAL-CONVENTION
     STATUS current
     DESCRIPTION
        "This object defines the enumerations
        for the result of an operation "
     SYNTAX INTEGER {
                none(1),
                success(2),
                failure(3),
                inProgress(4)
     }

InitiatorTypes ::=  TEXTUAL-CONVENTION
     STATUS current
     DESCRIPTION
        "This object defines the enumerations
        for the result of an operation "
     SYNTAX INTEGER {
             noop(1),
             telnet(2),
             console(3),
             snmp(4)
           }

NTPMode ::= TEXTUAL-CONVENTION
     STATUS current
     DESCRIPTION
           "This object describes the mode in which NTP/SNTP will operate."
     SYNTAX INTEGER {
                  unicast(1),
                  broadcast(2),
                  multicast(3)
          }

DNSServerType ::= TEXTUAL-CONVENTION
    STATUS  current
    DESCRIPTION
           "This object describes the DNS server Type"
	SYNTAX  INTEGER {
                  primary(1),
                  secondary(2)
                 }


MibOidType ::=  TEXTUAL-CONVENTION
    STATUS  current
    DESCRIPTION
        "This Object describes the type of a mib object
              Scalar - Single Instance Object
              Table - Multi-instance Object
              Mib - A Mib.
                 Section - A Section Within A MIB"
    SYNTAX INTEGER {
                    scalar (1),
                    table (2),
                    mib (3),
                    section (4)
                 }

SocketType ::=  TEXTUAL-CONVENTION
    STATUS  current
    DESCRIPTION
           "This object describes the type of socket"
    SYNTAX INTEGER {
                    unknown(1),
                    stream(2),
                    datagram(3),
                    rawProtocol(4),
                    reliableMessageDelivery(5),
                    sequencedPacket(6)
                   }


SocketFamily ::=  TEXTUAL-CONVENTION
     STATUS  current
     DESCRIPTION
            "This object describes the socket Family"
     SYNTAX  INTEGER {
                           unknown(1),
                           unix(2),
                           darpaInternet(3),
                           darpaIMP(4),
                           pUP(5),
                           cHAOSFamily(6),
                           xeroxNovell(7),
                           nBS(8),
                           eCMA(9),
                           dATAKIT(10),
                           cCITT(11),
                           sNA(12),
                           dECnet(13),
                           directDataLinkInterface(14),
                           dECLAT(15),
                           nSCHyperChannel(16),
                           appleTalk(17),
                           netqorkInterfaceTap(18),
                           iEEE8020ISO8802(19),
                           oSI(20),
                           x25(21),
                           oSIAFI47IDI4(22),
                           uSGovermentOSI(23)
                   }

SocketState ::=  TEXTUAL-CONVENTION
       STATUS  current
       DESCRIPTION
              "This object describes the state of a stream socket"
       SYNTAX INTEGER {
                          closed (1),
                          listen (2),
                          sYNSent(3),
                          sYNRCVD(4),
                          established(5),
                          closeWait(6),
                          fINWait(7),
                          closing(8),
                          lastAck(9),
                          fINWait2(10),
                          timeWait(11)
                 }

DomainName ::=  TEXTUAL-CONVENTION
       STATUS  current
       DESCRIPTION
            "The domain name space is a tree structure.  Each node and 
            leaf on the tree corresponds to a resource set (which may be 
            empty).  The domain system makes no distinctions between the 
            uses of the interior nodes and leaves, and this memo uses the 
            term 'node' to refer to both. Each node has a label, which is 
            zero to 63 octets in length.  Brother nodes may not have the 
            same label, although the same label can be used for nodes 
            which are not brothers.  One label is reserved, and that is
            the null (i.e., zero length) label used for the root.
            The domain name of a node is the list of the labels on the 
            path from the node to the root of the tree.  By convention, 
            the labels that compose a domain name are printed or read 
            left to right, from the most specific (lowest, farthest from 
            the root) to the least specific (highest, closest to the 
            root).
 
            Internally, programs that manipulate domain names should 
            represent them as sequences of labels, where each label is a 
            length octet followed by  an octet string.  Because all domain 
            names end at the root, which has a null string for a label, 
            these internal representations can use a length byte of zero 
            to terminate a domain name.
 
            By convention, domain names can be stored with arbitrary case, but
            domain name comparisons for all present domain functions are done in 
            a case-insensitive manner, assuming an ASCII character set, and a 
            high order zero bit.  This means that you are free to create a node 
            with label 'A' or a node with label 'a', but not both as brothers; 
            you could refer to either using 'a' or 'A'.  When you receive a 
            domain name or label, you should preserve its case.  The rationale 
            for this  choice is that we may someday need to add full binary 
            domain names for  new services; existing services would not be 
            changed.
 
            When a user needs to type a domain name, the length of each label is
            omitted and the labels are separated by dots ('.').  Since a complete
            domain name ends with the root label, this leads to a printed form 
            which ends in a dot.  We use this property to distinguish between:
 
            character string which represents a complete domain name
            (often called 'absolute').  For example, 'poneria.ISI.EDU.'
 
           - a character string that represents the starting labels of a
           domain name which is incomplete, and should be completed by
           local software using knowledge of the local domain (often
           called 'relative').  For example, 'poneria' used in the
           ISI.EDU domain.
 
           Relative names are either taken relative to a well known 
           origin, or to a list of domains used as a search list.  Relative 
           names appear mostly at the user interface, where their interpretation 
           varies  from implementation to implementation, and in master files, 
           where they  are  relative to a single origin domain name.  The most 
           common interpretation uses the root '.' as either the single origin 
           or as one of the members of the search list, so a multi-label relative 
           name is often one where the trailing dot has been omitted to save 
           typing.
 
           To simplify implementations, the total number of octets that represent  a
           domain name (i.e., the sum of all label octets and label lengths) is
           limited to 255.
 
           A domain is identified by a domain name, and consists of that part of
           the domain name space that is at or below the domain name which
           specifies the domain.  A domain is a subdomain of another domain if it
           is contained within that domain.  This relationship can be tested by
           seeing if the subdomain's name ends with the containing domain's name.
           For example, A.B.C.D is a subdomain of B.C.D, C.D, D, and  '.' "
        SYNTAX OCTET STRING (SIZE (1..64))

   SnmpAdminString ::= TEXTUAL-CONVENTION
        DISPLAY-HINT "255a"
        STATUS       current
        DESCRIPTION "An octet string containing administrative
           information, preferably in human-readable form.
 
           To facilitate internationalization, this
           information is represented using the ISO/IEC
           IS 10646-1 character set, encoded as an octet
           string using the UTF-8 transformation format
           described in [RFC2044].
 
           Since additional code points are added by
           amendments to the 10646 standard from time
           to time, implementations must be prepared to
           encounter any code point from 0x00000000 to
           0x7fffffff.
 
           The use of control codes should be avoided.
 
           When it is necessary to represent a newline,
           the control code sequence CR LF should be used.
 
 
           The use of leading or trailing white space should
           be avoided.
 
           For code points not directly supported by user
           interface hardware or software, an alternative
           means of entry and display, such as hexadecimal,
           may be provided.
 
           For information encoded in 7-bit US-ASCII,
           the UTF-8 encoding is identical to the
           US-ASCII encoding.
 
           Note that when this TC is used for an object that
           is used or envisioned to be used as an index, then
           a SIZE restriction must be specified so that the
           number of sub-identifiers for any object instance
           does not exceed the limit of 128, as defined by
           [RFC1905].
                "
    SYNTAX OCTET STRING (SIZE (0..255))

InetAddressType ::= TEXTUAL-CONVENTION
  STATUS       current
  DESCRIPTION
    "This object describes the type of address configured 
     for a interface"
  SYNTAX INTEGER { primary (1), secondary (2) }

ManagementType ::= TEXTUAL-CONVENTION
	STATUS current
	DESCRIPTION
	"This object is used to specify the type of
	management. This can be either Inband
	Management or OutBand Management."
	SYNTAX INTEGER
	{
		inband  (1),
		outband (2)
	}

ContactState ::= TEXTUAL-CONVENTION
	STATUS current
	DESCRIPTION
	"This convension can be used to indicate the
	state of a switch, door, connector, etc. that
	can be by nature opened or closed."
	SYNTAX INTEGER
	{
		open  (1),
		close (2)
	}

IdslClockMode ::= TEXTUAL-CONVENTION
	STATUS current
	DESCRIPTION
    "This object indicates the network clock mode set
    for the secondary network clock. IDSL portcards with a
    port configured as an NT will be set to
    portCardDriveClockOnboard(4), both driving the backplane
    and using the clock for the other Local Timing transceivers
    on the card. Port cards with only LT ports configured will
    receive a clock from the backplane using portCardSinkClock(2).
    portCardDriveClock(3) will drive the backplane alone."
   SYNTAX INTEGER 
   {
      triState(1),
      portCardSinkClock(2),
      portCardDriveClock(3),
      portCardDriveClockOnboard(4)
   }

TimeOfDay ::= TEXTUAL-CONVENTION
    DISPLAY-HINT "1d:1d"
    STATUS	current
    DESCRIPTION
	"A time of day specification

	field	octets	contents	range
	-----	------	--------	-----
	  1	   1	hour		0..23
	  2	   2	minutes		0..59"

    SYNTAX	OCTET STRING(SIZE(2))

DayOfWeek ::= TEXTUAL-CONVENTION
    STATUS	current
    DESCRIPTION
	"This object indicates the day of the week, with
	an additional option 'Daily' to work with interfaces
	that use this convention to schedule events."
    SYNTAX	INTEGER { sunday(1), monday(2), tuesday(3), wednesday(4),
			thursday(5), friday(6), saturday(7), daily(8) }

END
