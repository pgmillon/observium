PDN-MPD-EXT-MIB DEFINITIONS ::= BEGIN

IMPORTS
    MODULE-IDENTITY, OBJECT-TYPE
        FROM SNMPv2-SMI
    TEXTUAL-CONVENTION
        FROM SNMPv2-TC
    pdnMpdExt
        FROM PDN-HEADER-MIB
    MODULE-COMPLIANCE, OBJECT-GROUP
        FROM SNMPv2-CONF;

pdnMpdExtMIB MODULE-IDENTITY
    LAST-UPDATED "200304081900Z"
    ORGANIZATION "Paradyne Corporation MIB Working Group"
    CONTACT-INFO
            "         Paradyne Networks Inc.

             Postal:  8545, 126th Ave. N.
                      Largo, FL 33779
                      US
             Editor:  Jesus Pinto
             Email:   mibwg_team@eng.paradyne.com"

    DESCRIPTION
            "This management information module supports the objects
             that extend the Message Processing Dispatcher mib as
	     described in rfc3412_std62_a.mib."

    ::= { pdnMpdExt 1 }

pdnMpdExtMIBObjects OBJECT IDENTIFIER ::= 
	{ pdnMpdExtMIB 1 }

pdnMpdExtMIBConformance OBJECT IDENTIFIER ::= 
	{ pdnMpdExtMIB 2 }

PdnMpdExtSecurityMode ::= TEXTUAL-CONVENTION
             STATUS       current
             DESCRIPTION
                  "A set of combinations of Model and SecurityLevel
		   that can be supported by an agent. An agent can
		   support more than a single combination at once.

                     Bit 0 : None.
				- SNMP access is not allowed.

                     Bit 1 : SNMPv1, noAuthNoPriv.
				- SNMPv1 access is allowed with
				- no auth and no privacy.

				- Only Security checking based on
				  community names is performed.

                     Bit 2 : SNMPv2c, no AuthNoPriv.
				- SNMPv2c access is allowed with
				- no auth and no privacy.

				- Only Security checking based on
				  community names is performed.

                     Bit 3 : SNMPv3, noAuthNoPriv.
				- SNMPv3 access is allowed with
				- no auth and no privacy.

                     Bit 4 : SNMPv3, AuthNoPriv.
				- SNMPv3 access is allowed with
				- authentication and no privacy.

                     Bit 5 : SNMPv3, AuthPriv.
				- SNMPv3 access is allowed with
				- authentication and privacy.
                  "
              SYNTAX      BITS {
                  none(0),
                  snmpv1NoAuthNoPriv(1),
                  snmpv2cNoAuthNoPriv(2),
                  snmpv3NoAuthNoPriv(3),
		  snmpv3AuthNoPriv(4),
		  snmpv3AuthPriv(5)
              }

pdnMpdExtSecurityModeConfig OBJECT-TYPE
    SYNTAX      PdnMpdExtSecurityMode
    MAX-ACCESS  read-write
    STATUS      current
    DESCRIPTION
            "This object is used to configure the level of SNMP
	     access that the agent supports. That is, which
	     combinations of Model Processing can be dispatched
	     and what security levels are supported for those models.

	     An agent can choose to support more than a single 
	     combination of modes, (e.g., SNMPv1 and SNMPv2 with
	     noAuthNoPriv) or choose to support a single option
	     (e.g., a very secured agent with only SNMPv3 with
             authentication and privacy enabled.). Even some of
	     these combinations may not be supported at all.

	     Setting this object to a valid value will cause 
	     the entries associated with those Models and
	     SecurityLevels being changed to become active/inactive
	     in tables processed by the SNMPv3 Framework.
	    "

    ::= { pdnMpdExtMIBObjects 1 }

--
-- Conformance Information
--

pdnMpdExtCompliances OBJECT IDENTIFIER
     ::= { pdnMpdExtMIBConformance 1 }

pdnMpdExtGroups OBJECT IDENTIFIER
     ::= { pdnMpdExtMIBConformance 2 }

pdnMpdExtCompliance MODULE-COMPLIANCE
     STATUS  current
     DESCRIPTION
             "The compliance statement for MPD extension mib."
     MODULE -- this module
     MANDATORY-GROUPS
	{
	pdnMpdExtGroup
	}

     OBJECT pdnMpdExtSecurityModeConfig
     MIN-ACCESS read-only
     DESCRIPTION
	     "Write access is not required."


     ::= { pdnMpdExtCompliances 1 }

-- units of conformance

pdnMpdExtGroup	OBJECT-GROUP
     OBJECTS
     {
	pdnMpdExtSecurityModeConfig
     }
     STATUS current
     DESCRIPTION
             "A collection of configuration objects applicable
              to MPD extention."
     ::= { pdnMpdExtGroups 1 }

END
