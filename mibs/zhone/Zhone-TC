--
-- Zhone-TC.mib
-- MIB generated by MG-SOFT Visual MIB Builder Version 3.0 Build 285
-- Thursday, May 31, 2012 at 11:48:27
--

	Zhone-TC DEFINITIONS ::= BEGIN
 
		IMPORTS
			Integer32, MODULE-IDENTITY			
				FROM SNMPv2-SMI			
			TEXTUAL-CONVENTION			
				FROM SNMPv2-TC			
			zhoneModules			
				FROM Zhone;
	
	
		-- 1.3.6.1.4.1.5504.6.5
		zhoneTC MODULE-IDENTITY 
			LAST-UPDATED "201205311130Z"		-- May 31, 2012 at 11:30 GMT
			ORGANIZATION 
				"Zhone Technologies, Inc."
			CONTACT-INFO 
				"  Postal: 
				           Zhone Technologies, Inc.
				           @ Zhone Way
				           7001 Oakport Street
				           Oakland, CA  94621
				           USA
				Toll-Free: +1 877-ZHONE20 (+1 877-946-6320)
				      Tel: +1-510-777-7000
				      Fax: +1-510-777-7001
				   E-mail: support@zhone.com"
			DESCRIPTION 
				"This is the textual conventions modules which defines
				all the conventions for Zhone Enterprise mibs."
			REVISION "201205081136Z"		-- May 08, 2012 at 11:36 GMT
			DESCRIPTION 
				"Update zhoneIfType"
			REVISION "201202101103Z"		-- February 10, 2012 at 11:03 GMT
			DESCRIPTION 
				"rework CFM alarms/traps"
			REVISION "201201311120Z"		-- January 31, 2012 at 11:20 GMT
			DESCRIPTION 
				"Add cfmFaultAlarmTrap"
			REVISION "201201181844Z"		-- January 18, 2012 at 18:44 GMT
			DESCRIPTION 
				"Added zhoneIfTypes ptp and ppsClock"
			REVISION "201112021634Z"		-- December 02, 2011 at 16:34 GMT
			DESCRIPTION 
				"Add card type mxUp2Tg8gTOP"
			REVISION "201111301131Z"		-- November 30, 2011 at 11:31 GMT
			DESCRIPTION 
				"add the new mx1Ux80-TP-RJ45 cardTypes"
			REVISION "201111300653Z"		-- November 30, 2011 at 06:53 GMT
			DESCRIPTION 
				"Added card type for Mxk Oc3/Stm1 Pwe linecard."
			REVISION "201111132019Z"		-- November 13, 2011 at 20:19 GMT
			DESCRIPTION 
				"Added bridgeStormDetection(10181) to zhoneAlarmTypeId enum list."
			REVISION "201109021719Z"		-- September 02, 2011 at 17:19 GMT
			DESCRIPTION 
				"add mxkAlarmInput alarm"
			REVISION "201107270512Z"		-- July 27, 2011 at 05:12 GMT
			DESCRIPTION 
				"Added mx1U19x cardTypes."
			REVISION "201107061727Z"		-- July 06, 2011 at 17:27 GMT
			DESCRIPTION 
				"Add Add mxLc20Ae1SCsfp line card type."
			REVISION "201106162139Z"		-- June 16, 2011 at 21:39 GMT
			DESCRIPTION 
				"Add bridgeLoopDetection alarm."
			REVISION "201106082345Z"		-- June 08, 2011 at 23:45 GMT
			DESCRIPTION 
				"Added card types for mxk ulcs card"
			REVISION "201106021906Z"		-- June 02, 2011 at 19:06 GMT
			DESCRIPTION 
				"Added zhoneGponOltError Alarm."
			REVISION "201103240910Z"		-- March 24, 2011 at 09:10 GMT
			DESCRIPTION 
				"Add mxLc72bAdslBond, mxLc4Gp, mxLc8Gp, mxDcAdslAnnexB"
			REVISION "201101111550Z"		-- January 11, 2011 at 15:50 GMT
			DESCRIPTION 
				"Added a new textual convention ZhoneAdminState."
			REVISION "201010201351Z"		-- October 20, 2010 at 13:51 GMT
			DESCRIPTION 
				"Add zhoneGponOnuError to ZhoneAlarmTypeId."
			REVISION "201009161757Z"		-- September 16, 2010 at 17:57 GMT
			DESCRIPTION 
				"Added 2 Vdsl2 Splitter cards 900 & 600"
			REVISION "201008121744Z"		-- August 12, 2010 at 17:44 GMT
			DESCRIPTION 
				"Added mxFtOne09, mxFtOne19, mxFtOne23, mxFtTwo09, mxFtTwo19, mxFtTwo23"
			REVISION "201007131053Z"		-- July 13, 2010 at 10:53 GMT
			DESCRIPTION 
				"Added ZhoneAlarmTypeId zhoneTrapCardCpuUsage."
			REVISION "201006070652Z"		-- June 07, 2010 at 06:52 GMT
			DESCRIPTION 
				"add a new zhoneEfmLineTrafficDisabled trap"
			REVISION "201006030500Z"		-- June 03, 2010 at 05:00 GMT
			DESCRIPTION 
				"Add new Card Type for mxLc24T1E1Pwe"
			REVISION "201005130612Z"		-- May 13, 2010 at 06:12 GMT
			DESCRIPTION 
				"add Gshdsl Bonded Extended rates cardTypes
				add mx1U family cardTypes"
			REVISION "201004150922Z"		-- April 15, 2010 at 09:22 GMT
			DESCRIPTION 
				"Add Line Redundancy Unsafe alarm"
			REVISION "201003270715Z"		-- March 27, 2010 at 07:15 GMT
			DESCRIPTION 
				"Add new Card Type for mxLc24T1E1Bond"
			REVISION "200906101358Z"		-- June 10, 2009 at 13:58 GMT
			DESCRIPTION 
				"Change existing mxUp4G cardtype to 10125 and add mxUp4GCopper with cardtype 10121."
			REVISION "200906031631Z"		-- June 03, 2009 at 16:31 GMT
			DESCRIPTION 
				"Added new card type CARD_TYPE_MXLC48AADSLPOTS"
			REVISION "200904211309Z"		-- April 21, 2009 at 13:09 GMT
			DESCRIPTION 
				"Add new card type for CARD_TYPE_MXLC72AADSL_BOND"
			REVISION "200904140952Z"		-- April 14, 2009 at 09:52 GMT
			DESCRIPTION 
				"Add to card type for Mxk 24 Port Vdsl2"
			REVISION "200903111606Z"		-- March 11, 2009 at 16:06 GMT
			DESCRIPTION 
				"Add new card type for Mxk 72 Ports Pots"
			REVISION "200902231329Z"		-- February 23, 2009 at 13:29 GMT
			DESCRIPTION 
				"Add new card type and card line type for EBS-POTS-PV."
			REVISION "200902111329Z"		-- February 11, 2009 at 13:29 GMT
			DESCRIPTION 
				"adding efm bond group traffic disable trap"
			REVISION "200902041014Z"		-- February 04, 2009 at 10:14 GMT
			DESCRIPTION 
				"add cardtype for tac and tacFc"
			REVISION "200901061147Z"		-- January 06, 2009 at 11:47 GMT
			DESCRIPTION 
				"Add new Card Type for mxLc24GshdslBond and the missing mxLc20AE1S"
			REVISION "200811261051Z"		-- November 26, 2008 at 10:51 GMT
			DESCRIPTION 
				"add zhonePmeErrorMonitorEfmTrafficDisabled alarmtypeid"
			REVISION "200811060755Z"		-- November 06, 2008 at 07:55 GMT
			DESCRIPTION 
				"Changed the malcMtac card names to new names."
			REVISION "200810290835Z"		-- October 29, 2008 at 08:35 GMT
			DESCRIPTION 
				"Add raptorXP170(5242) to ZhoneCardType"
			REVISION "200810131154Z"		-- October 13, 2008 at 11:54 GMT
			DESCRIPTION 
				"adding PmeSnrMgnThresholdCrossing 
				trap id"
			REVISION "200810030600Z"		-- October 03, 2008 at 06:00 GMT
			DESCRIPTION 
				"Add mxLc48bAdslBond"
			REVISION "200808210746Z"		-- August 21, 2008 at 07:46 GMT
			DESCRIPTION 
				"Added new card subtypes for 600 and 900 Ohm splitter boards.
				"
			REVISION "200807071107Z"		-- July 07, 2008 at 11:07 GMT
			DESCRIPTION 
				"change cardtype range for 3 mtac"
			REVISION "200807021000Z"		-- July 02, 2008 at 10:00 GMT
			DESCRIPTION 
				"add card type for malcTacItmRingFc, malcTacRing, malcTacRingFc"
			REVISION "200806271205Z"		-- June 27, 2008 at 12:05 GMT
			DESCRIPTION 
				"Add mxUp8G.
				Change names for mxk line cards."
			REVISION "200806231309Z"		-- June 23, 2008 at 13:09 GMT
			DESCRIPTION 
				"Add missing alarm type id"
			REVISION "200806041647Z"		-- June 04, 2008 at 16:47 GMT
			DESCRIPTION 
				"Added new card type mxUp4g"
			REVISION "200805201034Z"		-- May 20, 2008 at 10:34 GMT
			DESCRIPTION 
				"Add new card types mxLc48aAdsl and mxLc48aAdslBond."
			REVISION "200805121655Z"		-- May 12, 2008 at 16:55 GMT
			DESCRIPTION 
				"Linkagg linetypes removed"
			REVISION "200803271645Z"		-- March 27, 2008 at 16:45 GMT
			DESCRIPTION 
				"Add new card types and line types for EBS, EBS-PV.
				
				Correct labels for card types ethX3400 CPE.
				
				Update new card line types gshdsl-ntp, gshdsl-nt."
			REVISION "200803170457Z"		-- March 17, 2008 at 04:57 GMT
			DESCRIPTION 
				"Add new card types for ethX3400 CPE. "
			REVISION "200710161126Z"		-- October 16, 2007 at 11:26 GMT
			DESCRIPTION 
				"Add new Zhone Interface types: wdmLine, wdmTrib."
			REVISION "200709150937Z"		-- September 15, 2007 at 09:37 GMT
			DESCRIPTION 
				"Add new card types. malcAdsl48AnxAmBond, malcAdsl48AnxBBond, malcGshdslBondedNtp and malcGshdslBondedNt"
			REVISION "200709131801Z"		-- September 13, 2007 at 18:01 GMT
			DESCRIPTION 
				"Add malcUpFeGeRpr(5091)"
			REVISION "200709131758Z"		-- September 13, 2007 at 17:58 GMT
			DESCRIPTION 
				"Add new card type malcUpFeGeRprTdm(5090)"
			REVISION "200707091418Z"		-- July 09, 2007 at 14:18 GMT
			DESCRIPTION 
				"Add card type fiberSlam101 (9101)"
			REVISION "200706211443Z"		-- June 21, 2007 at 14:43 GMT
			DESCRIPTION 
				"Add alarm type zhoneUnassignedGponOnu"
			REVISION "200706200653Z"		-- June 20, 2007 at 06:53 GMT
			DESCRIPTION 
				"Add new card type ethXpwe"
			REVISION "200706151037Z"		-- June 15, 2007 at 10:37 GMT
			DESCRIPTION 
				"V01.72.00 - Add card type malcT1ImaF2 and malcT1E1TdmF2."
			REVISION "200705221601Z"		-- May 22, 2007 at 16:01 GMT
			DESCRIPTION 
				"Added zhoneBondGroupDown, zhoneLinkAggLink1Down, zhoneLinkAggLink2Down"
			REVISION "200705111555Z"		-- May 11, 2007 at 15:55 GMT
			DESCRIPTION 
				"Add new card type raptorXP160 (5238) in ZhoneCardType "
			REVISION "200705091147Z"		-- May 09, 2007 at 11:47 GMT
			DESCRIPTION 
				"Added raptorXP350A, malcXP350A card types to ZhoneCardType attribute."
			REVISION "200704191328Z"		-- April 19, 2007 at 13:28 GMT
			DESCRIPTION 
				"add card line types for link aggregation."
			REVISION "200704031550Z"		-- April 03, 2007 at 15:50 GMT
			DESCRIPTION 
				"V01.67.00 - Add malcXP150A card type"
			REVISION "200703091439Z"		-- March 09, 2007 at 14:39 GMT
			DESCRIPTION 
				"V01.66.00 - Add RaptorXP105A card type"
			REVISION "200702281758Z"		-- February 28, 2007 at 17:58 GMT
			DESCRIPTION 
				"V01.65.00 - add malcXdsl17a to card types"
			REVISION "200611181405Z"		-- November 18, 2006 at 14:05 GMT
			DESCRIPTION 
				"V01.64.00 - Added ZhoneEnabledFlag."
			REVISION "200610261508Z"		-- October 26, 2006 at 15:08 GMT
			DESCRIPTION 
				"V01.63.00 - Added card type definition for mxUp2Tg8g."
			REVISION "200609141111Z"		-- September 14, 2006 at 11:11 GMT
			DESCRIPTION 
				"V01.63.00 - Added new members fan C/D/E to ZhoneAlarmTypeId."
			REVISION "200609101813Z"		-- September 10, 2006 at 18:13 GMT
			DESCRIPTION 
				"V01.62.00 - Added ZhoneIfType cellRelayProxy"
			REVISION "200609061213Z"		-- September 06, 2006 at 12:13 GMT
			DESCRIPTION 
				"V01.61.00 - Added card type for m100Adsl2pAnxB"
			REVISION "200608181250Z"		-- August 18, 2006 at 12:50 GMT
			DESCRIPTION 
				"V01.60.00 - Added card type malcGpon (5076)."
			REVISION "200607251922Z"		-- July 25, 2006 at 19:22 GMT
			DESCRIPTION 
				"V01.59.00 - Added gigaMux100 card type."
			REVISION "200607131612Z"		-- July 13, 2006 at 16:12 GMT
			DESCRIPTION 
				"V01.58.00 - Added card type for r100Adsl2pAnxB"
			REVISION "200606191331Z"		-- June 19, 2006 at 13:31 GMT
			DESCRIPTION 
				"V01.57.00 - added new card type malcT1E1Bonded and malcGshdslBonded"
			REVISION "200606051022Z"		-- June 05, 2006 at 10:22 GMT
			DESCRIPTION 
				"V01.56.00 Add malcNextGen card type."
			REVISION "200605221610Z"		-- May 22, 2006 at 16:10 GMT
			DESCRIPTION 
				"V01.55.00 Add new Raptor card types"
			REVISION "200605051204Z"		-- May 05, 2006 at 12:04 GMT
			DESCRIPTION 
				"VO1.55.00 Added EFM card types"
			REVISION "200603091757Z"		-- March 09, 2006 at 17:57 GMT
			DESCRIPTION 
				"V01.54.00 - Add malcXdsl48AnxBm to zhoneCardType"
			REVISION "200603061125Z"		-- March 06, 2006 at 11:25 GMT
			DESCRIPTION 
				"V01.53.00 - Added new zhoneCardType malcMtacEnh."
			REVISION "200511101848Z"		-- November 10, 2005 at 18:48 GMT
			DESCRIPTION 
				"V01.52.00 - Added new Zhone If Bonding Types"
			REVISION "200510271653Z"		-- October 27, 2005 at 16:53 GMT
			DESCRIPTION 
				"V01.51.00 - Add new CardType malcGshdsl48. Removed CardLineType pots-meter & pots-meter-coin. Changed pots-meter-coin & pots-meter-coin-pv to pots-coin & pots-coin-pv. Removed meter from malcUlcsPots*."
			REVISION "200510271325Z"		-- October 27, 2005 at 13:25 GMT
			DESCRIPTION 
				"Added rpr east and west span alarm id's."
			REVISION "200510111622Z"		-- October 11, 2005 at 16:22 GMT
			DESCRIPTION 
				"Added card line types isdn, isdn-pv, pots-meter, pots-meter-pv, pots-meter-coin & pots-meter-coin-pv"
			REVISION "200508251428Z"		-- August 25, 2005 at 14:28 GMT
			DESCRIPTION 
				"Added card types: malcUlcs, malcUlcsISDN-2B1Q, malcUlcsISDN-2B1Q-Pv, malcUlcsISDN-4B3T, malcUlcsISDN-4B3T-Pv, malcUlcsPotsMeter, malcUlcsPotsMeter-Pv, malcUlcsPotsMeterCoin, malcUlcsPotsMeterCoin-Pv, m100Adsl2Pip, m100Adsl2PGigE, malcOc3GigE, malcDs3GigE"
			REVISION "200508111907Z"		-- August 11, 2005 at 19:07 GMT
			DESCRIPTION 
				"Added various battery states to ZhonealarmTypeId."
			REVISION "200507131136Z"		-- July 13, 2005 at 11:36 GMT
			DESCRIPTION 
				"Added new members of ZhonealarmTypeId."
			REVISION "200505171832Z"		-- May 17, 2005 at 18:32 GMT
			DESCRIPTION 
				"card type malcIsdn24(5049) added
				"
			REVISION "200505120928Z"		-- May 12, 2005 at 09:28 GMT
			DESCRIPTION 
				"V01.45.00- Added comment regarding change of card-line-type for packet voice cards.
				 "
			REVISION "200504291457Z"		-- April 29, 2005 at 14:57 GMT
			DESCRIPTION 
				"V01.44.00- zhonePermanentLockoutFailure."
			REVISION "200504061042Z"		-- April 06, 2005 at 10:42 GMT
			DESCRIPTION 
				"V01.43.00- Add new ZhoneCardLineType values."
			REVISION "200503241714Z"		-- March 24, 2005 at 17:14 GMT
			DESCRIPTION 
				"V01.42.00- Add new card type malcPots48 and malcPots48Pv"
			REVISION "200502181107Z"		-- February 18, 2005 at 11:07 GMT
			DESCRIPTION 
				"V01.41.00- Add new card type malcXdslPots48, malcXdslPots48Pv and zrg800."
			REVISION "200411051348Z"		-- November 05, 2004 at 13:48 GMT
			DESCRIPTION 
				"Added new cardLineType rprT1Gr303, rprE1V52, rprT1Cas"
			REVISION "200410061033Z"		-- October 06, 2004 at 10:33 GMT
			DESCRIPTION 
				"Added new cardLineType rpr"
			REVISION "200409021102Z"		-- September 02, 2004 at 11:02 GMT
			DESCRIPTION 
				"Added new cardLineType t1Cas"
			REVISION "200408051645Z"		-- August 05, 2004 at 16:45 GMT
			DESCRIPTION 
				"Change ZhoneCardType malcXdslAnnexA to malcXdslSpltAnxA"
			REVISION "200407091351Z"		-- July 09, 2004 at 13:51 GMT
			DESCRIPTION 
				"V01.35.00- Add/modify ZhoneIfTypes."
			REVISION "200406211940Z"		-- June 21, 2004 at 19:40 GMT
			DESCRIPTION 
				"V01.34.00- add new ZhoneAlarmTypeIds."
			REVISION "200405271028Z"		-- May 27, 2004 at 10:28 GMT
			DESCRIPTION 
				"V01.33.00- add new ZhoneIfTypes."
			REVISION "200405241026Z"		-- May 24, 2004 at 10:26 GMT
			DESCRIPTION 
				"V01.32.00 - Add r100ADSL2PIP, r100ADSL2PHDSL4, r100ADSL2PT1IMA, zrg600."
			REVISION "200405241025Z"		-- May 24, 2004 at 10:25 GMT
			DESCRIPTION 
				"V01.31.00 -- Add malcT1E132Vg."
			REVISION "200405141612Z"		-- May 14, 2004 at 16:12 GMT
			DESCRIPTION 
				"V01.30.00 -- Add malcOc48Trunk, malcXdslAnnexA
				and malcXdslAnnexB card types."
			REVISION "200404201035Z"		-- April 20, 2004 at 10:35 GMT
			DESCRIPTION 
				"V01.29.00 -- add t1UniT1Cas and t1ImaT1Cas to cardlinetype"
			REVISION "200403161847Z"		-- March 16, 2004 at 18:47 GMT
			DESCRIPTION 
				"V01.28.00 - add new CardType malcXdsl48"
			REVISION "200403021330Z"		-- March 02, 2004 at 13:30 GMT
			DESCRIPTION 
				"V01.27.00 - Create raptor50 card type"
			REVISION "200402241301Z"		-- February 24, 2004 at 13:01 GMT
			DESCRIPTION 
				"V01.26.00 - Added new card type malcT1E1Ces12"
			REVISION "200402181355Z"		-- February 18, 2004 at 13:55 GMT
			DESCRIPTION 
				"V01.25.00 -  Added ZhoneAlarmTypeId and
				ZhoneAlarmSeverity definitions."
			REVISION "200401231457Z"		-- January 23, 2004 at 14:57 GMT
			DESCRIPTION 
				"V01.24.00 -  Added new card type malcT1E1TdmF"
			REVISION "200401231056Z"		-- January 23, 2004 at 10:56 GMT
			DESCRIPTION 
				"V01.23.00 -  Added new card type malcPotsVg"
			REVISION "200401211656Z"		-- January 21, 2004 at 16:56 GMT
			DESCRIPTION 
				"V01.22.00 -  Added new card type malcT1E1Atm32"
			REVISION "200401131713Z"		-- January 13, 2004 at 17:13 GMT
			DESCRIPTION 
				"V01.21.00 -  Added zrg300 and zrg500
				  card types."
			REVISION "200312220836Z"		-- December 22, 2003 at 08:36 GMT
			DESCRIPTION 
				"V01.20.00 -  Added raptor100Gshdsl local power card types."
			REVISION "200309161203Z"		-- September 16, 2003 at 12:03 GMT
			DESCRIPTION 
				"V01.19.00 -  Added Aal5Proxy, Onu
				             and Olt to ZhoneIfType."
			REVISION "200309081332Z"		-- September 08, 2003 at 13:32 GMT
			DESCRIPTION 
				"V01.18.00 - Add card type zrg700 for pon residential gateway"
			REVISION "200309051844Z"		-- September 05, 2003 at 18:44 GMT
			DESCRIPTION 
				"V01.17.00 - Add malcGshdsl4w and malcOc12
				            to ZhoneCardType."
			REVISION "200308211843Z"		-- August 21, 2003 at 18:43 GMT
			DESCRIPTION 
				"V01.16.00 - Add zedge6200 card definitions."
			REVISION "200308181115Z"		-- August 18, 2003 at 11:15 GMT
			DESCRIPTION 
				"V01.15.00 - Add malcOlt and malcVdsl card definitions."
			REVISION "200305091238Z"		-- May 09, 2003 at 12:38 GMT
			DESCRIPTION 
				"V01.14.00 - Add malcUlcPower and
				malc100Splt card types."
			REVISION "200305081703Z"		-- May 08, 2003 at 17:03 GMT
			DESCRIPTION 
				"V01.13.00 -Added host(3) to ZhoneIfType."
			REVISION "200305081453Z"		-- May 08, 2003 at 14:53 GMT
			DESCRIPTION 
				"V01.12.00 - Add daughter cardtype malcUlcEbs and malcDs3F to ZhoneCardType."
			REVISION "200304101759Z"		-- April 10, 2003 at 17:59 GMT
			DESCRIPTION 
				"V01.11.00 - Add malcT1ImaF and malcDs3F to ZhoneCardType."
			REVISION "200303041927Z"		-- March 04, 2003 at 19:27 GMT
			DESCRIPTION 
				"V01.10.00 - Add malcUlc to ZhoneCardType."
			REVISION "200303031633Z"		-- March 03, 2003 at 16:33 GMT
			DESCRIPTION 
				"V01.09.00 - Add malcOc3F"
			REVISION "200211221546Z"		-- November 22, 2002 at 15:46 GMT
			DESCRIPTION 
				"01.08.00 - Add malcAdslSpltUkAc5 and malcAdslSpltUkC"
			REVISION "200210291544Z"		-- October 29, 2002 at 15:44 GMT
			DESCRIPTION 
				"V01.07.00 - Add malcAdslC, malcAdslPotsC and malcAdslSpltC. Change malcAdslAc6, malcAdslAc6Pots, malcAdslAc6Splt, malcAdslAc6SnxB and malcAdslAc6AnxBSplt."
			REVISION "200210241800Z"		-- October 24, 2002 at 18:00 GMT
			DESCRIPTION 
				"V01.06.00 - add malcMtacFc"
			REVISION "200210181555Z"		-- October 18, 2002 at 15:55 GMT
			DESCRIPTION 
				"V01.05.00 - Added new line types
				for malcT1E1Tdm card which has
				8 ATM T1/E1 Ports and 8 TDM T1/E1
				ports."
			REVISION "200205291301Z"		-- May 29, 2002 at 13:01 GMT
			DESCRIPTION 
				"V01.04.00 -Added ZhoneCardType TC
				Added ZhoneCardLineType TC"
			REVISION "200108011600Z"		-- August 01, 2001 at 16:00 GMT
			DESCRIPTION 
				"V01.03.00 - Add ZhoneCountryCode textual convention."
			REVISION "200106281112Z"		-- June 28, 2001 at 11:12 GMT
			DESCRIPTION 
				"V01.02.00 - fix 17 slot limit problem"
			REVISION "200105161239Z"		-- May 16, 2001 at 12:39 GMT
			DESCRIPTION 
				"V01.01.00 - Added ZhoneIfType"
			REVISION "200009121051Z"		-- September 12, 2000 at 10:51 GMT
			DESCRIPTION 
				"V01.00.00 - Initial Release"
			::= { zhoneModules 5 }

		
	
--
-- Textual conventions
--
	
		ZhoneWdmWavelength ::= TEXTUAL-CONVENTION
			STATUS current
			DESCRIPTION 
				"This field describes Zhone WDM WaveLength."
			SYNTAX INTEGER
				{
				auto(1),
				cwdm1310(2),
				cwdm1470(3),
				cwdm1490(4),
				cwdm1510(5),
				cwdm1530(6),
				cwdm1550(7),
				cwdm1570(8),
				cwdm1590(9),
				cwdm1610(10),
				dwdm20(11),
				dwdm21(12),
				dwdm22(13),
				dwdm23(14),
				dwdm24(15),
				dwdm25(16),
				dwdm26(17),
				dwdm27(18),
				dwdm28(19),
				dwdm29(20),
				dwdm30(21),
				dwdm31(22),
				dwdm32(23),
				dwdm33(24),
				dwdm34(25),
				dwdm35(26),
				dwdm36(27),
				dwdm37(28),
				dwdm38(29),
				dwdm39(30),
				dwdm40(31),
				dwdm41(32),
				dwdm42(33),
				dwdm43(34),
				dwdm44(35),
				dwdm45(36),
				dwdm46(37),
				dwdm47(38),
				dwdm48(39),
				dwdm49(40),
				dwdm50(41),
				dwdm51(42),
				dwdm52(43),
				dwdm53(44),
				dwdm54(45),
				dwdm55(46),
				dwdm56(47),
				dwdm57(48),
				dwdm58(49),
				dwdm59(50),
				mm850(51)
				}

		ZhoneFileName ::= TEXTUAL-CONVENTION
			STATUS current
			DESCRIPTION 
				"The Zhone File Name specification. Any file name should
				follow this convention."
			SYNTAX OCTET STRING (SIZE (0..64))

		ZhoneAdminString ::= TEXTUAL-CONVENTION
			DISPLAY-HINT 
				"32a"
			STATUS current
			DESCRIPTION 
				"Most of Zhone's string names will be 20 characters or less. 
				In these cases the ZhoneAdminString convention should be
				used."
			SYNTAX OCTET STRING (SIZE (0..32))

		ZhoneRowStatus ::= TEXTUAL-CONVENTION
			STATUS current
			DESCRIPTION 
				"
				In any case where a new row can be created either via
				the cli or zms there will always be a proprietary mib
				entity called zhrowstatus which has the basic 
				equivalence of the standard rowstatus object_id with 
				the following exceptions:
				
				1)	all column entries that are not defaulted are
				        documented in the DESCRIPTION for the object.
				2)	Only CREATE_AND_GO will be supported as all 
				        mib values for the row should be specified in 
				        a single request (via either zms or cli).
				
				Note that even though a standard mib may have a 
				rowstatus field already defined in it's mib, it will 
				not be supported and all sets to this field will 
				return a E_NOSUCHINSTANCE error code. 'get's to this 
				value will return an active value and no 
				error code so as not to fail a mibwalk or standard's 
				based browser.
				
				NOTE 1:
				ZhoneRowStatus will also support active(1) as 
				READ-ONLY instead of the conventional READ-WRITE or 
				READ-CREATE.  The row creation mechanism in the 
				SNMPv2 framework uses 3 actions states: createAndGo, 
				createAndWait, and destroy, combined with two desired 
				states: active and notInService, and a current state: 
				notReady.   
				
				ZhoneRowStatus will not support createAndWait,
				notInService, and notReady.  However, when an SNMP SET 
				using createAndGo succeeds, a new row is created - and 
				the RowStatus value automatically becomes active. Later
				if we want to delete the row, we can issue an SNMP SET 
				with RowStatus destroy.  We can subsequently SNMP GET 
				the RowStatus on a successfully created row, and the 
				returned RowStatus value will be active.  
				
				In the RowStatus interaction state machine/diagram, 
				the notInService(2) state is transitioned to via a 
				notInService action, which we will not support. 
				Similarly, the notReady(3) state is transitioned to 
				via the createAndWait action which we also don't 
				support.  So there is no reason to support 
				notInService(2) or notReady(3) because the operations 
				required to place the row in either of two states are 
				not supported and there is no legal way for our 
				supported RowStatus state machine to take us to either 
				notInService or notReady.
								
						
				ZhoneRowStatus implements the one-shot row creation 
				or activation form.  In one-shot mode, all values 
				required to activate a row in a single SET operation 
				along with an assignment of the status variable to 
				createAndGo.  If all requirements are satisfied and 
				an instance of the resource is created, then the status 
				of the row transitions to active.
				
				If the values of the row do not make sense, or there 
				were not enough values specified in the SET to fill in 
				the row, the agent returns an error code.  The only 
				appropriate error code is inconsistentValue (in SNMPv2)."
			SYNTAX INTEGER
				{
				active(1),
				createAndGo(4),
				destroy(6)
				}

		ZhoneShelfValue ::= TEXTUAL-CONVENTION
			STATUS current
			DESCRIPTION 
				"Index used to order the application of shelf access
				entries. Valid range is 1..255 and 0 is an invalid 
				value."
			SYNTAX Integer32 (1..255)

		ZhoneShelfValueOrZero ::= TEXTUAL-CONVENTION
			STATUS current
			DESCRIPTION 
				"Index used to order the application of shelf access
				entries.  Valid range is 0..255.
				
				This textual convention is an extension of the
				ZhoneShelfValue convention.  The latter defines a
				greater than zero value used to identify a shelf
				in the managed system.  This extension permits the 
				additional value of zero.  the value zero is 
				object-specific and must therefore be defined as 
				part of the description of any object which uses 
				this syntax."
			SYNTAX Integer32 (0..255)

		ZhoneSlotValue ::= TEXTUAL-CONVENTION
			STATUS current
			DESCRIPTION 
				"The slot number of this card.  Valid range is 1..30 
				and 0 is an invalid value."
			SYNTAX Integer32 (1..30)

		ZhoneSlotValueOrZero ::= TEXTUAL-CONVENTION
			STATUS current
			DESCRIPTION 
				"The slot number of this card.  Valid range is 0..30.
				
				This textual convention is an extension of the
				ZhoneSlotValue convention.  The latter defines a
				greater than zero value used to identify an interface
				or interface sub-layer in the managed system.  This
				extension permits the additional value of zero.  the
				value zero is object-specific and must therefore be
				defined as part of the description of any object which
				uses this syntax."
			SYNTAX Integer32 (0..30)

		ZhoneDiagResult ::= TEXTUAL-CONVENTION
			STATUS current
			DESCRIPTION 
				"This represents the overall test results from the 
				execution of any diagnostics.
				  diagPass        : diagnostics were successful.
				  diagNotSupported: diagnostics are not supported.
				  diagUnableToRun : diagnostics are unable to execute
				                    because of resource state. For 
				                    example a port is not in the down
				                    state or a card is not in the
				                    maintenance state.
				  diagFail        : diagnostics have failed.
				  diagInProgress  : diagnostics are currently executing."
			SYNTAX INTEGER
				{
				diagPass(1),
				diagNotSupported(2),
				diagUnableToRun(3),
				diagFail(4),
				diagInProgress(5)
				}

		ZhoneDiagAction ::= TEXTUAL-CONVENTION
			STATUS current
			DESCRIPTION 
				"This represents the overall test request for the 
				execution of any diagnostics.
				  diagStart   : begin diagnostic execution and
				                initialize diagnostic results.
				  diagStop    : stop diagnostics and store diagnostic
				                results.
				  diagSuspend : suspend diagnostic execution until
				                'diagResume' entered. 
				                NOTE: if no 'diagResume' is received
				                in 10 minutes diagnostics are stopped
				                at the last diagnostic executed after
				                being suspended.
				  diagResume  : resume diagnostics at the point where
				                they were suspended. This has no
				                affect if the diagnostics are not
				                suspended."
			SYNTAX INTEGER
				{
				diagStart(1),
				diagStop(2),
				diagSuspend(3),
				diagResume(4)
				}

		ZhoneIfType ::= TEXTUAL-CONVENTION
			STATUS current
			DESCRIPTION 
				"This represents Zhone's interface type beyond what is
				already defined by IANAifType of iftype.mib.  This data 
				type is used as the syntax of the ifTypeExtension
				object in the  definition of zhoneIfXTable.
				
				   zhoneIfType_None       : none
				   zhoneIfType_LineGroup  : line group interface type
				   zhoneIfType_Aal5Proxy  : AAl5 Proxy
				   zhoneIfType_Host       : IP Host
				   zhoneIfType_Onu        : Optical Network Unit
				   zhoneIfType_Olt        : Optical Line Termination Unit
				   zhoneIfType_DspProxy   : DSP Proxy
				   
				   Synchronous Transport Signal (Sts)Info:
				
				   StsN is N * 51.84Mbps so STS3C is 155.52Mbps. This
				   refers to how many STS1 are put into a concatenated group.
				
				   zhoneIfType_Sts1       : Synchronous Transport Signal 1
				   zhoneIfType_Sts3       : Synchronous Transport Signal 3
				   zhoneIfType_Sts12      : Synchronous Transport Signal 12
				   zhoneIfType_Sts48      : Synchronous Transport Signal 48
				   zhoneIfType_Stm1       : Synchronous Transport Mode 1
				   zhoneIfType_Stm4       : Synchronous Transport Mode 4
				   zhoneIfType_Vt1_5      : Virtual Tributary which may contain a DS1
				
				   Virtual Container (VC) Info:
				
				   There is 1 VC4 in an STM1.
				   There are 3 VC3s in STM1.
				   There can also be 3 VC3s in a VC4.
				   There are 7 groups of VC11/VC12s in a VC3 or 21 groups
				   of VC11/VC12 in a VC4.  Each group must be all VC11s or
				   VC12s there are 4 VC11s in a group and 3 VC12s in
				   a group.
				
				   zhoneIfType_Vc3        : Virtual Container 3
				   zhoneIfType_Vc4        : Virtual Container 4
				   zhoneIfType_Vc11       : Virtual Container 11
				   zhoneIfType_Vc12       : Virtual Container 12
				   zhoneIfType_aal2Proxy  : AAl2 Proxy"
			SYNTAX INTEGER
				{
				none(0),
				lineGroup(1),
				aal5Proxy(2),
				host(3),
				onu(4),
				olt(5),
				dspProxy(6),
				sts1(7),
				sts3(8),
				sts12(9),
				sts48(10),
				stm1(11),
				stm4(12),
				vt1-5(13),
				vc3(14),
				vc4(15),
				vc11(16),
				vc12(17),
				aal2Proxy(18),
				n2nLink(19),
				n2nBond(20),
				efmLink(21),
				efmBond(22),
				cellRelayProxy(23),
				ethProxy(24),
				gponOnu(25),
				gponOlt(26),
				gponPort(27),
				wdmLine(28),
				wdmTrib(29),
				ipoBridge(30),
				gBond(31),
				mpLink(32),
				mpBond(33),
				vt2(34),
				ptp(35),
				ppsClock(36)
				}

		ZhoneCountryCode ::= TEXTUAL-CONVENTION
			STATUS current
			DESCRIPTION 
				"ZhoneCountryCode defines complete list of country names
				as specified by ISO 3166-1 as of June 12, 2001.
				
				This Zhone textual convention is established based on
				the enum values that are already defined in the
				zhoneSystemConfigurationCountryRegion in the Zhone
				System MIB. The previous 'unknown(1)' definition is
				no longer valid.
				
				This country list is further expanded by the ISO
				3166-1 specification."
			SYNTAX INTEGER
				{
				argentina(2),
				australia(3),
				belgium(4),
				china(5),
				costarica(6),
				finland(7),
				france(8),
				germany(9),
				hongkong(10),
				italy(11),
				japan(12),
				korea(13),
				mexico(14),
				netherlands(15),
				newzealand(16),
				singapore(17),
				spain(18),
				sweden(19),
				switzerland(20),
				uk(21),
				us(22),
				afghanistan(23),
				albania(24),
				algeria(25),
				americansamoa(26),
				andorra(27),
				angola(28),
				anguilla(29),
				antarctica(30),
				antiguabarbuda(31),
				armenia(32),
				aruba(33),
				austria(34),
				azerbaijan(35),
				bahamas(36),
				bahrain(37),
				bangladesh(38),
				barbados(39),
				belarus(40),
				belize(41),
				benin(42),
				bermuda(43),
				bhutan(44),
				bolivia(45),
				bosniaherzegovina(46),
				botswana(47),
				bouvetisland(48),
				brazil(49),
				britishindianoceanterritory(50),
				bruneidarussalam(51),
				bulgaria(52),
				burkinafaso(53),
				burundi(54),
				cambodia(55),
				cameroon(56),
				canada(57),
				capeverde(58),
				caymanislands(59),
				centralafricanrepublic(60),
				chad(61),
				chile(62),
				christmasisland(63),
				cocosislands(64),
				colombia(65),
				comoros(66),
				congo(67),
				cookislands(68),
				cotedivoire(69),
				croatia(70),
				cuba(71),
				cyprus(72),
				czechrepublic(73),
				denmark(74),
				djibouti(75),
				dominica(76),
				dominicanrepublic(77),
				easttimor(78),
				ecuador(79),
				egypt(80),
				elsalvador(81),
				equatorialguinea(82),
				eritrea(83),
				estonia(84),
				ethiopia(85),
				falklandislands(86),
				faroeislands(87),
				fiji(88),
				frenchguiana(89),
				frenchpolynesia(90),
				frenchsouthernterritories(91),
				gabon(92),
				gambia(93),
				georgia(94),
				ghana(95),
				gibraltar(96),
				greece(97),
				greenland(98),
				grenada(99),
				guadeloupe(100),
				guam(101),
				guatemala(102),
				guinea(103),
				guineabissau(104),
				guyana(105),
				haiti(106),
				heardislandmcdonaldislands(107),
				holysee(108),
				honduras(109),
				hungary(110),
				iceland(111),
				india(112),
				indonesia(113),
				iran(114),
				iraq(115),
				ireland(116),
				israel(117),
				jamaica(118),
				jordan(119),
				kazakstan(120),
				kenya(121),
				kiribati(122),
				northkorea(123),
				kuwait(124),
				kyrgyzstan(125),
				lao(126),
				latvia(127),
				lebanon(128),
				lesotho(129),
				liberia(130),
				libyanarabjamahiriya(131),
				liechtenstein(132),
				lithuania(133),
				luxembourg(134),
				macau(135),
				macedonia(136),
				madagascar(137),
				malawi(138),
				malaysia(139),
				maldives(140),
				mali(141),
				malta(142),
				marshallislands(143),
				martinique(144),
				mauritania(145),
				mauritius(146),
				mayotte(147),
				micronesia(148),
				moldova(149),
				monaco(150),
				mongolia(151),
				montserrat(152),
				morocco(153),
				mozambique(154),
				myanmar(155),
				namibia(156),
				nauru(157),
				nepal(158),
				netherlandsantilles(159),
				newcaledonia(160),
				nicaragua(161),
				niger(162),
				nigeria(163),
				niue(164),
				norfolkisland(165),
				northernmarianaislands(166),
				norway(167),
				oman(168),
				pakistan(169),
				palau(170),
				palestinianterritory(171),
				panama(172),
				papuanewguinea(173),
				paraguay(174),
				peru(175),
				philippines(176),
				pitcairn(177),
				poland(178),
				portugal(179),
				puertorico(180),
				qatar(181),
				reunion(182),
				romania(183),
				russia(184),
				rwanda(185),
				sainthelena(186),
				saintkittsnevis(187),
				saintlucia(188),
				saintpierremiquelon(189),
				saintvincentthegrenadines(190),
				samoa(191),
				sanmarino(192),
				saotomeprincipe(193),
				saudiarabia(194),
				senegal(195),
				seychelles(196),
				sierraleone(197),
				slovakia(198),
				slovenia(199),
				solomonislands(200),
				somalia(201),
				southafrica(202),
				southgeorgia(203),
				srilanka(204),
				sudan(205),
				suriname(206),
				svalbardjanmayen(207),
				swaziland(208),
				syria(209),
				taiwan(210),
				tajikistan(211),
				tanzania(212),
				thailand(213),
				togo(214),
				tokelau(215),
				tonga(216),
				trinidadtobago(217),
				tunisia(218),
				turkey(219),
				turkmenistan(220),
				turkscaicosislands(221),
				uganda(222),
				ukraine(223),
				unitedarabemirates(224),
				uruguay(225),
				uzbekistan(226),
				vanuatu(227),
				venezuela(228),
				vietnam(229),
				virginislandsuk(230),
				virginislandsus(231),
				wallisfutuna(232),
				westernsahara(233),
				yemen(234),
				yugoslavia(235),
				zambia(236),
				zimbabwe(237)
				}

		ZhoneCardType ::= TEXTUAL-CONVENTION
			STATUS current
			DESCRIPTION 
				"ZhoneCardType defines a complete list of card types.
				
				This Zhone textual convention is established based on
				the enum values that are already defined in cardZhoneType in
				genCardResources.mib.
				
				malcUlc is a main linecard and provides ISDN service.
				
				malcUlcEBS is a malcUlc daughter card and provides line power,
				EBS (enhanced business services - aka Nortel P-Phone), and
				POTS services.
				
				malcUlcPower is a malcUlc daughter card and provides line
				power only."
			SYNTAX INTEGER
				{
				unknownType(1),
				interShelf(2),
				infoServices(3),
				dataASP(4),
				voiceASP(5),
				t3Tdm(6),
				t3Atm(7),
				atmTrnkCr(8),
				ethernet(9),
				hdsl2(10),
				adsl(11),
				oc3Atm(13),
				atmTrnk(15),
				atmTrnkAal25(16),
				atmTrnkT1e1(17),
				tdmT1e1(18),
				mxFtOne09(800),
				mxFtOne19(801),
				mxFtOne23(802),
				mxFtTwo09(803),
				mxFtTwo19(804),
				mxFtTwo23(805),
				sechtor100(1001),
				zedge64(2001),
				zrg700(2003),
				zplex10(3001),
				skyzhone(4001),
				malcUplinkNt1(5001),
				malcPots(5002),
				mtacRing(5003),
				malcAdsl(5004),
				malcAdslPots(5005),
				malcGshdsl(5006),
				malcGshdslPots(5007),
				malcPots900(5008),
				malcDs3(5009),
				malcAdslAc5(5010),
				malcOc3(5011),
				mtacRingFc(5012),
				malcAc5AnxB(5013),
				malcT1E1Tdm(5014),
				malcAdslAc6(5015),
				malcAdslPotsAc6(5016),
				malcAdslSpltAc6(5017),
				malcAdslAnxBAc6(5018),
				malcAdslAnxBSpltAc6(5019),
				malcAdslC(5020),
				malcAdslPotsC(5021),
				malcAdslSpltC(5022),
				malcAdslSpltUkAc6(5023),
				malcAdslSpltUkC(5024),
				malcUlc(5025),
				malcVdsl(5026),
				malcUlcEbs(5027),
				malcUlcPower(5028),
				malcOc12(5029),
				malcGshdsl4w(5030),
				malcOlt(5031),
				malcT1E1Atm32(5032),
				malcPotsVg(5033),
				malcT1E1Ces12(5034),
				malcGigE(5035),
				malcXdsl48(5036),
				malcOc48Trunk(5037),
				malcXdslSpltAnxA(5038),
				malcXdslAnnexB(5039),
				malcT1E1Vg(5040),
				malcRprGigE(5041),
				malcXdslPots48(5044),
				malcXdslPots48Pv(5045),
				malcPots48(5047),
				malcPots48Pv(5048),
				malcUlcs(5049),
				malcUlcsISDN-2B1Q(5050),
				malcOc3GigE(5051),
				malcDs3GigE(5052),
				malcUlcsISDN-2B1Q-Pv(5053),
				malcUlcsISDN-4B3T(5054),
				malcUlcsISDN-4B3T-Pv(5055),
				malcUlcsPots(5056),
				malcUlcsPots-Pv(5057),
				malcUlcsPotsCoin(5058),
				malcUlcsPotsCoin-Pv(5059),
				malcT1E1-4Vg(5060),
				malcT1E1-8Vg(5061),
				malcT1E1-16Vg(5062),
				malcT1E1-32Vg(5063),
				malcReachDsl(5064),
				malcXdsl48AnxAm(5065),
				malcRprGigENt(5066),
				malcVdsl2(5067),
				malcT1E1Bonded(5068),
				malcGshdsl48(5069),
				malcDs3E3Atm4(5070),
				malcActEth10(5071),
				tacItmRing(5072),
				malcXdsl48AnxBm(5073),
				malcGshdslBonded(5074),
				malcReachDslSplitter(5075),
				malcGpon(5076),
				malcXdsl17a(5077),
				malcXdslSpltAnxA600(5078),
				malcXdslSpltAnxA900(5079),
				malcAdsl48AnxAmBond(5080),
				malcAdsl48AnxBBond(5081),
				malcXdslPots48PvRngItm(5083),
				malcUpFeGeRprTdm(5090),
				malcUpFeGeRpr(5091),
				malcGshdslBondedNtp(5092),
				malcGshdslBondedNt(5093),
				malcUlcsEbs(5094),
				malcUlcsEbs-Pv(5095),
				tacItmRingFc(5096),
				tacRing(5097),
				tacRingFc(5098),
				malcUlcsEbsPots-Pv(5099),
				malcT1ImaF(5101),
				malcDs3F(5109),
				malcOc3F(5111),
				malcT1E1TdmF(5114),
				malc100T1Ima(5201),
				malc100Gshdsl(5202),
				malc100T1ImaTDM(5203),
				malc100Ip(5204),
				malc100Splt(5205),
				malc100Gshdsl48V(5206),
				malc100Gshdsl48VSplt(5207),
				malc50Gshdsl(5231),
				malc50Splt(5232),
				r100ADSL2PIP(5233),
				r100ADSL2PHDSL4(5234),
				r100ADSL2PHT1IMA(5235),
				r100ADSL2PGIGE(5236),
				raptorXP160(5238),
				r100Adsl2pAnxB(5239),
				raptorXP150A(5240),
				raptorXP350A(5241),
				raptorXP170(5242),
				malcT1ImaF2(5301),
				malcT1E1TdmF2(5314),
				m100Adsl2Pip(5333),
				m100Adsl2pAnxB(5339),
				malcXP150A(5340),
				malcXP350A(5341),
				tac(5363),
				tacFc(5364),
				malcGshdslBondedNtpExt(5365),
				malcGshdslBondedNtwcExt(5366),
				s300Cpu(6001),
				s300St1Dsx(6002),
				s300Se1(6003),
				s300Mt3c(6004),
				s300Sts1(6005),
				s300Fxs(6006),
				s300Fxo(6007),
				s300S155(6008),
				s300Ixcon(6009),
				s300Xcon(6010),
				s300St1Csu(6011),
				ipIad(7001),
				zedge6200em(7002),
				zedge6200fxs(7003),
				ethXShdsl(7101),
				ethXT1E1(7102),
				ethXShdsl4(7103),
				ethXShdsl8(7104),
				ethXT1E14(7105),
				ethXT1E18(7106),
				ethXPwe(7107),
				ethX3400(7108),
				ethX34004(7109),
				ethX34008(7110),
				ethX34004Ext(7111),
				ethX34008Ext(7112),
				zrg500(8001),
				zrg300(8002),
				zrg600(8003),
				zrg800(8004),
				gigaMux100(9100),
				fiberSlam101(9101),
				malcNextGen(10000),
				mxUp2Tg8g(10100),
				mxUp8G(10101),
				mxUp4gCopper(10121),
				mxUp4G(10125),
				mxUp2Tg8gTOP(10150),
				mxLc20AE(10200),
				mxLcGp(10201),
				mxLc48aAdslBond(10202),
				mxLc8Gp(10203),
				mxLc48aAdsl(10204),
				mxLc4Gp(10205),
				mxLc48bAdslBond(10206),
				mxLc20AE1S(10207),
				mxLc24GshdslBond(10208),
				mxLc72Pots(10209),
				mxLc24Vdsl2(10210),
				mxLc72aAdslBond(10212),
				mxLc48Pots(10213),
				mxLc24T1E1Bond(10214),
				mxLc24T1E1Pwe(10215),
				mxLc20Ae1SCsfp(10216),
				mxLcOc3Stm1Pwe(10217),
				mxLcVdsl2Splt900(10220),
				mxLcVdsl2Splt600(10221),
				mxLc24Vdsl2Pots(10222),
				mxLc24Vdsl2Pots2(10223),
				mxLc48Vdsl2(10224),
				mxLc72bAdslBond(10225),
				mxDcAdslAnnexB(10226),
				mxLc24Ulcs(10230),
				mxLc24UlcsISDN-2B1Q-Pv(10231),
				mxLc24UlcsISDN-4B3T-Pv(10232),
				mxLc24UlcsPots-Pv(10233),
				mx1UGponD1(10296),
				mxp1UPotsD2(10297),
				mx1USplitter600D2(10298),
				mx1USplitter900D2(10299),
				mx1Ux6xFamily(10300),
				mx1U160(10301),
				mx1U161(10302),
				mx1U162(10303),
				mx1U260(10304),
				mx1U261(10305),
				mx1U262(10306),
				mxp1U160(10307),
				mxp1U260(10308),
				mx1Ux80Family(10400),
				mx1U180(10401),
				mx1U280(10402),
				mxp1U180(10403),
				mxp1U280(10404),
				mx1U180-TP-RJ45(10405),
				mx1U280-TP-RJ45(10406),
				mx1U180-LT-TP-RJ45(10407),
				mx1U280-LT-TP-RJ45(10408),
				mxp1U180-TP-RJ45(10409),
				mxp1U280-TP-RJ45(10410),
				mx1U19xFamily(10500),
				mx1U194(10501),
				mx1U198(10502),
				mx1U194-10GE(10503),
				mx1U198-10GE(10504),
				mx1U194-TOP(10505),
				mx1U198-TOP(10506),
				mx1U194-10GE-TOP(10507),
				mx1U198-10GE-TOP(10508),
				mx1Ux5xFamily(10600),
				mx1U150(10601),
				mxp1U150(10602),
				mx1U151(10603),
				mx1U152(10604)
				}

		ZhoneCardLineType ::= TEXTUAL-CONVENTION
			STATUS current
			DESCRIPTION 
				"This field is used to identify which line types for
				different cards
								
				For normal e1/t1 cards only t1 and e1 (uni mode)
				line types are supported.
								
				For MALC t1Ima Uplink card, e1, t1, e1-ima, and
				t1-ima line types are supported
								
				For MALC ds3 Uplink card, e3 and t3 line types
				are supported.
				
				For malcXdsl48 with optional pots daughter board,
				unknown, adsl-pots and adsl-pots-pv are supported.
								
				For malcPots48 unknown, pots and pots-pv are supported.
				
				For malcUlcS unknown, isdn, isdn-pv, pots-meter, 
				pots-meter-pv, pots-meter-coin & pots-meter-coin-pv 
				are supported.
				
				All other cards only support unknown.
								
				Default value for MALC t1Ima uplink will be
				t1 line type if the line type was not stored
				in the Real Time Clock (RTC).  Otherwise it
				will be the value stored in the RTC.
								
				Default value for MALC ds3 Uplink will be
				t3 line type if the line type was not stored
				in the Real Time Clock (RTC).  Otherwise it
				will be the value stored in the RTC.
								
				This field is only set upon row-creation.
				Modifications to this value after row creation
				will only be allowed on packet voice capable cards.
				
				Values 31-34, formerly used for linkagg linetypes,
				are now deprecated.
				"
			SYNTAX INTEGER
				{
				unknown(1),
				e1(2),
				ds1(3),
				e1ima(4),
				ds1ima(5),
				e3(6),
				ds3(7),
				t1UniGr303(8),
				t1ImaGr303(9),
				e1UniV52(10),
				e1ImaV52(11),
				gshdsl(12),
				t1UniT1Cas(13),
				t1ImaT1Cas(14),
				t1Cas(15),
				rpr(16),
				rprT1Gr303(17),
				rprE1V52(18),
				rprT1Cas(19),
				adsl-pots(20),
				adsl-pots-pv(21),
				adsl-splitter(22),
				pots(23),
				pots-pv(24),
				isdn(25),
				isdn-pv(26),
				pots-coin(27),
				pots-coin-pv(28),
				reach-dsl-splitter(29),
				t1-tr008(30),
				gshdsl-ntp(35),
				gshdsl-nt(36),
				ebs(37),
				ebs-pv(38),
				ebs-pots-pv(39),
				adsl-pots-pv-rng-itm(40)
				}

		ZhoneAlarmTypeId ::= TEXTUAL-CONVENTION
			STATUS current
			DESCRIPTION 
				"This type defines the alarm id definitions for all alarms in
				the system.  
				
				The ZhoneAlarmTypeId is grouped into two seperate numeric blocks:
				
				- 1..10000: alarms generated as a result of a trap notifications
				  defined in standard IETF MIBs will have an alarm ID in the 
				  1..10000 range.
				
				- 10000+: alarms generated as a result of a trap notifications
				  defined in Zhone enterprise MIBs will have an alarm ID above
				  10000."
			SYNTAX INTEGER
				{
				coldStart(1),
				warmStart(2),
				linkDown(3),
				dsx3LineStatusChange(5),
				adslAtucPerfLofsThreshTrap(6),
				adslAtucPerfLossThreshTrap(7),
				adslAtucPerfLprsThreshTrap(8),
				adslAtucPerfESsThreshTrap(9),
				adslAtucRateChangeTrap(10),
				adslAtucPerfLolsThreshTrap(11),
				adslAtucInitFailureTrap(12),
				adslAturPerfLofsThreshTrap(13),
				adslAturPerfLossThreshTrap(14),
				adslAturPerfLprsThreshTrap(15),
				adslAturPerfESsThreshTrap(16),
				adslAturRateChangeTrap(17),
				isdnMibCallInformation(18),
				aal2ExternalAIS(10001),
				aal2ExternalRAI(10002),
				aal2InternalAIS(10003),
				aal2InternalRDI(10004),
				aal2PvcDown(10005),
				aal2PerfCellLossThreshTrap(10006),
				aal2PerfCongestionThreshTrap(10007),
				atmVclOperStatusChange(10008),
				atmDsx3PlcpAlarmStatusChange(10009),
				atmInterfaceTCAlarmStateChange(10010),
				atmVclBandwidthUnavailable(10011),
				atmVplOperStatusChange(10012),
				atmOamF5PingStatus(10013),
				atmVpiAutoCreateComplete(10014),
				atmOamF4PingStatus(10015),
				zhoneLineStatusChange(10016),
				zhoneTrapShelfStatusChange(10017),
				zhoneTrapCardStatusChange(10018),
				zhoneTrapCardVersionCheck(10019),
				zhoneTrapFlashCardStatusChange(10020),
				zhoneAdslPotsBypassRelayChangeNotification(10021),
				zhoneDslLineAlarmStatusChange(10022),
				isdnTrapFrameSynchLoss(10023),
				isdnTrapFECV(10024),
				isdnTrapAmiViolations(10025),
				isdnTrapUnbalancedFrame(10026),
				sonetClockTransmitSourceChange(10027),
				sonetSectionStatusChange(10028),
				sonetLineStatusChange(10029),
				sonetPathStatusChange(10030),
				zhoneCardServicesStatusChange(10031),
				zhoneExternalAlarmTrap(10032),
				zrgBatteryRelayNotification(10033),
				zhoneTrapCpeConnectionDown(10034),
				zhoneTrapConfigSyncChange(10035),
				zhoneTrapSnmpSATimeout(10036),
				zhoneCardRedundancyStatusChange(10037),
				zhoneBulkStatisticsIntervalFailure(10038),
				zhoneZmsBlockCliChange(10039),
				apsEventSwitchover(10040),
				apsEventModeMismatch(10041),
				apsEventChannelMismatch(10042),
				apsEventPSBF(10043),
				apsEventFEPLF(10044),
				sechtor100FanStatusChange(10045),
				sechtor100ThermoStatusChange(10046),
				sipStatusCodeNotif(10047),
				sipStatusCodeThreshExceededNotif(10048),
				zhoneTraceRoutePathChange(10049),
				zhoneTraceRouteTestFailed(10050),
				voiceDspReset(10051),
				voiceDspChannelPktsLoss(10052),
				voiceDspChannelInterArrvJitterTrigger(10053),
				igOperStatusChange(10054),
				igTmcPrimaryStateChange(10055),
				igTmcSecondaryStateChange(10056),
				igEocPrimaryStateChange(10057),
				igEocSecondaryStateChange(10058),
				igCrvRemoteStateChange(10059),
				igCrvTmcStateChange(10060),
				igSystemTimeChange(10061),
				v52IgProvVariantRequestNotification(10062),
				v52IgPortAlignmentNotification(10063),
				v52LinkCheckIdNotification(10064),
				v52LinkBlockNotification(10065),
				v52IgOperStatusChange(10066),
				v52CChannelStatusChange(10067),
				v52CPathOperStatusChange(10068),
				v52ProtectionCPathOperStatusChange(10069),
				dhcpTrapZhoneCpeDetected(10070),
				dhcpTrapZhoneCpeSysObjectID(10071),
				dhcpTrapZhoneIpAddressUpdate(10072),
				zapTrapZhoneMalcDetected(10073),
				zapTrapZhoneCpeDetected(10074),
				zapTrapZhoneBanDetected(10075),
				zapTrapZhoneProvisioningDone(10076),
				zapTrapZhoneCpeConnectionDown(10077),
				zapTrapZhoneMalcConnectionDown(10078),
				zhoneTrapCardMemStatus(10079),
				zhonePingTestCompleted(10080),
				zhoneImaGroupDown(10081),
				zhoneLeftOutletTempOverLimit(10082),
				zhoneLeftOutletTempNormal(10083),
				zhoneRightOutletTempOverLimit(10084),
				zhoneRightOutletTempNormal(10085),
				zhonePowerSupplyAFailure(10086),
				zhonePowerSupplyAOk(10087),
				zhonePowerSupplyBFailure(10088),
				zhonePowerSupplyBOk(10089),
				zhoneFanSpeedError(10090),
				zhoneShelfControllerFault(10091),
				zhoneTempOverLimit(10092),
				zhoneTempUnderLimit(10093),
				zhoneTempNormal(10094),
				zhoneFanPowerSupplyAFailure(10095),
				zhoneFanPowerSupplyAOk(10096),
				zhoneFanPowerSupplyBFailure(10097),
				zhoneFanPowerSupplyBOk(10098),
				zhoneFanTrayAdded(10099),
				zhoneFanTrayRemoved(10100),
				zhoneFanSpeedOk(10101),
				zhoneFanAFailure(10102),
				zhoneFanAOk(10103),
				zhoneFanBFailure(10104),
				zhoneFanBOk(10105),
				zhonePowerSupplyCFailure(10106),
				zhonePowerSupplyCOk(10107),
				zhonePowerSupplyDFailure(10108),
				zhonePowerSupplyDOk(10109),
				zhoneShelfControllerCleared(10110),
				zhonePermanentLockoutFailure(10111),
				zhoneElcpIGOperStatusChange(10112),
				zhoneISDNLinkDown(10113),
				zhoneCPEConnectionUp(10114),
				zhoneOnBatteryPower(10115),
				zhoneLowBatteryPower(10116),
				zhoneBadBattery(10117),
				zhoneNoBatteryBackup(10118),
				zhoneNoUPS(10119),
				zhoneRprEastSpanDown(10120),
				zhoneRprWestSpanDown(10121),
				zhoneAdsllAtucMinTxAlarm(10122),
				zhoneAdsllAturMinTxAlarm(10123),
				zhoneRingerFailure(10124),
				zhoneFanCFailure(10125),
				zhoneFanDFailure(10126),
				zhoneFanEFailure(10127),
				zhoneBondGroupDown(10128),
				zhoneLinkAggLink1Down(10129),
				zhoneLinkAggLink2Down(10130),
				zhoneUnassignedGponOnu(10131),
				zhoneRedundancyUnsafe(10132),
				zhoneCardRemoved(10133),
				zhoneCardAdded(10134),
				zhoneCardTimeoutError(10135),
				zhoneCardFaultError(10136),
				zhoneCardReset(10137),
				zhoneIPSLATimeout(10138),
				zhoneIPSLALatency(10139),
				zhoneIPSLAJitter(10140),
				zhoneBitRateThresholdExceeded(10141),
				zhoneVdslXTUCPerf15minLOFSThresholdExceeded(10142),
				zhoneVdslXTUCPerf15minLOSSThresholdExceeded(10143),
				zhoneVdslXTUCPerf15minLPRSThresholdExceeded(10144),
				zhoneVdslXTUCPerf15minLOLSThresholdExceeded(10145),
				zhoneVdslXTUCPerf15minESSThresholdExceeded(10146),
				zhoneVdslXTUCPerf15minSESSThresholdExceeded(10147),
				zhoneVdslXTUCPerf15minUASSThresholdExceeded(10148),
				zhoneVdslXTUCPerf1dayLOFSThresholdExceeded(10149),
				zhoneVdslXTUCPerf1dayLOSSThresholdExceeded(10150),
				zhoneVdslXTUCPerf1dayLPRSThresholdExceeded(10151),
				zhoneVdslXTUCPerf1dayLOLSThresholdExceeded(10152),
				zhoneVdslXTUCPerf1dayESSThresholdExceeded(10153),
				zhoneVdslXTUCPerf1daySESSThresholdExceeded(10154),
				zhoneVdslXTUCPerf1dayUASSThresholdExceeded(10155),
				zhoneVdslXTUCInitFailure(10156),
				zhoneVdslXTUCMinTxThresholdExceeded(10157),
				zhoneVdslXTURMinTxThresholdExceeded(10158),
				zhonePmeSnrMgnThresholdCrossing(10159),
				zhonePmeErrorMonitorEfmTrafficDisabled(10160),
				zhoneRingerPowerBusFailure(10162),
				zhoneEfmBondGroupTrafficDisabled(10163),
				zhoneCardLinkToBkplaneStatusChange(10170),
				zhoneLineRedundancyUnsafe(10171),
				zhoneEfmLineTrafficDisabled(10172),
				zhoneTrapCardProcessorUsage(10173),
				zhoneGponOnuError(10174),
				cpeCfgMgrStatusChange(10175),
				zhoneGponOltRogueOnu(10176),
				zhoneGponOltRssiRogueOnu(10177),
				zhoneGponOltError(10178),
				bridgeLoopDetection(10179),
				mxkAlarmInput(10180),
				bridgeStormDetection(10181),
				upstreamTrafficTrap(10182),
				cfmFaultAlarmRdiCcmTrap(10183),
				cfmFaultAlarmMacStatusTrap(10184),
				cfmFaultAlarmRemoteCcmTrap(10185),
				cfmFaultAlarmErrorCcmUnexpectedMepTrap(10186),
				cfmFaultAlarmErrorCcmUnexpectedPeriodTrap(10187),
				cfmFaultAlarmXconCcmUnexpectedMepTrap(10188),
				cfmFaultAlarmXconCcmUnexpectedLevelTrap(10189),
				cfmFaultAlarmXconCcmMismergeTrap(10190)
				}

		ZhoneAlarmSeverity ::= TEXTUAL-CONVENTION
			STATUS current
			DESCRIPTION 
				"This type defines the severity of the alarm raised/cleared."
			SYNTAX INTEGER
				{
				critical(1),
				major(2),
				minor(3),
				warning(4)
				}

		ZhoneEnabledFlag ::= TEXTUAL-CONVENTION
			STATUS current
			DESCRIPTION 
				"A field which is either enabled or disabled."
			SYNTAX INTEGER
				{
				enabled(1),
				disabled(2)
				}

		ZhoneAdminState ::= TEXTUAL-CONVENTION
			STATUS current
			DESCRIPTION 
				"This represents the admin state with the values - UP, DOWN and TESTING."
			SYNTAX INTEGER
				{
				up(1),
				down(2),
				testing(3)
				}

	
--
-- Node definitions
--
	
	
	END

--
-- Zhone-TC.mib
--
