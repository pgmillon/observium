NTNTECH-CHASSIS-STATUS-MIB DEFINITIONS ::= BEGIN    

--	****************************************************************    
--  Enterprise:
--   	Paradyne Corporation.    
--
--  ContactInfo:
--    	Paradyne Corporation
--     	8545 126th Avenue North
--     	phone: +1 (727) 530 - 2000
--     	email: support@paradyne.com 
--		www:   http://www.nettonet.com/support/
--
--  Description:
--    	ntntech-chassis-status-MIB.my
--    	Revision: 1.02.02
--    	Part Number: xx-xxxx-xx
--    	Date: November 17, 2004
--   
--    	This module provides explicit definitions for the Net to
--		Net Technologies naming	tree below:
--    
--    	nettonettech { enterprises 8059 }
--    
--    	This module will be extended, as additional sub-sections
--    	of this naming tree are defined.
--
--  Disclaimer:
--	   	This is an extremely preliminary MIB module and is subject
--		to change at any time therefore, use at your own risk.
--    
-- 	Copyright (c)2000 - 2004 by Paradyne Corporation.
-- 	All rights reserved.    

-- ****************************************************************
IMPORTS  
	ntntechChassis,NtnDisplayString,
	NtnMacAddress								FROM NTNTECH-ROOT-MIB
   	OBJECT-TYPE, MODULE-IDENTITY				FROM SNMPv2-SMI
   	TEXTUAL-CONVENTION	 						FROM SNMPv2-TC;
-- ****************************************************************       
ntntechChassisStatusMIB MODULE-IDENTITY  
    LAST-UPDATED "0411170200Z"  -- November 17, 2004
    ORGANIZATION "Paradyne Corporation"
    CONTACT-INFO
        "Paradyne Corporation
        8545 126th Avenue North
        Largo, FL 33773        
     	
        phone: +1 (727) 530-2000
        email: support@paradyne.com 
        www:   http://www.nettonet.com/support/"

    DESCRIPTION
    	 "This mib module defines an SNMP API to manage the Paradyne Corporation's
         IPD12000, IPD4000, and Mini/Micro DSLAMs' chassis status. The interface
         types are described below,  
    
         AMD8000-12
	     12-Port ADSL Mini DSLAMs With Full Rate and G.lite Operational Modes      
	
         SMD2000-12, SMD2000Q-12, SMD2000G-12
         12-Port SDSL Mini DSLAMs: AC and DC Versions with Cap, 2B1Q
         and G.SHDSL line encoding     
         
         SuD2011_12T, SuD2011_12E, SuD2003_12T, SuD2003_12E
         12-Port SDSL Micro DSLAMs: Cap, 2B1Q and G.SHDSL line encoding 
         
         SuD2011_6T, SuD2011_6E, SuD2002_6T, SuD2002_6E 
         6-Port SDSL Micro DSLAMs: Cap, 2B1Q and G.SHDSL line encoding 
           
         MUM200-2, MUM2000-2
         Multiplexer Uplink Module with Dual Uplink Interface Module Capacity  
         
         UIM-10/100
         Uplink Interface Module   
         
         UIM-DS3
         DS3 Uplink Interface Module  
         
         UIM-E1
         E1 Uplink Interface Module  
         
         UIM-E3
         E3 Uplink Interface Module  
         
         UIM-T1
         T1 Uplink Interface Module    "    
         
         
    REVISION     "0205061054Z"
    DESCRIPTION
      	"Add Gigabit detect value to uimStaEthRxTxRate - > uimEthGig(3)."    
      	
      	
    REVISION	"0208061045Z"
    DESCRIPTION
        "Added to the mumStaMgmtPortTable the OIDs mumStaMgmtPortRxTxRate and
         mumStaMgmtPortDuplex.
         
         Added to the mumStaTable OID mumStaType the value smD2000p24(130).
         Added to the uimStaTable OID uimStaType the value uimGig(6)."   
         
    REVISION     "0208280935Z"
    DESCRIPTION
      	"New Release - v1.01.00"  
      	
    REVISION     "0209241124Z"
    DESCRIPTION
      	"Added to the uimStaTable OID uimStaType the value uimFx(7)." 
      	
    REVISION     "0210110900Z"
    DESCRIPTION
      	"Added to the mumStaMgmtPortType OID the value uplink(2)."   
      	
    REVISION     "0210220200Z"
    DESCRIPTION
      	"New Release - v1.01.01"    
      	
    REVISION     "0211041036Z"
    DESCRIPTION
      	"Added to the uimStaTable OID uimStaType the value uim100Fx(8)."      
      	
    REVISION     "0311140842Z"
    DESCRIPTION
      	"Added networkExtender, iPD12000E, and iPD4000E to the mumStaChassisType OID."     
      	
    REVISION     "0403151016Z"
    DESCRIPTION
      	"Added sne2040p4 to the mumStaType OID."
    
    REVISION  "0404271042Z"
    DESCRIPTION
    	"Added ane8420,sne2040,and bsx8000 to the mumStaType OID." 	       
		
	REVISION "0410110919Z"
	DESCRIPTION
		"Adjusted the copyright statement and references to Paradyne." 
		
		REVISION "0411171000Z"
		DESCRIPTION
			"New release version 1.02.01"

::= { ntntechChassis 2 }  
 
--	Objects                        
                                                                                     
chsStaMIBObjects OBJECT IDENTIFIER ::= { ntntechChassisStatusMIB 1 }   

--	NTNTECH Chassis Status(chsSta) MIB objects for the MUM200-2/2000-2 module and
--	the Mini/Micro DSLAM. 
--
--			IPD12000 	- slots 13,14  MIB index - 1,2 respecitively
--			IPD4000	 	- slot 5       MIB index - 1
--			Mini DSLAM 	- NA           MIB index - 1  
--			Micro DSLAM - NA		   MIB index - 1
--                            

chsStaValues OBJECT IDENTIFIER ::= { chsStaMIBObjects 1 }    

-- NTNTECH Chassis Status(chsSta) values.      

valMultiplexerUplinkModule OBJECT IDENTIFIER ::= { chsStaValues 1 }
                      
mumStaChassisType  OBJECT-TYPE
	SYNTAX      INTEGER {
		           	iPD12000(1),   -- a 12 slot DSLAM
		           	iPD4000(2),    -- a 5 slot DSLAM 
					miniDSLAM(3),  -- not applicable 
					microDSLAM(4), -- not applicable  
					networkExtender(5),
					iPD12000E(6),   -- a 12 slot DSLAM
		           	iPD4000E(7)     -- a 5 slot DSLAM 

				}   

    MAX-ACCESS  read-only
    STATUS      current
    DESCRIPTION
    "The physical chassis type - IPD12000, IPD4000, or Mini/Micro DSLAM."
    ::= { valMultiplexerUplinkModule 1 }  
       	
mumStaFanState  OBJECT-TYPE
    SYNTAX     	INTEGER {    
					on(1),
					fault(2),
					alert(3)
				} 
    MAX-ACCESS  read-only
    STATUS      current
    DESCRIPTION
    "Check the current state of the chassis fan unit.
    
    	1 = ON (all fans operational)
    	2 = Fault (at least one fan within the fan system has malfunctioned)
    	3 = Alert (all fans within the fan system have malfunctioned)"
    ::= { valMultiplexerUplinkModule 2 }   
       	                 
mumStaTable OBJECT-TYPE
     SYNTAX		SEQUENCE OF MumStaEntry
     MAX-ACCESS  not-accessible
     STATUS      current
     DESCRIPTION
     "A list of MUM200-2/2000-2 module and Mini/Micro DSLAM entries."
     ::= { valMultiplexerUplinkModule 4 }

mumStaEntry OBJECT-TYPE
     SYNTAX		MumStaEntry
     MAX-ACCESS  not-accessible
     STATUS      current
     DESCRIPTION
     "An entry containing management information applicable to a MUM200-2/MUM2000-2
     module and Mini/Micro DSLAM."
     INDEX   { mumStaIndex }
     ::= { mumStaTable 1 }

	MumStaEntry ::=
		SEQUENCE {
           		mumStaIndex			INTEGER,
           		mumStaMacAddress	NtnMacAddress,   
           		mumStaFirmWareRev	OCTET STRING,
           		mumStaType			INTEGER   
        }
                   
    mumStaIndex OBJECT-TYPE
       	SYNTAX      INTEGER (1..2)
       	MAX-ACCESS  read-only
       	STATUS      current
       	DESCRIPTION
        "Translates to the physical slot number that a MUM200-2/2000-2 module 
        exists within a chassis. The Mini/Micro DSLAMs' physical location is
        set to 1 by default.  See below,  
        
         chassis type     physical location(s) translation
         ------------     --------------------------------          
           IPD12000       MUM in slots 13,14 = mumCfgIndex 1,2 respecitively 
           IPD4000        MUM in slot 5      = mumCfgIndex 1 
           Mini DSLAM     NA				 = mumCfgIndex 1
           Micro DSLAM    NA				 = mumCfgIndex 1"
       	::= { mumStaEntry 1 }
   
   	mumStaMacAddress OBJECT-TYPE
       	SYNTAX      NtnMacAddress
       	MAX-ACCESS  read-only
       	STATUS      current
       	DESCRIPTION
        "The Mac Address of the MUM200-2/2000-2 module or Mini/Micro DSLAM."
       	::= { mumStaEntry 2 }

   	mumStaFirmWareRev OBJECT-TYPE
       	SYNTAX      OCTET STRING  (SIZE (7))
       	MAX-ACCESS  read-only
       	STATUS      current
       	DESCRIPTION
        "The firmware revision of the MUM200-2/2000-2 module or Mini/Micro DSLAM."
       ::= { mumStaEntry 3 }     
       
    mumStaType OBJECT-TYPE
       	SYNTAX      INTEGER {           
       					mum2000p2(129),
       					mum200p2(128),   
       					amD8000p12(11),
       					smD2000p12(7),
       					smD2000Qp12(8),
       					smD2000Gp12(19),  
       					smD2000p24(130),
       					suD2011p12T(22),
						suD2011p12E(23),
						suD2003p12T(24),
						suD2003p12E(25),
						suD2011p6T(26),
						suD2011p6E(27),
						suD2002p6T(28),
						suD2002p6E(29),
						ane8420(135),
						sne2040(14),
						bsx8000(137) 			

       				}

       	MAX-ACCESS  read-only
       	STATUS      current
       	DESCRIPTION
        "The physical multiplexer uplink module type."
       	::= { mumStaEntry 4 } 
       	
mumStaMgmtPortTable OBJECT-TYPE
	SYNTAX		SEQUENCE OF MumStaMgmtPortEntry
   	MAX-ACCESS  not-accessible
   	STATUS      current
   	DESCRIPTION
    "A list of the hardware platform management port entries."
   	::= { valMultiplexerUplinkModule 5 }

mumStaMgmtPortEntry OBJECT-TYPE
    SYNTAX		MumStaMgmtPortEntry
    MAX-ACCESS  not-accessible
    STATUS      current
    DESCRIPTION
    "An entry containing information about the state of the managment (ethernet type) port."  
	INDEX   { mumStaMgmtPortMumIndex }
    ::= { mumStaMgmtPortTable 1 }

   	MumStaMgmtPortEntry ::=
       SEQUENCE {
           mumStaMgmtPortMumIndex			INTEGER,
           mumStaMgmtPortType		    	INTEGER, 
           mumStaMgmtPortLinkState			INTEGER,
           mumStaMgmtPortRxTxRate			INTEGER,
           mumStaMgmtPortDuplex				INTEGER       
       }   
         
	mumStaMgmtPortMumIndex OBJECT-TYPE
       	SYNTAX      INTEGER (1..2)
       	MAX-ACCESS  read-only
       	STATUS      current
       	DESCRIPTION
        "Translates to the physical slot number that a MUM200-2/2000-2 module 
        exists within a chassis. The Mini/Micro DSLAMs' physical location is
        set to 1 by default.  See below,  
        
         chassis type     physical location(s) translation
         ------------     --------------------------------          
           IPD12000       MUM in slots 13,14 = mumStaMgmtPortMumIndex 1,2 respecitively 
           IPD4000        MUM in slot 5      = mumStaMgmtPortMumIndex 1 
           Mini DSLAM     NA				 = mumStaMgmtPortMumIndex 1
           Micro DSLAM    NA				 = mumStaMgmtPortMumIndex 1"
       	::= { mumStaMgmtPortEntry 1 }  
       
   	mumStaMgmtPortType OBJECT-TYPE
       	SYNTAX	INTEGER { 
       				mgmt(1),
       				uplink(2)			
       			}
       	MAX-ACCESS  read-only
       	STATUS      current
       	DESCRIPTION
        "The management port type installed in the MUM200-2/2000-2 module or Mini/Micro DSLAM."
       	::= { mumStaMgmtPortEntry 2 } 
       	
    mumStaMgmtPortLinkState OBJECT-TYPE
       	SYNTAX	INTEGER { 
       				link(1),
       				noLink(2),						
       				fault(3)
       			}
       	MAX-ACCESS  read-only
       	STATUS      current
       	DESCRIPTION
        "The management port Link state."
       	::= { mumStaMgmtPortEntry 3 }     
       	
    mumStaMgmtPortRxTxRate OBJECT-TYPE
       	SYNTAX	INTEGER {    
       				uimEthNoLink(0),
       				uimEth10(1),			
       				uimEth100(2),
       				uimEthGig(3)	   						
       			}
       	MAX-ACCESS  read-only
       	STATUS      current
       	DESCRIPTION
        "The RxTx rate for an ethernet management port."
        ::= { mumStaMgmtPortEntry 4 } 
        
    mumStaMgmtPortDuplex OBJECT-TYPE
       	SYNTAX	INTEGER {  
       				uimEthNoLink(0), 
       				uimEthHalf(1),    
       				uimEthFull(2)								
       			}
       	MAX-ACCESS  read-only
       	STATUS      current
       	DESCRIPTION
        "The current duplex setting for an ethernet UIM."
        ::= { mumStaMgmtPortEntry 5 }      
                           
mumStaUplinkInterfaceModule OBJECT IDENTIFIER ::= { valMultiplexerUplinkModule 6 }
                 
uimStaTable OBJECT-TYPE
	SYNTAX		SEQUENCE OF UimStaEntry
   	MAX-ACCESS  not-accessible
   	STATUS      current
   	DESCRIPTION
    "A list of MUM200-2/2000-2 module or Mini/Micro DSLAM Uplink Interface 
    Module (UIM) entries."
   	::= { mumStaUplinkInterfaceModule 1 }

uimStaEntry OBJECT-TYPE
    SYNTAX		UimStaEntry
    MAX-ACCESS  not-accessible
    STATUS      current
    DESCRIPTION
    "An entry containing information applicable to a MUM200-2, MUM2000-2, or
    Mini/Micro DSLAM Uplink Interface Module (UIM)."  
	INDEX   { uimStaMumIndex, uimStaIndex }
    ::= { uimStaTable 1 }

   	UimStaEntry ::=
       SEQUENCE {
           uimStaMumIndex			INTEGER,
           uimStaIndex				INTEGER,
           uimStaType		    	INTEGER, 
           uimStaLinkState			INTEGER      
       }   
         
	uimStaMumIndex OBJECT-TYPE
       	SYNTAX      INTEGER (1..2)
       	MAX-ACCESS  read-only
       	STATUS      current
       	DESCRIPTION
        "Translates to the physical slot number that a MUM200-2/2000-2 module 
        exists within a chassis. The Mini/Micro DSLAMs' physical location is
        set to 1 by default.  See below,  
        
         chassis type     physical location(s) translation
         ------------     --------------------------------          
           IPD12000       MUM in slots 13,14 = uimStaMumIndex 1,2 respecitively 
           IPD4000        MUM in slot 5      = uimStaMumIndex 1 
           Mini DSLAM     NA				 = uimStaMumIndex 1
           Micro DSLAM    NA				 = uimStaMumIndex 1"
       	::= { uimStaEntry 1 }  
       
   	uimStaIndex OBJECT-TYPE
       	SYNTAX      INTEGER (1..4)
       	MAX-ACCESS  read-only
       	STATUS      current
       	DESCRIPTION
        "The physical slot used to access the UIM in the MUM200-2/2000-2 module or
        Mini/Micro DSLAM."
       	::= { uimStaEntry 2 }    
       
   	uimStaType OBJECT-TYPE
       	SYNTAX	INTEGER { 
       				uimEther100(1),			
       				uimT1(2),						
       				uimDS3(3),
       				uimE1(4),
       				uimE3(5),
       				uimGig(6),
       				uimGigFx(7),  
       				uim100Fx(8)       				
       			}
       	MAX-ACCESS  read-only
       	STATUS      current
       	DESCRIPTION
        "The UIM type installed in the MUM200-2/2000-2 module or Mini/Micro DSLAM.
        
        Exception: 
          	A MUM200-2 module will represent a T1 or E1 UIM with the uimT1(2) identifier. 
        	In addition, the MUM200-2 will represent a DS3 or E3 UIM with the uimDS3(3) 
        	identifier."
       	::= { uimStaEntry 3 } 
       	
    uimStaLinkState OBJECT-TYPE
       	SYNTAX	INTEGER { 
       				link(1),
       				noLink(2),						
       				fault(3)
       			}
       	MAX-ACCESS  read-only
       	STATUS      current
       	DESCRIPTION
        "The UIM Link state."
       	::= { uimStaEntry 4 }    
       	  	
uimStaEthTable OBJECT-TYPE
	SYNTAX		SEQUENCE OF UimStaEthEntry
   	MAX-ACCESS  not-accessible
   	STATUS      current
   	DESCRIPTION
    "A list of ethernet Uplink Interface Module (UIM) entries."
   	::= { mumStaUplinkInterfaceModule 2 }

uimStaEthEntry OBJECT-TYPE
    SYNTAX		UimStaEthEntry
    MAX-ACCESS  not-accessible
    STATUS      current
    DESCRIPTION
    "An entry containing information applicable to an ethernet Uplink Interface Module (UIM)."  
	INDEX   { uimStaEthMumIndex, uimStaEthIndex }
    ::= { uimStaEthTable 1 }

   	UimStaEthEntry ::=
       SEQUENCE {
           uimStaEthMumIndex			INTEGER,
           uimStaEthIndex				INTEGER,  
           uimStaEthRxTxRate			INTEGER,
           uimStaEthDuplex	    		INTEGER               
       }   
         
	uimStaEthMumIndex OBJECT-TYPE
       	SYNTAX      INTEGER (1..2)
       	MAX-ACCESS  read-only
       	STATUS      current
       	DESCRIPTION
        "Translates to the physical slot number that a MUM200-2/2000-2 module 
        exists within a chassis. The Mini/Micro DSLAMs' physical location is
        set to 1 by default.  See below,  
        
         chassis type     physical location(s) translation
         ------------     --------------------------------          
           IPD12000       MUM in slots 13,14 = uimStaEthMumIndex 1,2 respecitively 
           IPD4000        MUM in slot 5      = uimStaEthMumIndex 1 
           Mini DSLAM     NA				 = uimStaEthMumIndex 1
           Micro DSLAM    NA				 = uimStaEthMumIndex 1"
       	::= { uimStaEthEntry 1 }  
       
   	uimStaEthIndex OBJECT-TYPE
       	SYNTAX      INTEGER (1..4)
       	MAX-ACCESS  read-only
       	STATUS      current
       	DESCRIPTION
        "The physical slot used to access the UIM in the MUM200-2/2000-2 module or
        Mini/Micro DSLAM."
       	::= { uimStaEthEntry 2 }    
       
   	uimStaEthRxTxRate OBJECT-TYPE
       	SYNTAX	INTEGER {      
       				uimEthNoLink(0),
       				uimEth10(1),			
       				uimEth100(2),
       				uimEthGig(3)						
       			}
       	MAX-ACCESS  read-only
       	STATUS      current
       	DESCRIPTION
        "The current RxTx rate for an ethernet UIM."
       	::= { uimStaEthEntry 3 }       
       	
    uimStaEthDuplex OBJECT-TYPE
       	SYNTAX	INTEGER {   
       				uimEthNoLink(0),
       				uimEthHalf(1),    
       				uimEthFull(2)								
       			}
       	MAX-ACCESS  read-only
       	STATUS      current
       	DESCRIPTION
        "The current duplex setting for an ethernet UIM."
        ::= { uimStaEthEntry 4 } 
        
uimStaT1Table OBJECT-TYPE
	SYNTAX		SEQUENCE OF UimStaT1Entry
   	MAX-ACCESS  not-accessible
   	STATUS      current
   	DESCRIPTION
    "A list of T1 Uplink Interface Module (UIM) entries."
   	::= { mumStaUplinkInterfaceModule 3 }

uimStaT1Entry OBJECT-TYPE
    SYNTAX		UimStaT1Entry
    MAX-ACCESS  not-accessible
    STATUS      current
    DESCRIPTION
    "An entry containing information applicable to a T1 Uplink Interface Module (UIM)."  
	INDEX   { uimStaT1MumIndex, uimStaT1Index }
    ::= { uimStaT1Table 1 }

   	UimStaT1Entry ::=
       SEQUENCE {
           uimStaT1MumIndex			INTEGER,
           uimStaT1Index			INTEGER,  
           uimStaT1RxTxRate			INTEGER              
       }   
         
	uimStaT1MumIndex OBJECT-TYPE
       	SYNTAX      INTEGER (1..2)
       	MAX-ACCESS  read-only
       	STATUS      current
       	DESCRIPTION
        "Translates to the physical slot number that a MUM200-2/2000-2 module 
        exists within a chassis. The Mini/Micro DSLAMs' physical location is
        set to 1 by default.  See below,  
        
         chassis type     physical location(s) translation
         ------------     --------------------------------          
           IPD12000       MUM in slots 13,14 = uimStaT1MumIndex 1,2 respecitively 
           IPD4000        MUM in slot 5      = uimStaT1MumIndex 1 
           Mini DSLAM     NA				 = uimStaT1MumIndex 1
           Micro DSLAM    NA				 = uimStaT1MumIndex 1"
       	::= { uimStaT1Entry 1 }  
       
   	uimStaT1Index OBJECT-TYPE
       	SYNTAX      INTEGER (1..4)
       	MAX-ACCESS  read-only
       	STATUS      current
       	DESCRIPTION
        "The physical slot used to access the UIM in the MUM200-2/2000-2 module or
        Mini/Micro DSLAM."
       	::= { uimStaT1Entry 2 }    
       
   	uimStaT1RxTxRate OBJECT-TYPE
       	SYNTAX	INTEGER { 
       				uimT1NoLink(0),     
       				uimT1Rate192(1),
       				uimT1Rate384(2),
       				uimT1Rate576(3),
       				uimT1Rate768(4),
       				uimT1Rate960(5),
       				uimT1Rate1152(6),
       				uimT1Rate1344(7),
       				uimT1Rate1536(8)			
       			}
       	MAX-ACCESS  read-only
       	STATUS      current
       	DESCRIPTION
        "The current RxTx rate for a T1 UIM."
       	::= { uimStaT1Entry 3 }       
                
uimStaE1Table OBJECT-TYPE
	SYNTAX		SEQUENCE OF UimStaE1Entry
   	MAX-ACCESS  not-accessible
   	STATUS      current
   	DESCRIPTION
    "A list of E1 Uplink Interface Module (UIM) entries."
   	::= { mumStaUplinkInterfaceModule 4 }

uimStaE1Entry OBJECT-TYPE
    SYNTAX		UimStaE1Entry
    MAX-ACCESS  not-accessible
    STATUS      current
    DESCRIPTION
    "An entry containing information applicable to an E1 Uplink Interface Module (UIM)."  
	INDEX   { uimStaE1MumIndex, uimStaE1Index }
    ::= { uimStaE1Table 1 }

   	UimStaE1Entry ::=
       SEQUENCE {
           uimStaE1MumIndex			INTEGER,
           uimStaE1Index			INTEGER,  
           uimStaE1RxTxRate			INTEGER        
       }   
         
	uimStaE1MumIndex OBJECT-TYPE
       	SYNTAX      INTEGER (1..2)
       	MAX-ACCESS  read-only
       	STATUS      current
       	DESCRIPTION
        "Translates to the physical slot number that a MUM200-2/2000-2 module 
        exists within a chassis. The Mini/Micro DSLAMs' physical location is
        set to 1 by default.  See below,  
        
         chassis type     physical location(s) translation
         ------------     --------------------------------          
           IPD12000       MUM in slots 13,14 = uimStaE1MumIndex 1,2 respecitively 
           IPD4000        MUM in slot 5      = uimStaE1MumIndex 1 
           Mini DSLAM     NA				 = uimStaE1MumIndex 1
           Micro DSLAM    NA				 = uimStaE1MumIndex 1"
       	::= { uimStaE1Entry 1 }  
       
   	uimStaE1Index OBJECT-TYPE
       	SYNTAX      INTEGER (1..4)
       	MAX-ACCESS  read-only
       	STATUS      current
       	DESCRIPTION
        "The physical slot used to access the UIM in the MUM200-2/2000-2 module or
        Mini/Micro DSLAM."
       	::= { uimStaE1Entry 2 }    
       
   	uimStaE1RxTxRate OBJECT-TYPE
       	SYNTAX	INTEGER { 
       				uimE1NoLink(0),   
       				uimE1Rate256(1),
       				uimE1Rate512(2),
       				uimE1Rate768(3),
       				uimE1Rate1024(4),
       				uimE1Rate1280(5),
       				uimE1Rate1536(6),
       				uimE1Rate1792(7),
       				uimE1Rate1984(8)			
       			}
       	MAX-ACCESS  read-only
       	STATUS      current
       	DESCRIPTION
        "The current RxTx rate for an E1 UIM."
       	::= { uimStaE1Entry 3 }       
       	               	           	
END
