--
-- comBridgeRec.mib
-- MIB generated by MG-SOFT Visual MIB Builder Version 3.0 Build 285
-- Tuesday, November 11, 2014 at 07:06:59
--

	ZHONE-COM-BRIDGE-REC-MIB DEFINITIONS ::= BEGIN
 
		IMPORTS
			AtmVpIdentifier, AtmVcIdentifier			
				FROM ATM-TC-MIB			
			ifIndex, ifAlias, InterfaceIndex			
				FROM IF-MIB			
			ifPhysAddress, PhysAddress			
				FROM RFC1213-MIB			
			SnmpAdminString			
				FROM SNMP-FRAMEWORK-MIB			
			OBJECT-GROUP, NOTIFICATION-GROUP			
				FROM SNMPv2-CONF			
			IpAddress, Integer32, Unsigned32, Counter64, OBJECT-TYPE, 
			MODULE-IDENTITY, OBJECT-IDENTITY, NOTIFICATION-TYPE			
				FROM SNMPv2-SMI			
			TruthValue, MacAddress, TEXTUAL-CONVENTION			
				FROM SNMPv2-TC			
			zhone, zhoneBridge, zhoneModules			
				FROM Zhone			
			ZhoneAdminString, ZhoneRowStatus			
				FROM Zhone-TC;
	
	
-- To create generated mib handler: 
-- /vob/EPILOGUE/binaries/emissary/solaris/mibcomp iftype.mib Zhone.mib Zhone-TC.mib rfc1907.mib rfc2233.mib rfc2514.mib rfc1213.mib rfc2571.mib -stub -o bridgeHdlr.c comBridgeRec.mib
-- 
-- To create generated protection layer:
--  /vob/zhonetools/bin/pahrser.pl iftype.mib Zhone.mib Zhone-TC.mib rfc2514.mib rfc2233.mib rfc2571.mib comBridgeRec.mib
-- 
-- 
-- 
-- 
-- 
-- 
-- 
-- 
-- 
-- 
-- 
-- 
-- 
-- 
-- 
-- 
-- 
-- 
		-- 1.3.6.1.4.1.5504.6.77
		bridgeRecord MODULE-IDENTITY 
			LAST-UPDATED "201302200249Z"		-- February 20, 2013 at 02:49 GMT
			ORGANIZATION 
				"Zhone Technologies, Inc."
			CONTACT-INFO 
				"  Postal: 
				Zhone Technologies, Inc.
				@ Zhone Way
				7001 Oakport Street
				Oakland, CA  94621
				USA
				Toll-Free: +1 877-ZHONE20 (+1 877-946-6320)
				Tel: +1-510-777-7000
				Fax: +1-510-777-7001
				E-mail: support@zhone.com"
			DESCRIPTION 
				"BRIDGE record MIB
				IP Software
				Minneapolis, MN
				"
			REVISION "201411110701Z"		-- November 11, 2014 at 07:01 GMT
			DESCRIPTION 
				"1. add more fields to bridgeStats
				2. add mroe fields to bridgeCmd
				3. clean up group errors
				4. clean up IGMP STATS code generation"
			REVISION "201409060532Z"		-- September 06, 2014 at 05:32 GMT
			DESCRIPTION 
				"1. Add BridgeInterfaceStatus table"
			REVISION "201405160558Z"		-- May 16, 2014 at 05:58 GMT
			DESCRIPTION 
				"Fix NetworkAddress compatibility issues with netsnmp"
			REVISION "201404071038Z"		-- April 07, 2014 at 10:38 GMT
			DESCRIPTION 
				"1. add staticBridgePathTable
				2. add bridgePathIfLookupTable
				3. add bridgePathAddressLookupTable"
			REVISION "201311120856Z"		-- November 12, 2013 at 08:56 GMT
			DESCRIPTION 
				"1. Add byte counters to bridgeStats
				2. Add GPON object to bridge I/F record table"
			REVISION "201310101121Z"		-- October 10, 2013 at 11:21 GMT
			DESCRIPTION 
				"Add bytes option to bridgeIfOnDemandStatsEnabled"
			REVISION "201308140351Z"		-- August 14, 2013 at 03:51 GMT
			DESCRIPTION 
				"Modified the range for unicastAgingPeriod"
			REVISION "201306181103Z"		-- June 18, 2013 at 11:03 GMT
			DESCRIPTION 
				"Add IPOB bridge types"
			REVISION "201306141208Z"		-- June 14, 2013 at 12:08 GMT
			DESCRIPTION 
				"reorder bridge-type values to be compatible with ZMS"
			REVISION "201306062102Z"		-- June 06, 2013 at 21:02 GMT
			DESCRIPTION 
				"add bridgeType to Bridge Interface Record"
			REVISION "201305100359Z"		-- May 10, 2013 at 03:59 GMT
			DESCRIPTION 
				"Changed the start range of packetRuleGroupIndex to 0 to support default packet group"
			REVISION "201302201334Z"		-- February 20, 2013 at 13:34 GMT
			DESCRIPTION 
				"Added IGMP V3 stats."
			REVISION "201210221559Z"		-- October 22, 2012 at 15:59 GMT
			DESCRIPTION 
				"Added secMvrAddr(15) as a new static-bridge address type."
			REVISION "201206121240Z"		-- June 12, 2012 at 12:40 GMT
			DESCRIPTION 
				"Add bridgeIgmpTable."
			REVISION "201204111444Z"		-- April 11, 2012 at 14:44 GMT
			DESCRIPTION 
				"Added staticBridgeIgmpDscp."
			REVISION "201203150704Z"		-- March 15, 2012 at 07:04 GMT
			DESCRIPTION 
				"changed some defaults for 'stp-params' due to support of MSTP."
			REVISION "201203060905Z"		-- March 06, 2012 at 09:05 GMT
			DESCRIPTION 
				"Change default value of eapsConfigSnmpTrap to TRUE"
			REVISION "201201261735Z"		-- January 26, 2012 at 17:35 GMT
			DESCRIPTION 
				"Added 4 new Bridge Storm Detect counters to the BridgeStats table."
			REVISION "201111151759Z"		-- November 15, 2011 at 17:59 GMT
			DESCRIPTION 
				"Added bridgeStormDetect(46) enum to packetRuleType and created new bridgestormDetection Trap."
			REVISION "201109200249Z"		-- September 20, 2011 at 02:49 GMT
			DESCRIPTION 
				"Added eaps topology table."
			REVISION "201107061707Z"		-- July 06, 2011 at 17:07 GMT
			DESCRIPTION 
				"Add bridgeState and bridgeIfUnblock"
			REVISION "201106211146Z"		-- June 21, 2011 at 11:46 GMT
			DESCRIPTION 
				"Add mac address string to bridge loop trap"
			REVISION "201106162107Z"		-- June 16, 2011 at 21:07 GMT
			DESCRIPTION 
				"Add bridgeLoopDetection Trap."
			REVISION "201105151035Z"		-- May 15, 2011 at 10:35 GMT
			DESCRIPTION 
				"Added staticBridgeLoopPrevention in static bridge table"
			REVISION "201102151716Z"		-- February 15, 2011 at 17:16 GMT
			DESCRIPTION 
				"Added vlanParms(14) to staticBridgeAddressType."
			REVISION "201101312116Z"		-- January 31, 2011 at 21:16 GMT
			DESCRIPTION 
				"Added a value clrIgmpStats to bridgeCmdOperation enum field"
			REVISION "201008311726Z"		-- August 31, 2010 at 17:26 GMT
			DESCRIPTION 
				"Changed bridgeIfMaxVideoStreams upper limit to 1024."
			REVISION "201008161247Z"		-- August 16, 2010 at 12:47 GMT
			DESCRIPTION 
				"Add igmpCustomIPAddress to static bridge profile"
			REVISION "201007301207Z"		-- July 30, 2010 at 12:07 GMT
			DESCRIPTION 
				"Add Vlan and Xlan translation to bridge I/F"
			REVISION "201003171032Z"		-- March 17, 2010 at 10:32 GMT
			DESCRIPTION 
				"Added bridgeIgmpStats"
			REVISION "201002081508Z"		-- February 08, 2010 at 15:08 GMT
			DESCRIPTION 
				"Added eapsTrapPrefix (traps for EAPS)"
			REVISION "201002081507Z"		-- February 08, 2010 at 15:07 GMT
			DESCRIPTION 
				"Added eapsStatsTable (row of eapsStatsEntry for each domain)."
			REVISION "201002081505Z"		-- February 08, 2010 at 15:05 GMT
			DESCRIPTION 
				"Added EapsStatusTable (row of eapsStatusEntry for each domain state machine)."
			REVISION "201002081455Z"		-- February 08, 2010 at 14:55 GMT
			DESCRIPTION 
				"Added eapsConfigRowStatus to eapsConfigEntry"
			REVISION "200909161635Z"		-- September 16, 2009 at 16:35 GMT
			DESCRIPTION 
				"Added eapsProtectedVlanEntryIndex to the eapsProtectedVlanTable.
				Fixed a couple of typos. Swapped the Zhone markup comments for
				eapsProtectedVlanLowerRange and UpperRange because they were
				in reverse order. The swapping of the markup comments was
				completely cosmetic and did not change any functionality or
				behavior."
			REVISION "200909101649Z"		-- September 10, 2009 at 16:49 GMT
			DESCRIPTION 
				"Add blockAsym(5) and blockAll(6) to flap control."
			REVISION "200907061621Z"		-- July 06, 2009 at 16:21 GMT
			DESCRIPTION 
				"Changed INDEX for eapsConfigEntry to primaryPortLineGroup, secondaryPortLineGroup, controlVlan"
			REVISION "200906261042Z"		-- June 26, 2009 at 10:42 GMT
			DESCRIPTION 
				"Added 'enable' field to eaps-domain-record
				Added QUICK_ACCESS keyword to 'domainName'"
			REVISION "200905011521Z"		-- May 01, 2009 at 15:21 GMT
			DESCRIPTION 
				"Added EAPS Group to MIB."
			REVISION "200903231623Z"		-- March 23, 2009 at 16:23 GMT
			DESCRIPTION 
				"1. Rename bridgeIfIngressStats to bridgeIfOnDemandStatsEnabled
				2. Rename bridgeStatsRulesSupported to bridgeOnDemandStatsRulesSupported
				3. Rename bridgeStatsIngressRemaing to bridgeOnDemandStatsRulesRemaining"
			REVISION "200902131650Z"		-- February 13, 2009 at 16:50 GMT
			DESCRIPTION 
				"Added bridgeIfIngressStats to bridgeInterfaceTable
				and bridgeStatsIngressSupported,bridgeStatsIngressRemaing
				to bridgeStatsTable"
			REVISION "200901141324Z"		-- January 14, 2009 at 13:24 GMT
			DESCRIPTION 
				"Add bridgeStatsTable"
			REVISION "200811040954Z"		-- November 04, 2008 at 09:54 GMT
			DESCRIPTION 
				"Added aclAllow/aclDeny to packetRuleType
				and updated description field."
			REVISION "200804181429Z"		-- April 18, 2008 at 14:29 GMT
			DESCRIPTION 
				"Add packet-rule-type colorAwareRateLimitDiscard"
			REVISION "200801101628Z"		-- January 10, 2008 at 16:28 GMT
			DESCRIPTION 
				"Add staticBridgeAddressType values 
				dhcpIpAddr and dhcpMacAddr"
			REVISION "200711210723Z"		-- November 21, 2007 at 07:23 GMT
			DESCRIPTION 
				"Fixed a comment."
			REVISION "200711121421Z"		-- November 12, 2007 at 14:21 GMT
			DESCRIPTION 
				"Added stpBind, and mstpInstance"
			REVISION "200711081308Z"		-- November 08, 2007 at 13:08 GMT
			DESCRIPTION 
				"Added profile for STP."
			REVISION "200710101528Z"		-- October 10, 2007 at 15:28 GMT
			DESCRIPTION 
				"Added dstMacSwapStatic and dstMacSwapDynamic to the packetRuleType enum values."
			REVISION "200709250931Z"		-- September 25, 2007 at 09:31 GMT
			DESCRIPTION 
				"Added fast(4) to staticBridgeFlapControl."
			REVISION "200707181604Z"		-- July 18, 2007 at 16:04 GMT
			DESCRIPTION 
				"Added new objects in bridgeInterfaceEntry record.
				Then new objects are bridgeIfTableBasedFilter and bridgeIfDhcpLearn."
			REVISION "200704161736Z"		-- April 16, 2007 at 17:36 GMT
			DESCRIPTION 
				"Add bridgePPoETable."
			REVISION "200704111222Z"		-- April 11, 2007 at 12:22 GMT
			DESCRIPTION 
				"Add fields floodUnknown and floodMulticast
				 to bridge-interface record"
			REVISION "200611270925Z"		-- November 27, 2006 at 09:25 GMT
			DESCRIPTION 
				"Add isPPPoA to bridgeInterface and
				bridgeInsertPPPoEVendorTag(99) to
				bridgeConfigType."
			REVISION "200609101002Z"		-- September 10, 2006 at 10:02 GMT
			DESCRIPTION 
				"Add fields to bridgeInterface and staticBridge entries. 
				Add a bridgeConfigType."
			REVISION "200604261551Z"		-- April 26, 2006 at 15:51 GMT
			DESCRIPTION 
				"added slanId to index for bridgeIfLookup, and bridgeaddressLookup."
			REVISION "200602011419Z"		-- February 01, 2006 at 14:19 GMT
			DESCRIPTION 
				"V01.00.12 - Added slan to static-Bridge profile reqd for QinQ support."
			REVISION "200601201500Z"		-- January 20, 2006 at 15:00 GMT
			DESCRIPTION 
				"V01.00.11 - Added support for QinQ"
			REVISION "200511111646Z"		-- November 11, 2005 at 16:46 GMT
			DESCRIPTION 
				"V01.00.10 - Add staticBridgeFlapControl."
			REVISION "200508011213Z"		-- August 01, 2005 at 12:13 GMT
			DESCRIPTION 
				"V01.00.09 - Added bridgeIfLookupFlush to bridgeIfLookupTableEntry
				and bridgeAddressLookupFlush to bridgeAddressLookupTable."
			REVISION "200507201713Z"		-- July 20, 2005 at 17:13 GMT
			DESCRIPTION 
				"V01.00.08 - Added bridgeIfVlanIdCOS, bridgeIfOutgoingCOSOption,
				bridgeIfOutgoingCOSValue to bridgeInterfaceTableEntry."
			REVISION "200412171506Z"		-- December 17, 2004 at 15:06 GMT
			DESCRIPTION 
				"V01.00.07 - added two new address 
				types to staticBridgeAddressTyoe."
			REVISION "200406021609Z"		-- June 02, 2004 at 16:09 GMT
			DESCRIPTION 
				"V01.00.06 - Added bridgeIfCustomDHCP, bridgeIfConfigGroupIndex to
				bridgeInterfaceTableEntry.  Added bridgeIfConfigGroupNextIndexTable
				Added bridgeConfigTable Removed bridgeForbidOui from
				staticBridgeAddressType members
				"
			REVISION "200404151326Z"		-- April 15, 2004 at 13:26 GMT
			DESCRIPTION 
				"V01.00.05 - Added to staticBridgeAddressType members:
				bridgeForbidOui, dhcpAllowOui."
			REVISION "200402011321Z"		-- February 01, 2004 at 13:21 GMT
			DESCRIPTION 
				"V01.00.04 - changed lower range of bridgeIfVci to 0
				in order to accomate ethernet bridging."
			REVISION "200310071422Z"		-- October 07, 2003 at 14:22 GMT
			DESCRIPTION 
				"V01.00.03 -  Add index value to staticBridge.
				             Add lowerIfIndex to BridgeIf."
			REVISION "200309220932Z"		-- September 22, 2003 at 09:32 GMT
			DESCRIPTION 
				"V01.00.02 -  Changed staticBridgeEntry INDEX."
			REVISION "200307291921Z"		-- July 29, 2003 at 19:21 GMT
			DESCRIPTION 
				"V01.00.01 - modified for VLAN bridging."
			REVISION "200109181100Z"		-- September 18, 2001 at 11:00 GMT
			DESCRIPTION 
				"V01.00.00 - Initial Release"
			::= { zhoneModules 77 }

		
	
	
--
-- Textual conventions
--
	
		PacketRuleGroupIndex ::= TEXTUAL-CONVENTION
			STATUS current
			DESCRIPTION 
				"Description."
			SYNTAX Integer32 (0..2147483647)

		EapsState ::= TEXTUAL-CONVENTION
			STATUS current
			DESCRIPTION 
				"EAPS State Values (per RFC 3619bis).
				
				IDLE          = 0x00 (EAPS Domain (Master/Transit) still not
				                      running)
				COMPLETE      = 0x01 (Master in complete State)
				FAILED        = 0x02 (Master in Failed State)
				LINKS-UP      = 0x03 (Transit in links-up State. Both ring-ports
				                      are up)
				LINK-DOWN     = 0x04 (Transit in Link-Down State. One or both
				                      ring-ports are down)
				PREFORWARDING = 0x05 (Transit in Preforwarding State)
				INIT          = 0x06 (Master in Init State)"
			SYNTAX INTEGER
				{
				idle(0),
				complete(1),
				failed(2),
				links-up(3),
				link-down(4),
				preForwarding(5),
				init(6)
				}

		BridgeState ::= TEXTUAL-CONVENTION
			STATUS current
			DESCRIPTION 
				"state as shown in 'bridge show'."
			SYNTAX INTEGER
				{
				up(1),
				down(2),
				trouble(3),
				notAvailable(4),
				initializing(5),
				adminDown(6),
				adminStateTest(7),
				adminStateNone(8),
				ready(9),
				discovering(10),
				unknown(11),
				blocked(12),
				pending(13),
				disabled(14),
				learning(15),
				forwarding(16),
				blockedFlapping(17),
				blockedPersistent(18),
				blockedFlappingPersistent(19)
				}

-- Same as PhysAddress except 16-byte IPv6 is used.
-- 
	NetworkAddress ::= OCTET STRING

	
--
-- Node definitions
--
	
		-- 1.3.6.1.4.1.5504.4.7.1
		bridgeInterfaceGroup OBJECT-GROUP
			OBJECTS { bridgeIfVci, bridgeIfVpi, bridgeIfVlanId, bridgeIfStripAndInsert, bridgeIfCustomARP, 
				bridgeIfFilterBroadcast, bridgeIfLearnIp, bridgeIfLearnUnicast, bridgeIfMaxUnicast, bridgeIfLearnMulticast, 
				bridgeIfForwardToUnicast, bridgeIfForwardToMulticast, bridgeIfForwardToDefault, bridgeLowerIfIndex , bridgeAddressLookupStaticOrDynamic, 
				bridgeIfLookupStaticOrDynamic, bridgeIfCustomDHCP, staticBridgeMulticastAging, bridgeIfRowStatus, staticBridgeRowStatus, 
				bridgeIfLookupFlush, bridgeIfOutgoingCOSValue , bridgeIfOutgoingCOSOption, bridgeIfVlanIdCOS, bridgeAddressLookupFlush, 
				staticBridgeFlapControl, bridgeIfStagOutgoingCOSValue, bridgeIfStagCOS, bridgeIfStagOutgoingCOSOption, bridgeIfStagStripAndInsert, 
				bridgeIfStagId, bridgeIfStagTPID, packetRuleValue, packetRuleRowStatus, packetRuleGroupMemberNextIndex, 
				bridgeIfEgressPacketRuleGroupIndex, bridgeIfIngressPacketRuleGroupIndex, packetRuleGroupIndexNext, packetRuleValue5, packetRuleValue4, 
				packetRuleValue3, eapsConfigControlVlan, eapsConfigPrimaryPortLineGroup, eapsConfigSecondaryPortLineGroup, eapsConfigIsMasterNode, 
				eapsConfigControlVlanPriority, eapsConfigDomainName, eapsConfigMsgTxInterval, eapsConfigTimeout, eapsConfigMaxDroppedMessages, 
				eapsConfigSnmpTrap, eapsProtectedVlanLowerRange, eapsProtectedVlanUpperRange, eapsConfigDomainEnable, eapsProtectedVlanEntryIndex, 
				genQueryRx, genQueryTx, specQueryRx, specQueryTx, v2ReportsRx, 
				v2ReportsTx, leavesRx, leavesTx, unknownRx, errorRx, 
				actChans, actHosts, staticBridgeLoopPrevention, v3ReportsTx, v3ReportsRx, 
				v3SpecQueryTx, v3SpecQueryRx, v3GenQueryTx, v3GenQueryRx, packetRuleValue2, 
				packetRuleType }
			STATUS current
			DESCRIPTION 
				"The bridge Interface Record object group. "
			::= { zhoneBridge 1 }

		
		-- 1.3.6.1.4.1.5504.4.7.2
		bridgeInterfaceTable OBJECT-TYPE
			SYNTAX SEQUENCE OF BridgeInterfaceEntry
			MAX-ACCESS not-accessible
			STATUS current
			DESCRIPTION
				"This table contains information required for the management
				of bridge interfaces."
			::= { zhoneBridge 2 }

		
		-- 1.3.6.1.4.1.5504.4.7.2.1
		bridgeInterfaceEntry OBJECT-TYPE
			SYNTAX BridgeInterfaceEntry
			MAX-ACCESS not-accessible
			STATUS current
			DESCRIPTION
				"An entry exists for each bridge interface in the system.
				At a mininum the ifIndex must be present to create a row."
			INDEX { ifIndex }
			::= { bridgeInterfaceTable 1 }

		
		BridgeInterfaceEntry ::=
			SEQUENCE { 
				bridgeIfVpi
					AtmVpIdentifier,
				bridgeIfVci
					AtmVcIdentifier,
				bridgeIfVlanId
					Integer32,
				bridgeIfStripAndInsert
					TruthValue,
				bridgeIfCustomARP
					TruthValue,
				bridgeIfFilterBroadcast
					TruthValue,
				bridgeIfLearnIp
					TruthValue,
				bridgeIfLearnUnicast
					TruthValue,
				bridgeIfMaxUnicast
					Integer32,
				bridgeIfLearnMulticast
					TruthValue,
				bridgeIfForwardToUnicast
					TruthValue,
				bridgeIfForwardToMulticast
					TruthValue,
				bridgeIfForwardToDefault
					TruthValue,
				bridgeLowerIfIndex 
					InterfaceIndex,
				bridgeIfRowStatus
					ZhoneRowStatus,
				bridgeIfCustomDHCP
					TruthValue,
				bridgeIfIngressPacketRuleGroupIndex
					PacketRuleGroupIndex,
				bridgeIfVlanIdCOS
					Integer32,
				bridgeIfOutgoingCOSOption
					INTEGER,
				bridgeIfOutgoingCOSValue 
					Integer32,
				bridgeIfStagTPID
					Integer32,
				bridgeIfStagId
					Integer32,
				bridgeIfStagStripAndInsert
					TruthValue,
				bridgeIfStagOutgoingCOSOption
					INTEGER,
				bridgeIfStagCOS
					Integer32,
				bridgeIfStagOutgoingCOSValue
					Integer32,
				bridgeIfMcastControlList
					SnmpAdminString,
				bridgeIfMaxVideoStreams
					Unsigned32,
				bridgeIfIsPPPoA
					TruthValue,
				bridgeIfFloodUnknown
					TruthValue,
				bridgeIfFloodMulticast
					TruthValue,
				bridgeIfEgressPacketRuleGroupIndex
					PacketRuleGroupIndex,
				bridgeIfTableBasedFilter
					BITS,
				bridgeIfDhcpLearn
					BITS,
				bridgeIfOnDemandStatsEnabled
					INTEGER,
				bridgeIfMvrVlan
					Integer32,
				bridgeIfVlanXlateFrom
					Integer32,
				bridgeIfSlanXlateFrom
					Integer32,
				bridgeIfBridgeState
					BridgeState,
				bridgeIfUnblock
					TruthValue,
				bridgeType
					INTEGER,
				bridgeIfGponGemPortId
					Unsigned32,
				bridgeIfGponTrafficProfile
					Unsigned32,
				bridgeIfIncomingCOSOption
					INTEGER,
				bridgeIfStagIncomingCOSOption
					INTEGER
			 }

-- 
		-- 1.3.6.1.4.1.5504.4.7.2.1.1
		bridgeIfVpi OBJECT-TYPE
			SYNTAX AtmVpIdentifier
			MAX-ACCESS read-create
			STATUS current
			DESCRIPTION
				"If this bridge interface is on an ATM VC, the ATM VPI    
				is specified here. If the bridge interface is not an ATM VC, 
				this field is ignored. The VPI value for a VPL or VCL. The 
				value VPI=0 is only allowed for a VCL. For ATM UNIs supporting
				VPCs the VPI value ranges from 0 to 255.  The VPI
				value 0 is supported for ATM UNIs conforming to
				the ATM Forum UNI 4.0 Annex 8 (Virtual UNIs)
				specification. For ATM UNIs supporting VCCs the
				VPI value ranges from 0 to 255.  For ATM NNIs the
				VPI value ranges from 0 to 4095.  The maximum VPI
				value cannot exceed the value allowable by
				atmInterfaceMaxVpiBits defined in ATM-MIB."
			DEFVAL { 0 }
			::= { bridgeInterfaceEntry 1 }

		
-- 
		-- 1.3.6.1.4.1.5504.4.7.2.1.2
		bridgeIfVci OBJECT-TYPE
			SYNTAX AtmVcIdentifier
			MAX-ACCESS read-create
			STATUS current
			DESCRIPTION
				"If this bridge interface is on an ATM VC, the ATM VCI is 
				specified here.  The range is 32...65535.  The maximum VCI
				value cannot exceed the value allowable by atmInterfaceMaxVciBits defined in ATM-MIB.
				
				If the bridge interface is not an ATM VC, but for example an
				ethernet interface, this field should be set to 0."
			::= { bridgeInterfaceEntry 2 }

		
		-- 1.3.6.1.4.1.5504.4.7.2.1.3
		bridgeIfVlanId OBJECT-TYPE
			SYNTAX Integer32 (0..2147483647)
			MAX-ACCESS read-create
			STATUS current
			DESCRIPTION
				"The Virtual LAN Id for VLAN Tag Insertion."
			DEFVAL { 0 }
			::= { bridgeInterfaceEntry 3 }

		
		-- 1.3.6.1.4.1.5504.4.7.2.1.4
		bridgeIfStripAndInsert OBJECT-TYPE
			SYNTAX TruthValue
			MAX-ACCESS read-create
			STATUS current
			DESCRIPTION
				"If true, enable VLAN Tagging."
			DEFVAL { false }
			::= { bridgeInterfaceEntry 4 }

		
		-- 1.3.6.1.4.1.5504.4.7.2.1.5
		bridgeIfCustomARP OBJECT-TYPE
			SYNTAX TruthValue
			MAX-ACCESS read-create
			STATUS current
			DESCRIPTION
				"If true, send ARP requests selectively or by flood."
			DEFVAL { false }
			::= { bridgeInterfaceEntry 5 }

		
		-- 1.3.6.1.4.1.5504.4.7.2.1.6
		bridgeIfFilterBroadcast OBJECT-TYPE
			SYNTAX TruthValue
			MAX-ACCESS read-create
			STATUS current
			DESCRIPTION
				"If true, discard non-ARP broadcast packets."
			DEFVAL { false }
			::= { bridgeInterfaceEntry 6 }

		
		-- 1.3.6.1.4.1.5504.4.7.2.1.7
		bridgeIfLearnIp OBJECT-TYPE
			SYNTAX TruthValue
			MAX-ACCESS read-create
			STATUS current
			DESCRIPTION
				"If true, snoop unicast packets to build ARP table. "
			DEFVAL { false }
			::= { bridgeInterfaceEntry 7 }

		
		-- 1.3.6.1.4.1.5504.4.7.2.1.8
		bridgeIfLearnUnicast OBJECT-TYPE
			SYNTAX TruthValue
			MAX-ACCESS read-create
			STATUS current
			DESCRIPTION
				"If true, snoop unicast packets to build MAC paths."
			DEFVAL { false }
			::= { bridgeInterfaceEntry 8 }

		
		-- 1.3.6.1.4.1.5504.4.7.2.1.9
		bridgeIfMaxUnicast OBJECT-TYPE
			SYNTAX Integer32 (0..2147483647)
			MAX-ACCESS read-create
			STATUS current
			DESCRIPTION
				"Maximum number of unicast addresses for I/F."
			::= { bridgeInterfaceEntry 9 }

		
		-- 1.3.6.1.4.1.5504.4.7.2.1.10
		bridgeIfLearnMulticast OBJECT-TYPE
			SYNTAX TruthValue
			MAX-ACCESS read-create
			STATUS current
			DESCRIPTION
				"If true, snoop multicast packets for IGMP joins/leaves."
			DEFVAL { false }
			::= { bridgeInterfaceEntry 10 }

		
		-- 1.3.6.1.4.1.5504.4.7.2.1.11
		bridgeIfForwardToUnicast OBJECT-TYPE
			SYNTAX TruthValue
			MAX-ACCESS read-create
			STATUS current
			DESCRIPTION
				"If true, attempt to forward via unicast MAC paths."
			DEFVAL { false }
			::= { bridgeInterfaceEntry 11 }

		
		-- 1.3.6.1.4.1.5504.4.7.2.1.12
		bridgeIfForwardToMulticast OBJECT-TYPE
			SYNTAX TruthValue
			MAX-ACCESS read-create
			STATUS current
			DESCRIPTION
				"If true, attempt to forward via multicast MAC paths."
			DEFVAL { false }
			::= { bridgeInterfaceEntry 12 }

		
		-- 1.3.6.1.4.1.5504.4.7.2.1.13
		bridgeIfForwardToDefault OBJECT-TYPE
			SYNTAX TruthValue
			MAX-ACCESS read-create
			STATUS current
			DESCRIPTION
				"If true, attempt to forward via VLAN default paths."
			DEFVAL { false }
			::= { bridgeInterfaceEntry 13 }

		
		-- 1.3.6.1.4.1.5504.4.7.2.1.14
		bridgeLowerIfIndex  OBJECT-TYPE
			SYNTAX InterfaceIndex
			MAX-ACCESS read-create
			STATUS current
			DESCRIPTION
				"An entry exists for each bridge interface in the 
				system.  Only Ifindex and lower if index is needed
				to create a row."
			::= { bridgeInterfaceEntry 14 }

		
		-- 1.3.6.1.4.1.5504.4.7.2.1.15
		bridgeIfRowStatus OBJECT-TYPE
			SYNTAX ZhoneRowStatus
			MAX-ACCESS read-create
			STATUS current
			DESCRIPTION
				"This object is used to create and remove rows in the table.
				See bridgeInterfaceEntry description for minimum requirements."
			DEFVAL { active }
			::= { bridgeInterfaceEntry 15 }

		
		-- 1.3.6.1.4.1.5504.4.7.2.1.16
		bridgeIfCustomDHCP OBJECT-TYPE
			SYNTAX TruthValue
			MAX-ACCESS read-create
			STATUS current
			DESCRIPTION
				"If TRUE, forwards broadcast DHCPOFFER or DHCPACK 
				packets even if bridgeFilterBroadcast is TRUE for that
				interface.
				"
			DEFVAL { false }
			::= { bridgeInterfaceEntry 16 }

		
		-- 1.3.6.1.4.1.5504.4.7.2.1.17
		bridgeIfIngressPacketRuleGroupIndex OBJECT-TYPE
			SYNTAX PacketRuleGroupIndex
			MAX-ACCESS read-create
			STATUS current
			DESCRIPTION
				"Index used as partial address of a group of entries
				in the packetRuleTable, each of which prescribes
				a filtering condition for the ingress interface."
			::= { bridgeInterfaceEntry 17 }

		
		-- 1.3.6.1.4.1.5504.4.7.2.1.18
		bridgeIfVlanIdCOS OBJECT-TYPE
			SYNTAX Integer32 (0..7)
			MAX-ACCESS read-create
			STATUS current
			DESCRIPTION
				"The Class-Of-Service (COS) value used for VLAN Tag Insertion."
			DEFVAL { 0 }
			::= { bridgeInterfaceEntry 18 }

		
		-- 1.3.6.1.4.1.5504.4.7.2.1.19
		bridgeIfOutgoingCOSOption OBJECT-TYPE
			SYNTAX INTEGER
				{
				outgoingCOSOptionDisable(1),
				outgoingCOSOptionAll(2)
				}
			MAX-ACCESS read-create
			STATUS current
			DESCRIPTION
				"Determines COS setting on packets bridged out this interface.
				    disable - COS setting is untouched.
				    all - COS will be set to bridgeIfOutgoingCOSValue."
			DEFVAL { outgoingCOSOptionDisable }
			::= { bridgeInterfaceEntry 19 }

		
		-- 1.3.6.1.4.1.5504.4.7.2.1.20
		bridgeIfOutgoingCOSValue  OBJECT-TYPE
			SYNTAX Integer32 (0..7)
			MAX-ACCESS read-create
			STATUS current
			DESCRIPTION
				"The COS value loaded into outgoing tagged packets.
				Applicable only if interface sends tagged packets and
				bridgeIfOutgoingCOSOption is outgoingCOSOption_all."
			DEFVAL { 0 }
			::= { bridgeInterfaceEntry 20 }

		
		-- 1.3.6.1.4.1.5504.4.7.2.1.21
		bridgeIfStagTPID OBJECT-TYPE
			SYNTAX Integer32 (33024 | 34984 | 37120 | 37376)
			MAX-ACCESS read-create
			STATUS current
			DESCRIPTION
				"The value of the tag protocol identifier that is being 
				used for QinQ packets. (0x8100 is default.)"
			DEFVAL { '8100'h }
			::= { bridgeInterfaceEntry 21 }

		
		-- 1.3.6.1.4.1.5504.4.7.2.1.22
		bridgeIfStagId OBJECT-TYPE
			SYNTAX Integer32 (0..4095)
			MAX-ACCESS read-create
			STATUS current
			DESCRIPTION
				"The s-tag value that we are expecting to put on packets 
				that are Rxed on this interface."
			DEFVAL { '0'h }
			::= { bridgeInterfaceEntry 22 }

		
		-- 1.3.6.1.4.1.5504.4.7.2.1.23
		bridgeIfStagStripAndInsert OBJECT-TYPE
			SYNTAX TruthValue
			MAX-ACCESS read-create
			STATUS current
			DESCRIPTION
				"If true, enable S-tag tagging on this IF."
			DEFVAL { false }
			::= { bridgeInterfaceEntry 23 }

		
		-- 1.3.6.1.4.1.5504.4.7.2.1.24
		bridgeIfStagOutgoingCOSOption OBJECT-TYPE
			SYNTAX INTEGER
				{
				sTagCOSDisable(1),
				sTagCOSAll(2)
				}
			MAX-ACCESS read-create
			STATUS current
			DESCRIPTION
				"Determines s-tag COS settings on packets bridged
				  out this interface:
				  disable - s-tag COS setting just passed as Rxed.
				  all - s-tag COS will be set with s_tagOutgoingCOSValue."
			DEFVAL { sTagCOSDisable }
			::= { bridgeInterfaceEntry 24 }

		
		-- 1.3.6.1.4.1.5504.4.7.2.1.25
		bridgeIfStagCOS OBJECT-TYPE
			SYNTAX Integer32 (0..7)
			MAX-ACCESS read-create
			STATUS current
			DESCRIPTION
				"The s-tag COS to be used when doing s-tag insertion."
			DEFVAL { 0 }
			::= { bridgeInterfaceEntry 25 }

		
		-- 1.3.6.1.4.1.5504.4.7.2.1.26
		bridgeIfStagOutgoingCOSValue OBJECT-TYPE
			SYNTAX Integer32 (0..7)
			MAX-ACCESS read-create
			STATUS current
			DESCRIPTION
				"The s-tag COS value loaded into outgoing tagged packets.
				Applicaple only if interface sends S-tagged packets and
				s_tagOutgoingCOSOption is All."
			DEFVAL { '0'h }
			::= { bridgeInterfaceEntry 26 }

		
		-- 1.3.6.1.4.1.5504.4.7.2.1.27
		bridgeIfMcastControlList OBJECT-TYPE
			SYNTAX SnmpAdminString
			MAX-ACCESS read-create
			STATUS current
			DESCRIPTION
				"List of mcast-control-ids this bridge-interface-record
				is associated with. It is an integer stored as string, and 
				controls which channels a user can watch. Note: unlike
				for IP, an empty list here allows user to watch all 
				channels."
			::= { bridgeInterfaceEntry 27 }

		
		-- 1.3.6.1.4.1.5504.4.7.2.1.28
		bridgeIfMaxVideoStreams OBJECT-TYPE
			SYNTAX Unsigned32 (0..1024)
			MAX-ACCESS read-create
			STATUS current
			DESCRIPTION
				"Maximum number of multicast (video) streams that
				we will support."
			DEFVAL { 0 }
			::= { bridgeInterfaceEntry 28 }

		
		-- 1.3.6.1.4.1.5504.4.7.2.1.29
		bridgeIfIsPPPoA OBJECT-TYPE
			SYNTAX TruthValue
			MAX-ACCESS read-create
			STATUS current
			DESCRIPTION
				"If true, this interface accepts PPPoA packets and will
				bridge them out as PPPoE packets."
			DEFVAL { false }
			::= { bridgeInterfaceEntry 29 }

		
		-- 1.3.6.1.4.1.5504.4.7.2.1.30
		bridgeIfFloodUnknown OBJECT-TYPE
			SYNTAX TruthValue
			MAX-ACCESS read-create
			STATUS current
			DESCRIPTION
				"If true, flood frames with unknown unicast MAC 
				address that would otherwise be discarded."
			DEFVAL { false }
			::= { bridgeInterfaceEntry 30 }

		
		-- 1.3.6.1.4.1.5504.4.7.2.1.31
		bridgeIfFloodMulticast OBJECT-TYPE
			SYNTAX TruthValue
			MAX-ACCESS read-create
			STATUS current
			DESCRIPTION
				"If true, flood all multicast traffic received on
				this bridge to all other ports on this vlan."
			DEFVAL { false }
			::= { bridgeInterfaceEntry 31 }

		
-- 
		-- 1.3.6.1.4.1.5504.4.7.2.1.32
		bridgeIfEgressPacketRuleGroupIndex OBJECT-TYPE
			SYNTAX PacketRuleGroupIndex
			MAX-ACCESS read-create
			STATUS current
			DESCRIPTION
				"Index used as partial address of a group of entries
				in the packetRuleTable, each of which prescribes
				a filtering condition for the egress interface."
			::= { bridgeInterfaceEntry 32 }

		
		-- 1.3.6.1.4.1.5504.4.7.2.1.33
		bridgeIfTableBasedFilter OBJECT-TYPE
			SYNTAX BITS
				{
				mac(0),
				ip(1)
				}
			MAX-ACCESS read-create
			STATUS current
			DESCRIPTION
				"none           : Dynamic IP Filtering on bridge based on DHCP, 
				                  is disabled.
				 BIT 1(mac)     : MAC address based Filtering based on DHCP, is enabled.
				 BIT 2(ip)      : IP address based dynamic IP Filtering based on DHCP,
				 	          is enabled.
				
				Defval is changed to correct the Zhone script errors.
				
				"
			::= { bridgeInterfaceEntry 33 }

		
		-- 1.3.6.1.4.1.5504.4.7.2.1.34
		bridgeIfDhcpLearn OBJECT-TYPE
			SYNTAX BITS
				{
				mac(0),
				ip(1)
				}
			MAX-ACCESS read-create
			STATUS current
			DESCRIPTION
				"none       :IP address and Mac address are not learned from DHCP packets.
				 BIT 1 (mac): MAC addresses are learned from DHCP packets.
				 ip  2 (ip) : IP addresses are learned from DHCP packets.
				
				The Defval is changed to correct the Zhone script errors."
			::= { bridgeInterfaceEntry 34 }

		
		-- 1.3.6.1.4.1.5504.4.7.2.1.35
		bridgeIfOnDemandStatsEnabled OBJECT-TYPE
			SYNTAX INTEGER
				{
				true(1),
				false(2),
				bytes(3)
				}
			MAX-ACCESS read-create
			STATUS current
			DESCRIPTION
				"If true, the on-demand stats collection for this bridge 
				interface will be enabled and packets will be counted.
				If bytes, the on-demand stats collection for this bridge
				interface will be enabled and abd bytes will be counted."
			DEFVAL { false }
			::= { bridgeInterfaceEntry 35 }

		
		-- 1.3.6.1.4.1.5504.4.7.2.1.36
		bridgeIfMvrVlan OBJECT-TYPE
			SYNTAX Integer32 (0..4095)
			MAX-ACCESS read-create
			STATUS current
			DESCRIPTION
				"The Multicast Vlan Registration (MVR) vlan ID.
				Multicast video packets with this vlan can be 
				vlan translated out this bridge."
			DEFVAL { 0 }
			::= { bridgeInterfaceEntry 36 }

		
		-- 1.3.6.1.4.1.5504.4.7.2.1.37
		bridgeIfVlanXlateFrom OBJECT-TYPE
			SYNTAX Integer32 (0..4095)
			MAX-ACCESS read-create
			STATUS current
			DESCRIPTION
				"If a packet's VLAN ID value matches this object's
				value then the packet's VLAN ID will be translated
				to the value of bridgeIfVlanId.
				
				A zero value disables translation."
			DEFVAL { 0 }
			::= { bridgeInterfaceEntry 37 }

		
		-- 1.3.6.1.4.1.5504.4.7.2.1.38
		bridgeIfSlanXlateFrom OBJECT-TYPE
			SYNTAX Integer32 (0..4095)
			MAX-ACCESS read-create
			STATUS current
			DESCRIPTION
				"If a packet's SLAN ID value matches this object's
				value then the packet's SLAN ID will be translated
				to the value of bridgeIfStagId.
				
				A zero value disables translation."
			DEFVAL { 0 }
			::= { bridgeInterfaceEntry 38 }

		
		-- 1.3.6.1.4.1.5504.4.7.2.1.39
		bridgeIfBridgeState OBJECT-TYPE
			SYNTAX BridgeState
			MAX-ACCESS read-create
			STATUS current
			DESCRIPTION
				"Values:
				up(1),                 UP
				down(2),               DWN
				trouble(3),            TRB
				notAvailable(4),       NA
				initializing(5),       INI
				adminDown(6),          ADN
				adminStateTest(7),     TST
				adminStateNone(8),     N/S
				ready(9),              RDY
				discovering(10),       DSC
				unknown(11),           ???
				blocked(12),           BLK
				pending(13),           PND
				disabled(14),          DIS
				learning(15),          LRN
				forwarding(16),        FWD
				blockedFlapping(17),   BLF
				blockedPersistent(18), BLP
				blockedFlappingPersistenr(19), BFP
				"
			::= { bridgeInterfaceEntry 39 }

		
		-- 1.3.6.1.4.1.5504.4.7.2.1.40
		bridgeIfUnblock OBJECT-TYPE
			SYNTAX TruthValue
			MAX-ACCESS read-write
			STATUS current
			DESCRIPTION
				"Set to TRUE to unblock a bridge that is 
				blocked due to flapping.
				"
			::= { bridgeInterfaceEntry 40 }

		
		-- 1.3.6.1.4.1.5504.4.7.2.1.41
		bridgeType OBJECT-TYPE
			SYNTAX INTEGER
				{
				uplink(1),
				downlink(2),
				intralink(4),
				tls(6),
				rlink(8),
				pppoa(9),
				wire(10),
				mvr(11),
				user(12),
				downlinkVideo(13),
				downlinkData(14),
				downlinkPPPoE(15),
				downlinkP2P(16),
				downlinkVoice(17),
				downlinkUpstreamMcast(18),
				ipobTls(19),
				ipobUplink(20),
				ipobDownlink(21)
				}
			MAX-ACCESS read-create
			STATUS current
			DESCRIPTION
				"bridge type"
			::= { bridgeInterfaceEntry 41 }

		
		-- 1.3.6.1.4.1.5504.4.7.2.1.42
		bridgeIfGponGemPortId OBJECT-TYPE
			SYNTAX Unsigned32
			MAX-ACCESS read-write
			STATUS current
			DESCRIPTION
				"GPON GEM Port ID used only to create a bridge on a GPON ONU."
			DEFVAL { 0 }
			::= { bridgeInterfaceEntry 42 }

		
		-- 1.3.6.1.4.1.5504.4.7.2.1.43
		bridgeIfGponTrafficProfile OBJECT-TYPE
			SYNTAX Unsigned32
			MAX-ACCESS read-write
			STATUS current
			DESCRIPTION
				"GPON Traffic Profile Index used only to create a bridge
				on a GPON ONU."
			DEFVAL { 0 }
			::= { bridgeInterfaceEntry 43 }

		
		-- 1.3.6.1.4.1.5504.4.7.2.1.44
		bridgeIfIncomingCOSOption OBJECT-TYPE
			SYNTAX INTEGER
				{
				incomingCOSOptionDisable(1),
				incomingCOSOptionAll(2)
				}
			MAX-ACCESS read-write
			STATUS current
			DESCRIPTION
				"Determines COS settings on incoming packets bridged
				  out this interface:
				  disable - COS replcement feature is disabled
				  all - COS will be set with vlanIDCOS."
			DEFVAL { incomingCOSOptionDisable }
			::= { bridgeInterfaceEntry 44 }

		
		-- 1.3.6.1.4.1.5504.4.7.2.1.45
		bridgeIfStagIncomingCOSOption OBJECT-TYPE
			SYNTAX INTEGER
				{
				stagIncomingCOSOptionDisable(1),
				stagIncomingCOSOptionAll(2)
				}
			MAX-ACCESS read-write
			STATUS current
			DESCRIPTION
				"Determines s-tag COS settings on incoming packets bridged
				  out this interface:
				  disable - s-tag COS setting just passed as Rxed.
				  all - s-tag COS will be set with s-tagIdCOS."
			DEFVAL { stagIncomingCOSOptionDisable }
			::= { bridgeInterfaceEntry 45 }

		
		-- 1.3.6.1.4.1.5504.4.7.3
		staticBridgeTable OBJECT-TYPE
			SYNTAX SEQUENCE OF StaticBridgeEntry
			MAX-ACCESS not-accessible
			STATUS current
			DESCRIPTION
				"A collection of staticBridgeEntries."
			::= { zhoneBridge 3 }

		
		-- 1.3.6.1.4.1.5504.4.7.3.1
		staticBridgeEntry OBJECT-TYPE
			SYNTAX StaticBridgeEntry
			MAX-ACCESS not-accessible
			STATUS current
			DESCRIPTION
				"Static Bridge entries are created by the user in
				order to specify forwarding for a particular
				interface, vlanId, mac address or ip address,
				slanId (for QinQ).
				
				The INDEX value for staticBridgeEntry consists of
				following 5 values:
				
				ifIndex
				staticBridgeAddressType
				bridgeIfVlanId
				staticBridgeMacOrIpAddress
				bridgeIfStagId
				
				If staticBridgeAddressType is set to macAddr(1), then
				staticBridgeMacOrIpAddress represents a MAC Address,
				and ifIndex, bridgeIfVlanId and staticBridgeMacOrIpAddress
				are used for the bridge path.
				
				If staticBridgeAddressType is set to ipAddr(2), then
				staticBridgeMacOrIpAddress represents an IP Address,
				and ifIndex, bridgeIfVlanId and staticBridgeMacOrIpAddress
				are used for the bridge path.
				
				If staticBridgeAddressType is set to vlanIdAddr(3),
				then ifIndex and bridgeIfVlanId are used for the
				bridge path.
				
				If staticBridgeAddressType is set to globalAddr(4),
				then ifIndex is used for the bridge path."
			INDEX { ifIndex, staticBridgeAddressType, bridgeIfVlanId, staticBridgeMacOrIpAddress, bridgeIfStagId
				 }
			::= { staticBridgeTable 1 }

		
		StaticBridgeEntry ::=
			SEQUENCE { 
				staticBridgeMacOrIpAddress
					PhysAddress,
				staticBridgeAddressType
					INTEGER,
				staticBridgeMulticastAging
					Integer32,
				staticBridgeRowStatus
					ZhoneRowStatus,
				staticBridgeFlapControl
					INTEGER,
				staticBridgeUnicastAging
					Integer32,
				staticBridgeIgmpQueryInterval
					Integer32,
				staticBridgeFlags
					BITS,
				staticBridgeIgmpCustomIpAddress
					IpAddress,
				staticBridgeLoopPrevention
					INTEGER,
				staticBridgeIgmpDscp
					OCTET STRING
			 }

		-- 1.3.6.1.4.1.5504.4.7.3.1.1
		staticBridgeMacOrIpAddress OBJECT-TYPE
			SYNTAX PhysAddress (SIZE (6))
			MAX-ACCESS not-accessible
			STATUS current
			DESCRIPTION
				"If the staticBridgeAddressType is set to macAddr(1),
				then this field represents a MAC address.
				
				If the staticBridgeAddressType is set to ipAddr(2),
				then this field represents an IP address."
			::= { staticBridgeEntry 1 }

		
		-- 1.3.6.1.4.1.5504.4.7.3.1.2
		staticBridgeAddressType OBJECT-TYPE
			SYNTAX INTEGER
				{
				macAddr(1),
				ipAddr(2),
				vlanIdAddr(3),
				globalAddr(4),
				intralinkAddr(7),
				globalIntralinkAddr(8),
				dhcpIpAddr(9),
				dhcpMacAddr(10),
				mvrAddr(13),
				vlanParms(14),
				secMvrAddr(15),
				dhcpAllowOui(720901)
				}
			MAX-ACCESS not-accessible
			STATUS current
			DESCRIPTION
				"If staticBridgeAddressType is set to macAddr(1), then
				staticBridgeMacOrIpAddress represents a MAC Address,
				and ifIndex, bridgeIfVlanId and staticBridgeMacOrIpAddress
				are used for the bridge path.
				
				If staticBridgeAddressType is set to ipAddr(2), then
				staticBridgeMacOrIpAddress represents an IP Address,
				and ifIndex, bridgeIfVlanId and staticBridgeMacOrIpAddress
				are used for the bridge path.
				
				If staticBridgeAddressType is set to vlanIdAddr(3) or 
				intralinkAddr(7), then ifIndex and bridgeIfVlanId are 
				used for the bridge path.
				
				If staticBridgeAddressType is set to globalAddr(4), 
				globalIntralinkAddr(8), or mvrAddr(13) then ifIndex 
				is used for the bridge path. 
				
				If staticBridgeAddressType is set to
				dhcpAllowOui( 720901) then the first 3 bytes of the
				MAC address contains the OUI that we will allow DHCP
				addresses to be granted to, global scope.
				
				If staticBridgeAddressType is set to dhcpIpAddr(9), or
				to dhcpMacAddr(10), then the other fields are populated
				as for address types ipAddr and macAddr respectively,
				with the difference that these are secure entries,
				learned by snooping DHCP.
				
				If staticBridgeAddressType is set to vlanParms(14), 
				then the static bridge entry holds parameters for 
				the given VLAN and SLAN ID (for example, flap mode, 
				unicast aging period, etc) and is not associated 
				with any specific bridge, but with all bridges 
				with the same VLAN/SLAN ID. For this reason, 
				the IfIndex of this entry must be zero. 
				
				If staticBridgeAddressType is set to secMvrAddr(15), 
				then the static bridge entry holds parameters for 
				a Secondary MVR path. The VLAN ID of this entry is
				the Secondary VLAN ID."
			::= { staticBridgeEntry 2 }

		
		-- 1.3.6.1.4.1.5504.4.7.3.1.3
		staticBridgeMulticastAging OBJECT-TYPE
			SYNTAX Integer32 (0..2147483647)
			MAX-ACCESS read-create
			STATUS current
			DESCRIPTION
				"Multicast Aging period in tenths of seconds for the
				specified VLAN.  After the specified aging period is
				met, the  VLAN address is deleted from the routing table.
				
				A value of 0 indicates that aging is turned off.
				
				Maximum value is 2147483647 tenths of seconds,
				which equates to approximately 2485.51 days."
			::= { staticBridgeEntry 3 }

		
		-- 1.3.6.1.4.1.5504.4.7.3.1.4
		staticBridgeRowStatus OBJECT-TYPE
			SYNTAX ZhoneRowStatus
			MAX-ACCESS read-create
			STATUS current
			DESCRIPTION
				"Used to create, modify or delete an entry in this
				table."
			DEFVAL { active }
			::= { staticBridgeEntry 4 }

		
		-- 1.3.6.1.4.1.5504.4.7.3.1.5
		staticBridgeFlapControl OBJECT-TYPE
			SYNTAX INTEGER
				{
				default(1),
				disable(2),
				enable(3),
				fast(4)
				}
			MAX-ACCESS read-create
			STATUS current
			DESCRIPTION
				"This object enables or disable Flap Control in the Bridge 
				Filter Table. The value 'disable(2)' turns Flap Control mode 
				off. The values 'enable(3)' or 'fast(4) turn flap control mode on.
				'Enable(3)' applies a hold time of 60 secs before allowing addr/IP
				to be moved to a new port, while 'fast(4)' applies a hold time of
				0 secs. A value  of 'default(1)' indicates 'Don't Care' and defaults
				to a  disable or enable set by another entry. "
			DEFVAL { default }
			::= { staticBridgeEntry 5 }

		
		-- 1.3.6.1.4.1.5504.4.7.3.1.6
		staticBridgeUnicastAging OBJECT-TYPE
			SYNTAX Integer32 (0 | 120..2147483647)
			MAX-ACCESS read-create
			STATUS current
			DESCRIPTION
				"Multicast Aging period in tenths of seconds for the
				specified VLAN.  After the specified aging period is
				met, the  VLAN address is deleted from the routing table.
				
				A value of 0 indicates that aging is turned off.
				
				Maximum value is 2147483647 tenths of seconds,
				which equates to approximately 2485.51 days."
			::= { staticBridgeEntry 6 }

		
		-- 1.3.6.1.4.1.5504.4.7.3.1.7
		staticBridgeIgmpQueryInterval OBJECT-TYPE
			SYNTAX Integer32
			MAX-ACCESS read-create
			STATUS current
			DESCRIPTION
				"How often (in seconds) we as a bridge inject IGMP query 
				values into the stream."
			DEFVAL { 0 }
			::= { staticBridgeEntry 7 }

		
		-- 1.3.6.1.4.1.5504.4.7.3.1.8
		staticBridgeFlags OBJECT-TYPE
			SYNTAX BITS
				{
				igmpProcessJoinAndLeave(0),
				igmpRespondToQuery(1),
				igmpUseBridgeIpAddress(2),
				forceIGMPv2Down(3),
				forceIGMPv2Up(4)
				}
			MAX-ACCESS read-create
			STATUS current
			DESCRIPTION
				"none                               : IGMP Snooping with Proxy reporting is disabled.
				BIT 0(igmpProcessJoinAndLeave)     : igmpProcessJoinandLeave is enabled for IGMP packets.
				BIT 1(igmpRespondToQuery)          : igmpRespondToQuery is enabled for IGMP packets.
				BIT 2(igmpUseBridgeIpAddress)      : igmpUseBridgeIpAddress is enabled for IGMP packets.
				BIT 3(forceIGMPv2Down)             : forceIGMPv2Down is enabled for subscriber side 
				BIT 4(forceIGMPv2Up)               : forceIGMPv2Up is enabled for uplink/network side "
			::= { staticBridgeEntry 8 }

		
		-- 1.3.6.1.4.1.5504.4.7.3.1.9
		staticBridgeIgmpCustomIpAddress OBJECT-TYPE
			SYNTAX IpAddress
			MAX-ACCESS read-create
			STATUS current
			DESCRIPTION
				"Allow the configuration of the source IP address for 
				packets that we originate upstream when doing IGMP 
				Porxy on a bridge. "
			::= { staticBridgeEntry 9 }

		
		-- 1.3.6.1.4.1.5504.4.7.3.1.10
		staticBridgeLoopPrevention OBJECT-TYPE
			SYNTAX INTEGER
				{
				none(0),
				blockAsym(1),
				blockAll(2),
				blockAsymAuto(3),
				blockAllAuto(4)
				}
			MAX-ACCESS read-write
			STATUS current
			DESCRIPTION
				"This field does the following options,'BlockAsym(1)' blocks a 
				learning bridge if flap is detected between it and an uplink bridge.
				'BlockAll(2)' incorporates 'blockAsym(1)' but it also blocks a 
				learning bridge if it flaps against another learning bridge."
			DEFVAL { none }
			::= { staticBridgeEntry 10 }

		
		-- 1.3.6.1.4.1.5504.4.7.3.1.11
		staticBridgeIgmpDscp OBJECT-TYPE
			SYNTAX OCTET STRING (SIZE (1..8))
			MAX-ACCESS read-create
			STATUS current
			DESCRIPTION
				"This parameter indicates DSCP value for igmp traffic.
								
								
								Valid code values:
								
								<0-63>   Differentiated services codepoint value 
								   af11     Mark packets with AF11 dscp (001010) 
								   af12     Mark packets with AF12 dscp (001100) 
								   af13     Mark packets with AF13 dscp (001110) 
								   af21     Mark packets with AF21 dscp (010010) 
								   af22     Mark packets with AF22 dscp (010100) 
								   af23     Mark packets with AF23 dscp (010110) 
								   af31     Mark packets with AF31 dscp (011010) 
								   af32     Mark packets with AF32 dscp (011100) 
								   af33     Mark packets with AF33 dscp (011110) 
								   af41     Mark packets with AF41 dscp (100010) 
								   af42     Mark packets with AF42 dscp (100100) 
								   af43     Mark packets with AF43 dscp (100110) 
								   cs1      Mark packets with CS1(precedence 1) dscp (001000) 
								   cs2      Mark packets with CS2(precedence 2) dscp (010000) 
								   cs3      Mark packets with CS3(precedence 3) dscp (011000) 
								   cs4      Mark packets with CS4(precedence 4) dscp (100000) 
								   cs5      Mark packets with CS5(precedence 5) dscp (101000) 
								   cs6      Mark packets with CS6(precedence 6) dscp (110000) 
								   cs7      Mark packets with CS7(precedence 7) dscp (111000) 
								   default  Mark packets with default dscp (000000) 
								   ef       Mark packets with EF dscp (101110)"
			::= { staticBridgeEntry 11 }

		
		-- 1.3.6.1.4.1.5504.4.7.4
		bridgeIfLookupTable OBJECT-TYPE
			SYNTAX SEQUENCE OF BridgeIfLookupEntry
			MAX-ACCESS not-accessible
			STATUS current
			DESCRIPTION
				"A collection of bridgeIfLookupTable entries."
			::= { zhoneBridge 4 }

		
		-- 1.3.6.1.4.1.5504.4.7.4.1
		bridgeIfLookupEntry OBJECT-TYPE
			SYNTAX BridgeIfLookupEntry
			MAX-ACCESS not-accessible
			STATUS current
			DESCRIPTION
				"Bridge IfLookup entries are created by the user
				or learned by the software in
				order to specify forwarding for a particular
				interface, vlanId/slanId, mac address or ip address.
				
				The INDEX value for bridgeIfLookupEntry consists of
				following 5 values:
				
				bridgeIfAddressType
				bridgeIfMacOrIpAddress
				bridgeIfVlanId
				ifIndex
				bridgeIfStagId
				
				
				If bridgeIfAddressType is set to unicast_mac(1),
				then bridgeIfMacOrIpAddress represents a MAC Address,
				and ifIndex, bridgeIfVlanId/Slanid and 
				bridgeIfMacOrIpAddress are use for the bridge path.
				
				If bridgeIfAddressType is set to multicast_mac(2),
				then bridgeMacOrIpAddress represents a MAC Address,
				and ifIndex, bridgeIfVlanId/SlanId and 
				bridgeIfMacOrIpAddress are used for bridge path.
				
				If bridgeIfAddressType is set to ip_address(3),
				then ifIndex and bridgeIfVlanId/SlanId are used 
				for the bridge path."
			INDEX { bridgeIfAddressType, bridgeIfMacOrIpAddress, bridgeIfVlanId, ifIndex, bridgeIfStagId
				 }
			::= { bridgeIfLookupTable 1 }

		
		BridgeIfLookupEntry ::=
			SEQUENCE { 
				bridgeIfAddressType
					INTEGER,
				bridgeIfMacOrIpAddress
					PhysAddress,
				bridgeIfLookupStaticOrDynamic
					INTEGER,
				bridgeIfLookupFlush
					TruthValue
			 }

		-- 1.3.6.1.4.1.5504.4.7.4.1.1
		bridgeIfAddressType OBJECT-TYPE
			SYNTAX INTEGER
				{
				unicastMac(1),
				multicastMac(2),
				ipAddress(3),
				dhcpMac(4),
				dhcpIp(5),
				ipV6Address(6),
				dhcpV6Mac(7),
				dhcpV6Ip(8)
				}
			MAX-ACCESS not-accessible
			STATUS current
			DESCRIPTION
				"If bridgeIfAddressType is set to unicast_mac(1),
				then bridgeIfMacOrIpAddress represents a MAC Address,
				and ifIndex, bridgeIfVlanId and bridgeIfMacOrIpAddress
				are used for the bridge path.
				
				If bridgeIfAddressType is set to multicast_mac(2),
				then bridgeMacOrIpAddress represents a MAC Address,
				and ifIndex, bridgeIfVlanId and bridgeIfMacOrIpAddress
				are used for the bridge path.
				
				If bridgeIfAddressType is set to ip_address(3),
				then ifIndex and bridgeIfVlanId are used for the
				bridge path.
				
				If bridgeIfAddressType is set to dhcp_mac(4), or
				dhcp_ip(5), then the address is as desribed for types
				1 and 3, respectively, and the address was learned
				by snooping DHCP packets.
				
				ipV6Address(6) is the same as ipAddress(3) except for IPv6
				address format.
				
				dhcpV6Mac(7) is the same as dhacpMac(4) except for IPv6
				address format.
				
				dhcpV7Ip(8) is the same as dhcpIp(5) except for IPv6
				address format."
			::= { bridgeIfLookupEntry 1 }

		
		-- 1.3.6.1.4.1.5504.4.7.4.1.2
		bridgeIfMacOrIpAddress OBJECT-TYPE
			SYNTAX PhysAddress
			MAX-ACCESS not-accessible
			STATUS current
			DESCRIPTION
				"If bridgeIfAddressType is set to FILTER_ENTRY_UNICAST_MAC(1)
				or to FILTER_ENTRY_MULTICAST_MAC(2), or to FILTER_ENTRY_DHCP_MAC(4),
				then bridgeIfMacOrIpAddress represents a MAC Address.
				
				If bridgeIfAddressType is set to FILTER_ENTRY_IP_ADDRESS(3), or
				to FILTER_ENTRY_DHCP_IP(5),
				then bridgeIfMacOrIpAddress represents an IP Address."
			::= { bridgeIfLookupEntry 2 }

		
		-- 1.3.6.1.4.1.5504.4.7.4.1.3
		bridgeIfLookupStaticOrDynamic OBJECT-TYPE
			SYNTAX INTEGER
				{
				staticEntry(1),
				dynamicEntry(2)
				}
			MAX-ACCESS read-only
			STATUS current
			DESCRIPTION
				"If bridgeIfLookupStaticOrDynamic is set to 1,
				then this table entry is static and persistent.
				
				If bridgeIfLookupStaticOrDynamic is set to 2,
				then this table entry is learned and is not persistent."
			::= { bridgeIfLookupEntry 3 }

		
		-- 1.3.6.1.4.1.5504.4.7.4.1.4
		bridgeIfLookupFlush OBJECT-TYPE
			SYNTAX TruthValue
			MAX-ACCESS read-write
			STATUS current
			DESCRIPTION
				"The object 'bridgeIfLookupFlush' allows a user to flush
				learned entries in the bridgeFilterTable when the ifIndex
				of the entry is not known.  A combination of address type,
				MAC or IP address and vlan ID is used to determine the
				ifIndex of the entry to be removed.  Setting the object 
				to 'true' causes the flush action to occur.
				
				After the flush action is taken, the value of
				bridgeIfLookupFlush is immediately set back to 'false'."
			DEFVAL { false }
			::= { bridgeIfLookupEntry 4 }

		
		-- 1.3.6.1.4.1.5504.4.7.5
		bridgeAddressLookupTable OBJECT-TYPE
			SYNTAX SEQUENCE OF BridgeAddressLookupEntry
			MAX-ACCESS not-accessible
			STATUS current
			DESCRIPTION
				"A collection of bridgeAddressLookupTable entries."
			::= { zhoneBridge 5 }

		
		-- 1.3.6.1.4.1.5504.4.7.5.1
		bridgeAddressLookupEntry OBJECT-TYPE
			SYNTAX BridgeAddressLookupEntry
			MAX-ACCESS not-accessible
			STATUS current
			DESCRIPTION
				"BridgeAddressLookup entries are created by the user
				or learned by the software in
				order to specify forwarding for a particular
				interface, vlanId/slanId, mac address or ip address.
				
				The INDEX value for bridgeIfLookupEntry consists of
				following 5 values:
				
				ifIndex
				bridgeIfAddressType
				bridgeIfMacOrIpAddress
				bridgeIfVlanId
				bridgeIfStagId"
			INDEX { ifIndex, bridgeIfAddressType, bridgeIfMacOrIpAddress, bridgeIfVlanId, bridgeIfStagId
				 }
			::= { bridgeAddressLookupTable 1 }

		
		BridgeAddressLookupEntry ::=
			SEQUENCE { 
				bridgeAddressLookupStaticOrDynamic
					INTEGER,
				bridgeAddressLookupFlush
					TruthValue
			 }

		-- 1.3.6.1.4.1.5504.4.7.5.1.1
		bridgeAddressLookupStaticOrDynamic OBJECT-TYPE
			SYNTAX INTEGER
				{
				staticEntry(1),
				dynamicEntry(2)
				}
			MAX-ACCESS read-only
			STATUS current
			DESCRIPTION
				"If bridgeAddressLookupStaticOrDynamic is set to 1,
				then this table entry is static and persistent.
				
				If bridgeAddressLookupStaticOrDynamic is set to 2,
				then this table entry is learned and is not persistent."
			::= { bridgeAddressLookupEntry 1 }

		
		-- 1.3.6.1.4.1.5504.4.7.5.1.2
		bridgeAddressLookupFlush OBJECT-TYPE
			SYNTAX TruthValue
			MAX-ACCESS read-write
			STATUS current
			DESCRIPTION
				"The object 'bridgeIfAddressFlush' allows a user to flush
				learned entries in the bridgeFilterTable when the ifIndex
				of the entry is known.  The ifIndex is used to determine 
				which interface is to be removed.  Setting the object 
				to 'true' causes the flush action to occur.
				
				After the flush action is taken, the value of
				bridgeIfLookupFlush is immediately set back to 'false'."
			DEFVAL { false }
			::= { bridgeAddressLookupEntry 2 }

		
		-- 1.3.6.1.4.1.5504.4.7.6
		packetRuleGroup OBJECT IDENTIFIER ::= { zhoneBridge 6 }

		
		-- 1.3.6.1.4.1.5504.4.7.6.1
		packetRuleGroupIndexNext OBJECT-TYPE
			SYNTAX PacketRuleGroupIndex
			MAX-ACCESS read-only
			STATUS current
			DESCRIPTION
				"A scalar representing the next available Group Index for 
				Packet Rule Table Entries."
			::= { packetRuleGroup 1 }

		
		-- 1.3.6.1.4.1.5504.4.7.6.2
		packetRuleGroupNextIndexTable OBJECT-TYPE
			SYNTAX SEQUENCE OF PacketRuleGroupNextIndexEntry
			MAX-ACCESS not-accessible
			STATUS current
			DESCRIPTION
				"A collection of entries each representing the next
				available index for that group."
			::= { packetRuleGroup 2 }

		
		-- 1.3.6.1.4.1.5504.4.7.6.2.1
		packetRuleGroupNextIndexEntry OBJECT-TYPE
			SYNTAX PacketRuleGroupNextIndexEntry
			MAX-ACCESS not-accessible
			STATUS current
			DESCRIPTION
				"A packetRuleGroupNextIndexEntry contains the next 
				available index for that packetRuleGroup."
			INDEX { packetRuleGroupIndex }
			::= { packetRuleGroupNextIndexTable 1 }

		
		PacketRuleGroupNextIndexEntry ::=
			SEQUENCE { 
				packetRuleGroupMemberNextIndex
					PacketRuleGroupIndex
			 }

		-- 1.3.6.1.4.1.5504.4.7.6.2.1.1
		packetRuleGroupMemberNextIndex OBJECT-TYPE
			SYNTAX PacketRuleGroupIndex
			MAX-ACCESS read-only
			STATUS current
			DESCRIPTION
				"The next index available in a given packetRuleGroup 
				for a new packetRuleEntry."
			::= { packetRuleGroupNextIndexEntry 1 }

		
		-- 1.3.6.1.4.1.5504.4.7.6.3
		packetRuleTable OBJECT-TYPE
			SYNTAX SEQUENCE OF PacketRuleEntry
			MAX-ACCESS not-accessible
			STATUS current
			DESCRIPTION
				"A collection of packetRuleEntries."
			::= { packetRuleGroup 3 }

		
		-- 1.3.6.1.4.1.5504.4.7.6.3.1
		packetRuleEntry OBJECT-TYPE
			SYNTAX PacketRuleEntry
			MAX-ACCESS not-accessible
			STATUS current
			DESCRIPTION
				"Packet Rule entries are created by the user in
				order to specify filtering or other packet manipulation
				for a particular interface."
			INDEX { packetRuleGroupIndex, packetRuleGroupMemberIndex }
			::= { packetRuleTable 1 }

		
		PacketRuleEntry ::=
			SEQUENCE { 
				packetRuleGroupMemberIndex
					Integer32,
				packetRuleType
					INTEGER,
				packetRuleValue
					SnmpAdminString,
				packetRuleRowStatus
					ZhoneRowStatus,
				packetRuleValue2
					SnmpAdminString,
				packetRuleValue3
					SnmpAdminString,
				packetRuleValue4
					SnmpAdminString,
				packetRuleValue5
					SnmpAdminString,
				packetRuleGroupIndex
					PacketRuleGroupIndex,
				packetRuleValue6
					SnmpAdminString,
				packetRuleValue7
					SnmpAdminString
			 }

		-- 1.3.6.1.4.1.5504.4.7.6.3.1.1
		packetRuleGroupMemberIndex OBJECT-TYPE
			SYNTAX Integer32 (1..2147483647)
			MAX-ACCESS not-accessible
			STATUS current
			DESCRIPTION
				"The index of a packetRuleEntry in a given packetRuleGroup."
			::= { packetRuleEntry 1 }

		
		-- 1.3.6.1.4.1.5504.4.7.6.3.1.2
		packetRuleType OBJECT-TYPE
			SYNTAX INTEGER
				{
				dstMacSwapStatic(37),
				dstMacSwapDynamic(38),
				dscpToCos(41),
				promoteFirstEncapsulationVlan(42),
				filterFirstEncapsulationVlan(43),
				promoteSecondEncapsulationVlan(44),
				filterSecondEncapsulationVlan(45),
				bridgeStormDetect(46),
				bridgeInsertOption82(97),
				dhcpRelay(98),
				bridgeInsertPPPoEVendorTag(99),
				rateLimitDiscard(100),
				colorAwareRateLimitDiscard(103),
				aclAllow(104),
				bridgeForbidOui(114),
				aclDeny(120)
				}
			MAX-ACCESS read-create
			STATUS current
			DESCRIPTION
				"A 32-bit value which determines a filter to be applied to
				packets on the interface matching the pattern specified in 
				packetRuleValue.  The size and offset of the pattern in the
				packet will depend on packetRuleType.  
				
				Bits may be set in packetRuleType determining properties 
				of the filtering to be applied:
				BRIDGE_FORBID      = 0x10
				BRIDGE_INPUT       = 0x20
				BRIDGE_TERMINATE   = 0x40
				
				When BRIDGE_FORBID is set, packets matching the pattern are
				dropped; when it is clear, matching packets are forwarded.
				When BRIDGE_INPUT is set, filtering is applied to packets
				received on the interface; when it is clear, filtering is
				applied to packets to be transmitted on the interface.
				When BRIDGE_TERMINATE is set, processing of a packet matching
				the pattern ends the scan of filtering specifications; when
				it is clear, processing continues.
				
				Values of packetRuleType include
				DST_MAC_SWAP_STATIC = 0x25
				DST_MAC_SWAP_DYNAMIC = 0x28
				BRIDGE_INSERT_OPTION82 = 0x61
				BRIDGE_DHCP_RELAY      = 0x62
				BRIDGE_INSERT_PPPOE_VENDOR_TAG = 0x63
				BRIDGE_FORBID_OUI      = 0x72
				RATE_LIMIT_DISCARD  = 0x64
				COLOR_AWARE_RATE_LIMIT_DISCARD = 0x67"
			::= { packetRuleEntry 2 }

		
		-- 1.3.6.1.4.1.5504.4.7.6.3.1.3
		packetRuleValue OBJECT-TYPE
			SYNTAX SnmpAdminString
			MAX-ACCESS read-create
			STATUS current
			DESCRIPTION
				"A variable-length field whose meaning depends on 
				packetRuleType. 
				
				If bridgeForbidOui, it specifies a bit pattern to be 
				matched in a packet, stored as a string, but specified in
				the pattern 'nn:nn:nn...nn:nn', where 'nn' is a hex number
				specifying a byte of the pattern.  E.g. a packetRuleValue 
				of '00:02:02' specifies the OUI to be dropped.
				
				If dhcpRelay, it is ascii integer which specifies dhcp
				subnet group.
				
				If bridgeInsertOption82, this value is ignored.
				
				If bridgeInsertPPPoEVendorTag, it specifies an ASCII string
				of up to 48 bytes to be inserted into PPPoE discovery packets
				(PADI/PADR) which transit this node. String will be inserted
				as a Vendor-Specific tag.
				
				If rateLimitDiscard, this value represents a maximum rate (in kbps).
				
				If aclAllow/aclDeny, a text string of the form:
				  all | [Keyword NamedValue | Value[/N]]*
				where Keyword identifies the field of interest,
				Value is context dependent on the field, NamedValue
				is an alias for a Value. N indicates the number of
				most significant bits of Value to test.  If omitted
				it defaults to the max allowed for the field.
				"
			DEFVAL { "" }
			::= { packetRuleEntry 3 }

		
		-- 1.3.6.1.4.1.5504.4.7.6.3.1.4
		packetRuleRowStatus OBJECT-TYPE
			SYNTAX ZhoneRowStatus
			MAX-ACCESS read-create
			STATUS current
			DESCRIPTION
				"This object is used to create and remove rows in the table."
			DEFVAL { active }
			::= { packetRuleEntry 4 }

		
		-- 1.3.6.1.4.1.5504.4.7.6.3.1.5
		packetRuleValue2 OBJECT-TYPE
			SYNTAX SnmpAdminString
			MAX-ACCESS read-create
			STATUS current
			DESCRIPTION
				"A variable-length field whose meaning depends on 
				packetRuleType. 
				"
			DEFVAL { "" }
			::= { packetRuleEntry 5 }

		
		-- 1.3.6.1.4.1.5504.4.7.6.3.1.6
		packetRuleValue3 OBJECT-TYPE
			SYNTAX SnmpAdminString
			MAX-ACCESS read-create
			STATUS current
			DESCRIPTION
				"A variable-length field whose meaning depends on 
				packetRuleType. 
				"
			DEFVAL { "" }
			::= { packetRuleEntry 6 }

		
		-- 1.3.6.1.4.1.5504.4.7.6.3.1.7
		packetRuleValue4 OBJECT-TYPE
			SYNTAX SnmpAdminString
			MAX-ACCESS read-create
			STATUS current
			DESCRIPTION
				"A variable-length field whose meaning depends on 
				packetRuleType. 
				"
			DEFVAL { "" }
			::= { packetRuleEntry 7 }

		
		-- 1.3.6.1.4.1.5504.4.7.6.3.1.8
		packetRuleValue5 OBJECT-TYPE
			SYNTAX SnmpAdminString
			MAX-ACCESS read-create
			STATUS current
			DESCRIPTION
				"A variable-length field whose meaning depends on 
				packetRuleType. 
				"
			DEFVAL { "" }
			::= { packetRuleEntry 8 }

		
		-- 1.3.6.1.4.1.5504.4.7.6.3.1.9
		packetRuleGroupIndex OBJECT-TYPE
			SYNTAX PacketRuleGroupIndex (0..2147483647)
			MAX-ACCESS not-accessible
			STATUS current
			DESCRIPTION
				"A scalar representing the Group Index for a set of
				Packet Rule Table Entries."
			::= { packetRuleEntry 9 }

		
		-- 1.3.6.1.4.1.5504.4.7.6.3.1.10
		packetRuleValue6 OBJECT-TYPE
			SYNTAX SnmpAdminString
			MAX-ACCESS read-create
			STATUS current
			DESCRIPTION
				"A variable-length field whose meaning depends on 
				packetRuleType. 
				"
			DEFVAL { "" }
			::= { packetRuleEntry 10 }

		
		-- 1.3.6.1.4.1.5504.4.7.6.3.1.11
		packetRuleValue7 OBJECT-TYPE
			SYNTAX SnmpAdminString
			MAX-ACCESS read-create
			STATUS current
			DESCRIPTION
				"A variable-length field whose meaning depends on 
				packetRuleType. 
				"
			DEFVAL { "" }
			::= { packetRuleEntry 11 }

		
		-- 1.3.6.1.4.1.5504.4.7.7
		bridgePPPoETable OBJECT-TYPE
			SYNTAX SEQUENCE OF BridgePPPoEEntry
			MAX-ACCESS not-accessible
			STATUS current
			DESCRIPTION
				"For PPPoA-to-PPPoE tables, provide a lookup by ifIndex into the
				PPPoE tables. If the session has not been created for this PPPoA
				ifIndex, then there will be no table data."
			::= { zhoneBridge 7 }

		
		-- 1.3.6.1.4.1.5504.4.7.7.1
		bridgePPPoEEntry OBJECT-TYPE
			SYNTAX BridgePPPoEEntry
			MAX-ACCESS not-accessible
			STATUS current
			DESCRIPTION
				"Description."
			INDEX { ifIndex }
			::= { bridgePPPoETable 1 }

		
		BridgePPPoEEntry ::=
			SEQUENCE { 
				bridgePPPoEBrasMac
					OCTET STRING,
				bridgePPPoELocalHostMac
					OCTET STRING,
				bridgePPPoEEIfIndex
					InterfaceIndex,
				bridgePPPoESessionID
					Integer32,
				bridgePPPoESlanId
					Integer32,
				bridgePPPoEVlanId
					Integer32,
				bridgePPPoEEncapLLC
					INTEGER
			 }

		-- 1.3.6.1.4.1.5504.4.7.7.1.1
		bridgePPPoEBrasMac OBJECT-TYPE
			SYNTAX OCTET STRING (SIZE (6))
			MAX-ACCESS read-only
			STATUS current
			DESCRIPTION
				"Destination mac address."
			::= { bridgePPPoEEntry 1 }

		
		-- 1.3.6.1.4.1.5504.4.7.7.1.2
		bridgePPPoELocalHostMac OBJECT-TYPE
			SYNTAX OCTET STRING (SIZE (6))
			MAX-ACCESS read-only
			STATUS current
			DESCRIPTION
				"Source mac address."
			::= { bridgePPPoEEntry 2 }

		
		-- 1.3.6.1.4.1.5504.4.7.7.1.3
		bridgePPPoEEIfIndex OBJECT-TYPE
			SYNTAX InterfaceIndex
			MAX-ACCESS read-only
			STATUS current
			DESCRIPTION
				"PPPoE port's ifIndex."
			::= { bridgePPPoEEntry 3 }

		
		-- 1.3.6.1.4.1.5504.4.7.7.1.4
		bridgePPPoESessionID OBJECT-TYPE
			SYNTAX Integer32 (0..65535)
			MAX-ACCESS read-only
			STATUS current
			DESCRIPTION
				"PPPoE session ID."
			::= { bridgePPPoEEntry 4 }

		
		-- 1.3.6.1.4.1.5504.4.7.7.1.5
		bridgePPPoESlanId OBJECT-TYPE
			SYNTAX Integer32 (0..4094)
			MAX-ACCESS read-only
			STATUS current
			DESCRIPTION
				"SLan ID of BRAS."
			::= { bridgePPPoEEntry 5 }

		
		-- 1.3.6.1.4.1.5504.4.7.7.1.6
		bridgePPPoEVlanId OBJECT-TYPE
			SYNTAX Integer32 (0..4094)
			MAX-ACCESS read-only
			STATUS current
			DESCRIPTION
				"VLAN ID of BRAS."
			::= { bridgePPPoEEntry 6 }

		
		-- 1.3.6.1.4.1.5504.4.7.7.1.7
		bridgePPPoEEncapLLC OBJECT-TYPE
			SYNTAX INTEGER
				{
				vcmux(1),
				llc(2)
				}
			MAX-ACCESS read-only
			STATUS current
			DESCRIPTION
				"PPPoA encapsulation"
			::= { bridgePPPoEEntry 7 }

		
		-- 1.3.6.1.4.1.5504.4.7.8
		stpParam OBJECT IDENTIFIER ::= { zhoneBridge 8 }

		
		-- 1.3.6.1.4.1.5504.4.7.8.1
		stpParamName OBJECT-TYPE
			SYNTAX ZhoneAdminString
			MAX-ACCESS read-write
			STATUS current
			DESCRIPTION
				"set this field if you are using MSTP, use the name of the bridge as a key."
			::= { stpParam 1 }

		
		-- 1.3.6.1.4.1.5504.4.7.8.2
		stpParamRevision OBJECT-TYPE
			SYNTAX Unsigned32 (0)
			MAX-ACCESS read-write
			STATUS current
			DESCRIPTION
				"This parameter is used if you are running MSTP only. Currently
				we don't support any revisions to MSTP, so revision 0 is default."
			::= { stpParam 2 }

		
		-- 1.3.6.1.4.1.5504.4.7.8.3
		stpParamBridgePriority OBJECT-TYPE
			SYNTAX Unsigned32 (4096..61440)
			MAX-ACCESS read-write
			STATUS current
			DESCRIPTION
				"The priority ID that will be advertised for this bridge."
			DEFVAL { 36864 }
			::= { stpParam 3 }

		
		-- 1.3.6.1.4.1.5504.4.7.8.4
		stpParamForceVersion OBJECT-TYPE
			SYNTAX Unsigned32 (0 | 2 | 3)
			MAX-ACCESS read-write
			STATUS current
			DESCRIPTION
				"The protocol to initiate with. 3- MSTP, 2- RSTP, 0- STP."
			DEFVAL { 2 }
			::= { stpParam 4 }

		
		-- 1.3.6.1.4.1.5504.4.7.8.5
		stpParamFwdDelay OBJECT-TYPE
			SYNTAX Unsigned32 (4..20)
			MAX-ACCESS read-write
			STATUS current
			DESCRIPTION
				"The delay used by STP bridges to transition Root and Designated Ports to Forwarding."
			DEFVAL { 15 }
			::= { stpParam 5 }

		
		-- 1.3.6.1.4.1.5504.4.7.8.6
		stpParamHelloTime OBJECT-TYPE
			SYNTAX Unsigned32 (2)
			MAX-ACCESS read-write
			STATUS current
			DESCRIPTION
				"The interval between periodic transmissions of Configuration 
				Messages by Designated Ports. We only support a hello time of 2 currently.
				"
			DEFVAL { 2 }
			::= { stpParam 6 }

		
		-- 1.3.6.1.4.1.5504.4.7.8.7
		stpParamMigrateTime OBJECT-TYPE
			SYNTAX Unsigned32 (3)
			MAX-ACCESS read-write
			STATUS current
			DESCRIPTION
				"The initial value of the mdelayWhile and edgeDelayWhile timers.
				We currently only support a value of 3 for this timer."
			::= { stpParam 7 }

		
		-- 1.3.6.1.4.1.5504.4.7.8.8
		stpParamTxHoldCount OBJECT-TYPE
			SYNTAX Unsigned32 (1..5)
			MAX-ACCESS read-write
			STATUS current
			DESCRIPTION
				"The transmit hold count is used by the Port Transmit state machine to limit transmission rate."
			DEFVAL { 3 }
			::= { stpParam 8 }

		
		-- 1.3.6.1.4.1.5504.4.7.8.9
		stpParamMaxAge OBJECT-TYPE
			SYNTAX Unsigned32 (6..20)
			MAX-ACCESS read-write
			STATUS current
			DESCRIPTION
				"The maximum age of the information transmitted by the bridge when it is the Root Bridge."
			DEFVAL { 20 }
			::= { stpParam 9 }

		
		-- 1.3.6.1.4.1.5504.4.7.9
		stpBindTable OBJECT-TYPE
			SYNTAX SEQUENCE OF StpBindEntry
			MAX-ACCESS not-accessible
			STATUS current
			DESCRIPTION
				"The stpBind table is used to store the entries of stpBind
				which hold the relationship between the ifIndex on which 
				STP is to run on, and the MSTP instance if any."
			::= { zhoneBridge 9 }

		
		-- 1.3.6.1.4.1.5504.4.7.9.1
		stpBindEntry OBJECT-TYPE
			SYNTAX StpBindEntry
			MAX-ACCESS not-accessible
			STATUS current
			DESCRIPTION
				"stpBindEntry is used to specify the type of STP
				that is to run on an ifIndex. An InstanceID of 0
				specifies RSTP.
				An InstanceId > 0 indicates MSTP."
			INDEX { ifIndex, stpBindInstanceID }
			::= { stpBindTable 1 }

		
		StpBindEntry ::=
			SEQUENCE { 
				stpBindInstanceID
					Unsigned32,
				stpBindRowStatus
					ZhoneRowStatus,
				stpBindPortPriority
					Unsigned32
			 }

		-- 1.3.6.1.4.1.5504.4.7.9.1.1
		stpBindInstanceID OBJECT-TYPE
			SYNTAX Unsigned32
			MAX-ACCESS not-accessible
			STATUS current
			DESCRIPTION
				"This is a hidden storage of the InstanceId of an entry."
			::= { stpBindEntry 1 }

		
		-- 1.3.6.1.4.1.5504.4.7.9.1.2
		stpBindRowStatus OBJECT-TYPE
			SYNTAX ZhoneRowStatus
			MAX-ACCESS read-create
			STATUS current
			DESCRIPTION
				"Description."
			::= { stpBindEntry 2 }

		
		-- 1.3.6.1.4.1.5504.4.7.9.1.3
		stpBindPortPriority OBJECT-TYPE
			SYNTAX Unsigned32 (0..65535)
			MAX-ACCESS read-create
			STATUS current
			DESCRIPTION
				"PortPriority is used to specify the STP priority of
				this port."
			::= { stpBindEntry 3 }

		
-- The mstpInstanceTable holds entries of Mutiple Spanning Tree.
-- Currently not used.
		-- 1.3.6.1.4.1.5504.4.7.10
		mstpInstanceTable OBJECT-TYPE
			SYNTAX SEQUENCE OF MstpInstanceEntry
			MAX-ACCESS not-accessible
			STATUS current
			DESCRIPTION
				"Description."
			::= { zhoneBridge 10 }

		
		-- 1.3.6.1.4.1.5504.4.7.10.1
		mstpInstanceEntry OBJECT-TYPE
			SYNTAX MstpInstanceEntry
			MAX-ACCESS not-accessible
			STATUS current
			DESCRIPTION
				"Description."
			INDEX { stpBindInstanceID, bridgeIfVlanId }
			::= { mstpInstanceTable 1 }

		
		MstpInstanceEntry ::=
			SEQUENCE { 
				mstpInstanceRowStatus
					ZhoneRowStatus,
				mstpInstanceName
					ZhoneAdminString
			 }

		-- 1.3.6.1.4.1.5504.4.7.10.1.1
		mstpInstanceRowStatus OBJECT-TYPE
			SYNTAX ZhoneRowStatus
			MAX-ACCESS read-create
			STATUS current
			DESCRIPTION
				"Description."
			::= { mstpInstanceEntry 1 }

		
		-- 1.3.6.1.4.1.5504.4.7.10.1.2
		mstpInstanceName OBJECT-TYPE
			SYNTAX ZhoneAdminString
			MAX-ACCESS read-create
			STATUS current
			DESCRIPTION
				"A name for this mstp instance and vlanId."
			::= { mstpInstanceEntry 2 }

		
		-- 1.3.6.1.4.1.5504.4.7.11
		bridgeStatsTable OBJECT-TYPE
			SYNTAX SEQUENCE OF BridgeStatsEntry
			MAX-ACCESS not-accessible
			STATUS current
			DESCRIPTION
				"The bridgeStatsTable is used to access the statistics of the entries in the bridge table."
			::= { zhoneBridge 11 }

		
		-- 1.3.6.1.4.1.5504.4.7.11.1
		bridgeStatsEntry OBJECT-TYPE
			SYNTAX BridgeStatsEntry
			MAX-ACCESS not-accessible
			STATUS current
			DESCRIPTION
				"Displays the bridge statistics table entries."
			INDEX { ifIndex }
			::= { bridgeStatsTable 1 }

		
		BridgeStatsEntry ::=
			SEQUENCE { 
				bridgeStatsUcastRcvd
					Unsigned32,
				bridgeStatsMcastRcvd
					Unsigned32,
				bridgeStatsBcastRcvd
					Unsigned32,
				bridgeStatsUcastSent
					Unsigned32,
				bridgeStatsMcastSent
					Unsigned32,
				bridgeStatsBcastSent
					Unsigned32,
				bridgeStatsErrorSent
					Unsigned32,
				bridgeOnDemandStatsRulesSupported
					Unsigned32,
				bridgeOnDemandStatsRulesRemaining
					Unsigned32,
				bridgeStatsBSDUcastBlocked
					Unsigned32,
				bridgeStatsBSDMcastBlocked
					Unsigned32,
				bridgeStatsBSDBcastBlocked
					Unsigned32,
				bridgeStatsBSDAlarmCount
					Unsigned32,
				bridgeStatsBytesRcvdCount
					Counter64,
				bridgeStatsBytesSentCount
					Counter64,
				bridgeStatsTicksLastCleared
					Counter64,
				bridgeStatsTicksNow
					Counter64,
				bridgeStatsTicksPerSecond
					Counter64
			 }

		-- 1.3.6.1.4.1.5504.4.7.11.1.1
		bridgeStatsUcastRcvd OBJECT-TYPE
			SYNTAX Unsigned32
			MAX-ACCESS read-only
			STATUS current
			DESCRIPTION
				"Unicast packets received."
			::= { bridgeStatsEntry 1 }

		
		-- 1.3.6.1.4.1.5504.4.7.11.1.2
		bridgeStatsMcastRcvd OBJECT-TYPE
			SYNTAX Unsigned32
			MAX-ACCESS read-only
			STATUS current
			DESCRIPTION
				"Multicast packets received."
			::= { bridgeStatsEntry 2 }

		
		-- 1.3.6.1.4.1.5504.4.7.11.1.3
		bridgeStatsBcastRcvd OBJECT-TYPE
			SYNTAX Unsigned32
			MAX-ACCESS read-only
			STATUS current
			DESCRIPTION
				"Broadcast packets received."
			::= { bridgeStatsEntry 3 }

		
		-- 1.3.6.1.4.1.5504.4.7.11.1.4
		bridgeStatsUcastSent OBJECT-TYPE
			SYNTAX Unsigned32
			MAX-ACCESS read-only
			STATUS current
			DESCRIPTION
				"Unicast packets sent."
			::= { bridgeStatsEntry 4 }

		
		-- 1.3.6.1.4.1.5504.4.7.11.1.5
		bridgeStatsMcastSent OBJECT-TYPE
			SYNTAX Unsigned32
			MAX-ACCESS read-only
			STATUS current
			DESCRIPTION
				"Multicast packets sent."
			::= { bridgeStatsEntry 5 }

		
		-- 1.3.6.1.4.1.5504.4.7.11.1.6
		bridgeStatsBcastSent OBJECT-TYPE
			SYNTAX Unsigned32
			MAX-ACCESS read-only
			STATUS current
			DESCRIPTION
				"Broadcast packets sent."
			::= { bridgeStatsEntry 6 }

		
		-- 1.3.6.1.4.1.5504.4.7.11.1.7
		bridgeStatsErrorSent OBJECT-TYPE
			SYNTAX Unsigned32
			MAX-ACCESS read-only
			STATUS current
			DESCRIPTION
				"Error packets sent."
			::= { bridgeStatsEntry 7 }

		
		-- 1.3.6.1.4.1.5504.4.7.11.1.8
		bridgeOnDemandStatsRulesSupported OBJECT-TYPE
			SYNTAX Unsigned32
			MAX-ACCESS read-only
			STATUS current
			DESCRIPTION
				"Get the number of supported Ingress Stats available for a line card."
			::= { bridgeStatsEntry 8 }

		
		-- 1.3.6.1.4.1.5504.4.7.11.1.9
		bridgeOnDemandStatsRulesRemaining OBJECT-TYPE
			SYNTAX Unsigned32
			MAX-ACCESS read-only
			STATUS current
			DESCRIPTION
				"Get the number of remaining Ingress Stats available for a line card"
			::= { bridgeStatsEntry 9 }

		
		-- 1.3.6.1.4.1.5504.4.7.11.1.10
		bridgeStatsBSDUcastBlocked OBJECT-TYPE
			SYNTAX Unsigned32
			MAX-ACCESS read-only
			STATUS current
			DESCRIPTION
				"Number of unicast packets dropped due to Bridge Packet Storm Detection 
				threshold exceeded."
			::= { bridgeStatsEntry 10 }

		
		-- 1.3.6.1.4.1.5504.4.7.11.1.11
		bridgeStatsBSDMcastBlocked OBJECT-TYPE
			SYNTAX Unsigned32
			MAX-ACCESS read-only
			STATUS current
			DESCRIPTION
				"Number of multicast packets dropped due to Bridge Packet Storm Detection 
				threshold exceeded."
			::= { bridgeStatsEntry 11 }

		
		-- 1.3.6.1.4.1.5504.4.7.11.1.12
		bridgeStatsBSDBcastBlocked OBJECT-TYPE
			SYNTAX Unsigned32
			MAX-ACCESS read-only
			STATUS current
			DESCRIPTION
				"Number of broadcast packets dropped due to Bridge Packet Storm Detection 
				threshold exceeded."
			::= { bridgeStatsEntry 12 }

		
		-- 1.3.6.1.4.1.5504.4.7.11.1.13
		bridgeStatsBSDAlarmCount OBJECT-TYPE
			SYNTAX Unsigned32
			MAX-ACCESS read-only
			STATUS current
			DESCRIPTION
				"This counter reflects the number of times this interface has
				transitioned to the alarm state due to the Bridge Packet Storm
				Detection threshold being exceeded for a pre-defined number of
				seconds.
				"
			::= { bridgeStatsEntry 13 }

		
		-- 1.3.6.1.4.1.5504.4.7.11.1.14
		bridgeStatsBytesRcvdCount OBJECT-TYPE
			SYNTAX Counter64
			MAX-ACCESS read-only
			STATUS current
			DESCRIPTION
				"This is a count of the number of bytes received.
				On-demand stats must be enabled for byte counters
				otherwise this counter is zero.
				"
			::= { bridgeStatsEntry 14 }

		
		-- 1.3.6.1.4.1.5504.4.7.11.1.15
		bridgeStatsBytesSentCount OBJECT-TYPE
			SYNTAX Counter64
			MAX-ACCESS read-only
			STATUS current
			DESCRIPTION
				"This is a count of the number of bytes transmitted.
				On-demand stats must be enabled for byte counters
				otherwise this counter is zero.
				"
			::= { bridgeStatsEntry 15 }

		
		-- 1.3.6.1.4.1.5504.4.7.11.1.16
		bridgeStatsTicksLastCleared OBJECT-TYPE
			SYNTAX Counter64
			MAX-ACCESS read-only
			STATUS current
			DESCRIPTION
				"Linecard tick value when bridge was last cleared."
			::= { bridgeStatsEntry 16 }

		
		-- 1.3.6.1.4.1.5504.4.7.11.1.17
		bridgeStatsTicksNow OBJECT-TYPE
			SYNTAX Counter64
			MAX-ACCESS read-only
			STATUS current
			DESCRIPTION
				"Linecard current tick value."
			::= { bridgeStatsEntry 17 }

		
		-- 1.3.6.1.4.1.5504.4.7.11.1.18
		bridgeStatsTicksPerSecond OBJECT-TYPE
			SYNTAX Counter64
			MAX-ACCESS read-only
			STATUS current
			DESCRIPTION
				"Linecard current tick value."
			::= { bridgeStatsEntry 18 }

		
		-- 1.3.6.1.4.1.5504.4.7.12
		bridgeCmd OBJECT IDENTIFIER ::= { zhoneBridge 12 }
-- The Bridge Command objects are used to send commands to the
-- bridge RP.   Only the 'bridge stats clear' operation is
-- currently supported. 
-- 
-- 
-- Command Examples:
-- 
--   Clear all bridge stats for all bridges:
--     bridgeCmdOperation.0  = 1    (clrStats)
--     bridgeCmdFilterMask.0 = 00.00.00.00
-- 
--   Clear all bridge stats for slot 5:
--     bridgeCmdOperation.0  = 1    (clrStats)
--     bridgeCmdFilterMask.0 = 10.00.00.00
--     bridgeCmdSlot.0       = 5    (slot 5)
-- 
--   Clear bridge stats for a single bridge:
--     bridgeCmdOperation.0  = 1    (clrStats)
--     bridgeCmdFilterMask.0 = 80.00.00.00 
--     bridgeCmdIfIndex.0    = 279  (bridge ifIndex) 
-- 
--   Clear bridge stats for a single bridge on slot 5:
--     bridgeCmdOperation.0  = 1    (clrStats) 
--     bridgeCmdFilterMask.0 = 90.00.00.00 
--     bridgeCmdIfIndex.0    = 279  (bridge ifIndex) 
--     bridgeCmdSlot.0       = 5    (slot)
-- 
--   Clear bridge stats for all bridges with VLAN 100:
--     bridgeCmdOperation.0  = 1    (clrStats)
--     bridgeCmdFilterMask.0 = 40.00.00.00 
--     bridgeCmdVlanId.0     = 100  (vlan)
-- 
--   Clear bridge stats for bridges on slot 5 with VLAN 100: 
--     bridgeCmdOperation.0  = 1    (clrStats)
--     bridgeCmdFilterMask.0 = 50.00.00.00 
--     bridgeCmdVlanId.0     = 100  (vlan)
--     bridgeCmdSlot.0       = 5    (slot)
-- 
--   Clear bridge stats for bridges on MXK uplink with VLAN 100:
--     bridgeCmdOperation.0  = 1    (clrStats)
--     bridgeCmdFilterMask.0 = 50.00.00.00 
--     bridgeCmdVlanId.0     = 100  (vlan)
--     bridgeCmdSlot.0       = 30   (slot)
		
		-- 1.3.6.1.4.1.5504.4.7.12.1
		bridgeCmdOperation OBJECT-TYPE
			SYNTAX INTEGER
				{
				clrStats(1),
				clrIgmpStats(2),
				unblock(3),
				flush(4)
				}
			MAX-ACCESS read-write
			STATUS current
			DESCRIPTION
				"Bridge command ID value."
			::= { bridgeCmd 1 }

		
		-- 1.3.6.1.4.1.5504.4.7.12.2
		bridgeCmdFilterMask OBJECT-TYPE
			SYNTAX BITS
				{
				filterIfIndex(0),
				filterVlan(1),
				filterSlan(2),
				filterSlot(3),
				filterPort(4),
				filterIpAddress(5),
				filterMacAddress(6),
				filterSecure(7)
				}
			MAX-ACCESS read-write
			STATUS current
			DESCRIPTION
				"Bridge command filters bit mask.   
				
				If a bridge filter is enabled then the associated bridge filter
				value must be included in the SNMP packet.
				
				If the bridge filter mask is all zeros then no filters will
				be applied and the bridge command will apply to all bridges
				in the system."
			::= { bridgeCmd 2 }
-- 
--  
		
		-- 1.3.6.1.4.1.5504.4.7.12.3
		bridgeCmdIfIndex OBJECT-TYPE
			SYNTAX InterfaceIndex
			MAX-ACCESS read-write
			STATUS current
			DESCRIPTION
				"Bridge command 'ifIndex' filter value.  If this object is 
				included in the SNMP packet then the associated filter must
				be enabled in the bridge filter mask (bridgeCmdFilterMask)."
			::= { bridgeCmd 3 }

		
		-- 1.3.6.1.4.1.5504.4.7.12.5
		bridgeCmdVlanId OBJECT-TYPE
			SYNTAX INTEGER (0..4090)
			MAX-ACCESS read-write
			STATUS current
			DESCRIPTION
				"Bridge command 'VLAN' filter value.  If this object is 
				included in the SNMP packet then the associated filter must
				be enabled in the bridge filter mask (bridgeCmdFilterMask)."
			DEFVAL { 0 }
			::= { bridgeCmd 5 }

		
		-- 1.3.6.1.4.1.5504.4.7.12.6
		bridgeCmdSlanId OBJECT-TYPE
			SYNTAX INTEGER (0..4090)
			MAX-ACCESS read-write
			STATUS current
			DESCRIPTION
				"Bridge command 'SLAN' filter value.  If this object is 
				included in the SNMP packet then the associated filter must
				be enabled in the bridge filter mask (bridgeCmdFilterMask)."
			DEFVAL { 0 }
			::= { bridgeCmd 6 }

		
		-- 1.3.6.1.4.1.5504.4.7.12.7
		bridgeCmdSlot OBJECT-TYPE
			SYNTAX INTEGER (1..32)
			MAX-ACCESS read-write
			STATUS current
			DESCRIPTION
				"Bridge command 'SLOT' filter value.  If this object is 
				included in the SNMP packet then the associated filter must
				be enabled in the bridge filter mask (bridgeCmdFilterMask)."
			DEFVAL { 1 }
			::= { bridgeCmd 7 }

		
		-- 1.3.6.1.4.1.5504.4.7.12.8
		bridgeCmdPort OBJECT-TYPE
			SYNTAX INTEGER (1..2147483647)
			MAX-ACCESS read-write
			STATUS current
			DESCRIPTION
				"Bridge command 'PORT' filter value.    This is the ifIndex 
				of the linegroup on which the bridge is stacked
				
				If this object is included in the SNMP packet then the 
				associated filter must be enabled in the bridge filter 
				mask (bridgeCmdFilterMask)."
			DEFVAL { 1 }
			::= { bridgeCmd 8 }

		
		-- 1.3.6.1.4.1.5504.4.7.12.9
		bridgeCmdIpAddress OBJECT-TYPE
			SYNTAX IpAddress
			MAX-ACCESS read-write
			STATUS current
			DESCRIPTION
				"Bridge command 'IP Address' filter value.    
				
				If this object is included in the SNMP packet then the 
				associated filter must be enabled in the bridge filter 
				mask (bridgeCmdFilterMask)."
			::= { bridgeCmd 9 }

		
		-- 1.3.6.1.4.1.5504.4.7.12.10
		bridgeCmdMacAddress OBJECT-TYPE
			SYNTAX MacAddress
			MAX-ACCESS read-write
			STATUS current
			DESCRIPTION
				"Bridge command 'MAC Address' filter value.    
				
				If this object is included in the SNMP packet then the 
				associated filter must be enabled in the bridge filter 
				mask (bridgeCmdFilterMask)."
			::= { bridgeCmd 10 }

		
		-- 1.3.6.1.4.1.5504.4.7.13
		eapsGroup OBJECT IDENTIFIER ::= { zhoneBridge 13 }

		
		-- 1.3.6.1.4.1.5504.4.7.13.1
		eapsConfigTable OBJECT-TYPE
			SYNTAX SEQUENCE OF EapsConfigEntry
			MAX-ACCESS not-accessible
			STATUS current
			DESCRIPTION
				"This table contains information required for the management
				of EAPS domains."
			::= { eapsGroup 1 }

		
		-- 1.3.6.1.4.1.5504.4.7.13.1.1
		eapsConfigEntry OBJECT-TYPE
			SYNTAX EapsConfigEntry
			MAX-ACCESS not-accessible
			STATUS current
			DESCRIPTION
				"An entry exists for each EAPS domain in the system.
				"
			INDEX { eapsConfigPrimaryPortLineGroup, eapsConfigSecondaryPortLineGroup, eapsConfigControlVlan }
			::= { eapsConfigTable 1 }

		
		EapsConfigEntry ::=
			SEQUENCE { 
				eapsConfigPrimaryPortLineGroup
					InterfaceIndex,
				eapsConfigSecondaryPortLineGroup
					InterfaceIndex,
				eapsConfigControlVlan
					Integer32,
				eapsConfigIsMasterNode
					TruthValue,
				eapsConfigControlVlanPriority
					Integer32,
				eapsConfigDomainName
					ZhoneAdminString,
				eapsConfigMsgTxInterval
					Integer32,
				eapsConfigTimeout
					Integer32,
				eapsConfigMaxDroppedMessages
					Integer32,
				eapsConfigSnmpTrap
					TruthValue,
				eapsConfigDomainEnable
					TruthValue,
				eapsConfigRowStatus
					ZhoneRowStatus
			 }

		-- 1.3.6.1.4.1.5504.4.7.13.1.1.1
		eapsConfigPrimaryPortLineGroup OBJECT-TYPE
			SYNTAX InterfaceIndex
			MAX-ACCESS accessible-for-notify
			STATUS current
			DESCRIPTION
				"This object contains the line group IfIndex of the Primary EAPS Port."
			::= { eapsConfigEntry 1 }

		
		-- 1.3.6.1.4.1.5504.4.7.13.1.1.2
		eapsConfigSecondaryPortLineGroup OBJECT-TYPE
			SYNTAX InterfaceIndex
			MAX-ACCESS accessible-for-notify
			STATUS current
			DESCRIPTION
				"This object contains the line group IfIndex of the Secondary EAPS Port."
			::= { eapsConfigEntry 2 }

		
		-- 1.3.6.1.4.1.5504.4.7.13.1.1.3
		eapsConfigControlVlan OBJECT-TYPE
			SYNTAX Integer32 (1..4090)
			MAX-ACCESS accessible-for-notify
			STATUS current
			DESCRIPTION
				"This object contains the VLAN ID of the control VLAN for this domain
				record. This is the VLAN ID used in EAPS control messages."
			::= { eapsConfigEntry 3 }

		
		-- 1.3.6.1.4.1.5504.4.7.13.1.1.4
		eapsConfigIsMasterNode OBJECT-TYPE
			SYNTAX TruthValue
			MAX-ACCESS read-create
			STATUS current
			DESCRIPTION
				"If this value is True, then this record describes a Master Node. 
				Otherwise, it describes a Transit Node."
			DEFVAL { false }
			::= { eapsConfigEntry 4 }

		
		-- 1.3.6.1.4.1.5504.4.7.13.1.1.5
		eapsConfigControlVlanPriority OBJECT-TYPE
			SYNTAX Integer32 (0..7)
			MAX-ACCESS read-create
			STATUS current
			DESCRIPTION
				"This object contains the Priority of the Control Vlan."
			DEFVAL { 6 }
			::= { eapsConfigEntry 5 }

		
		-- 1.3.6.1.4.1.5504.4.7.13.1.1.6
		eapsConfigDomainName OBJECT-TYPE
			SYNTAX ZhoneAdminString
			MAX-ACCESS read-create
			STATUS current
			DESCRIPTION
				"This object contains the user assigned ASCII representation of 
				the Domain Name for this record. This name must be unique device
				wide.
				"
			::= { eapsConfigEntry 6 }

		
		-- 1.3.6.1.4.1.5504.4.7.13.1.1.7
		eapsConfigMsgTxInterval OBJECT-TYPE
			SYNTAX Integer32
			UNITS "seconds"
			MAX-ACCESS read-create
			STATUS current
			DESCRIPTION
				"This object contains the interval, in seconds, that a node sends 
				Health Messages on the ring."
			DEFVAL { 1 }
			::= { eapsConfigEntry 7 }

		
		-- 1.3.6.1.4.1.5504.4.7.13.1.1.8
		eapsConfigTimeout OBJECT-TYPE
			SYNTAX Integer32
			UNITS "seconds"
			MAX-ACCESS read-create
			STATUS current
			DESCRIPTION
				"On a Master Node, this object contains the timeout, in seconds, which
				the Master Node will report a Ring Fault if it does not receive a
				Health Message on the ring. On a Transit Node, this is the pre-forwarding
				delay timeout (also in seconds). "
			DEFVAL { 3 }
			::= { eapsConfigEntry 8 }

		
		-- 1.3.6.1.4.1.5504.4.7.13.1.1.9
		eapsConfigMaxDroppedMessages OBJECT-TYPE
			SYNTAX Integer32
			MAX-ACCESS read-create
			STATUS current
			DESCRIPTION
				"On a Master Node, this object contains the number of contigious Health
				messages that may be dropped before the node declared a Ring Fault.
				This object is not used for a Transit node.
				"
			DEFVAL { 2 }
			::= { eapsConfigEntry 9 }

		
		-- 1.3.6.1.4.1.5504.4.7.13.1.1.10
		eapsConfigSnmpTrap OBJECT-TYPE
			SYNTAX TruthValue
			MAX-ACCESS read-create
			STATUS current
			DESCRIPTION
				"If this object is set to True, then this node will send SNMP Traps on
				Ring State transition. 
				"
			DEFVAL { true }
			::= { eapsConfigEntry 10 }

		
		-- 1.3.6.1.4.1.5504.4.7.13.1.1.11
		eapsConfigDomainEnable OBJECT-TYPE
			SYNTAX TruthValue
			MAX-ACCESS read-create
			STATUS current
			DESCRIPTION
				"If this value is TRUE, the EAPS state machine will transition through 
				the initialization process to the Health state.   It will begin 
				passing Control Messages and allow Protected VLAN data through the 
				EAPS Domain.
				If this value is FALSE, the EAPS state machine will transition 
				through the reset  process to the Inactivate state.  It will stop 
				passing Control Messages and prohibit Protected VLAN data from being 
				passed through the EAPS Domain."
			DEFVAL { false }
			::= { eapsConfigEntry 11 }

		
		-- 1.3.6.1.4.1.5504.4.7.13.1.1.12
		eapsConfigRowStatus OBJECT-TYPE
			SYNTAX ZhoneRowStatus
			MAX-ACCESS read-create
			STATUS current
			DESCRIPTION
				"This object is used to create and remove rows in the table.
				See eapsConfigEntry description for minimum requirements."
			DEFVAL { active }
			::= { eapsConfigEntry 12 }

		
		-- 1.3.6.1.4.1.5504.4.7.13.2
		eapsProtectedVlanTable OBJECT-TYPE
			SYNTAX SEQUENCE OF EapsProtectedVlanEntry
			MAX-ACCESS not-accessible
			STATUS current
			DESCRIPTION
				"This table contains information required for the management
				of a list of protected VLAN's in an EAPS domains."
			::= { eapsGroup 2 }

		
		-- 1.3.6.1.4.1.5504.4.7.13.2.1
		eapsProtectedVlanEntry OBJECT-TYPE
			SYNTAX EapsProtectedVlanEntry
			MAX-ACCESS not-accessible
			STATUS current
			DESCRIPTION
				"An entry for each VLAN ranges that is to be protected 
				in the EAPS domain.
				"
			INDEX { eapsConfigPrimaryPortLineGroup, eapsConfigSecondaryPortLineGroup, eapsConfigControlVlan, eapsProtectedVlanEntryIndex }
			::= { eapsProtectedVlanTable 1 }

		
		EapsProtectedVlanEntry ::=
			SEQUENCE { 
				eapsProtectedVlanEntryIndex
					Integer32,
				eapsProtectedVlanLowerRange
					Integer32,
				eapsProtectedVlanUpperRange
					Integer32,
				eapsProtectedVlanRowStatus
					ZhoneRowStatus,
				eapsProtectedVlanDomainName
					ZhoneAdminString
			 }

		-- 1.3.6.1.4.1.5504.4.7.13.2.1.1
		eapsProtectedVlanEntryIndex OBJECT-TYPE
			SYNTAX Integer32 (0..9)
			MAX-ACCESS accessible-for-notify
			STATUS current
			DESCRIPTION
				"This object is an index which indicates which entry
				in the Protected Vlan Table is being addressed. For 
				example, a value of 5 would indicate that the 5th entry
				(row) of this table is being addressed. This entry,
				along with eapsConfigPrimaryLineGroup, 
				eapsConfigSecondaryLineGroup, and 
				eapsConfigControlVlan indices select which 
				Protected Vlan Table entry for a given 
				eaps-domain-record profile. The first three 
				indices select the profile, this last index selects
				 the N'th entry in that profile
				"
			::= { eapsProtectedVlanEntry 1 }

		
-- 
		-- 1.3.6.1.4.1.5504.4.7.13.2.1.2
		eapsProtectedVlanLowerRange OBJECT-TYPE
			SYNTAX Integer32 (0..4090)
			MAX-ACCESS read-create
			STATUS current
			DESCRIPTION
				"The eapsProtectedVlanLowerRange and eapsProtectedVlanUpperRange objects
				work in conjunction with one another to set the range of the protected
				vlans. If eapsProtectedVlanLowerRange is 0, then this indicates end
				of list. If eapsProtectedVlanLowerRange is not 0, but 
				eapsProtectedVlanUpperRange is 0, then this would be have the same
				effect as both object having the same value and protect a single
				vlan ID. If they are both different and non-zero, then it specifies
				an inclusive range. Note that eapsProtectedVlanLowerRange must be
				numerically lower than eapsProtectedVlanUpperRange.
				
				"
			::= { eapsProtectedVlanEntry 2 }

		
-- 
		-- 1.3.6.1.4.1.5504.4.7.13.2.1.3
		eapsProtectedVlanUpperRange OBJECT-TYPE
			SYNTAX Integer32 (0..4090)
			MAX-ACCESS read-create
			STATUS current
			DESCRIPTION
				"The eapsProtectedVlanLowerRange and eapsProtectedVlanUpperRange objects
				work in conjunction with one another to set the range of the protected
				vlans. If eapsProtectedVlanLowerRange is 0, then this indicates end
				of list. If eapsProtectedVlanLowerRange is not 0, but 
				eapsProtectedVlanUpperRange is 0, then this would be have the same
				effect as both object having the same value and protect a single
				vlan ID. If they are both different and non-zero, then it specifies
				an inclusive range. Note that eapsProtectedVlanLowerRange must be
				numerically lower than eapsProtectedVlanUpperRange.
				"
			::= { eapsProtectedVlanEntry 3 }

		
		-- 1.3.6.1.4.1.5504.4.7.13.2.1.4
		eapsProtectedVlanRowStatus OBJECT-TYPE
			SYNTAX ZhoneRowStatus
			MAX-ACCESS read-create
			STATUS current
			DESCRIPTION
				"This object is used to create and remove rows in the table.
				See eapsProtectedVlanEntry description for minimum requirements."
			DEFVAL { active }
			::= { eapsProtectedVlanEntry 4 }

		
		-- 1.3.6.1.4.1.5504.4.7.13.2.1.5
		eapsProtectedVlanDomainName OBJECT-TYPE
			SYNTAX ZhoneAdminString
			MAX-ACCESS read-only
			STATUS current
			DESCRIPTION
				"The domain name for the EAPS protected vlan entry."
			DEFVAL { "" }
			::= { eapsProtectedVlanEntry 5 }

		
		-- 1.3.6.1.4.1.5504.4.7.13.3
		eapsStatusTable OBJECT-TYPE
			SYNTAX SEQUENCE OF EapsStatusEntry
			MAX-ACCESS not-accessible
			STATUS current
			DESCRIPTION
				"This table contains status of each EAPS domain state machine."
			::= { eapsGroup 3 }

		
		-- 1.3.6.1.4.1.5504.4.7.13.3.1
		eapsStatusEntry OBJECT-TYPE
			SYNTAX EapsStatusEntry
			MAX-ACCESS not-accessible
			STATUS current
			DESCRIPTION
				"The entry contains status of the domain's state machine."
			INDEX { eapsConfigPrimaryPortLineGroup, eapsConfigSecondaryPortLineGroup, eapsConfigControlVlan }
			::= { eapsStatusTable 1 }

		
		EapsStatusEntry ::=
			SEQUENCE { 
				eapsPrevState
					EapsState,
				eapsState
					EapsState
			 }

		-- 1.3.6.1.4.1.5504.4.7.13.3.1.1
		eapsPrevState OBJECT-TYPE
			SYNTAX EapsState
			MAX-ACCESS read-only
			STATUS current
			DESCRIPTION
				"Previous state for the domain."
			::= { eapsStatusEntry 1 }

		
		-- 1.3.6.1.4.1.5504.4.7.13.3.1.2
		eapsState OBJECT-TYPE
			SYNTAX EapsState
			MAX-ACCESS read-only
			STATUS current
			DESCRIPTION
				"Current state for the domain."
			::= { eapsStatusEntry 2 }

		
		-- 1.3.6.1.4.1.5504.4.7.13.4
		eapsStatsTable OBJECT-TYPE
			SYNTAX SEQUENCE OF EapsStatsEntry
			MAX-ACCESS not-accessible
			STATUS current
			DESCRIPTION
				"EAPS statistics table."
			::= { eapsGroup 4 }

		
		-- 1.3.6.1.4.1.5504.4.7.13.4.1
		eapsStatsEntry OBJECT-TYPE
			SYNTAX EapsStatsEntry
			MAX-ACCESS not-accessible
			STATUS current
			DESCRIPTION
				"Displays the EAPS statistic table entries."
			INDEX { eapsConfigPrimaryPortLineGroup, eapsConfigSecondaryPortLineGroup, eapsConfigControlVlan }
			::= { eapsStatsTable 1 }

		
		EapsStatsEntry ::=
			SEQUENCE { 
				eapsStatsTotCtrlMsgSent
					Integer32,
				eapsStatsTotCtrlMsgRecvd
					Integer32
			 }

		-- 1.3.6.1.4.1.5504.4.7.13.4.1.1
		eapsStatsTotCtrlMsgSent OBJECT-TYPE
			SYNTAX Integer32
			MAX-ACCESS read-write
			STATUS current
			DESCRIPTION
				"Total EAPS control messages sent."
			::= { eapsStatsEntry 1 }

		
		-- 1.3.6.1.4.1.5504.4.7.13.4.1.2
		eapsStatsTotCtrlMsgRecvd OBJECT-TYPE
			SYNTAX Integer32
			MAX-ACCESS read-write
			STATUS current
			DESCRIPTION
				"Total EAPS control messages received."
			::= { eapsStatsEntry 2 }

		
		-- 1.3.6.1.4.1.5504.4.7.13.5
		eapsTrapPrefix OBJECT-IDENTITY
			STATUS current
			DESCRIPTION 
				"Place-holder object for EAPS traps, which must have a
				final digit of 0 in OID."
			::= { eapsGroup 5 }

		
		-- 1.3.6.1.4.1.5504.4.7.13.5.0
		eapsTraps OBJECT-IDENTITY
			STATUS current
			DESCRIPTION 
				"Traps raised by EAPS state machine."
			::= { eapsTrapPrefix 0 }

		
		-- 1.3.6.1.4.1.5504.4.7.13.5.0.1
		eapsStateChange NOTIFICATION-TYPE
			OBJECTS { eapsConfigPrimaryPortLineGroup, eapsConfigSecondaryPortLineGroup, eapsConfigControlVlan, eapsConfigDomainName }
			STATUS current
			DESCRIPTION 
				"State changed in the node for the EAPS domain."
			::= { eapsTraps 1 }

		
		-- 1.3.6.1.4.1.5504.4.7.13.5.0.2
		eapsFailTimerExpFlagSet NOTIFICATION-TYPE
			OBJECTS { eapsConfigPrimaryPortLineGroup, eapsConfigSecondaryPortLineGroup, eapsConfigControlVlan, eapsConfigDomainName }
			STATUS current
			DESCRIPTION 
				"The eapsFailTimerExpFlagSet notification is
				generated when the EAPS domain's fail timer expires
				for the first time, while its state is not in Fail state."
			::= { eapsTraps 2 }

		
		-- 1.3.6.1.4.1.5504.4.7.13.5.0.3
		eapsFailTimerExpFlagClear NOTIFICATION-TYPE
			OBJECTS { eapsConfigPrimaryPortLineGroup, eapsConfigSecondaryPortLineGroup, eapsConfigControlVlan, eapsConfigDomainName }
			STATUS current
			DESCRIPTION 
				"Description."
			::= { eapsTraps 3 }

		
		-- 1.3.6.1.4.1.5504.4.7.13.5.0.4
		eapsLinkDownRingComplete NOTIFICATION-TYPE
			OBJECTS { eapsConfigPrimaryPortLineGroup, eapsConfigSecondaryPortLineGroup, eapsConfigControlVlan, eapsConfigDomainName }
			STATUS current
			DESCRIPTION 
				"If a transit is in Link-Down state, and it receives a
				Health-Check-Pdu from the Master indicating the ring is
				Complete, it means there is some problem with the Transit
				switch that has issued this trap message."
			::= { eapsTraps 4 }

		
		-- 1.3.6.1.4.1.5504.4.7.13.6
		eapsTopologyTable OBJECT-TYPE
			SYNTAX SEQUENCE OF EapsTopologyEntry
			MAX-ACCESS not-accessible
			STATUS current
			DESCRIPTION
				"EAPS topology table."
			::= { eapsGroup 6 }

		
		-- 1.3.6.1.4.1.5504.4.7.13.6.1
		eapsTopologyEntry OBJECT-TYPE
			SYNTAX EapsTopologyEntry
			MAX-ACCESS not-accessible
			STATUS current
			DESCRIPTION
				"Displays the EAPS topology table entries."
			INDEX { eapsConfigPrimaryPortLineGroup, eapsConfigSecondaryPortLineGroup, eapsTopologyRing, eapsTopologyRowNumber }
			::= { eapsTopologyTable 1 }

		
		EapsTopologyEntry ::=
			SEQUENCE { 
				eapsTopologyRing
					INTEGER,
				eapsTopologyRowNumber
					Integer32,
				eapsTopologyDomainName
					ZhoneAdminString,
				eapsTopologyMacAddr
					MacAddress,
				eapsTopologyIpAddr
					IpAddress,
				eapsTopologyType
					INTEGER,
				eapsTopologyPrimaryLinkName
					ZhoneAdminString,
				eapsTopologyPrimaryLinkState
					EapsState,
				eapsTopologySecondaryLinkName
					ZhoneAdminString,
				eapsTopologySecondaryLinkState
					EapsState
			 }

		-- 1.3.6.1.4.1.5504.4.7.13.6.1.1
		eapsTopologyRing OBJECT-TYPE
			SYNTAX INTEGER
				{
				primary(0),
				secondary(1)
				}
			MAX-ACCESS not-accessible
			STATUS current
			DESCRIPTION
				"This represents the link as primary or secondary."
			::= { eapsTopologyEntry 1 }

		
		-- 1.3.6.1.4.1.5504.4.7.13.6.1.2
		eapsTopologyRowNumber OBJECT-TYPE
			SYNTAX Integer32 (0..47)
			MAX-ACCESS not-accessible
			STATUS current
			DESCRIPTION
				"This represents the node number in the ring."
			::= { eapsTopologyEntry 2 }

		
		-- 1.3.6.1.4.1.5504.4.7.13.6.1.3
		eapsTopologyDomainName OBJECT-TYPE
			SYNTAX ZhoneAdminString
			MAX-ACCESS read-only
			STATUS current
			DESCRIPTION
				"This represents the domain name for this record."
			::= { eapsTopologyEntry 3 }

		
		-- 1.3.6.1.4.1.5504.4.7.13.6.1.4
		eapsTopologyMacAddr OBJECT-TYPE
			SYNTAX MacAddress
			MAX-ACCESS read-only
			STATUS current
			DESCRIPTION
				"macAddress of the element in the ring."
			::= { eapsTopologyEntry 4 }

		
		-- 1.3.6.1.4.1.5504.4.7.13.6.1.5
		eapsTopologyIpAddr OBJECT-TYPE
			SYNTAX IpAddress
			MAX-ACCESS read-only
			STATUS current
			DESCRIPTION
				"Ip addressed of the element in the ring."
			::= { eapsTopologyEntry 5 }

		
		-- 1.3.6.1.4.1.5504.4.7.13.6.1.6
		eapsTopologyType OBJECT-TYPE
			SYNTAX INTEGER
				{
				master(0),
				transit(1)
				}
			MAX-ACCESS read-only
			STATUS current
			DESCRIPTION
				"This represents whether the node is master or transit."
			::= { eapsTopologyEntry 6 }

		
		-- 1.3.6.1.4.1.5504.4.7.13.6.1.7
		eapsTopologyPrimaryLinkName OBJECT-TYPE
			SYNTAX ZhoneAdminString
			MAX-ACCESS read-only
			STATUS current
			DESCRIPTION
				"This represents the primary link name."
			::= { eapsTopologyEntry 7 }

		
		-- 1.3.6.1.4.1.5504.4.7.13.6.1.8
		eapsTopologyPrimaryLinkState OBJECT-TYPE
			SYNTAX EapsState
			MAX-ACCESS read-only
			STATUS current
			DESCRIPTION
				"This represents the primary link state."
			::= { eapsTopologyEntry 8 }

		
		-- 1.3.6.1.4.1.5504.4.7.13.6.1.9
		eapsTopologySecondaryLinkName OBJECT-TYPE
			SYNTAX ZhoneAdminString
			MAX-ACCESS read-only
			STATUS current
			DESCRIPTION
				"This represents the secondary link name."
			::= { eapsTopologyEntry 9 }

		
		-- 1.3.6.1.4.1.5504.4.7.13.6.1.10
		eapsTopologySecondaryLinkState OBJECT-TYPE
			SYNTAX EapsState
			MAX-ACCESS read-only
			STATUS current
			DESCRIPTION
				"This represents the secondary link state."
			::= { eapsTopologyEntry 10 }

		
		-- 1.3.6.1.4.1.5504.4.7.14
		bridgeIgmpStatsTable OBJECT-TYPE
			SYNTAX SEQUENCE OF BridgeIgmpStatsEntry
			MAX-ACCESS not-accessible
			STATUS current
			DESCRIPTION
				"The bridgeIgmpStatsTable is used to access the IGMP statistics for bridges."
			::= { zhoneBridge 14 }

		
		-- 1.3.6.1.4.1.5504.4.7.14.1
		bridgeIgmpStatsEntry OBJECT-TYPE
			SYNTAX BridgeIgmpStatsEntry
			MAX-ACCESS not-accessible
			STATUS current
			DESCRIPTION
				"The bridgeIgmpStatsEntry holds IGMP stats for a bridge interface."
			INDEX { ifIndex }
			::= { bridgeIgmpStatsTable 1 }

		
		BridgeIgmpStatsEntry ::=
			SEQUENCE { 
				genQueryRx
					Unsigned32,
				genQueryTx
					Unsigned32,
				specQueryRx
					Unsigned32,
				specQueryTx
					Unsigned32,
				v2ReportsRx
					Unsigned32,
				v2ReportsTx
					Unsigned32,
				leavesRx
					Unsigned32,
				leavesTx
					Unsigned32,
				unknownRx
					Unsigned32,
				errorRx
					Unsigned32,
				actChans
					Unsigned32,
				actHosts
					Unsigned32,
				v3GenQueryRx
					Unsigned32,
				v3GenQueryTx
					Unsigned32,
				v3SpecQueryRx
					Unsigned32,
				v3SpecQueryTx
					Unsigned32,
				v3ReportsRx
					Unsigned32,
				v3ReportsTx
					Unsigned32
			 }

		-- 1.3.6.1.4.1.5504.4.7.14.1.1
		genQueryRx OBJECT-TYPE
			SYNTAX Unsigned32
			MAX-ACCESS read-only
			STATUS current
			DESCRIPTION
				"general IGMP queries received."
			::= { bridgeIgmpStatsEntry 1 }

		
		-- 1.3.6.1.4.1.5504.4.7.14.1.2
		genQueryTx OBJECT-TYPE
			SYNTAX Unsigned32
			MAX-ACCESS read-only
			STATUS current
			DESCRIPTION
				"general IGMP queries transmitted."
			::= { bridgeIgmpStatsEntry 2 }

		
		-- 1.3.6.1.4.1.5504.4.7.14.1.3
		specQueryRx OBJECT-TYPE
			SYNTAX Unsigned32
			MAX-ACCESS read-only
			STATUS current
			DESCRIPTION
				"Specific IGMP queries received."
			::= { bridgeIgmpStatsEntry 3 }

		
		-- 1.3.6.1.4.1.5504.4.7.14.1.4
		specQueryTx OBJECT-TYPE
			SYNTAX Unsigned32
			MAX-ACCESS read-only
			STATUS current
			DESCRIPTION
				"Specific IGMP queries transmitted."
			::= { bridgeIgmpStatsEntry 4 }

		
		-- 1.3.6.1.4.1.5504.4.7.14.1.5
		v2ReportsRx OBJECT-TYPE
			SYNTAX Unsigned32
			MAX-ACCESS read-only
			STATUS current
			DESCRIPTION
				"Version 2 reports received (JOINs)."
			::= { bridgeIgmpStatsEntry 5 }

		
		-- 1.3.6.1.4.1.5504.4.7.14.1.6
		v2ReportsTx OBJECT-TYPE
			SYNTAX Unsigned32
			MAX-ACCESS read-only
			STATUS current
			DESCRIPTION
				"Version 2 reports sent."
			::= { bridgeIgmpStatsEntry 6 }

		
		-- 1.3.6.1.4.1.5504.4.7.14.1.7
		leavesRx OBJECT-TYPE
			SYNTAX Unsigned32
			MAX-ACCESS read-only
			STATUS current
			DESCRIPTION
				"IGMP leaves received."
			::= { bridgeIgmpStatsEntry 7 }

		
		-- 1.3.6.1.4.1.5504.4.7.14.1.8
		leavesTx OBJECT-TYPE
			SYNTAX Unsigned32
			MAX-ACCESS read-only
			STATUS current
			DESCRIPTION
				"IGMP leaves transmitted."
			::= { bridgeIgmpStatsEntry 8 }

		
		-- 1.3.6.1.4.1.5504.4.7.14.1.9
		unknownRx OBJECT-TYPE
			SYNTAX Unsigned32
			MAX-ACCESS read-only
			STATUS current
			DESCRIPTION
				"Unknown IGMP packets received."
			::= { bridgeIgmpStatsEntry 9 }

		
		-- 1.3.6.1.4.1.5504.4.7.14.1.10
		errorRx OBJECT-TYPE
			SYNTAX Unsigned32
			MAX-ACCESS read-only
			STATUS current
			DESCRIPTION
				"IGMP packet is bad received."
			::= { bridgeIgmpStatsEntry 10 }

		
		-- 1.3.6.1.4.1.5504.4.7.14.1.11
		actChans OBJECT-TYPE
			SYNTAX Unsigned32
			MAX-ACCESS read-only
			STATUS current
			DESCRIPTION
				"Number of active muticast channels."
			::= { bridgeIgmpStatsEntry 11 }

		
		-- 1.3.6.1.4.1.5504.4.7.14.1.12
		actHosts OBJECT-TYPE
			SYNTAX Unsigned32
			MAX-ACCESS read-only
			STATUS current
			DESCRIPTION
				"Number of active multicast hosts."
			::= { bridgeIgmpStatsEntry 12 }

		
		-- 1.3.6.1.4.1.5504.4.7.14.1.13
		v3GenQueryRx OBJECT-TYPE
			SYNTAX Unsigned32
			MAX-ACCESS read-only
			STATUS current
			DESCRIPTION
				"Number of IGMP V3 Queries received."
			::= { bridgeIgmpStatsEntry 13 }

		
		-- 1.3.6.1.4.1.5504.4.7.14.1.14
		v3GenQueryTx OBJECT-TYPE
			SYNTAX Unsigned32
			MAX-ACCESS read-only
			STATUS current
			DESCRIPTION
				"Number of IGMP V3 queries sent."
			::= { bridgeIgmpStatsEntry 14 }

		
		-- 1.3.6.1.4.1.5504.4.7.14.1.15
		v3SpecQueryRx OBJECT-TYPE
			SYNTAX Unsigned32
			MAX-ACCESS read-only
			STATUS current
			DESCRIPTION
				"Number of IGMP V3 specific queries received."
			::= { bridgeIgmpStatsEntry 15 }

		
		-- 1.3.6.1.4.1.5504.4.7.14.1.16
		v3SpecQueryTx OBJECT-TYPE
			SYNTAX Unsigned32
			MAX-ACCESS read-only
			STATUS current
			DESCRIPTION
				"Number of IGMP V3 specific queries sent."
			::= { bridgeIgmpStatsEntry 16 }

		
		-- 1.3.6.1.4.1.5504.4.7.14.1.17
		v3ReportsRx OBJECT-TYPE
			SYNTAX Unsigned32
			MAX-ACCESS read-only
			STATUS current
			DESCRIPTION
				"Number of IGMP V3 reports received."
			::= { bridgeIgmpStatsEntry 17 }

		
		-- 1.3.6.1.4.1.5504.4.7.14.1.18
		v3ReportsTx OBJECT-TYPE
			SYNTAX Unsigned32
			MAX-ACCESS read-only
			STATUS current
			DESCRIPTION
				"Number of IGMP V3 reports sent."
			::= { bridgeIgmpStatsEntry 18 }

		
		-- 1.3.6.1.4.1.5504.4.7.15
		bridgeGroup OBJECT IDENTIFIER ::= { zhoneBridge 15 }

		
		-- 1.3.6.1.4.1.5504.4.7.15.1
		bridgeTrapPrefix OBJECT-IDENTITY
			STATUS current
			DESCRIPTION 
				"Traps raised for bridge conditions."
			::= { bridgeGroup 1 }

		
		-- 1.3.6.1.4.1.5504.4.7.15.1.0
		bridgeTraps OBJECT-IDENTITY
			STATUS current
			DESCRIPTION 
				"Bridge traps go under here - extra layer 
				needed to ensure '0' in OID."
			::= { bridgeTrapPrefix 0 }

		
		-- 1.3.6.1.4.1.5504.4.7.15.1.0.1
		bridgeLoopDetection NOTIFICATION-TYPE
			OBJECTS { ifIndex, ifAlias, bridgeMacAddrString }
			STATUS current
			DESCRIPTION 
				"Trap when bridge is looping on flap."
			::= { bridgeTraps 1 }

		
		-- 1.3.6.1.4.1.5504.4.7.15.1.0.2
		bridgeStormDetection NOTIFICATION-TYPE
			OBJECTS { ifIndex, ifAlias, bridgeMacAddrString }
			STATUS current
			DESCRIPTION 
				"Trap sent when a bridge packet storm is detected."
			::= { bridgeTraps 2 }

		
		-- 1.3.6.1.4.1.5504.4.7.16
		bridgeTrapObjects OBJECT IDENTIFIER ::= { zhoneBridge 16 }

		
		-- 1.3.6.1.4.1.5504.4.7.16.1
		bridgeMacAddrString OBJECT-TYPE
			SYNTAX OCTET STRING
			MAX-ACCESS accessible-for-notify
			STATUS current
			DESCRIPTION
				"vlan/slan/macAddress for bridge"
			::= { bridgeTrapObjects 1 }

		
		-- 1.3.6.1.4.1.5504.4.7.17
		bridgeIgmpTable OBJECT-TYPE
			SYNTAX SEQUENCE OF BridgeIgmpEntry
			MAX-ACCESS not-accessible
			STATUS current
			DESCRIPTION
				"The bridgeIgmpTable is used to access the IGMP data for bridges for when 
				IGMP is in proxy mode and the IGMP status must be obtained from the 
				linecard."
			::= { zhoneBridge 17 }

		
		-- 1.3.6.1.4.1.5504.4.7.17.1
		bridgeIgmpEntry OBJECT-TYPE
			SYNTAX BridgeIgmpEntry
			MAX-ACCESS not-accessible
			STATUS current
			DESCRIPTION
				"BridgeIgmpEntry contains the igmp multicast data information for a bridge,
				indexed by ifIndex, hostMac, and mcastMac."
			INDEX { ifIndex, hostMac, mcastMac }
			::= { bridgeIgmpTable 1 }

		
		BridgeIgmpEntry ::=
			SEQUENCE { 
				slanId
					Integer32,
				vlanId
					Integer32,
				mcastMac
					OCTET STRING,
				mcastIP
					IpAddress,
				hostMac
					OCTET STRING,
				lastJoinTimer
					Integer32
			 }

		-- 1.3.6.1.4.1.5504.4.7.17.1.1
		slanId OBJECT-TYPE
			SYNTAX Integer32 (0..4090)
			MAX-ACCESS read-only
			STATUS current
			DESCRIPTION
				"IGMP slan identifier. Maximum value 4090 as defined by MAX_VLAN_NUM."
			::= { bridgeIgmpEntry 1 }

		
		-- 1.3.6.1.4.1.5504.4.7.17.1.2
		vlanId OBJECT-TYPE
			SYNTAX Integer32 (0..4090)
			MAX-ACCESS read-only
			STATUS current
			DESCRIPTION
				"IGMP vlan identifier. Maximum value 4090 as defined my MAX_VLAN_NUM"
			::= { bridgeIgmpEntry 2 }

		
		-- 1.3.6.1.4.1.5504.4.7.17.1.3
		mcastMac OBJECT-TYPE
			SYNTAX OCTET STRING (SIZE (0..6))
			MAX-ACCESS read-only
			STATUS current
			DESCRIPTION
				"IGMP Multicast MAC addressed to bridge port."
			::= { bridgeIgmpEntry 3 }

		
		-- 1.3.6.1.4.1.5504.4.7.17.1.4
		mcastIP OBJECT-TYPE
			SYNTAX IpAddress
			MAX-ACCESS read-only
			STATUS current
			DESCRIPTION
				"IGMP Multicast IP addressed to bridge port."
			::= { bridgeIgmpEntry 4 }

		
		-- 1.3.6.1.4.1.5504.4.7.17.1.5
		hostMac OBJECT-TYPE
			SYNTAX OCTET STRING (SIZE (0..6))
			MAX-ACCESS read-only
			STATUS current
			DESCRIPTION
				"MAC address of end device receiving multicast packets."
			::= { bridgeIgmpEntry 5 }

		
		-- 1.3.6.1.4.1.5504.4.7.17.1.6
		lastJoinTimer OBJECT-TYPE
			SYNTAX Integer32
			MAX-ACCESS read-only
			STATUS current
			DESCRIPTION
				"Count down timer before IGMP entry ages out."
			::= { bridgeIgmpEntry 6 }

		
		-- 1.3.6.1.4.1.5504.4.7.18
		staticBridgePathTable OBJECT-TYPE
			SYNTAX SEQUENCE OF StaticBridgePathEntry
			MAX-ACCESS not-accessible
			STATUS current
			DESCRIPTION
				"A collection of staticBridgePathEntries.
				
				The StaticBridgePath OID has the following format:
				
				      OID psn      MAC entries     IPv4 entries     IPv6 entries
				     ----------    -------------   --------------   --------------
				     tlist[0]       ifIndex          ifIndex          ifIndex
				     tlist[1]       address type     address type     address type
				     tlist[2]       vlan             vlan             vlan
				     tlist[3]       macAddr[0]       IPv4[0]          IPv6[0]
				     tlist[4]       macAddr[1]       IPv4[1]          IPv6[1]
				     tlist[5]       macAddr[2]       IPv4[2]          IPv6[2]
				     tlist[6]       macAddr[3]       IPv4[3]          IPv6[3]
				     tlist[7]       macAddr[4]       zero             IPv6[4]
				     tlist[8]       macAddr[5]       zero             IPv6[5]
				     tlist[9]       zero             zero             IPv6[6]
				     tlist[10]      zero             zero             IPv6[7]
				     tlist[11]      zero             zero             IPv6[8]
				     tlist[12]      zero             zero             IPv6[9]
				     tlist[13]      zero             zero             IPv6[10]
				     tlist[14]      zero             zero             IPv6[11]
				     tlist[15]      zero             zero             IPv6[12]
				     tlist[16]      zero             zero             IPv6[13]
				     tlist[17]      zero             zero             IPv6[14]
				     tlist[18]      zero             zero             IPv6[15]
				     tlist[19]      slan             slan             slan "
			::= { zhoneBridge 18 }

		
		-- 1.3.6.1.4.1.5504.4.7.18.1
		staticBridgePathEntry OBJECT-TYPE
			SYNTAX StaticBridgePathEntry
			MAX-ACCESS not-accessible
			STATUS current
			DESCRIPTION
				"Static Path Bridge entries are created by the user in
				order to specify forwarding for a particular
				interface, vlanId, mac address or ip address,
				slanId (for QinQ).
						
				The INDEX value for staticBridgePathEntry consists of
				following 5 values:
						
				   ifIndex
				   staticBridgePathAddressType
				   bridgeIfVlanId
				   staticBridgePathMacOrIpAddress
				   bridgeIfStagId
						
				If staticBridgeAddressType is set to macAddr(1), then
				staticBridgeMacOrIpAddress represents a MAC Address,
				and ifIndex, bridgeIfVlanId and staticBridgeMacOrIpAddress
				are used for the bridge path.
						
				If staticBridgeAddressType is set to ipAddr(2), then
				staticBridgeMacOrIpAddress represents an IP Address,
				and ifIndex, bridgeIfVlanId and staticBridgeMacOrIpAddress
				are used for the bridge path.
						
				If staticBridgeAddressType is set to vlanIdAddr(3),
				then ifIndex and bridgeIfVlanId are used for the
				bridge path.
						
				If staticBridgeAddressType is set to globalAddr(4),
				then ifIndex is used for the bridge path."
			INDEX { ifIndex, staticBridgePathAddressType, bridgeIfVlanId, staticBridgePathMacOrIpAddress, bridgeIfStagId
				 }
			::= { staticBridgePathTable 1 }

		
		StaticBridgePathEntry ::=
			SEQUENCE { 
				staticBridgePathMacOrIpAddress
					NetworkAddress,
				staticBridgePathAddressType
					INTEGER,
				staticBridgePathMulticastAging
					Integer32,
				staticBridgePathRowStatus
					ZhoneRowStatus,
				staticBridgePathFlapControl
					INTEGER,
				staticBridgePathUnicastAging
					Integer32,
				staticBridgePathIgmpQueryInterval
					Integer32,
				staticBridgePathFlags
					BITS,
				staticBridgePathIgmpCustomIpAddress
					IpAddress,
				staticBridgePathLoopPrevention
					INTEGER,
				staticBridgePathIgmpDscp
					OCTET STRING
			 }

		-- 1.3.6.1.4.1.5504.4.7.18.1.1
		staticBridgePathMacOrIpAddress OBJECT-TYPE
			SYNTAX NetworkAddress
			MAX-ACCESS not-accessible
			STATUS current
			DESCRIPTION
				"If the staticBridgeAddressType is set to macAddr(1),
				then this field represents a MAC address.
				
				If the staticBridgeAddressType is set to ipAddr(2),
				then this field represents an IP address.  The IP 
				address can be four octets ( for IPv4 ) or sixteen
				octets ( for IPv6 )."
			::= { staticBridgePathEntry 1 }

		
		-- 1.3.6.1.4.1.5504.4.7.18.1.2
		staticBridgePathAddressType OBJECT-TYPE
			SYNTAX INTEGER
				{
				macAddr(1),
				ipAddr(2),
				vlanIdAddr(3),
				globalAddr(4),
				intralinkAddr(7),
				globalIntralinkAddr(8),
				dhcpIpAddr(9),
				dhcpMacAddr(10),
				mvrAddr(13),
				vlanParms(14),
				secMvrAddr(15),
				ipAddrV6(16),
				dhcpIpAddrV6(17),
				dhcpAllowOui(720901)
				}
			MAX-ACCESS not-accessible
			STATUS current
			DESCRIPTION
				"If staticBridgeIPv6AddressType is set to macAddr(1), then
				staticBridgeMacOrIpAddress represents a MAC Address,
				and ifIndex, bridgeIfVlanId and staticBridgeMacOrIpAddress
				are used for the bridge path.
				
				If staticBridgeIPv6AddressType is set to ipAddr(2), then
				staticBridgeMacOrIpAddress represents an IP Address,
				and ifIndex, bridgeIfVlanId and staticBridgeMacOrIpAddress
				are used for the bridge path.
				
				If staticBridgeIPv6AddressType is set to vlanIdAddr(3) or 
				intralinkAddr(7), then ifIndex and bridgeIfVlanId are 
				used for the bridge path.
				
				If staticBridgeIPv6AddressType is set to globalAddr(4), 
				globalIntralinkAddr(8), or mvrAddr(13) then ifIndex 
				is used for the bridge path. 
				
				If staticBridgeIPv6AddressType is set to
				dhcpAllowOui( 720901) then the first 3 bytes of the
				MAC address contains the OUI that we will allow DHCP
				addresses to be granted to, global scope.
				
				If staticBridgeIPv6AddressType is set to dhcpIpAddr(9), or
				to dhcpMacAddr(10), then the other fields are populated
				as for address types ipAddr and macAddr respectively,
				with the difference that these are secure entries,
				learned by snooping DHCP.
				
				If staticBridgeIPv6AddressType is set to vlanParms(14), 
				then the static bridge entry holds parameters for 
				the given VLAN and SLAN ID (for example, flap mode, 
				unicast aging period, etc) and is not associated 
				with any specific bridge, but with all bridges 
				with the same VLAN/SLAN ID. For this reason, 
				the IfIndex of this entry must be zero. 
				
				If staticBridgeIPv6AddressType is set to secMvrAddr(15), 
				then the static bridge entry holds parameters for 
				a Secondary MVR path. The VLAN ID of this entry is
				the Secondary VLAN ID.
				
				If staticBridgeIPv6AddressType is set to ipAddrV6(16), then
				staticBridgeMacOrIpAddress represents an IPv6 Address,
				and ifIndex, bridgeIfVlanId and staticBridgeIPv6MacOrIpAddress
				are used for the bridge path.
				
				
				If staticBridgeIPv6AddressType is set to dhcpIpAddrV6(17), or
				to dhcpMacAddr(10), then the other fields are populated
				as for address types ipAddr and macAddr respectively,
				with the difference that these are secure entries,
				learned by snooping DHCP."
			::= { staticBridgePathEntry 2 }

		
		-- 1.3.6.1.4.1.5504.4.7.18.1.3
		staticBridgePathMulticastAging OBJECT-TYPE
			SYNTAX Integer32 (0..2147483647)
			MAX-ACCESS read-create
			STATUS current
			DESCRIPTION
				"Multicast Aging period in tenths of seconds for the
				specified VLAN.  After the specified aging period is
				met, the  VLAN address is deleted from the routing table.
				
				A value of 0 indicates that aging is turned off.
				
				Maximum value is 2147483647 tenths of seconds,
				which equates to approximately 2485.51 days."
			::= { staticBridgePathEntry 3 }

		
		-- 1.3.6.1.4.1.5504.4.7.18.1.4
		staticBridgePathRowStatus OBJECT-TYPE
			SYNTAX ZhoneRowStatus
			MAX-ACCESS read-create
			STATUS current
			DESCRIPTION
				"Used to create, modify or delete an entry in this
				table."
			DEFVAL { active }
			::= { staticBridgePathEntry 4 }

		
		-- 1.3.6.1.4.1.5504.4.7.18.1.5
		staticBridgePathFlapControl OBJECT-TYPE
			SYNTAX INTEGER
				{
				default(1),
				disable(2),
				enable(3),
				fast(4)
				}
			MAX-ACCESS read-create
			STATUS current
			DESCRIPTION
				"This object enables or disable Flap Control in the Bridge 
				Filter Table. The value 'disable(2)' turns Flap Control mode 
				off. The values 'enable(3)' or 'fast(4) turn flap control mode on.
				'Enable(3)' applies a hold time of 60 secs before allowing addr/IP
				to be moved to a new port, while 'fast(4)' applies a hold time of
				0 secs. A value  of 'default(1)' indicates 'Don't Care' and defaults
				to a  disable or enable set by another entry. "
			DEFVAL { default }
			::= { staticBridgePathEntry 5 }

		
		-- 1.3.6.1.4.1.5504.4.7.18.1.6
		staticBridgePathUnicastAging OBJECT-TYPE
			SYNTAX Integer32 (0 | 120..2147483647)
			MAX-ACCESS read-create
			STATUS current
			DESCRIPTION
				"Multicast Aging period in tenths of seconds for the
				specified VLAN.  After the specified aging period is
				met, the  VLAN address is deleted from the routing table.
				
				A value of 0 indicates that aging is turned off.
				
				Maximum value is 2147483647 tenths of seconds,
				which equates to approximately 2485.51 days."
			::= { staticBridgePathEntry 6 }

		
		-- 1.3.6.1.4.1.5504.4.7.18.1.7
		staticBridgePathIgmpQueryInterval OBJECT-TYPE
			SYNTAX Integer32
			MAX-ACCESS read-create
			STATUS current
			DESCRIPTION
				"How often (in seconds) we as a bridge inject IGMP query 
				values into the stream."
			DEFVAL { 0 }
			::= { staticBridgePathEntry 7 }

		
		-- 1.3.6.1.4.1.5504.4.7.18.1.8
		staticBridgePathFlags OBJECT-TYPE
			SYNTAX BITS
				{
				igmpProcessJoinAndLeave(0),
				igmpRespondToQuery(1),
				igmpUseBridgeIpAddress(2)
				}
			MAX-ACCESS read-create
			STATUS current
			DESCRIPTION
				"none                               : IGMP Snooping with Proxy reporting is disabled.
				BIT 0(igmpProcessJoinAndLeave)     : igmpProcessJoinandLeave is enabled for IGMP packets.
				BIT 1(igmpRespondToQuery)          : igmpRespondToQuery is enabled for IGMP packets.
				BIT 2(igmpUseBridgeIpAddress)      : igmpUseBridgeIpAddress is enabled for IGMP packets.
				
				"
			::= { staticBridgePathEntry 8 }

		
		-- 1.3.6.1.4.1.5504.4.7.18.1.9
		staticBridgePathIgmpCustomIpAddress OBJECT-TYPE
			SYNTAX IpAddress
			MAX-ACCESS read-create
			STATUS current
			DESCRIPTION
				"Allow the configuration of the source IP address for 
				packets that we originate upstream when doing IGMP 
				Porxy on a bridge. "
			::= { staticBridgePathEntry 9 }

		
		-- 1.3.6.1.4.1.5504.4.7.18.1.10
		staticBridgePathLoopPrevention OBJECT-TYPE
			SYNTAX INTEGER
				{
				none(0),
				blockAsym(1),
				blockAll(2),
				blockAsymAuto(3),
				blockAllAuto(4)
				}
			MAX-ACCESS read-write
			STATUS current
			DESCRIPTION
				"This field does the following options,'BlockAsym(1)' blocks a 
				learning bridge if flap is detected between it and an uplink bridge.
				'BlockAll(2)' incorporates 'blockAsym(1)' but it also blocks a 
				learning bridge if it flaps against another learning bridge."
			DEFVAL { none }
			::= { staticBridgePathEntry 10 }

		
		-- 1.3.6.1.4.1.5504.4.7.18.1.11
		staticBridgePathIgmpDscp OBJECT-TYPE
			SYNTAX OCTET STRING (SIZE (1..8))
			MAX-ACCESS read-create
			STATUS current
			DESCRIPTION
				"This parameter indicates DSCP value for igmp traffic.
								
								
								Valid code values:
								
								<0-63>   Differentiated services codepoint value 
								   af11     Mark packets with AF11 dscp (001010) 
								   af12     Mark packets with AF12 dscp (001100) 
								   af13     Mark packets with AF13 dscp (001110) 
								   af21     Mark packets with AF21 dscp (010010) 
								   af22     Mark packets with AF22 dscp (010100) 
								   af23     Mark packets with AF23 dscp (010110) 
								   af31     Mark packets with AF31 dscp (011010) 
								   af32     Mark packets with AF32 dscp (011100) 
								   af33     Mark packets with AF33 dscp (011110) 
								   af41     Mark packets with AF41 dscp (100010) 
								   af42     Mark packets with AF42 dscp (100100) 
								   af43     Mark packets with AF43 dscp (100110) 
								   cs1      Mark packets with CS1(precedence 1) dscp (001000) 
								   cs2      Mark packets with CS2(precedence 2) dscp (010000) 
								   cs3      Mark packets with CS3(precedence 3) dscp (011000) 
								   cs4      Mark packets with CS4(precedence 4) dscp (100000) 
								   cs5      Mark packets with CS5(precedence 5) dscp (101000) 
								   cs6      Mark packets with CS6(precedence 6) dscp (110000) 
								   cs7      Mark packets with CS7(precedence 7) dscp (111000) 
								   default  Mark packets with default dscp (000000) 
								   ef       Mark packets with EF dscp (101110)"
			::= { staticBridgePathEntry 11 }

		
		-- 1.3.6.1.4.1.5504.4.7.19
		bridgePathIfLookupTable OBJECT-TYPE
			SYNTAX SEQUENCE OF BridgePathIfLookupEntry
			MAX-ACCESS not-accessible
			STATUS current
			DESCRIPTION
				"A collection of bridgePathIfLookupTable entries.
				
				The bridgePathIfLookup OID has the following format:
				
				      OID psn      MAC entries     IPv4 entries     IPv6 entries
				     ----------    -------------   --------------   --------------
				     tlist[0]       address type     address type     address type
				     tlist[1]       macAddr[0]       IPv4[0]          IPv6[0]
				     tlist[2]       macAddr[1]       IPv4[1]          IPv6[1]
				     tlist[3]       macAddr[2]       IPv4[2]          IPv6[2]
				     tlist[4]       macAddr[3]       IPv4[3]          IPv6[3]
				     tlist[5]       macAddr[4]       zero             IPv6[4]
				     tlist[6]       macAddr[5]       zero             IPv6[5]
				     tlist[7]       zero             zero             IPv6[6]
				     tlist[8]       zero             zero             IPv6[7]
				     tlist[9]       zero             zero             IPv6[8]
				     tlist[10]      zero             zero             IPv6[9]
				     tlist[11]      zero             zero             IPv6[10]
				     tlist[12]      zero             zero             IPv6[11]
				     tlist[13]      zero             zero             IPv6[12]
				     tlist[14]      zero             zero             IPv6[13]
				     tlist[15]      zero             zero             IPv6[14]
				     tlist[16]      zero             zero             IPv6[15]
				     tlist[17]      vlan             vlan             vlan
				     tlist[18]      ifIndex          ifIndex          ifIndex
				     tlist[19]      slan             slan             slan "
			::= { zhoneBridge 19 }

		
		-- 1.3.6.1.4.1.5504.4.7.19.1
		bridgePathIfLookupEntry OBJECT-TYPE
			SYNTAX BridgePathIfLookupEntry
			MAX-ACCESS not-accessible
			STATUS current
			DESCRIPTION
				"Bridge IfLookup entries are created by the user
				or learned by the software in
				order to specify forwarding for a particular
				interface, vlanId/slanId, mac address or ip address.
				
				The INDEX value for bridgeIfLookupEntry consists of
				following 5 values:
				
				bridgeIfAddressType
				bridgeIfMacOrIpAddress
				bridgeIfVlanId
				ifIndex
				bridgeIfStagId
				
				
				If bridgeIfAddressType is set to unicast_mac(1),
				then bridgeIfMacOrIpAddress represents a MAC Address,
				and ifIndex, bridgeIfVlanId/Slanid and 
				bridgeIfMacOrIpAddress are use for the bridge path.
				
				If bridgeIfAddressType is set to multicast_mac(2),
				then bridgeMacOrIpAddress represents a MAC Address,
				and ifIndex, bridgeIfVlanId/SlanId and 
				bridgeIfMacOrIpAddress are used for bridge path.
				
				If bridgeIfAddressType is set to ip_address(3),
				then ifIndex and bridgeIfVlanId/SlanId are used 
				for the bridge path."
			INDEX { bridgePathIfAddressType, bridgePathIfMacOrIpAddress, bridgeIfVlanId, ifIndex, bridgeIfStagId
				 }
			::= { bridgePathIfLookupTable 1 }

		
		BridgePathIfLookupEntry ::=
			SEQUENCE { 
				bridgePathIfAddressType
					INTEGER,
				bridgePathIfMacOrIpAddress
					NetworkAddress,
				bridgePathIfLookupStaticOrDynamic
					INTEGER,
				bridgePathIfLookupFlush
					TruthValue
			 }

		-- 1.3.6.1.4.1.5504.4.7.19.1.1
		bridgePathIfAddressType OBJECT-TYPE
			SYNTAX INTEGER
				{
				unicastMac(1),
				multicastMac(2),
				ipAddress(3),
				dhcpMac(4),
				dhcpIp(5)
				}
			MAX-ACCESS not-accessible
			STATUS current
			DESCRIPTION
				"If bridgeIfAddressType is set to unicast_mac(1),
				then bridgeIfMacOrIpAddress represents a MAC Address,
				and ifIndex, bridgeIfVlanId and bridgeIfMacOrIpAddress
				are used for the bridge path.
				
				If bridgeIfAddressType is set to multicast_mac(2),
				then bridgeMacOrIpAddress represents a MAC Address,
				and ifIndex, bridgeIfVlanId and bridgeIfMacOrIpAddress
				are used for the bridge path.
				
				If bridgeIfAddressType is set to ip_address(3),
				then ifIndex and bridgeIfVlanId are used for the
				bridge path.
				
				If bridgeIfAddressType is set to dhcp_mac(4), or
				dhcp_ip(5), then the address is as desribed for types
				1 and 3, respectively, and the address was learned
				by snooping DHCP packets."
			::= { bridgePathIfLookupEntry 1 }

		
		-- 1.3.6.1.4.1.5504.4.7.19.1.2
		bridgePathIfMacOrIpAddress OBJECT-TYPE
			SYNTAX NetworkAddress
			MAX-ACCESS not-accessible
			STATUS current
			DESCRIPTION
				"If bridgeIfAddressType is set to FILTER_ENTRY_UNICAST_MAC(1)
				or to FILTER_ENTRY_MULTICAST_MAC(2), or to FILTER_ENTRY_DHCP_MAC(4),
				then bridgeIfMacOrIpAddress represents a MAC Address.
				
				If bridgeIfAddressType is set to FILTER_ENTRY_IP_ADDRESS(3), or
				to FILTER_ENTRY_DHCP_IP(5),
				then bridgeIfMacOrIpAddress represents an IP Address."
			::= { bridgePathIfLookupEntry 2 }

		
		-- 1.3.6.1.4.1.5504.4.7.19.1.3
		bridgePathIfLookupStaticOrDynamic OBJECT-TYPE
			SYNTAX INTEGER
				{
				staticEntry(1),
				dynamicEntry(2)
				}
			MAX-ACCESS read-only
			STATUS current
			DESCRIPTION
				"If bridgeIfLookupStaticOrDynamic is set to 1,
				then this table entry is static and persistent.
				
				If bridgeIfLookupStaticOrDynamic is set to 2,
				then this table entry is learned and is not persistent."
			::= { bridgePathIfLookupEntry 3 }

		
		-- 1.3.6.1.4.1.5504.4.7.19.1.4
		bridgePathIfLookupFlush OBJECT-TYPE
			SYNTAX TruthValue
			MAX-ACCESS read-write
			STATUS current
			DESCRIPTION
				"The object 'bridgeIfLookupFlush' allows a user to flush
				learned entries in the bridgeFilterTable when the ifIndex
				of the entry is not known.  A combination of address type,
				MAC or IP address and vlan ID is used to determine the
				ifIndex of the entry to be removed.  Setting the object 
				to 'true' causes the flush action to occur.
				
				After the flush action is taken, the value of
				bridgeIfLookupFlush is immediately set back to 'false'."
			DEFVAL { false }
			::= { bridgePathIfLookupEntry 4 }

		
		-- 1.3.6.1.4.1.5504.4.7.20
		bridgePathAddressLookupTable OBJECT-TYPE
			SYNTAX SEQUENCE OF BridgePathAddressLookupEntry
			MAX-ACCESS not-accessible
			STATUS current
			DESCRIPTION
				"A collection of bridgePathAddressLookupTable entries.
				
				The bridgePathAddressLookup OID has the following format:
				
				      OID psn      MAC entries     IPv4 entries     IPv6 entries
				     ----------    -------------   --------------   --------------
				     tlist[0]       ifIndex          ifIndex          ifIndex
				     tlist[1]       address type     address type     address type
				     tlist[2]       macAddr[0]       IPv4[0]          IPv6[0]
				     tlist[3]       macAddr[1]       IPv4[1]          IPv6[1]
				     tlist[4]       macAddr[2]       IPv4[2]          IPv6[2]
				     tlist[5]       macAddr[3]       IPv4[3]          IPv6[3]
				     tlist[6]       macAddr[4]       zero             IPv6[4]
				     tlist[7]       macAddr[5]       zero             IPv6[5]
				     tlist[8]       zero             zero             IPv6[6]
				     tlist[9]       zero             zero             IPv6[7]
				     tlist[10]      zero             zero             IPv6[8]
				     tlist[11]      zero             zero             IPv6[9]
				     tlist[12]      zero             zero             IPv6[10]
				     tlist[13]      zero             zero             IPv6[11]
				     tlist[14]      zero             zero             IPv6[12]
				     tlist[15]      zero             zero             IPv6[13]
				     tlist[16]      zero             zero             IPv6[14]
				     tlist[17]      zero             zero             IPv6[15]
				     tlist[18]      vlan             vlan             vlan
				     tlist[19]      slan             slan             slan"
			::= { zhoneBridge 20 }

		
		-- 1.3.6.1.4.1.5504.4.7.20.1
		bridgePathAddressLookupEntry OBJECT-TYPE
			SYNTAX BridgePathAddressLookupEntry
			MAX-ACCESS not-accessible
			STATUS current
			DESCRIPTION
				"BridgePathAddressLookup entries are created by the user
				or learned by the software in
				order to specify forwarding for a particular
				interface, vlanId/slanId, mac address or ip address.
				
				The INDEX value for bridgePathLookupEntry consists of
				following 5 values:
				
				ifIndex
				bridgeIfAddressType
				bridgeIfMacOrIpAddress
				bridgeIfVlanId
				bridgeIfStagId"
			INDEX { ifIndex, bridgeIfAddressType, bridgePathIfLookupStaticOrDynamic, bridgeIfVlanId, bridgeIfStagId
				 }
			::= { bridgePathAddressLookupTable 1 }

		
		BridgePathAddressLookupEntry ::=
			SEQUENCE { 
				bridgePathAddressLookupStaticOrDynamic
					INTEGER,
				bridgePathAddressLookupFlush
					TruthValue
			 }

		-- 1.3.6.1.4.1.5504.4.7.20.1.1
		bridgePathAddressLookupStaticOrDynamic OBJECT-TYPE
			SYNTAX INTEGER
				{
				staticEntry(1),
				dynamicEntry(2)
				}
			MAX-ACCESS read-only
			STATUS current
			DESCRIPTION
				"If bridgePathAddressLookupStaticOrDynamic is set to 1,
				then this table entry is static and persistent.
				
				If bridgePathAddressLookupStaticOrDynamic is set to 2,
				then this table entry is learned and is not persistent."
			::= { bridgePathAddressLookupEntry 1 }

		
		-- 1.3.6.1.4.1.5504.4.7.20.1.2
		bridgePathAddressLookupFlush OBJECT-TYPE
			SYNTAX TruthValue
			MAX-ACCESS read-write
			STATUS current
			DESCRIPTION
				"The object 'bridgePathAddressFlush' allows a user to flush
				learned entries in the bridgeFilterTable when the ifIndex
				of the entry is known.  The ifIndex is used to determine 
				which interface is to be removed.  Setting the object 
				to 'true' causes the flush action to occur.
				
				After the flush action is taken, the value of
				bridgePathLookupFlush is immediately set back to 'false'."
			DEFVAL { false }
			::= { bridgePathAddressLookupEntry 2 }

		
		-- 1.3.6.1.4.1.5504.4.7.21
		bridgeStatusTable OBJECT-TYPE
			SYNTAX SEQUENCE OF BridgeStatusEntry
			MAX-ACCESS not-accessible
			STATUS current
			DESCRIPTION
				"This table contains runtime status for each bridge interface."
			::= { zhoneBridge 21 }

		
		-- 1.3.6.1.4.1.5504.4.7.21.1
		bridgeStatusEntry OBJECT-TYPE
			SYNTAX BridgeStatusEntry
			MAX-ACCESS not-accessible
			STATUS current
			DESCRIPTION
				"Runtime status data for a single bridge."
			INDEX { ifIndex }
			::= { bridgeStatusTable 1 }

		
		BridgeStatusEntry ::=
			SEQUENCE { 
				bridgeStatusState
					BridgeState
			 }

		-- 1.3.6.1.4.1.5504.4.7.21.1.1
		bridgeStatusState OBJECT-TYPE
			SYNTAX BridgeState
			MAX-ACCESS read-only
			STATUS current
			DESCRIPTION
				"Values:
				up(1),                 UP
				down(2),               DWN
				trouble(3),            TRB
				notAvailable(4),       NA
				initializing(5),       INI
				adminDown(6),          ADN
				adminStateTest(7),     TST
				adminStateNone(8),     N/S
				ready(9),              RDY
				discovering(10),       DSC
				unknown(11),           ???
				blocked(12),           BLK
				pending(13),           PND
				disabled(14),          DIS
				learning(15),          LRN
				forwarding(16),        FWD
				blockedFlapping(17),   BLF
				blockedPersistent(18), BLP
				blockedFlappingPersistenr(19), BFP
				"
			::= { bridgeStatusEntry 1 }

		
		-- 1.3.6.1.4.1.5504.9
		zhoneCompliances OBJECT IDENTIFIER ::= { zhone 9 }

		
		-- 1.3.6.1.4.1.5504.9.1
		zhoneGroups OBJECT IDENTIFIER ::= { zhoneCompliances 1 }

		
		-- 1.3.6.1.4.1.5504.9.1.23
		zhoneBridgeGroup OBJECT-GROUP
			OBJECTS { bridgeIfMcastControlList, bridgeIfMaxVideoStreams, bridgeIfIsPPPoA, bridgeIfFloodUnknown, bridgeIfFloodMulticast, 
				bridgeIfTableBasedFilter, bridgeIfDhcpLearn, staticBridgeUnicastAging, staticBridgeIgmpQueryInterval, bridgePPPoEBrasMac, 
				bridgePPPoELocalHostMac, bridgePPPoEEIfIndex, bridgePPPoESessionID, bridgePPPoESlanId, bridgePPPoEVlanId, 
				bridgePPPoEEncapLLC, stpParamName, stpParamRevision, stpParamBridgePriority, stpParamForceVersion, 
				stpParamFwdDelay, stpParamHelloTime, stpParamMigrateTime, stpParamTxHoldCount, stpParamMaxAge, 
				stpBindRowStatus, stpBindPortPriority, mstpInstanceRowStatus, bridgeCmdOperation, bridgeCmdFilterMask, 
				mstpInstanceName, staticBridgeFlags, staticBridgeIgmpCustomIpAddress, bridgeIfMvrVlan, bridgeIfVlanXlateFrom, 
				bridgeIfSlanXlateFrom, bridgeMacAddrString, bridgeIfGponTrafficProfile, bridgeIfGponGemPortId, bridgeType, 
				staticBridgePathMulticastAging, staticBridgePathRowStatus, staticBridgePathFlapControl, staticBridgePathUnicastAging, staticBridgePathIgmpQueryInterval, 
				staticBridgePathFlags, staticBridgePathIgmpCustomIpAddress, staticBridgePathLoopPrevention, staticBridgePathIgmpDscp, bridgePathIfLookupStaticOrDynamic, 
				bridgePathIfLookupFlush, bridgeIfStagIncomingCOSOption, bridgeIfIncomingCOSOption, bridgeIfUnblock, bridgeIfOnDemandStatsEnabled, 
				bridgeIfBridgeState, staticBridgeIgmpDscp, packetRuleValue6, packetRuleValue7, bridgePathAddressLookupFlush, 
				bridgePathAddressLookupStaticOrDynamic, bridgeStatusState }
			STATUS current
			DESCRIPTION 
				"The list of zhone bridge objects."
			::= { zhoneGroups 23 }

		
		-- 1.3.6.1.4.1.5504.9.1.76
		zhoneBridgeCmdGroup OBJECT-GROUP
			OBJECTS { bridgeCmdOperation, bridgeCmdFilterMask, bridgeCmdIfIndex, bridgeCmdVlanId, bridgeCmdSlanId, 
				bridgeCmdSlot, bridgeCmdPort, bridgeCmdIpAddress, bridgeCmdMacAddress }
			STATUS current
			DESCRIPTION 
				"Bridge CMD objects"
			::= { zhoneGroups 76 }

		
		-- 1.3.6.1.4.1.5504.9.1.77
		zhoneBridgeEapsGroup OBJECT-GROUP
			OBJECTS { eapsProtectedVlanEntryIndex, eapsProtectedVlanLowerRange, eapsProtectedVlanUpperRange, eapsProtectedVlanRowStatus, eapsProtectedVlanDomainName, 
				eapsPrevState, eapsState, eapsStatsTotCtrlMsgSent, eapsStatsTotCtrlMsgRecvd }
			STATUS current
			DESCRIPTION 
				"EAPS objects"
			::= { zhoneGroups 77 }

		
		-- 1.3.6.1.4.1.5504.9.1.78
		zhoneBridgeEapsConfigGroup OBJECT-GROUP
			OBJECTS { eapsConfigPrimaryPortLineGroup, eapsConfigSecondaryPortLineGroup, eapsConfigControlVlan, eapsConfigIsMasterNode, eapsConfigControlVlanPriority, 
				eapsConfigDomainName, eapsConfigMsgTxInterval, eapsConfigTimeout, eapsConfigMaxDroppedMessages, eapsConfigSnmpTrap, 
				eapsConfigDomainEnable, eapsConfigRowStatus }
			STATUS current
			DESCRIPTION 
				"EAPS config objects"
			::= { zhoneGroups 78 }

		
		-- 1.3.6.1.4.1.5504.9.1.79
		zhoneBridgeEapsTopologyGroup OBJECT-GROUP
			OBJECTS { eapsTopologyDomainName, eapsTopologyMacAddr, eapsTopologyIpAddr, eapsTopologyType, eapsTopologyPrimaryLinkName, 
				eapsTopologyPrimaryLinkState, eapsTopologySecondaryLinkName, eapsTopologySecondaryLinkState }
			STATUS current
			DESCRIPTION 
				"EAPS Topology objects"
			::= { zhoneGroups 79 }

		
		-- 1.3.6.1.4.1.5504.9.1.80
		zhoneBridgeNotificationGroup NOTIFICATION-GROUP
			NOTIFICATIONS { eapsStateChange, eapsFailTimerExpFlagSet, eapsFailTimerExpFlagClear, eapsLinkDownRingComplete, bridgeLoopDetection, 
				bridgeStormDetection }
			STATUS current
			DESCRIPTION 
				"BRIDGE Notifications"
			::= { zhoneGroups 80 }

		
		-- 1.3.6.1.4.1.5504.9.1.81
		zhoneBridgeIgmpGroup OBJECT-GROUP
			OBJECTS { slanId, vlanId, mcastMac, mcastIP, hostMac, 
				lastJoinTimer }
			STATUS current
			DESCRIPTION 
				"IGMP objects"
			::= { zhoneGroups 81 }

		
		-- 1.3.6.1.4.1.5504.9.1.82
		zhoneBridgeStatsGroup OBJECT-GROUP
			OBJECTS { bridgeStatsUcastRcvd, bridgeStatsMcastRcvd, bridgeStatsBcastRcvd, bridgeStatsUcastSent, bridgeStatsMcastSent, 
				bridgeStatsBcastSent, bridgeStatsErrorSent, bridgeOnDemandStatsRulesSupported, bridgeOnDemandStatsRulesRemaining, bridgeStatsBSDUcastBlocked, 
				bridgeStatsBSDMcastBlocked, bridgeStatsBSDBcastBlocked, bridgeStatsBSDAlarmCount, bridgeStatsBytesRcvdCount, bridgeStatsBytesSentCount, 
				bridgeStatsTicksLastCleared, bridgeStatsTicksNow, bridgeStatsTicksPerSecond }
			STATUS current
			DESCRIPTION 
				"Bridge STATS objects"
			::= { zhoneGroups 82 }

		
	
	END

--
-- comBridgeRec.mib
--
