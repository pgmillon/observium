PDN-DEVICE-TIME-MIB DEFINITIONS ::= BEGIN

-- Last Updated: 6/3/02

-- Enterprise Time MIB
-- Copyright (C) 1999-2002 Paradyne Corporation.

-- Created by : Prakash Easwar

-- REVISION HISTORY:
-- Date of Chg  Revision (Most Recent First)                            By
--
-- 06/03/02     Removed unneeded devNTPIf object.                       alfano
-- 05/07/02     Added new objects for SNTP support.  Changed/corrected  alfano
--              existing object descriptions to reflect SNTP support.
--

IMPORTS
IpAddress
FROM RFC1155-SMI
OBJECT-TYPE
FROM RFC-1212
DateAndTime
FROM SNMPv2-TC
NTPMode
FROM PDN-TC
pdn-time
FROM PDN-HEADER-MIB

;
devTimeMIBObjects       OBJECT IDENTIFIER ::= { pdn-time 1 }
devTimeMIBTraps         OBJECT IDENTIFIER ::= { pdn-time 2 }
devTimeAndDate          OBJECT IDENTIFIER ::= { devTimeMIBObjects 1 }
devNTP                  OBJECT IDENTIFIER ::= { devTimeMIBObjects 2 }


-- Time And Date Group

devDateAndTime OBJECT-TYPE
    SYNTAX  DateAndTime
    ACCESS  read-write
    STATUS  mandatory
    DESCRIPTION
       "This object displays the date and time on the entity.
       It allows an NMS to set the date and time in the appropriate
       timezone."
    ::= { devTimeAndDate 1 }

-- [S]NTP ([Simple] Network Time Protocol) group

devNTPServerIP OBJECT-TYPE
    SYNTAX  IpAddress
    ACCESS  read-write
    STATUS  mandatory
    DESCRIPTION
        "The IP address of the NTP/SNTP server."
    ::= { devNTP 1 }

devNTPMode OBJECT-TYPE
    SYNTAX  NTPMode
    ACCESS  read-write
    STATUS  mandatory
    DESCRIPTION
        "This object allows an NMS to configure the mode in which NTP/SNTP
        will operate.  In unicast(1) mode, NTP/SNTP polls the server
        specified via the devNTPServerIP object.  In broadcast(2) mode,
        NTP/SNTP polls by broadcasting a request so that any NTP/SNTP
        server could respond.  Alternatively, in broadcast(2) mode, the
        client only listens for messages broadcasted by any server.  In
        multicast(3) mode, the client listens for messages from any server
        sent to the multicast group defined for NTP/SNTP (224.0.1.1).
        Default value is broadcast(2)."
    ::= { devNTP 2 }

devNTPSynchronised OBJECT-TYPE
    SYNTAX  INTEGER (1 .. 24)
    ACCESS  read-write
    STATUS  mandatory
    DESCRIPTION
        "This object allows an NMS to configure the poll interval (hours)    
        for the NTP/SNTP client to use to send requests to an NTP/SNTP
        server to synchronize the local clock for the device.
        Default value is 1 hour."
    ::= { devNTP 3 }

devNTPEnable OBJECT-TYPE
    SYNTAX  INTEGER { enabled(1), disabled(2) }
    ACCESS  read-write
    STATUS  mandatory
    DESCRIPTION
        "Indicates whether or not the local clock is synchronized
        via NTP/SNTP.  When set to enabled(1), NTP/SNTP is operational
        and will attempt to synchronize the local clock based on the
        message(s) received from an NTP/SNTP server.
        Default value is enabled(1)."
    ::= { devNTP 4 }

devNTPOffsetFromUTC OBJECT-TYPE
    SYNTAX  INTEGER
    ACCESS  read-write
    STATUS  mandatory
    DESCRIPTION
        "Offset (minutes) from the coordinated universal time (UTC), also
        known as Greenwich mean time (GMT), to local time represented as a
        signed integer.  The sign of the integer denotes the direction of local
        time from UTC (e.g., offsets for local times west of the zero meridian
        to the international date line are negative).
        Default value is 0 (i.e., at UTC)."
    ::= { devNTP 5 }

END
