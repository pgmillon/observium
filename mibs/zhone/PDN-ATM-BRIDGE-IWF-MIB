-- ===============================================================
-- Copyright (C) 2003 Paradyne Corporation.
-- ===============================================================

PDN-ATM-BRIDGE-IWF-MIB DEFINITIONS ::= BEGIN

IMPORTS
    MODULE-IDENTITY, OBJECT-TYPE, Unsigned32
        FROM SNMPv2-SMI
    OBJECT-GROUP, MODULE-COMPLIANCE
        FROM SNMPv2-CONF
    RowStatus
        FROM SNMPv2-TC
    ifIndex
        FROM IF-MIB
    pdn-common
        FROM PDN-HEADER-MIB;
        
pdnAtmBridgeIwfMIB MODULE-IDENTITY
    LAST-UPDATED "200303240000Z"  -- April 24, 2003
    ORGANIZATION "Paradyne Networks
                  MIB Working Group
                  Other information about group editing the MIB"
    CONTACT-INFO "Paradyne Networks, Inc.
                  8545 126th Avenue North
                  Largo, FL 33733
                  www.paradyne.com
        
                  General Comments to: mibwg_team@paradyne.com

                  Editors
                        Clay Sikes"

    DESCRIPTION
        "This MIB contains objects that are used for monitoring and 
        controlling the ATM/Bridge Interworking Function."

    REVISION "200304240000Z"  -- April 24, 2003
    DESCRIPTION "Added stronger Conformance/Compliance statements."

    REVISION "200303240000Z"  -- March 24, 2003
    DESCRIPTION "Corrected typo in that the pdnAtmBridgeIwfVplVpi
                 should have been pdnAtmBridgeIwfVclVpi."
        
    REVISION "200303170000Z"  -- March 17, 2003
    DESCRIPTION "Initial release."


::=  { pdn-common 43 }

pdnAtmBridgeIwfNotifications OBJECT IDENTIFIER ::= { pdnAtmBridgeIwfMIB 0 }
pdnAtmBridgeIwfObjects       OBJECT IDENTIFIER ::= { pdnAtmBridgeIwfMIB 1 }
pdnAtmBridgeIwfConformance   OBJECT IDENTIFIER ::= { pdnAtmBridgeIwfMIB 2 }



pdnAtmBridgeIwfTable     OBJECT-TYPE
    SYNTAX      SEQUENCE OF PdnAtmBridgeIwfEntry
    MAX-ACCESS  not-accessible
    STATUS      current
    DESCRIPTION "This table allows mapping of ATM VCs to Bridge Ports."
    ::= { pdnAtmBridgeIwfObjects 1 }

pdnAtmBridgeIwfEntry     OBJECT-TYPE
    SYNTAX      PdnAtmBridgeIwfEntry
    MAX-ACCESS  not-accessible
    STATUS      current
    DESCRIPTION "An entry in the pdnAtmBridgeIwfTable."
    INDEX       { ifIndex,
                  pdnAtmBridgeIwfVclVpi,
                  pdnAtmBridgeIwfVclVci  }
    ::= { pdnAtmBridgeIwfTable 1 }

PdnAtmBridgeIwfEntry ::=
    SEQUENCE {
        pdnAtmBridgeIwfVclVpi          Unsigned32,
        pdnAtmBridgeIwfVclVci          Unsigned32,
        pdnAtmBridgeIwfRowStatus       RowStatus,
        pdnAtmBridgeIwfDot1dBasePort   Unsigned32
    }

pdnAtmBridgeIwfVclVpi OBJECT-TYPE
    SYNTAX      Unsigned32(0..4095)
    MAX-ACCESS  not-accessible
    STATUS      current
    DESCRIPTION "The VPI value of the VPL."
    ::= { pdnAtmBridgeIwfEntry 1 }

pdnAtmBridgeIwfVclVci OBJECT-TYPE
    SYNTAX      Unsigned32(0..65535)
    MAX-ACCESS  not-accessible
    STATUS      current
    DESCRIPTION "The VCI value of the VCL."
    ::= { pdnAtmBridgeIwfEntry 2 }

pdnAtmBridgeIwfRowStatus OBJECT-TYPE
    SYNTAX      RowStatus
    MAX-ACCESS  read-create
    STATUS      current
    DESCRIPTION "The SNMP RowStatus of the current row."
    ::= { pdnAtmBridgeIwfEntry 3 }

pdnAtmBridgeIwfDot1dBasePort OBJECT-TYPE
    SYNTAX      Unsigned32(1..65535)
    MAX-ACCESS  read-create
    STATUS      current
    DESCRIPTION "This object specifies the bridge port the 
                VPI/VCI maps to."
    ::= { pdnAtmBridgeIwfEntry 4 }


-- =============================================================================
-- ==                  Conformance Information                                ==
-- =============================================================================

pdnAtmBridgeIwfCompliances  OBJECT IDENTIFIER ::= { pdnAtmBridgeIwfConformance 1 }
pdnAtmBridgeIwfGroups       OBJECT IDENTIFIER ::= { pdnAtmBridgeIwfConformance 2 }


-- ===========================
-- == Compliance Statements ==
-- ===========================

pdnAtmBridgeIwfMIBCompliance MODULE-COMPLIANCE
    STATUS      current
    DESCRIPTION "The compliance statement for pdnAtmBridgeIwf entities which
                implement the pdnAtmBridgeIwfMIB."
    MODULE      -- this module
    MANDATORY-GROUPS { pdnAtmBridgeIwfGroup }
    ::= { pdnAtmBridgeIwfCompliances 1 }


-- ==========================
-- == Units of Conformance ==
-- ==========================

pdnAtmBridgeIwfGroup OBJECT-GROUP
    OBJECTS     {
                     pdnAtmBridgeIwfRowStatus, 
                     pdnAtmBridgeIwfDot1dBasePort           
    }
    STATUS      current
    DESCRIPTION "Objects grouped for ATM to Bridge Port Mapping."
    ::= { pdnAtmBridgeIwfGroups  1 }


END
