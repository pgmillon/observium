NTNTECH-MTM-MIB DEFINITIONS ::= BEGIN    

--	****************************************************************    
--  Enterprise:
--   	Paradyne Corporation.   
--
--  ContactInfo:
--    	Paradyne Corporation
--     	8545 126th Avenue North
--     	Largo, FL 33773
--     	phone: +1 (727) 530 - 2000
--     	email: support@paradyne.com 
--		www:   http://www.nettonet.com/support/
--
--  Description:
--    	ntntech-mtm-mib.my
--    	Revision: 1.02.02
--    	Part Number: xx-xxxx-xx
--    	Date: October , 2005
--   
--    	This module provides explicit definitions for the Net to
--		Net Technologies naming	tree below:
--    
--    	nettonettech { enterprises 8059 }
--    
--    	This module will be extended, as additional sub-sections
--    	of this naming tree are defined.
--
--  Disclaimer:
--	   	This is an extremely preliminary MIB module and is subject
--		to change at any time therefore, use at your own risk.
--    
-- 	Copyright (c) 2005 by Paradyne Corporation.
-- 	All rights reserved.    

-- ****************************************************************
IMPORTS 
    ntntechChassis,NtnDisplayString,NtnMacAddress,NtnIpAddress	FROM NTNTECH-ROOT-MIB
   	ifCfgSlotIndex, ifCfgPortIndex	FROM NTNTECH-INTERFACE-MODULE-CONFIGURATION-MIB
    OBJECT-TYPE, MODULE-IDENTITY	FROM SNMPv2-SMI
   	TEXTUAL-CONVENTION	 			FROM SNMPv2-TC;
-- ****************************************************************       
ntntechMTMMIB MODULE-IDENTITY  
    LAST-UPDATED "0410140200Z"  -- October 14, 2004
    ORGANIZATION "Paradyne Corporation"
    CONTACT-INFO
        "Paradyne Corporation
        8545 126th Avenue North
        Largo, FL 33773        
     	
        phone: +1 (727) 530-2000
        email: support@paradyne.com 
        www:   http://www.nettonet.com/support/"

    DESCRIPTION
    	 "This mib module defines an SNMP API to manage Paradyne Corporation's
         Quality of Service attributes on a per port basis."             	
  	      	    
::= { ntntechInterfaceModule 3}                 
                                                                                     
mtmMIBObjects OBJECT IDENTIFIER ::= {ntntechMTMMIB  1 }                       

------------------------------------------------------------------------------
-- DiffServ MTM Rules
------------------------------------------------------------------------------

diffServTable OBJECT-TYPE
   	SYNTAX      SEQUENCE OF DiffServEntry
   	MAX-ACCESS  not-accessible
   	STATUS      current
   	DESCRIPTION
    " This table describes objects applicable to managing a Differentiated Services
    Code Point (DSCP) Rule.  DSCP provides OSI Layer 3 identification information within
    a packet's IP header for the purpose of determining packet type.  Up to four (4) seperate
    DiffServ Rules may be configured per port. "
    ::= { mtmMIBObjects  2 }
     
diffServEntry OBJECT-TYPE
   	SYNTAX			DiffServEntry
   	MAX-ACCESS  	not-accessible
   	STATUS      	current
   	DESCRIPTION   " "
	INDEX { ifCfgSlotIndex, ifCfgPortIndex, diffServIndex }
    ::= { diffServTable 1 }

    DiffServEntry ::=
       SEQUENCE {
           	diffServIndex				INTEGER,
       		diffServActivateRule		INTEGER,
       		diffServDSValue				INTEGER,
       		diffServDSMask				INTEGER,
       		diffServAllowTagOnIngress	INTEGER,
	        diffServVlanIDStart		    INTEGER,   
        	diffServVlanIDEnd	        INTEGER,	    
       		diffServTagActionOnIngress	INTEGER,  
       		diffServReplaceVlanID		INTEGER,
		    diffServPriority			INTEGER,
			diffServFixedMaxValue		INTEGER,
			diffServIngressRateLimit	INTEGER,
			diffServEgressRateLimit	    INTEGER,
			diffServBackboneVlanID		INTEGER,
			diffServPVCIndex			INTEGER
	}
       	
    diffServIndex OBJECT-TYPE
       	SYNTAX      INTEGER (1..4)
       	MAX-ACCESS  read-only
       	STATUS      current
       	DESCRIPTION
        "A pointer to one of four possible DSCP Rules that can be assigned to a port."
    ::= { diffServEntry 1 } 
    
    diffServActivateRule  OBJECT-TYPE
    	SYNTAX   INTEGER { active(1), inactive(2) }
    	MAX-ACCESS read-write
    	STATUS current
    	DESCRIPTION
    	"Activate or deactivate the rule that is represented by the remaining attributes of this
    	table."
    ::= { diffServEntry 2 }
    
    diffServDSValue OBJECT-TYPE
       	SYNTAX      INTEGER(1..252) 
       	MAX-ACCESS  read-write
       	STATUS      current
       	DESCRIPTION
        "The value assigned to a port which designates the Differentiated Services Code Point. This 
        is a hexidecimal value calculated from the upper six (6) bits of an eight (8) bit field in 
        the packet's IP header (the remaining two[2] bits are unused).  It is one of several methods
        used to determine packet type.  Configuring this value requires knowledge of the users (desired)
        network traffic and, as such, a default value is not applicable (indicated as 00). "  
    ::= { diffServEntry 3 }  
       	
    diffServDSMask OBJECT-TYPE
       	SYNTAX      INTEGER(1..252)
       	MAX-ACCESS  read-write
       	STATUS      current
       	DESCRIPTION
        "The value assigned indicates which six (6) bits of the DSCP will be utilized in considering the 
        packets DSCP type. Default is 252, indicating that all of the DSCP's upper six bits will be used in 
        calculating the packet's DS value. "
    ::= { diffServEntry 4 }
    	
    diffServAllowTagOnIngress  OBJECT-TYPE        
		SYNTAX  INTEGER { tag(1), untag(2) }
		MAX-ACCESS  read-write
		STATUS	    current
		DESCRIPTION
		"The value assigned will determine a path for ingress packets. Tag (1) indicates that 
		only ingress packets with a vlan tag to be considered; all ingress packets without 
		a VLAN tag will be dropped. Untag (2) indicates that only ingress packets without a VLAN 
		tag will be considered.  All ingress packets with a VLAN tag will be dropped."
    ::= { diffServEntry  5 }
                        
    diffServVlanIDStart OBJECT-TYPE
       	SYNTAX      INTEGER(0..4085) 
       	MAX-ACCESS  read-write
       	STATUS      current
       	DESCRIPTION
        "If diffServAllowTagOnIngress is set to tag(1), then this value dictates the beginning of a VLAN range
        that ingress packets will be allowed to have. If diffServAllowTagOnIngress is set to untag(2), and 
        diffServTagActionOnIngress is set to add(1) then this value dictates what VLAN ID to add to all ingress
        packets."
    ::= { diffServEntry 6 }  
       	
    diffServVlanIDEnd OBJECT-TYPE
       	SYNTAX      INTEGER(0..4085)
       	MAX-ACCESS  read-write
       	STATUS      current
       	DESCRIPTION 
       	"If diffServAllowTagOnIngress is set to tag(1), then this value dictates the end of a VLAN range
        that ingress packets will be allowed to have."
    ::= { diffServEntry 7 }

	diffServTagActionOnIngress OBJECT-TYPE
		SYNTAX	INTEGER { add(1), keep(2), replace(3), drop(4), inaction(5)}
		MAX-ACCESS read-write
		STATUS   current
		DESCRIPTION
		" The value assigned will alter the VLAN information of the Ingress Packet.
		 
				1 --  Add VLAN information to the Ingress Packet
				2 --  Keep VLAN information on the Ingress Packet
				3 --  Replace VLAN information on the Ingress Packet to diffServReplaceVlanID
				4 --  Drop the Ingress Packet
				5 --  Inaction -- No Action to the VLAN information on the Ingress Packet
				
		  add(1) and inaction(5) are only valid if you have chosen untag(2) for the attribute 
		  diffServAllowTagOnIngress. keep(2) and replace(3) are only valid if tag(1) is chosen for 
		  the attribute diffServAllowTagOnIngress."
	::= { diffServEntry 8 }

   diffServReplaceVlanID OBJECT-TYPE
       	SYNTAX      INTEGER(0..4085) 
       	MAX-ACCESS  read-write
       	STATUS      current
       	DESCRIPTION
        "The value assigned dictates to which VLAN ID we will change the ingress packets VLAN ID. This attribute
        is valid only if tag(1) is chosen for diffServAllowTagOnIngress and replace(3) is chosen for
        diffServTagActionOnIngress."
	::= { diffServEntry 9 }  

    diffServPriority  OBJECT-TYPE      
		SYNTAX       INTEGER (0..7)
		MAX-ACCESS   read-write
		STATUS	     current
		DESCRIPTION
		" The value assigned to a port which indicates VLAN priority. This priority is relevant
		both within the DSLAM and at egress. "
	::= { diffServEntry 10 }

    diffServFixedMaxValue OBJECT-TYPE
		SYNTAX       INTEGER { fixed(1), max(2) }
		MAX-ACCESS   read-write   
		STATUS       current	
        DESCRIPTION
		" The value assigned dictates the action to be taken with the configured diffServPriority 
		for tagged ingress packets. The default value is fixed(1). If set to fixed(1), the packet's ingress 
		priority will automatically be replaced with the diffServPriority.  If set to max(2), the packet's
		ingress priority will only be replaced with the diffServPriority if the packet's ingress priority
		is higher than the diffServPriority."
    ::= { diffServEntry  11 }

    diffServIngressRateLimit OBJECT-TYPE
		SYNTAX       INTEGER
		MAX-ACCESS   read-write
		STATUS       current
		DESCRIPTION
		" The value assigned allows traffic-specific, rule-specific, bandwidth limits for each port. 
		The unit of measure is kbps.  The default value is 0 (no limit)."
	::= { diffServEntry 12 }

    diffServEgressRateLimit OBJECT-TYPE
		SYNTAX       INTEGER
		MAX-ACCESS   read-write
		STATUS	     current
		DESCRIPTION
		" The value assigned allows traffic-specific, rule-specific, bandwidth limits for each port.
		The unit of measure is kbps.  The default value is 0 (no limit)."
    ::= { diffServEntry 13 }
                                   
  	diffServBackboneVlanID  OBJECT-TYPE
		SYNTAX INTEGER(0..4085) 
		MAX-ACCESS read-write
		STATUS current
		DESCRIPTION 
		"The value assigned will dictate what VLAN ID we add as the Q-in-Q VLAN ID to all ingress traffic
		passing this diffserv rule set."
	::= { diffServEntry 14 }       
                            
	diffServPVCIndex  OBJECT-TYPE
 		SYNTAX 	INTEGER(1..4)
		MAX-ACCESS read-write
		STATUS 	current
		DESCRIPTION
		" The value assigned describes a PVC index that the ingress traffic defined by this diffServ rule
		is expected to be received on."
  	::= { diffServEntry 15 }
  	
------------------------------------------------------------------------------
-- IpRange MTM Rules
------------------------------------------------------------------------------
 	
ipRangeTable OBJECT-TYPE
   	SYNTAX      SEQUENCE OF IPRangeEntry
   	MAX-ACCESS  not-accessible
   	STATUS      current
   	DESCRIPTION
    "This table defines MTM rules associated with an IP Address or an IP Address Range.  Up to 
    four (4) seperate IP Range Rules may be configured per port. "
    ::= { mtmMIBObjects  4 }
     
ipRangeEntry OBJECT-TYPE
   	SYNTAX			IPRangeEntry
   	MAX-ACCESS  	not-accessible
   	STATUS      	current
   	DESCRIPTION
    "An entry containing management information applicable to an IPD12000, IPD4000 
    Access/Inverse module and Mini/Micro DSLAM port."
    INDEX   { ifCfgSlotIndex, ifCfgPortIndex, ipRangeIndex }
    ::= { ipRangeTable 1 }

    IPRangeEntry ::=                	
       SEQUENCE {
           	ipRangeIndex				INTEGER,  
           	ipRangeActivateRule			INTEGER,
       		ipRangeStart				NtnIpAddress,   
        	ipRangeEnd					NtnIpAddress,	    
       		ipRangeAllowTagOnIngress	INTEGER,
            ipRangeVlanIDStart			INTEGER,
            ipRangeVlanIDEnd			INTEGER,
       		ipRangeTagActionOnIngress	INTEGER,
		    ipRangePriority				INTEGER,
			ipRangeFixedMaxValue		INTEGER,
			ipRangeIngressRateLimit		INTEGER,
			ipRangeEgressRateLimit		INTEGER,
			ipRangeBackboneVlanID		INTEGER,
			ipRangePVCIndex				INTEGER
	}
         	
    ipRangeIndex OBJECT-TYPE
       	SYNTAX      INTEGER (1..4)
       	MAX-ACCESS  read-only
       	STATUS      current
       	DESCRIPTION
        "A pointer to one of four possible IP Range Rules that can be assigned to a port."
    ::= { ipRangeEntry 1 }                
    
    ipRangeActivateRule  OBJECT-TYPE
    	SYNTAX   INTEGER { active(1), inactive(2) }
    	MAX-ACCESS read-write
    	STATUS current
    	DESCRIPTION
    	"Setting this value, activates the rule that is represented by the remaining attributes of this
    	table."
    ::= { ipRangeEntry 2 }
    	                        
    ipRangeStart OBJECT-TYPE
       	SYNTAX      NtnIpAddress
       	MAX-ACCESS  read-write
       	STATUS      current
       	DESCRIPTION
        "The value assigned to a port which designates the start of an IP range. Packets 
        containing a source and/or desitination IP address that falls within the configured
        range will match the IP portion of the IP Range Rule. Default is 0.0.0.0. "
    ::= { ipRangeEntry 3 }  
       	
    ipRangeEnd OBJECT-TYPE
       	SYNTAX      NtnIpAddress
       	MAX-ACCESS  read-write
       	STATUS      current
       	DESCRIPTION
        "The value assigned to a port which designates the end of an IP range.  Packets containing a 
        source and/or destination IP address that falls within the configured range will match the IP
        portion of the IP Range Rule.  Default is 0.0.0.0. "
    ::= { ipRangeEntry 4 }
    
    ipRangeAllowTagOnIngress  OBJECT-TYPE      
		SYNTAX  INTEGER { tag(1), untag(2) }
		MAX-ACCESS  read-write
		STATUS	    current
		DESCRIPTION
		"The value assigned will determine a path for ingress packets. Tag indicates that 
		only ingress packets with a vlan tag to be considered; all ingress packets without 
		a VLAN tag will be dropped. Untag indicates that only ingress packets without a VLAN 
		tag will be considered.  All ingress packets with a VLAN tag will be dropped."
    ::= { ipRangeEntry  5 }
        
    ipRangeVlanIDStart OBJECT-TYPE
       	SYNTAX      INTEGER(0..4085) 
       	MAX-ACCESS  read-write
       	STATUS      current
       	DESCRIPTION
        "The value assigned to a port which designates the start of a VLAN ID range. This 
        should only be defined if vlanRulesAllowTagOnIngress is set to tag (1). "
    ::= { ipRangeEntry 6 }  
       	
    ipRangeVlanIDEnd OBJECT-TYPE
       	SYNTAX      INTEGER(0..4085)
       	MAX-ACCESS  read-write
       	STATUS      current
       	DESCRIPTION
        "The value assigned to a port which designates the end of a VLAN ID range. This 
        should only be defined if vlanRulesAllowTagOnIngress is set to tag (1). "
    ::= { ipRangeEntry 7 }
                                                                                       
	ipRangeTagActionOnIngress  OBJECT-TYPE
		SYNTAX	INTEGER { add(1), keep(2), replace(3), drop(4), inaction(5)}
		MAX-ACCESS read-write
		STATUS   current
		DESCRIPTION
		" The value assigned will alter the VLAN information of the Ingress Packet.    
		
				1 --  Add VLAN information to the Ingress Packet
				2 --  Keep VLAN information on the Ingress Packet
				3 --  Replace VLAN information on the Ingress Packet      
				4 --  Drop the Ingress Packet
				5 --  Inaction -- No Action to the VLAN information on the Ingress Packet
				
		  Add (1) and No Action (5) are only valid if you have chosen Untag (2) for the attribute 
		  ipRangeAllowTagOnIngress. Keep(2) and Replace(3) are only valid if Tag (1) is chosen for 
		  the attribute ipRangeAllowTagOnIngress."
		
	::= { ipRangeEntry 8 }

    ipRangePriority  OBJECT-TYPE      
		SYNTAX       INTEGER (0..7)
		MAX-ACCESS   read-write
		STATUS	     current
		DESCRIPTION
		" The value assigned to a port which indicates priority. This priority is relevant
		both within the DSLAM and at egress. "
	::= { ipRangeEntry 9 }

    ipRangeFixedMaxValue OBJECT-TYPE
		SYNTAX       INTEGER { fixed(1), max(2) }
		MAX-ACCESS   read-write   
		STATUS       current	
        DESCRIPTION
		" The value assigned dictates the action to be taken with the configured ipRangePriority 
		for tagged ingress packets. The default value is fixed.If set to Fixed, the packet's ingress 
		priority will automatically be replaced with the ipRangeRulePriority.  If set to Max, the packet's
		ingress priority will only be replaced with the ipRangeRulePriority if the packet's ingress priority
		is higher than the ipRangeRulePriority."
    ::= { ipRangeEntry  10 }

    ipRangeIngressRateLimit OBJECT-TYPE
		SYNTAX       INTEGER
		MAX-ACCESS   read-write
		STATUS       current
		DESCRIPTION
		" The value assigned allows traffic-specific, rule-specific, bandwidth limits for each port. 
		The unit of measure is kbps.  The default value is 0 (no limit)."
	::= { ipRangeEntry 11 }

    ipRangeEgressRateLimit OBJECT-TYPE
		SYNTAX       INTEGER
		MAX-ACCESS   read-write
		STATUS	     current
		DESCRIPTION
		" The value assigned allows traffic-specific, rule-specific, bandwidth limits for each port.
		The unit of measure is kbps.  The default value is 0 (no limit)."
    ::= { ipRangeEntry 12 }         

  	ipRangeBackboneVlanID  OBJECT-TYPE
		SYNTAX INTEGER(0..4085)
		MAX-ACCESS read-write
		STATUS current
		DESCRIPTION " "
	::= { ipRangeEntry 13 }       

	ipRangePVCIndex  OBJECT-TYPE
 		SYNTAX 	INTEGER(1..4)
		MAX-ACCESS read-write
		STATUS 	current
		DESCRIPTION
		" The value assigned describes a PVC that is assigned to this port for MTM purposes."
  	::= { ipRangeEntry 14 }
  
------------------------------------------------------------------------------
-- Mac Address Range MTM Rules
------------------------------------------------------------------------------

macAddrRangeTable OBJECT-TYPE
   	SYNTAX      SEQUENCE OF MacAddrRangeEntry
   	MAX-ACCESS  not-accessible
   	STATUS      current
   	DESCRIPTION
    "This table defines MTM rules associated with a Mac Address or Mac Address Range.  These rules can be 
    established on a per port basis. Up to four (4) seperate Mac Address Rules may be configured per port."
    ::= { mtmMIBObjects  6 }
     
macAddrRangeEntry OBJECT-TYPE
  	SYNTAX			MacAddrRangeEntry
    MAX-ACCESS  	not-accessible
   	STATUS      	current
   	DESCRIPTION
    "An entry containing management information applicable to an IPD12000, IPD4000 
    Access/Inverse module and Mini/Micro DSLAM port."
    INDEX   { ifCfgSlotIndex, ifCfgPortIndex, macAddrIndex }
    ::= { macAddrRangeTable 1 }

    MacAddrRangeEntry ::=
      SEQUENCE {
          macAddrRangeIndex			    INTEGER,
          macAddrRangeActivateRule		INTEGER,
	      macAddrRangeStart		    	NtnMacAddress,   
          macAddrRangeEnd				NtnMacAddress,	    
       	  macAddrRangeAllowTagOnIngress	INTEGER,
       	  macAddrRangeVlanIDStart		INTEGER,
       	  macAddrRangeVlanIDEnd			INTEGER,
       	  macAddrRangeTagActionOnIngress INTEGER,
		  macAddrRangePriority			INTEGER,
	      macAddrRangeFixedMaxValue		INTEGER,
	      macAddrRangeIngressRateLimit	INTEGER,
	      macAddrRangeEgressRateLimit	INTEGER,
		  macAddrRangeBackboneVlanID	INTEGER,
		  macAddrRangePVCIndex			INTEGER
	} 
      	
	macAddrRangeIndex OBJECT-TYPE
       	SYNTAX      INTEGER (1..4)
      	MAX-ACCESS  read-only
        STATUS      current
    	DESCRIPTION
        "A pointer to one of four possible Mac Address Rules that can be assigned to a port."
	::= { macAddrRangeEntry 1 } 
 
	macAddrRangeActivateRule  OBJECT-TYPE
		SYNTAX    INTEGER { active(1), inactive(2)} 
  		MAX-ACCESS read-write
    	STATUS current
		DESCRIPTION
  	    "Setting this value, activates the rule that is represented by the remaining attributes of this
    	table."
    ::= { macAddrRangeEntry 2 }
    	                          
	macAddrRangeStart OBJECT-TYPE
         SYNTAX      NtnMacAddress
         MAX-ACCESS  read-write
         STATUS      current
         DESCRIPTION
            "The value assigned to a port which designates the start of a MAC Address range. This 
             should only be defined if macaddrAllowTagOnIngress is set to tag. "
	::= { macAddrRangeEntry 3 }  
       	
	macAddrRangeEnd OBJECT-TYPE
        SYNTAX      NtnMacAddress
        MAX-ACCESS  read-write
     	STATUS      current
        DESCRIPTION
           "The value assigned to a port which designates the end of a MAC Address range. This should 
            only be defined if macaddrAllowTagOnIngress is set to tag. "
	::= { macAddrRangeEntry 4 }               
 
	macAddrRangeAllowTagOnIngress  OBJECT-TYPE        
         SYNTAX   INTEGER { tag(1), untag(2) }
         MAX-ACCESS  read-write
         STATUS	    current
         DESCRIPTION
    	"The value assigned will determine a path for ingress packets. Tag(1) indicates that 
    	only ingress packets with a vlan tag to be considered; all ingress packets without 
        a VLAN tag will be dropped. Untag(2) indicates that only ingress packets without a VLAN 
        tag will be considered.  All ingress packets with a VLAN tag will be dropped."
    ::= { macAddrRangeEntry  5 }

	macAddrRangeVlanIDStart OBJECT-TYPE
       	SYNTAX      INTEGER(0..4085) 
       	MAX-ACCESS  read-write
       	STATUS      current
       	DESCRIPTION
        "The value assigned to a port which designates the start of a VLAN ID range. This 
        should only be defined if vlanRulesAllowTagOnIngress is set to tag (1). "
    ::= { macAddrRangeEntry 6 }  
       	
    macAddrRangeVlanIDEnd OBJECT-TYPE
       	SYNTAX      INTEGER(0..4085)
       	MAX-ACCESS  read-write
       	STATUS      current
       	DESCRIPTION
        "The value assigned to a port which designates the end of a VLAN ID range. This 
        should only be defined if vlanRulesAllowTagOnIngress is set to tag (1). "  
	::= { macAddrRangeEntry 7 }

	macAddrRangeTagActionOnIngress  OBJECT-TYPE 
		SYNTAX	INTEGER { add(1), keep(2), replace(3), drop(4), inaction(5)}
		MAX-ACCESS read-write
        STATUS   current
        DESCRIPTION
          " The value assigned will alter the VLAN information of the Ingress Packet.          
	          	1 --  Add VLAN information to the Ingress Packet
				2 --  Keep VLAN information on the Ingress Packet
				3 --  Replace VLAN information on the Ingress Packet      
				4 --  Drop the Ingress Packet
				5 --  Inaction -- No Action to the VLAN information on the Ingress Packet
				
		  Add (1) and No Action (5) are only valid if you have chosen Untag (2) for the attribute 
		  macAddrAllowTagOnIngress.Keep(2) and Replace(3) are only valid if Tag (1) is chosen for 
		  the attribute macAddrAllowTagOnIngress "
		
	::= { macAddrRangeEntry 8 }

	macAddrRangePriority  OBJECT-TYPE      
         SYNTAX       INTEGER (0..7)
         MAX-ACCESS   read-write
         STATUS	     current
         DESCRIPTION
		" The value assigned to a port which indicates VLAN priority. This priority is relevant
		both within the DSLAM and at egress. "
    ::= { macAddrRangeEntry 9 }

	macAddrRangeFixedMaxValue OBJECT-TYPE
         SYNTAX       INTEGER{ fixed(1), max(2) }
         MAX-ACCESS   read-write   
         STATUS       current	
         DESCRIPTION
		" The value assigned dictates the action to be taken with the configured macaddrPriority 
		for tagged ingress packets. The default value is fixed. If set to Fixed, the packet's ingress 
		priority will automatically be replaced with the macAddrPriority.  If set to Max, the packet's
		ingress priority will only be replaced with the macAddrPriority if the packet's ingress priority
		is higher than the Mac Address Rule Priority."
	::= { macAddrRangeEntry  10 }

	macAddrRangeIngressRateLimit OBJECT-TYPE
		SYNTAX       INTEGER
		MAX-ACCESS   read-write
		STATUS       current
		DESCRIPTION
		" The value assigned allows traffic-specific, rule-specific, bandwidth limits for each port. 
		The unit of measure is kbps.  The default value is 0 (no limit)."
	::= { macAddrRangeEntry 11 }

	macAddrRangeEgressRateLimit OBJECT-TYPE
		SYNTAX       INTEGER
		MAX-ACCESS   read-write
		STATUS	     current
		DESCRIPTION
		" The value assigned allows traffic-specific, rule-specific, bandwidth limits for each port.
		The unit of measure is kbps.  The default value is 0 (no limit)."
	::= { macAddrRangeEntry 12 }         
                                                  
	macAddrRangeBackboneVlanID  OBJECT-TYPE
		SYNTAX INTEGER(0..4085)
		MAX-ACCESS read-write
		STATUS current
		DESCRIPTION " "
	::= { macAddrRangeEntry 13 }       

	macAddrRangePVCIndex  OBJECT-TYPE
 		SYNTAX 	INTEGER(1..4)
		MAX-ACCESS read-write
		STATUS 	current
		DESCRIPTION
		" The value assigned describes a PVC that is assigned to this port for MTM purposes."
  	::= { macAddrRangeEntry 14 }
 
------------------------------------------------------------------------------
-- VLAN MTM Rules
------------------------------------------------------------------------------
                             
vlanRulesTable OBJECT-TYPE
   	SYNTAX      SEQUENCE OF VLANRulesEntry
   	MAX-ACCESS  not-accessible
   	STATUS      current
   	DESCRIPTION
    " This table defines MTM rules associated with a VLAN or a VLAN Range.  These rules can be 
    established on a per port basis. Up to ten (10) seperate VLAN Rules may be configured per port."
    ::= { mtmMIBObjects  8 }
     
vlanRulesEntry OBJECT-TYPE
   	SYNTAX			VLANRulesEntry
   	MAX-ACCESS  	not-accessible
   	STATUS      	current
   	DESCRIPTION
    "An entry containing management information applicable to an IPD12000, IPD4000 
    Access/Inverse module and Mini/Micro DSLAM port."
    INDEX   { ifCfgSlotIndex, ifCfgPortIndex, vlanRulesVLANIndex }
    ::= { vlanRulesTable 1 }

    VLANRulesEntry ::=
       SEQUENCE {
           	vlanRulesVLANIndex			INTEGER, 
           	vlanRulesActivateRule	 	INTEGER,
       		vlanRulesAllowTagOnIngress	INTEGER,
	        vlanRulesVLANIdStart		INTEGER,   
        	vlanRulesVLANIdEnd			INTEGER,	    
       		vlanRulesTagActionOnIngress	INTEGER,
		    vlanRulesPriority			INTEGER,
			vlanRulesFixedMaxValue		INTEGER,
			vlanRulesIngressRateLimit	INTEGER,
			vlanRulesEgressRateLimit	INTEGER,
			vlanRulesBackboneVlanID		INTEGER,
			vlanRulesPVCIndex			INTEGER
	}
       	
    vlanRulesVLANIndex OBJECT-TYPE
       	SYNTAX      INTEGER (1..10)
       	MAX-ACCESS  read-only
       	STATUS      current
       	DESCRIPTION
        "A pointer to one of ten possible VLAN Rules that can be assigned to a port."
    ::= { vlanRulesEntry 1 } 
                        
    vlanRulesActivateRule  OBJECT-TYPE
    	SYNTAX    INTEGER { active(1), inactive(2) }

    	MAX-ACCESS read-write
    	STATUS current
    	DESCRIPTION
    	"Setting this value, activates the rule that is represented by the remaining attributes of this
    	table."
    ::= { vlanRulesEntry 2 }
    	
    vlanRulesAllowTagOnIngress  OBJECT-TYPE        
		SYNTAX    INTEGER { tag(1), untag(2) }
		MAX-ACCESS  read-write
		STATUS	    current
		DESCRIPTION
		"The value assigned will determine a path for ingress packets. Tag indicates that 
		only ingress packets with a vlan tag to be considered; all ingress packets without 
		a VLAN tag will be dropped. Untag indicates that only ingress packets without a VLAN 
		tag will be considered.  All ingress packets with a VLAN tag will be dropped."
    ::= { vlanRulesEntry  3 }
                        
    vlanRulesVLANIdStart OBJECT-TYPE
       	SYNTAX      INTEGER (0..4085)
       	MAX-ACCESS  read-write
       	STATUS      current
       	DESCRIPTION
        "The value assigned to a port which designates the start of a VLAN ID range. This 
        should only be defined if vlanRulesAllowTagOnIngress is set to tag. "
    ::= { vlanRulesEntry 4 }  
       	
    vlanRulesVLANIdEnd OBJECT-TYPE
       	SYNTAX      INTEGER (0..4085)
       	MAX-ACCESS  read-write
       	STATUS      current
       	DESCRIPTION
        "The value assigned to a port which designates the end of a VLAN ID range. This should 
        only be defined if vlanRulesAllowTagOnIngress is set to tag. "
    ::= { vlanRulesEntry 5 }

	vlanRulesTagActionOnIngress  OBJECT-TYPE
		SYNTAX	INTEGER {add(1), keep(2), replace(3), drop(4), noAction(5)}
		MAX-ACCESS read-write
		STATUS   current
		DESCRIPTION
		" The value assigned will allow VLAN information to be added to the Ingress Packet. 
			
		        1 --  Add VLAN information to the Ingress Packet
				2 --  Keep VLAN information on the Ingress Packet
				3 --  Replace VLAN information on the Ingress Packet  
				4 --  Drop the Ingress Packet
				5 --  Inaction -- No Action to the VLAN information on the Ingress Packet
				
		  Add (1) and No Action (5) are only valid if you have chosen Untag (2) for the attribute 
		  vlanRulesAllowTagOnIngress.Keep(2) and Replace(3) are only valid if Tag (1) is chosen for 
		  the attribute vlanRulesAllowTagOnIngress. "
		  
	::= { vlanRulesEntry 6 }

    vlanRulesPriority  OBJECT-TYPE      
		SYNTAX       INTEGER (0..7)
		MAX-ACCESS   read-write
		STATUS	     current
		DESCRIPTION
		" The value assigned to a port which indicates VLAN priority. This priority is relevant
		both within the DSLAM and at egress. "
	::= { vlanRulesEntry 7 }

    vlanRulesFixedMaxValue OBJECT-TYPE
		SYNTAX       INTEGER { fixed(1), max(2) }
		MAX-ACCESS   read-write   
		STATUS       current	
        DESCRIPTION
		" The value assigned dictates the action to be taken with the configured vlanRulesPriority 
		for tagged ingress packets. The default value is fixed. If set to Fixed, the packet's ingress 
		priority will automatically be replaced with the vlanRulesPriority.  If set to Max, the packet's
		ingress priority will only be replaced with the vlanRulesPriority if the packet's ingress priority
		is higher than the vlanRulesPriority."
    ::= { vlanRulesEntry  8 }

    vlanRulesIngressRateLimit OBJECT-TYPE
		SYNTAX       INTEGER
		MAX-ACCESS   read-write
		STATUS       current
		DESCRIPTION
		" The value assigned allows traffic-specific, rule-specific, bandwidth limits for each port. 
		The unit of measure is kbps.  The default value is 0 (no limit)."
	::= { vlanRulesEntry 9 }

    vlanRulesEgressRateLimit OBJECT-TYPE
		SYNTAX       INTEGER
		MAX-ACCESS   read-write
		STATUS	     current
		DESCRIPTION
		" The value assigned allows traffic-specific, rule-specific, bandwidth limits for each port.
		The unit of measure is kbps.  The default value is 0 (no limit)."
    ::= { vlanRulesEntry 10 }                    
    
	vlanRulesBackboneVlanID  OBJECT-TYPE
		SYNTAX INTEGER(0..4085)
		MAX-ACCESS read-write
		STATUS current
		DESCRIPTION " "
	::= { vlanRulesEntry 11 }       

	vlanRulesPVCIndex  OBJECT-TYPE
 		SYNTAX 	INTEGER(1..4)
		MAX-ACCESS read-write
		STATUS 	current
		DESCRIPTION
		" The value assigned describes a PVC that is assigned to this port for MTM purposes.	"
	::= { vlanRulesEntry 12 }
   
  
END
