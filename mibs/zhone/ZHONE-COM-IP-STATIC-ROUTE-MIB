--
-- comIpStaticRoute.mib
-- MIB generated by MG-SOFT Visual MIB Builder Version 3.0 Build 285
-- Tuesday, July 18, 2006 at 13:46:06
--

    ZHONE-COM-IP-STATIC-ROUTE-MIB DEFINITIONS ::= BEGIN
 
        IMPORTS
            InterfaceIndexOrZero            
                FROM IF-MIB            
            IpAddress, Integer32, Unsigned32, OBJECT-TYPE, MODULE-IDENTITY, 
            OBJECT-IDENTITY            
                FROM SNMPv2-SMI            
            rdIndex            
                FROM ZHONE-COM-IP-RD-MIB            
            zhoneIp, zhoneModules            
                FROM Zhone            
            ZhoneRowStatus            
                FROM Zhone-TC;
    
    
-- Issues:
--    - Should there be a field specifying the configurability of the
--      static route.  In other words, are there static routes that
--      cannot be modified or deleted, such as ones that are created
--      upon configuring an interface?
-- 
-- 
        -- 1.3.6.1.4.1.5504.6.63
        comIpStaticRoute MODULE-IDENTITY 
            LAST-UPDATED "200607141700Z"		-- July 14, 2006 at 17:00 GMT
            ORGANIZATION 
                "Zhone Technologies, Inc."
            CONTACT-INFO 
                "  Postal: 
                           Zhone Technologies, Inc.
                           @ Zhone Way
                           7001 Oakport Street
                           Oakland, CA  94621
                           USA
                Toll-Free: +1 877-ZHONE20 (+1 877-946-6320)
                      Tel: +1-510-777-7000
                      Fax: +1-510-777-7001
                   E-mail: support@zhone.com"
            DESCRIPTION 
                "IP Static Route MIB
                IP Software
                Minneapolis, MN"
            REVISION "200607141550Z"		-- July 14, 2006 at 15:50 GMT
            DESCRIPTION 
                "V01.00.02 - added staticRouteFallbackMatric,
                staticRoutePingInterval, and staticRoutePingFailMax."
            REVISION "200504291410Z"		-- April 29, 2005 at 14:10 GMT
            DESCRIPTION 
                "V01.00.02 - Added staticRouteType."
            REVISION "200009121023Z"		-- September 12, 2000 at 10:23 GMT
            DESCRIPTION 
                "V01.00.00 - Initial Release"
            REVISION "200009291634Z"		-- September 29, 2000 at 16:34 GMT
            DESCRIPTION 
                "V01.00.01 - Zhone keyword markup"
            ::= { zhoneModules 63 }

        
    
    
--
-- Node definitions
--
    
        -- 1.3.6.1.4.1.5504.4.1.13
        staticRoute OBJECT-IDENTITY
            STATUS current
            DESCRIPTION 
                "The MIB module representing static routes in Zhone
                Technologies products.  Static routes are user-defined routes
                that cause packets moving between a source and a destination
                to take a specified path.  Static routes can be important
                if a router cannot build a route to a particular destination.
                They are also useful for specifying a gateway of last resort
                to which all unroutable packets will be sent."
            ::= { zhoneIp 13 }

        
        -- 1.3.6.1.4.1.5504.4.1.13.1
        staticRouteTable OBJECT-TYPE
            SYNTAX SEQUENCE OF StaticRouteEntry
            MAX-ACCESS not-accessible
            STATUS current
            DESCRIPTION
                "The Static Routes table contains static routes assigned
                to all interfaces.  Each interface automatically gets
                one or more static routes upon interface initialization.
                More static routes are added as needed (e.g. default gateway).
                Rows are added by assigning staticRouteDest, staticRouteNetMask,
                staticRouteNextHop (or staticRouteIfNumber), and setting
                staticRouteRowStatus to 'createAndGo'.  Rows are removed
                by setting staticRouteRowStatus to 'destroy'."
            ::= { staticRoute 1 }

        
        -- 1.3.6.1.4.1.5504.4.1.13.1.1
        staticRouteEntry OBJECT-TYPE
            SYNTAX StaticRouteEntry
            MAX-ACCESS not-accessible
            STATUS current
            DESCRIPTION
                "An entry in the Static Route table."
            INDEX { rdIndex, staticRouteDest, staticRouteNetMask, staticRouteNextHop, staticRouteIfNumber, 
                staticRouteType }
            ::= { staticRouteTable 1 }

        
        StaticRouteEntry ::=
            SEQUENCE { 
                staticRouteDest
                    IpAddress,
                staticRouteNetMask
                    IpAddress,
                staticRouteNextHop
                    IpAddress,
                staticRouteIfNumber
                    InterfaceIndexOrZero,
                staticRouteMetric
                    Unsigned32,
                staticRouteEnable
                    INTEGER,
                staticRouteRowStatus
                    ZhoneRowStatus,
                staticRouteType
                    INTEGER,
                staticRouteFallbackMetric
                    Integer32,
                staticRoutePingInterval
                    Unsigned32,
                staticRoutePingFailMax
                    Integer32
             }

        -- 1.3.6.1.4.1.5504.4.1.13.1.1.1
        staticRouteDest OBJECT-TYPE
            SYNTAX IpAddress
            MAX-ACCESS not-accessible
            STATUS current
            DESCRIPTION
                "The destination network or host IP address of the static route.
                A default gateway is one with a destination of 0.0.0.0 and
                netmask 0.0.0.0."
            ::= { staticRouteEntry 1 }

        
        -- 1.3.6.1.4.1.5504.4.1.13.1.1.2
        staticRouteNetMask OBJECT-TYPE
            SYNTAX IpAddress
            MAX-ACCESS not-accessible
            STATUS current
            DESCRIPTION
                "The destination IP network mask of the static route.
                A default gateway is one with a destination of 0.0.0.0 and
                netmask 0.0.0.0."
            ::= { staticRouteEntry 2 }

        
        -- 1.3.6.1.4.1.5504.4.1.13.1.1.3
        staticRouteNextHop OBJECT-TYPE
            SYNTAX IpAddress
            MAX-ACCESS not-accessible
            STATUS current
            DESCRIPTION
                "The IP address of the nexthop router of the static route.
                This may be 0.0.0.0 for static routes that use an interface
                number rather than a nexthop address, as in the case of a
                destination directly reachable via an interface requiring
                no intermediary system to act as a gateway."
            ::= { staticRouteEntry 3 }

        
        -- 1.3.6.1.4.1.5504.4.1.13.1.1.4
        staticRouteIfNumber OBJECT-TYPE
            SYNTAX InterfaceIndexOrZero
            MAX-ACCESS not-accessible
            STATUS current
            DESCRIPTION
                "The interface of the static route.  This is for directly
                connected destinations (i.e. use this instead of
                staticRouteNextHop).  Unnumbered point-to-point interfaces
                require this value to be valid.  In general, this value must
                be valid if staticRouteNextHop is not valid.  If
                staticRouteNextHop is valid, then this value must represent
                the interface named by the nexthop address.  This index comes
                from ifIndex of RFC2233."
            ::= { staticRouteEntry 4 }

        
        -- 1.3.6.1.4.1.5504.4.1.13.1.1.5
        staticRouteMetric OBJECT-TYPE
            SYNTAX Unsigned32
            MAX-ACCESS read-create
            STATUS current
            DESCRIPTION
                "A dimensionless quantity chosen at the discretion of the
                provisioner for the purpose of comparing static routes.
                The meaning of this value when static routes are redistributed
                to other protocols is protocol-dependent, and the resulting
                value after redistribution is determined by the route-maps
                in use for that protocol.  Lower numeric values for this
                number indicate more preferred routes."
            DEFVAL { 2147483647 }
            ::= { staticRouteEntry 5 }

        
        -- 1.3.6.1.4.1.5504.4.1.13.1.1.6
        staticRouteEnable OBJECT-TYPE
            SYNTAX INTEGER
                {
                disabled(1),
                enabled(2)
                }
            MAX-ACCESS read-create
            STATUS current
            DESCRIPTION
                "An enumeration of the administrative state of the static route.
                The possible values are either 'disabled' or 'enabled',
                where the static route entry is not considered when making
                forwarding decisions for 'disabled', and is so for 'enabled'.
                The default is 'enabled'."
            DEFVAL { enabled }
            ::= { staticRouteEntry 6 }

        
        -- 1.3.6.1.4.1.5504.4.1.13.1.1.7
        staticRouteRowStatus OBJECT-TYPE
            SYNTAX ZhoneRowStatus
            MAX-ACCESS read-create
            STATUS current
            DESCRIPTION
                "The status of a static route entry."
            ::= { staticRouteEntry 7 }

        
        -- 1.3.6.1.4.1.5504.4.1.13.1.1.8
        staticRouteType OBJECT-TYPE
            SYNTAX INTEGER
                {
                destinationRoute(1),
                sourceRoute(2)
                }
            MAX-ACCESS not-accessible
            STATUS current
            DESCRIPTION
                "Determines if this entry is a traditional
                destination route or a source address based
                route.
                "
            ::= { staticRouteEntry 8 }

        
        -- 1.3.6.1.4.1.5504.4.1.13.1.1.9
        staticRouteFallbackMetric OBJECT-TYPE
            SYNTAX Integer32
            MAX-ACCESS read-create
            STATUS current
            DESCRIPTION
                "This object contains the fallback metric value for routes that
                are a part of a fallback route pair. Please refer to the Zhone
                Technologies User's Reference Manual for more information about
                fallback route pairs. The value of this object must be greater 
                than both of the staticRouteMetrics of fallback route pair.
                "
            DEFVAL { '0'b }
            ::= { staticRouteEntry 9 }

        
        -- 1.3.6.1.4.1.5504.4.1.13.1.1.10
        staticRoutePingInterval OBJECT-TYPE
            SYNTAX Unsigned32
            MAX-ACCESS read-create
            STATUS current
            DESCRIPTION
                "This object defines the interval, in milliseconds, of
                succesive pings of the nexthop of an active fallback route
                pair. The minimum value is 500 milliseconds, and must be
                specified in increments of 100 milliseconds.
                "
            DEFVAL { 0 }
            ::= { staticRouteEntry 10 }

        
        -- 1.3.6.1.4.1.5504.4.1.13.1.1.11
        staticRoutePingFailMax OBJECT-TYPE
            SYNTAX Integer32
            MAX-ACCESS read-create
            STATUS current
            DESCRIPTION
                "This object contain the maximum number of times that the ping
                of the nexthop of an active route in a fallback route pair 
                must fail, in a row, before this route is demoted to fallback
                and the other route in the fallback pair becomes the active 
                route."
            DEFVAL { 0 }
            ::= { staticRouteEntry 11 }

        
    
    END

--
-- comIpStaticRoute.mib
--
