-- =============================================================================
-- Copyright (C) 2003 Paradyne Corporation.
-- =============================================================================

PDN-IP-MULTICAST-MIB DEFINITIONS ::= BEGIN

IMPORTS
    MODULE-IDENTITY, OBJECT-TYPE
        FROM SNMPv2-SMI
    OBJECT-GROUP, MODULE-COMPLIANCE
        FROM SNMPv2-CONF
    SwitchState
        FROM PDN-TC
    pdn-common
        FROM PDN-HEADER-MIB;
        
pdnIpMcastMIB MODULE-IDENTITY
    LAST-UPDATED "200305010000Z"  -- May 1, 2003
    ORGANIZATION "Paradyne Networks
                  MIB Working Group
                  Other information about group editing the MIB."
    CONTACT-INFO "Paradyne Networks, Inc.
                  8545 126th Avenue North
                  Largo, FL 33733
                  www.paradyne.com
        
                  General Comments to: mibwg_team@paradyne.com

                  Editor(s)
                        Clay Sikes"

    DESCRIPTION
        "This MIB contains the objects pertaining to the configuration and 
        maintenance of the Internet Group Management Protocol (IGMP) and
        IP Multicast related operation in Paradyne devices."
        

    REVISION "200305010000Z"  -- May 1, 2003
    DESCRIPTION "Initial release."


::=  { pdn-common 48 }


pdnIpMcastNotifications OBJECT IDENTIFIER ::= { pdnIpMcastMIB 0 }
pdnIpMcastObjects       OBJECT IDENTIFIER ::= { pdnIpMcastMIB 1 }
pdnIpMcastAFNs          OBJECT IDENTIFIER ::= { pdnIpMcastMIB 2 }
pdnIpMcastConformance   OBJECT IDENTIFIER ::= { pdnIpMcastMIB 3 }

pdnIgmpProxy            OBJECT IDENTIFIER ::= { pdnIpMcastObjects 1 }
pdnIpMcastStats         OBJECT IDENTIFIER ::= { pdnIpMcastObjects 2 }
 

-- =============================================================================
-- == IGMP Proxy Objects                                                      ==
-- ==      IGMP Proxy is a process where a Paradyne device performs one or    ==
-- ==      more of the following:                                             ==
-- ==          1. Acts like a router by transmitting IGMP Query messages      ==
-- ==             towards hosts attached to one or more of its interfaces.    ==
-- ==          2. Acts like a host by transmitting IGMP Reports towards a     ==
-- ==             router attached to one of its interfaces.                   ==
-- ==          3. Acts like a host by transmitting IGMP Leaves towards a      ==
-- ==             router attached to one of its interfaces.                   ==
-- =============================================================================

pdnIgmpProxyEnableDisable  OBJECT-TYPE
    SYNTAX      SwitchState
    MAX-ACCESS  read-write
    STATUS      current
    DESCRIPTION "This object enables or disables IGMP Proxy."
    DEFVAL      { disabled }
    ::= { pdnIgmpProxy 1 }

pdnIgmpProxyReportSummaryEnableDisable  OBJECT-TYPE
    SYNTAX      SwitchState
    MAX-ACCESS  read-write
    STATUS      current
    DESCRIPTION "This object enables or disables the summarization of all 
                report messages into a single report message."
    DEFVAL      { disabled }
    ::= { pdnIgmpProxy 2 }



-- =============================================================================
-- == Conformance Information                                                 ==
-- =============================================================================


pdnIpMcastCompliances  OBJECT IDENTIFIER ::= { pdnIpMcastConformance 1 }
pdnIpMcastGroups       OBJECT IDENTIFIER ::= { pdnIpMcastConformance 2 }


-- ===========================
-- == Compliance Statements ==
-- ===========================

pdnIpMcastMIBCompliance MODULE-COMPLIANCE
    STATUS      current
    DESCRIPTION "The compliance statement for IP Multicast products which
                implement the pdnIpMcaseMIB."
    MODULE      -- this module
    -- No mandatory groups are specified

    GROUP       pdnIgmpProxyGroup
    DESCRIPTION "This group is mandatory only for implementations which
                require IGMP Proxy."

    ::= { pdnIpMcastCompliances 1 }


-- ==========================
-- == Units of Conformance ==
-- ==========================

pdnIpMcaseObjGroups    OBJECT IDENTIFIER ::= { pdnIpMcastGroups 1 }
pdnIpMcastAfnGroups    OBJECT IDENTIFIER ::= { pdnIpMcastGroups 2 }
pdnIpMcaseNtfyGroups   OBJECT IDENTIFIER ::= { pdnIpMcastGroups 3 }


-- ===================
-- == Object Groups ==
-- ===================

pdnIgmpProxyGroup OBJECT-GROUP
    OBJECTS     {
                     pdnIgmpProxyEnableDisable, 
                     pdnIgmpProxyReportSummaryEnableDisable
    }
    STATUS      current
    DESCRIPTION "Objects grouped for IGMP Proxy."
    ::= { pdnIpMcaseObjGroups  1 }


-- ==================================
-- == Accessible for Notify Groups ==
-- ==================================

-- None defined.


-- =========================
-- == Notification Groups ==
-- =========================

-- None defined.




-- =========
-- == END ==
-- =========
END
