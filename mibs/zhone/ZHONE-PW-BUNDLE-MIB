--
-- zhonePwBundle.mib
-- MIB generated by MG-SOFT Visual MIB Builder Version 3.0 Build 285
-- Friday, January 22, 2010 at 09:25:15
--

	ZHONE-PW-BUNDLE-MIB DEFINITIONS ::= BEGIN
 
		IMPORTS
			OBJECT-GROUP			
				FROM SNMPv2-CONF			
			IpAddress, Integer32, OBJECT-TYPE, MODULE-IDENTITY			
				FROM SNMPv2-SMI			
			RowStatus			
				FROM SNMPv2-TC			
			zhoneModules			
				FROM Zhone;
	
	
-- The markup shown in this mib was used to generate the PwStd_Config 
-- profile and the supporting PL code. 
-- 
-- The PwStd_Config profile is a composite of three mibs: PW-STD-MIB,
-- PW-TDM-MIB, AND ZHONE-PW-BUNDLE-MIB. The PW-STD-MIB contributions
-- to the profile were marked up for PwStd_Config. The PW-TDM-MIB 
-- contributions to the profile were marked up for PwStd_Config2. The 
-- ZHONE-PW-BUNDLE-MIB contributions to the profile were marked up for
-- PwStd_Config3. Then the resulting structures, _Compose(), _Decompose(),
-- and _Create() were then stitched together to their current form.
--  
-- CFG -----------------------------------------------------------------
-- 
-- BUILD --------------------------------------------------------------
-- 
-- mibcomp rfc1907.mib iftype.mib rfc2233.mib Zhone.mib -stub -o mibwork/bundle/zhonePwBundleMibHdlr.c zhonePwBundle.mib
-- /vob/zhonetools/bin/pahrser.pl -css rfc1213.mib rfc1907.mib iftype.mib rfc2233.mib ./Zhone.mib ./zhonePwBundle.mib
--  
		-- 1.3.6.1.4.1.5504.6.115
		zhonePwBundle MODULE-IDENTITY 
			LAST-UPDATED "201001210940Z"		-- January 21, 2010 at 09:40 GMT
			ORGANIZATION 
				"Zhone Technologies, Inc."
			CONTACT-INFO 
				"Postal: 
				    Zhone Technologies, Inc.
				    @ Zhone Way
				    7001 Oakport Street
				    Oakland, CA  94621
				    USA
				Toll-Free: +1 877-ZHONE20 (+1 877-946-6320)
				      Tel: +1-510-777-7000
				      Fax: +1-510-777-7001
				   E-mail: support@zhone.com"
			DESCRIPTION 
				"This is the Zhone module identifier for the Zhone Pseudowire ds0 bundle definition."
			REVISION "201001210641Z"		-- January 21, 2010 at 06:41 GMT
			DESCRIPTION 
				"Added IsdnMode leaf."
			REVISION "200808180650Z"		-- August 18, 2008 at 06:50 GMT
			DESCRIPTION 
				"Finalized. Removed portspec object, expanded the 
				CFG comment, and corrected the pahrser build info."
			::= { zhoneModules 115 }

		
	
	
--
-- Node definitions
--
	
		-- 1.3.6.1.4.1.5504.6.115.1
		zhonePwBundleTable OBJECT-TYPE
			SYNTAX SEQUENCE OF ZhonePwBundleEntry
			MAX-ACCESS not-accessible
			STATUS current
			DESCRIPTION
				"Zhone extension table for pseudowire configuration."
			::= { zhonePwBundle 1 }

		
		-- 1.3.6.1.4.1.5504.6.115.1.1
		zhonePwBundleEntry OBJECT-TYPE
			SYNTAX ZhonePwBundleEntry
			MAX-ACCESS not-accessible
			STATUS current
			DESCRIPTION
				"Zhone extension entry pseudowire configuration."
			INDEX { zhonePwBundlePwIndex }
			::= { zhonePwBundleTable 1 }

		
		ZhonePwBundleEntry ::=
			SEQUENCE { 
				zhonePwBundlePwIndex
					Integer32,
				zhonePwBundleLocalIpAddr
					IpAddress,
				zhonePwBundleDs0Bundle
					BITS,
				zhonePwBundleRowStatus
					RowStatus,
				zhonePwBundleTos
					Integer32,
				zhonePwBundleIsdnMode
					INTEGER
			 }

		-- 1.3.6.1.4.1.5504.6.115.1.1.1
		zhonePwBundlePwIndex OBJECT-TYPE
			SYNTAX Integer32 (1..2147483647)
			MAX-ACCESS not-accessible
			STATUS current
			DESCRIPTION
				"Index for the conceptual row associating an entry from
				this table to a unique pseudowire instance."
			::= { zhonePwBundleEntry 1 }

		
-- 
		-- 1.3.6.1.4.1.5504.6.115.1.1.2
		zhonePwBundleLocalIpAddr OBJECT-TYPE
			SYNTAX IpAddress
			MAX-ACCESS read-create
			STATUS current
			DESCRIPTION
				"The local IP address associated with the DS0 bundle."
			::= { zhonePwBundleEntry 2 }

		
-- 
		-- 1.3.6.1.4.1.5504.6.115.1.1.3
		zhonePwBundleDs0Bundle OBJECT-TYPE
			SYNTAX BITS
				{
				ds0-0(0),
				ds0-1(1),
				ds0-2(2),
				ds0-3(3),
				ds0-4(4),
				ds0-5(5),
				ds0-6(6),
				ds0-7(7),
				ds0-8(8),
				ds0-9(9),
				ds0-10(10),
				ds0-11(11),
				ds0-12(12),
				ds0-13(13),
				ds0-14(14),
				ds0-15(15),
				ds0-16(16),
				ds0-17(17),
				ds0-18(18),
				ds0-19(19),
				ds0-20(20),
				ds0-21(21),
				ds0-22(22),
				ds0-23(23),
				ds0-24(24),
				ds0-25(25),
				ds0-26(26),
				ds0-27(27),
				ds0-28(28),
				ds0-29(29),
				ds0-30(30),
				ds0-31(31)
				}
			MAX-ACCESS read-create
			STATUS current
			DESCRIPTION
				"This value is a bit field indicating the ds0's in the
				bundle. No bits selected is also a valid state."
			::= { zhonePwBundleEntry 3 }

		
		-- 1.3.6.1.4.1.5504.6.115.1.1.4
		zhonePwBundleRowStatus OBJECT-TYPE
			SYNTAX RowStatus
			MAX-ACCESS read-create
			STATUS current
			DESCRIPTION
				"For creating, modifying, and deleting this row.
				This object MAY be changed at any time."
			::= { zhonePwBundleEntry 4 }

		
		-- 1.3.6.1.4.1.5504.6.115.1.1.5
		zhonePwBundleTos OBJECT-TYPE
			SYNTAX Integer32 (0..255)
			MAX-ACCESS read-create
			STATUS current
			DESCRIPTION
				"Type-of-Service bitvalue for the pseudowire."
			::= { zhonePwBundleEntry 5 }

		
		-- 1.3.6.1.4.1.5504.6.115.1.1.6
		zhonePwBundleIsdnMode OBJECT-TYPE
			SYNTAX INTEGER
				{
				disabled(1),
				lt(2),
				nt1(3)
				}
			MAX-ACCESS read-create
			STATUS current
			DESCRIPTION
				"Type of ISDN termination."
			DEFVAL { disabled }
			::= { zhonePwBundleEntry 6 }

		
		-- 1.3.6.1.4.1.5504.6.115.2
		zhonePwBundleGroup OBJECT-GROUP
			OBJECTS { zhonePwBundleLocalIpAddr, zhonePwBundleDs0Bundle, zhonePwBundleRowStatus, zhonePwBundleTos, zhonePwBundleIsdnMode
				 }
			STATUS current
			DESCRIPTION 
				"A collection of objects from zhonePwBundle"
			::= { zhonePwBundle 2 }

		
	
	END

--
-- zhonePwBundle.mib
--
