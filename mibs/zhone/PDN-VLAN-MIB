-- ===============================================================
-- Copyright (C) 2003 Paradyne Corporation.
-- ===============================================================

PDN-VLAN-MIB DEFINITIONS ::= BEGIN

IMPORTS
    MODULE-IDENTITY, OBJECT-TYPE
        FROM SNMPv2-SMI
    OBJECT-GROUP, MODULE-COMPLIANCE
        FROM SNMPv2-CONF
    VlanIndex
        FROM Q-BRIDGE-MIB
    pdn-common
        FROM PDN-HEADER-MIB;
        
pdnVlanMIB MODULE-IDENTITY
    LAST-UPDATED "200311120000Z"  -- Nov 12, 2003
    ORGANIZATION "Paradyne Networks
                  MIB Working Group
                  Other information about group editing the MIB"
    CONTACT-INFO "Paradyne Networks, Inc.
                  8545 126th Avenue North
                  Largo, FL 33733
                  www.paradyne.com
        
                  General Comments to: mibwg_team@paradyne.com

                  Editors
                      Clay Sikes,
		      Jesus A. Pinto"

    DESCRIPTION
        "This MIB module contains objects pertaining to VLANs."

    REVISION "200311120000Z"  -- Nov 19, 2003, pinto
    DESCRIPTION "Added a second VlanId for in-band mgmt"

    REVISION "200304240000Z"  -- April 24, 2003
    DESCRIPTION "Changed the compliance/conformance section to be
                consistent with standard MIBs."
        
    REVISION "200304110000Z"  -- April 11, 2003
    DESCRIPTION "Initial release."


::=  { pdn-common 46 }

pdnVlanNotifications OBJECT IDENTIFIER ::= { pdnVlanMIB 0 }
pdnVlanObjects       OBJECT IDENTIFIER ::= { pdnVlanMIB 1 }
pdnVlanAFNs          OBJECT IDENTIFIER ::= { pdnVlanMIB 2 }
pdnVlanConformance   OBJECT IDENTIFIER ::= { pdnVlanMIB 3 }


-- =============================================================================
-- ==                  MIB Objects                                            ==
-- =============================================================================


pdnVlanReservedBlockStart OBJECT-TYPE
    SYNTAX      VlanIndex
    MAX-ACCESS  read-write
    STATUS      current
    DESCRIPTION "This object defines the starting VLAN for a sequential block
                of VLANS that are to be reserved for internal use. The actual 
                size of the block reserved is not specified as it could be 
                implementation specific. The size of the actual block being 
                reserved should be clearly specified in the SNMP Operational 
                Specification for the particular implementaion."
    ::= { pdnVlanObjects 1 }

pdnVlanInbandMgmtVlanId  OBJECT-TYPE
    SYNTAX      VlanIndex
    MAX-ACCESS  read-write
    STATUS      current
    DESCRIPTION "The VLAN ID assigned to the In-Band Management Channel."
    ::= { pdnVlanObjects 2 }

pdnVlanInbandMgmtVlanId2  OBJECT-TYPE
    SYNTAX      VlanIndex
    MAX-ACCESS  read-write
    STATUS      current
    DESCRIPTION "The VLAN ID assigned to the second In-Band Management Channel.

		 If the agent does not support a second In-Band Management
		 Channel, it should return NO-SUCH-NAME for the object.

		 *** A VALUE OF 0 IS NOT PERMITTED TO BE RETURNED ***

		 "
    ::= { pdnVlanObjects 3 }


-- =============================================================================
-- ==                  Conformance Information                                ==
-- =============================================================================

pdnVlanCompliances        OBJECT IDENTIFIER ::= { pdnVlanConformance  1 }
pdnVlanGroups             OBJECT IDENTIFIER ::= { pdnVlanConformance  2 }


-- ===========================
-- == Compliance Statements ==
-- ===========================

pdnVlanMIBCompliance MODULE-COMPLIANCE
    STATUS      current
    DESCRIPTION "The compliance statement for the pdnVlan entities which
                implement the pdnVlanMIB."
    MODULE      -- this module
    -- No mandatory groups are specified

    GROUP       pdnVlanReservedBlockGroup
    DESCRIPTION "This group is mandatory only in those entities which 
                implement reserving a single sequential block of VLANs for 
                internal purposes."

    GROUP       pdnVlanInbandMgmtVlanGroup
    DESCRIPTION "This group is mandatory only in those entities which
                require the VLAN for the In-Band Management channel to
                be configured and identified."
    --
    -- All objects, if implemented, are expected to be implemented to the
    -- maximal level as specified in their OBJECT-TYPE macro.
    --
    ::= { pdnVlanCompliances 1 }



-- ==========================
-- == Units of Conformance ==
-- ==========================

pdnVlanObjGroups       OBJECT IDENTIFIER ::= { pdnVlanGroups 1 }
pdnVlanAfnGroups       OBJECT IDENTIFIER ::= { pdnVlanGroups 2 }
pdnVlanNtfyGroups      OBJECT IDENTIFIER ::= { pdnVlanGroups 3 }


-- ===================
-- == Object Groups ==
-- ===================

pdnVlanReservedBlockGroup OBJECT-GROUP
    OBJECTS {
                pdnVlanReservedBlockStart        
    }
    STATUS      current
    DESCRIPTION "Objects grouped for reserving a block of sequential VLANs."
    ::= { pdnVlanObjGroups  1 }

pdnVlanInbandMgmtVlanGroup OBJECT-GROUP
    OBJECTS {
                pdnVlanInbandMgmtVlanId

    }
    STATUS      current
    DESCRIPTION "Objects grouped relating to the In-Band Managment VLAN."
    ::= { pdnVlanObjGroups 2 }

pdnVlanInbandMgmtVlan2Group OBJECT-GROUP
    OBJECTS {
                pdnVlanInbandMgmtVlanId,
                pdnVlanInbandMgmtVlanId2

    }
    STATUS      current
    DESCRIPTION "Multiples objects grouped relating to the In-Band Managment VLAN."
    ::= { pdnVlanObjGroups 3 }


-- =========
-- == END ==
-- =========
END
