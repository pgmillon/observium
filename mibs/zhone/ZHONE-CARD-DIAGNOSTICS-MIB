--
-- genCardDiagnostics.mib
-- MIB generated by MG-SOFT Visual MIB Builder Version 3.0 Build 285
-- Friday, March 05, 2010 at 14:11:29
--

	ZHONE-CARD-DIAGNOSTICS-MIB DEFINITIONS ::= BEGIN
 
		IMPORTS
			InterfaceIndexOrZero			
				FROM IF-MIB			
			OBJECT-GROUP			
				FROM SNMPv2-CONF			
			TimeTicks, Integer32, Counter32, OBJECT-TYPE, MODULE-IDENTITY, 
			OBJECT-IDENTITY, NOTIFICATION-TYPE			
				FROM SNMPv2-SMI			
			DateAndTime			
				FROM SNMPv2-TC			
			zhoneCard, zhoneShelfIndex, zhoneSlotIndex, zhoneModules, zhoneShelfIndex, 
			zhoneSlotIndex			
				FROM Zhone			
			ZhoneDiagAction, ZhoneDiagResult, ZhoneRowStatus			
				FROM Zhone-TC;
	
	
-- The Zhone CardDiagnostics MIB defines management variables for testing
-- cards on Zhone systems.
-- 
-- /vob/zhonetools/bin/pahrser.pl rfc2514.mib rfc1907.mib iftype.mib
--  rfc2233.mib rfc2571.mib Zhone.mib Zhone-TC.mib genCardDiagnostics.mib 
-- 
-- /vob/EPILOGUE/binaries/emissary/solaris/mibcomp rfc2514.mib rfc1907.mib
--  iftype.mib rfc2233.mib rfc2571.mib Zhone.mib Zhone-TC.mib -stub 
--  -o mtacHdlrs.c genCardDiagnostics.mib
-- 
-- 1. Card diagnostics request information
-- 
-- 
-- 
-- 2. Card diagnostics result information.
-- 
-- 
-- 
-- 
		-- 1.3.6.1.4.1.5504.6.11
		zhoneCardDiagnosticsModule MODULE-IDENTITY 
			LAST-UPDATED "201003030930Z"		-- March 03, 2010 at 09:30 GMT
			ORGANIZATION 
				"Zhone Technologies, Inc."
			CONTACT-INFO 
				"  Postal: 
				Zhone Technologies, Inc.
				@ Zhone Way
				7001 Oakport Street
				Oakland, CA  94621
				USA
				Toll-Free: +1 877-ZHONE20 (+1 877-946-6320)
				Tel: +1-510-777-7000
				Fax: +1-510-777-7001
				E-mail: support@zhone.com"
			DESCRIPTION 
				"Contains the diagnostics and results available on a per card or resource basis."
			REVISION "201003051405Z"		-- March 05, 2010 at 14:05 GMT
			DESCRIPTION 
				"V01.00.14 change tactestresults to persistent"
			REVISION "200905140939Z"		-- May 14, 2009 at 09:39 GMT
			DESCRIPTION 
				"V01.00.13 add optional parameters for line test"
			REVISION "200905072237Z"		-- May 07, 2009 at 22:37 GMT
			DESCRIPTION 
				"V01.00.12 mtac name changes"
			REVISION "200901121536Z"		-- January 12, 2009 at 15:36 GMT
			DESCRIPTION 
				"add trap for mtac ringer power bus fault alarm"
			REVISION "200810220528Z"		-- October 22, 2008 at 05:28 GMT
			DESCRIPTION 
				"Changing the mtac name into tac and removing the name metallic."
			REVISION "200607241128Z"		-- July 24, 2006 at 11:28 GMT
			DESCRIPTION 
				"V01.00.09 - Add new Mtac test controls
				for the Legerity Test Suite."
			REVISION "200111141528Z"		-- November 14, 2001 at 15:28 GMT
			DESCRIPTION 
				"V01.00.08. Added comments for mtactestmode"
			REVISION "200108301121Z"		-- August 30, 2001 at 11:21 GMT
			DESCRIPTION 
				"V01.00.07 - Modify description of zhoneCardDiagType to include
				             specific diagnostics for T3TDM card"
			REVISION "200108271814Z"		-- August 27, 2001 at 18:14 GMT
			DESCRIPTION 
				"V01.00.06 - Modify description of zhoneCardDiagType to include
				             specific diagnostics for VASP card
				           - Add DEFVAL for zhoneCardDiagType
				           - Modify DEFVAL for zhoneCardDiagRepetition, zhoneCardDiagDuration"
			REVISION "200106281201Z"		-- June 28, 2001 at 12:01 GMT
			DESCRIPTION 
				"V01.00.05 - fix the 17 slot problem"
			REVISION "200106261240Z"		-- June 26, 2001 at 12:40 GMT
			DESCRIPTION 
				"V01.00.04 - Added zhoneMetallicTest Table entry,and also added the markups. Removed zhoneCardDiagIndex field from zhoneCardDiagObjects. "
			REVISION "200012121630Z"		-- December 12, 2000 at 16:30 GMT
			DESCRIPTION 
				"V01.00.03 - move zhoneCardDiagNextIndex into table."
			REVISION "200010191945Z"		-- October 19, 2000 at 19:45 GMT
			DESCRIPTION 
				"V01.00.02 - Corrected revision information."
			REVISION "200010171032Z"		-- October 17, 2000 at 10:32 GMT
			DESCRIPTION 
				"VO1.00.01 - Added ZHONE_KEYWORD markup."
			REVISION "200009121107Z"		-- September 12, 2000 at 11:07 GMT
			DESCRIPTION 
				"V01.00.00 - Initial Release"
			::= { zhoneModules 11 }

		
	
	
--
-- Node definitions
--
	
		-- 1.3.6.1.4.1.5504.3.3.5
		zhoneCardDiagNextTable OBJECT-TYPE
			SYNTAX SEQUENCE OF ZhoneCardDiagNextEntry
			MAX-ACCESS not-accessible
			STATUS current
			DESCRIPTION
				"Augment table of the unit/card resource but specific
				to the diagnostic results information. This card 
				contains the index to create diagnostics table 
				entries (zhoneCardDiagEntry) which contains all the data
				for executing and obtaining diagnostic results."
			::= { zhoneCard 5 }

		
		-- 1.3.6.1.4.1.5504.3.3.5.1
		zhoneCardDiagNextEntry OBJECT-TYPE
			SYNTAX ZhoneCardDiagNextEntry
			MAX-ACCESS not-accessible
			STATUS current
			DESCRIPTION
				"This is the card diagnostics next index table which contains
				 all the data for:
				- index for creating next zhoneCardDiagEntry."
			INDEX { zhoneShelfIndex, zhoneSlotIndex }
			::= { zhoneCardDiagNextTable 1 }

		
		ZhoneCardDiagNextEntry ::=
			SEQUENCE { 
				zhoneCardDiagNextIndex
					Integer32
			 }

-- 
-- 
		-- 1.3.6.1.4.1.5504.3.3.5.1.1
		zhoneCardDiagNextIndex OBJECT-TYPE
			SYNTAX Integer32 (1..10)
			MAX-ACCESS read-only
			STATUS current
			DESCRIPTION
				"We allow ten diagnostic requests from multiple 
				interfaces. 
				
				The diagNextIndex represents the next available 
				diagnostic request handle for requesting a 
				diagnostic.
				
				NOTE: this operates as a wrap-around counter starting
				      at 1 and wrapping around to 1 after reaching 10."
			::= { zhoneCardDiagNextEntry 1 }

		
		-- 1.3.6.1.4.1.5504.3.3.6
		zhoneCardDiagTable OBJECT-TYPE
			SYNTAX SEQUENCE OF ZhoneCardDiagEntry
			MAX-ACCESS not-accessible
			STATUS current
			DESCRIPTION
				"Augment table of the unit/card resource but specific
				to the diagnostic results information. This is the card 
				diagnostics table which contains all the data for 
				executing and obtaining diagnostic results."
			::= { zhoneCard 6 }

		
		-- 1.3.6.1.4.1.5504.3.3.6.1
		zhoneCardDiagEntry OBJECT-TYPE
			SYNTAX ZhoneCardDiagEntry
			MAX-ACCESS not-accessible
			STATUS current
			DESCRIPTION
				"This is the card diagnostics table which contains all the data for:
				- invoking diagnostics,
				- obtaining diagnostic results."
			INDEX { zhoneShelfIndex, zhoneSlotIndex, zhoneCardDiagIndex }
			::= { zhoneCardDiagTable 1 }

		
		ZhoneCardDiagEntry ::=
			SEQUENCE { 
				zhoneCardDiagIndex
					Integer32,
				zhoneCardDiagType
					INTEGER,
				zhoneCardDiagAction
					ZhoneDiagAction,
				zhoneCardDiagRepetition
					Integer32,
				zhoneCardDiagDuration
					Integer32,
				zhoneCardDiagResult
					ZhoneDiagResult,
				zhoneCardDiagPassCount
					Counter32,
				zhoneCardDiagFailCount
					Counter32,
				zhoneCardDiagDetails
					OCTET STRING,
				zhoneCardDiagStartTime
					DateAndTime,
				zhoneCardDiagEndTime
					DateAndTime,
				zhoneCardDiagRowStatus
					ZhoneRowStatus
			 }

-- 
-- 
		-- 1.3.6.1.4.1.5504.3.3.6.1.1
		zhoneCardDiagIndex OBJECT-TYPE
			SYNTAX Integer32 (1..10)
			MAX-ACCESS not-accessible
			STATUS current
			DESCRIPTION
				"We allow ten diagnostic requests from multiple 
				interfaces. 
				
				The diagIndex represents the diagnostic request to 
				start a diagnostic or obtain test results for a 
				completed diagnostic.
				
				NOTE: this operates as a wrap-around counter starting
				      at 1 and wrapping around to 1 after reaching 10."
			::= { zhoneCardDiagEntry 1 }

		
-- 
-- 
		-- 1.3.6.1.4.1.5504.3.3.6.1.2
		zhoneCardDiagType OBJECT-TYPE
			SYNTAX INTEGER
				{
				selftest(1),
				supvBus(2),
				cardEEprom(3),
				frbus(4),
				pcmcia(5),
				shelfLamp(6),
				realTimeClock(7),
				fanTray(8),
				shelfMonitor(9),
				ioCard(10),
				mezzanineCard(11),
				backPlane(12),
				midPlane(13)
				}
			MAX-ACCESS read-create
			STATUS current
			DESCRIPTION
				"This field specifies the diagnostic to execute. The default 
				value is 'selftest'.
				
				NOTE: not all of the individual diagnostics are available on 
				      every Zhone card type.
				NOTE: Zhone card types (cardZhoneType) are defined in the
				      genCardResources.mib
				
				List of possible diagnostics:
				============================
				Common to all PLS cards
				-----------------------
				selftest(1) 
				  - this diagnostic will execute all of the individual tests 
				    available on this card.
				    Supports: diagStart, diagStop, diagRepetition.
				cardEEprom(3) 
				  - this diagnostic will verify the main card EEPROM checksum.
				    Supports: diagStart, diagStop, diagRepetition.
				frbus(4) 
				  - this diagnostic will verify that the BAN slot card can 
				    access the Fhrame Bus by doing a loopback with 10 message
				    of 100 bytes.
				    Supports: diagStart, diagStop, diagRepetition.
				backPlane(12)
				  - this diagnostic will verify that the BAN slot card can
				    access the back plane by verifying the back plane EEPROM
				    checksum.
				    Supports: diagStart, diagStop, diagRepetition.
				
				cardZhoneType::infoServices(3) specific
				---------------------------------------
				supvBus(2)
				  - this diagnostic will verify that the BAN slot card can
				    access the supervisory Bus by doing a loopback of 20 
				    bytes.
				    Supports: diagStart, diagStop, diagRepetition.
				pcmcia(5) 
				  - this diagnostic will verify that the InfoServ card can
				    access the PCMCIA flash card I/O by doing a file create,
				    write, and read of length 4000 bytes.
				    Supports: diagStart, diagStop, diagRepetition.
				shelfLamp(6)
				  - this diagnostic will illuminate the shelf alarm indicators 
				    for a period of 1.5 seconds. The indicators will return to
				    their original settings after the diagnostic completes.
				    Supports: diagStart, diagStop, diagRepetition.
				realTimeClk(7) 
				  - this diagnostic will verify that the real time clock 
				    increments.
				    Supports: diagStart, diagStop, diagRepetition.
				fanTray(8) 
				  - this diagnostic tests that the fan tray is operational by 
				    verifying the fan tray EEPROM checksum.
				    Supports: diagStart, diagStop, diagRepetition.
				shelfMonitor(9) 
				  - this diagnostic tests the shelf monitor board is operational 
				    by checking the POST status register and verifying the shelf 
				    monitor board EEPROM checksum.
				    Supports: diagStart, diagStop, diagRepetition.
				midPlane(13) 
				  - this diagnostic will verify that the mid plane card is present 
				    by verifying the mid plane card EEPROM checksum.
				    Supports: diagStart, diagStop, diagRepetition.
				
				cardZhoneType::vasp(5) specific
				---------------------------------
				ioCard(10) 
				  - this diagnostic will verify that the I/O card is present by 
				    verifying the I/O card EEPROM checksum.
				    Supports: diagStart, diagStop, diagRepetition.
				mezzanineCard(11) 
				  - this diagnostic will test that the mezzanine card is operational
				    by verifying the mezzanine card EEPROM checksum.
				    Supports: diagStart, diagStop, diagRepetition.
				
				cardZhoneType::t3Tdm(6) specific
				---------------------------------
				ioCard(10) 
				  - this diagnostic will verify that the I/O card is present by 
				    verifying the I/O card EEPROM checksum.
				    Supports: diagStart, diagStop, diagRepetition.
				midPlane(13) 
				  - this diagnostic will verify that the mid plane card is present 
				    by verifying the mid plane card EEPROM checksum.
				    Supports: diagStart, diagStop, diagRepetition.
				
				cardZhoneType::ethernet(9) specific
				-----------------------------------
				midPlane(13) 
				  - this diagnostic will verify that the mid plane card is present 
				    by verifying the mid plane card EEPROM checksum.
				    Supports: diagStart, diagStop, diagRepetition.
				
				cardZhoneType::hdsl2(10) specific
				---------------------------------
				ioCard(10) 
				  - this diagnostic will verify that the I/O card is present by 
				    verifying the I/O card EEPROM checksum.
				    Supports: diagStart, diagStop, diagRepetition.
				mezzanineCard(11) 
				  - this diagnostic will test that the mezzanine card is operational
				    by verifying the mezzanine card EEPROM checksum.
				    Supports: diagStart, diagStop, diagRepetition."
			DEFVAL { selftest }
			::= { zhoneCardDiagEntry 2 }

		
-- 
-- 
		-- 1.3.6.1.4.1.5504.3.3.6.1.3
		zhoneCardDiagAction OBJECT-TYPE
			SYNTAX ZhoneDiagAction
			MAX-ACCESS read-create
			STATUS current
			DESCRIPTION
				"The diagAction field represents the diagnostic
				operation to execute. Current supported actions are
				as follows:
				  diagStart  : begin diagnostics and initialize results.
				  diagStop   : stop diagnostics if not yet complete.
				  diagSuspend: suspend diagnostics at current point.
				  diagResume : resume diagnostics from point of 
				               suspension."
			DEFVAL { diagStart }
			::= { zhoneCardDiagEntry 3 }

		
-- 
-- 
		-- 1.3.6.1.4.1.5504.3.3.6.1.4
		zhoneCardDiagRepetition OBJECT-TYPE
			SYNTAX Integer32 (0..10)
			MAX-ACCESS read-create
			STATUS current
			DESCRIPTION
				"This field specifies the number of repetitions of diagnostics to execute.
				The default value is 1.
				
				NOTE: this field operates as an OR with the diagDuration field. If this 
				      field is set to non-zero then the diagnostics will be executed 
				      that amount of repetitions."
			DEFVAL { 1 }
			::= { zhoneCardDiagEntry 4 }

		
-- 
-- 
		-- 1.3.6.1.4.1.5504.3.3.6.1.5
		zhoneCardDiagDuration OBJECT-TYPE
			SYNTAX Integer32 (0..600)
			UNITS "seconds"
			MAX-ACCESS read-create
			STATUS current
			DESCRIPTION
				"This field specifies the duration of diagnostics to execute. The default 
				value is 60 seconds.
				
				NOTE: this field operates as an OR with the diagRepetition field. If this 
				      field is set to non-zero then the diagnostics will be executed that
				      amount of time."
			DEFVAL { 60 }
			::= { zhoneCardDiagEntry 5 }

		
-- 
-- 
		-- 1.3.6.1.4.1.5504.3.3.6.1.6
		zhoneCardDiagResult OBJECT-TYPE
			SYNTAX ZhoneDiagResult
			MAX-ACCESS read-only
			STATUS current
			DESCRIPTION
				"This represents the overall diagnostic result."
			::= { zhoneCardDiagEntry 6 }

		
-- 
-- 
		-- 1.3.6.1.4.1.5504.3.3.6.1.7
		zhoneCardDiagPassCount OBJECT-TYPE
			SYNTAX Counter32
			MAX-ACCESS read-only
			STATUS current
			DESCRIPTION
				"The number of diagnostics that executed successfully."
			::= { zhoneCardDiagEntry 7 }

		
-- 
-- 
		-- 1.3.6.1.4.1.5504.3.3.6.1.8
		zhoneCardDiagFailCount OBJECT-TYPE
			SYNTAX Counter32
			MAX-ACCESS read-only
			STATUS current
			DESCRIPTION
				"The number of diagnostics that have failed."
			::= { zhoneCardDiagEntry 8 }

		
-- 
-- 
		-- 1.3.6.1.4.1.5504.3.3.6.1.9
		zhoneCardDiagDetails OBJECT-TYPE
			SYNTAX OCTET STRING (SIZE (0..64))
			MAX-ACCESS read-only
			STATUS current
			DESCRIPTION
				"The failure reason, if any, for the last diagnostic which has executed. 
				
				NOTE: An empty string indicates that no additional information is available."
			::= { zhoneCardDiagEntry 9 }

		
-- 
-- 
		-- 1.3.6.1.4.1.5504.3.3.6.1.10
		zhoneCardDiagStartTime OBJECT-TYPE
			SYNTAX DateAndTime
			MAX-ACCESS read-only
			STATUS current
			DESCRIPTION
				"Starting date and time of last selftest execution."
			::= { zhoneCardDiagEntry 10 }

		
-- 
-- 
		-- 1.3.6.1.4.1.5504.3.3.6.1.11
		zhoneCardDiagEndTime OBJECT-TYPE
			SYNTAX DateAndTime
			MAX-ACCESS read-only
			STATUS current
			DESCRIPTION
				"Ending date and time of last selftest execution."
			::= { zhoneCardDiagEntry 11 }

		
-- 
-- 
		-- 1.3.6.1.4.1.5504.3.3.6.1.12
		zhoneCardDiagRowStatus OBJECT-TYPE
			SYNTAX ZhoneRowStatus
			MAX-ACCESS read-create
			STATUS current
			DESCRIPTION
				"In any case where a new row can be created either via
				the cli or zms there will always be a proprietary mib
				entity of type ZhoneRowStatus which has the basic 
				equivalence of the standard rowstatus object_id."
			::= { zhoneCardDiagEntry 12 }

		
		-- 1.3.6.1.4.1.5504.3.3.7
		zhoneTacTestTable OBJECT-TYPE
			SYNTAX SEQUENCE OF ZhoneTacTestEntry
			MAX-ACCESS not-accessible
			STATUS current
			DESCRIPTION
				"This table contains one entry for each tac
				test channel available on Zhone devices. In the
				initial release only the primary channel (1) is
				supported. Future line cards may support the
				second channel. If the second channel is supported
				the row will be populated, if the second channel
				is not supported a get will return no such instance.
				"
			::= { zhoneCard 7 }

		
		-- 1.3.6.1.4.1.5504.3.3.7.1
		zhoneTacTestEntry OBJECT-TYPE
			SYNTAX ZhoneTacTestEntry
			MAX-ACCESS not-accessible
			STATUS current
			DESCRIPTION
				"One row per tac test channel."
			INDEX { zhoneTacIndex }
			::= { zhoneTacTestTable 1 }

		
		ZhoneTacTestEntry ::=
			SEQUENCE { 
				zhoneTacIndex
					Integer32,
				zhoneTacInterfaceIndex
					InterfaceIndexOrZero,
				zhoneTacTestMode
					INTEGER,
				zhoneTacTestId
					INTEGER,
				zhoneTacTestParam1
					INTEGER,
				zhoneTacTestParam2
					INTEGER,
				zhoneTacTestParam3
					INTEGER,
				zhoneTacTestParam4
					INTEGER,
				zhoneTacTestParam5
					INTEGER
			 }

		-- 1.3.6.1.4.1.5504.3.3.7.1.1
		zhoneTacIndex OBJECT-TYPE
			SYNTAX Integer32 (1..2)
			MAX-ACCESS not-accessible
			STATUS current
			DESCRIPTION
				"This field is the index field for the tac test
				channel which will be connected on the external
				port. This device supports a maximum of two channels,
				one or both channels may be supported by a device
				depending on which lines cards are installed."
			::= { zhoneTacTestEntry 1 }

		
-- 
		-- 1.3.6.1.4.1.5504.3.3.7.1.2
		zhoneTacInterfaceIndex OBJECT-TYPE
			SYNTAX InterfaceIndexOrZero
			MAX-ACCESS read-write
			STATUS current
			DESCRIPTION
				"This field contains the InterfaceIndex of the physical line to
				be tested. If no line is currently being tested this
				value is 0.
				
				The ability of a physical line type to support tac test may 
				vary depending on the line cards installed and the external test 
				equipment.
				
				This field may not be modified when an tac test is
				in progress as indicated by a non-zero value in this field
				and the test mode set to one of tacModeLookIn, tacModeLookOut
				or tacModeBridge"
			DEFVAL { 0 }
			::= { zhoneTacTestEntry 2 }

		
-- 
-- The current implementation supports mtacModeLookOut and mtacModeNone
-- only.
		-- 1.3.6.1.4.1.5504.3.3.7.1.3
		zhoneTacTestMode OBJECT-TYPE
			SYNTAX INTEGER
				{
				mtacModeBridge(1),
				mtacModeLookIn(2),
				mtacModeLookOut(3),
				mtacModeNone(4)
				}
			MAX-ACCESS read-write
			STATUS current
			DESCRIPTION
				"This field is used to set the mtac test mode for a
				given line. The options are:
				
				mtacModeBridge - All traffic on the given line is bridged
				across the mtac lines
				mtacModeLookIn - All outbound traffic on the given line originates
				exclusively to the mtac lines
				mtacModeLookIn - All inbound traffic on the given line originates
				exclusively to the mtac lines
				mtacModeNone - No mtac test is in progress.
				
				The mtac test mode may be changed only if the zhoneInterfaceIndex
				is set, Otherwise it defaults to mtacModeNone.
				And can be changed again by setting InterfaceIndex to non-zero values.
				
				  
				"
			DEFVAL { mtacModeNone }
			::= { zhoneTacTestEntry 3 }

		
		-- 1.3.6.1.4.1.5504.3.3.7.1.4
		zhoneTacTestId OBJECT-TYPE
			SYNTAX INTEGER
				{
				none(1),
				runAllTests(2),
				abortTest(3),
				calibration(4),
				foreignDCVoltage(5),
				foreignACVoltage(6),
				dcLoopResistance(7),
				threeElementInsulationResistance(8),
				fiveElementInsulationResistance(9),
				threeElementCapacitance(10),
				receiverOffHook(11),
				distanceToOpen(12),
				foreignACCurrents(13),
				ringerEquivalencyNumber(14),
				dtmfAndPulseDigitMeasurement(15),
				noiseMeasurement(16),
				signalToNoiseRatio(17),
				arbitrarySignalToneMeasurement(18),
				toneGeneration(19),
				transHybridLoss(20),
				drawAndBreakDialTone(21),
				inwardCurrent(22),
				dcFeedSelf(23),
				onAndOffHookSelfTest(24),
				ringingSelfTest(25),
				ringingMonitor(26),
				meteringSelfTest(27),
				transmissionSelfTest(28),
				dialingSelfTest(29),
				howlerTest(30),
				fuseTest(31),
				readLoopAndBatteryConditions(32)
				}
			MAX-ACCESS read-write
			STATUS current
			DESCRIPTION
				"This object is only valid for Tac Cards which
				support the new Legerity Suite of tests.
				
				This object identifies which test is to
				be run, or can be set to abort the current test.
				
				Test results are sent to the zhoneTacTestResultsTable.
				
				There are 3 Legerity software packages: Basic Test (VCP-BT),
				Advanced Test (VCP-AT), and Advanced Test Plus (VCP-ATP).
				We currently support Basic Test package.
				The following lists which tests are supported in each 
				software package.
				
				Calibration	VCP-ATP
				Foreign DC Voltage Test	VCP-BT, VCP-AT, VCP-ATP
				Foreign AC VoltageTest	VCP-BT, VCP-AT, VCP-ATP
				DC Loop Resistance Test	VCP-BT, VCP-AT, VCP-ATP
				Three-Element Insulation Resistance Test	VCP-BT, VCP-AT, VCP-ATP
				Five-Element Insulation Resistance Test	VCP-ATP
				Three-Element Capacitance Test	VCP-BT, VCP-AT
				Receiver Off-Hook Test	VCP-BT, VCP-AT, VCP-ATP
				Distance to Open Test 	VCP-BT, VCP-AT
				Foreign AC Currents Test	VCP-BT, VCP-AT
				Ringer Equivalency Number Test	VCP-BT, VCP-AT, VCP-ATP
				DTMF and Pulse Digit Measurement Test	VCP-BT, VCP-AT
				Noise Measurement Test	VCP-BT, VCP-AT, VCP-ATP
				Signal to Noise Ratio Test	VCP-ATP
				Arbitrary Single Tone Measurement Test	VCP-ATP
				Tone Generation Test	VCP-BT, VCP-AT
				Trans-Hybrid Loss Test	VCP-BT, VCP-AT, VCP-ATP
				Draw and Break Dial Tone Test	VCP-BT, VCP-AT
				Inward Current Test 	VCP-ATP
				DC Feed Self-Test	VCP-BT, VCP-AT, VCP-ATP
				On/Off Hook Self-Test	VCP-BT, VCP-AT, VCP-ATP
				Ringing Self-Test 	VCP-BT, VCP-AT, VCP-ATP
				Ringing Monitor Test	VCP-BT, VCP-AT, VCP-ATP
				Metering Self-Test	VCP-BT, VCP-AT
				Transmission Self-Test	VCP-BT, VCP-AT, VCP-ATP
				Dialing Sef Test	VCP-BT, VCP-AT
				Howler Test	VCP-BT, VCP-AT
				Fuse Test	VCP-ATP
				Read Loop and Battery Conditions	VCP-BT, VCP-AT, VCP-ATP
				"
			DEFVAL { none }
			::= { zhoneTacTestEntry 4 }

		
		-- 1.3.6.1.4.1.5504.3.3.7.1.5
		zhoneTacTestParam1 OBJECT-TYPE
			SYNTAX INTEGER
			MAX-ACCESS read-write
			STATUS current
			DESCRIPTION
				"Optional Test Parameter #1"
			DEFVAL { 0 }
			::= { zhoneTacTestEntry 5 }

		
		-- 1.3.6.1.4.1.5504.3.3.7.1.6
		zhoneTacTestParam2 OBJECT-TYPE
			SYNTAX INTEGER
			MAX-ACCESS read-write
			STATUS current
			DESCRIPTION
				"Optional Test Paramerter #2"
			DEFVAL { 0 }
			::= { zhoneTacTestEntry 6 }

		
		-- 1.3.6.1.4.1.5504.3.3.7.1.7
		zhoneTacTestParam3 OBJECT-TYPE
			SYNTAX INTEGER
			MAX-ACCESS read-write
			STATUS current
			DESCRIPTION
				"Optional Test Parameter #3"
			DEFVAL { 0 }
			::= { zhoneTacTestEntry 7 }

		
		-- 1.3.6.1.4.1.5504.3.3.7.1.8
		zhoneTacTestParam4 OBJECT-TYPE
			SYNTAX INTEGER
			MAX-ACCESS read-write
			STATUS current
			DESCRIPTION
				"Optional Test Parameter #4"
			DEFVAL { 0 }
			::= { zhoneTacTestEntry 8 }

		
		-- 1.3.6.1.4.1.5504.3.3.7.1.9
		zhoneTacTestParam5 OBJECT-TYPE
			SYNTAX INTEGER
			MAX-ACCESS read-write
			STATUS current
			DESCRIPTION
				"Optional Test Parameter #5
				
				Value:
				0x00000001 Force Line-Test mode"
			DEFVAL { 0 }
			::= { zhoneTacTestEntry 9 }

		
		-- 1.3.6.1.4.1.5504.3.3.12
		zhoneTacTestResultsTable OBJECT-TYPE
			SYNTAX SEQUENCE OF ZhoneTacTestResultsEntry
			MAX-ACCESS not-accessible
			STATUS current
			DESCRIPTION
				"Table of Tac Test Results objects.  Indexed by same index
				as zhoneTacTestTable.
				
				This table is only valid for Tac cards which support
				the Legerity Suite of tests."
			::= { zhoneCard 12 }

		
		-- 1.3.6.1.4.1.5504.3.3.12.1
		zhoneTacTestResultsEntry OBJECT-TYPE
			SYNTAX ZhoneTacTestResultsEntry
			MAX-ACCESS not-accessible
			STATUS current
			DESCRIPTION
				"Entry of Test Results objects.  Indexed by same index
				as zhoneTacTestEntry.
				
				
				This entry is only valid for Tac cards which support
				the Legerity Suite of tests."
			INDEX { zhoneTacIndex }
			::= { zhoneTacTestResultsTable 1 }

		
		ZhoneTacTestResultsEntry ::=
			SEQUENCE { 
				zhoneTacTestResultsTimeStarted
					TimeTicks,
				zhoneTacTestResultsTimeEnded
					TimeTicks,
				zhoneTacTestResultStatus
					INTEGER,
				zhoneTacTestResultsOutput
					OCTET STRING
			 }

		-- 1.3.6.1.4.1.5504.3.3.12.1.1
		zhoneTacTestResultsTimeStarted OBJECT-TYPE
			SYNTAX TimeTicks
			MAX-ACCESS read-only
			STATUS current
			DESCRIPTION
				"Description."
			::= { zhoneTacTestResultsEntry 1 }

		
		-- 1.3.6.1.4.1.5504.3.3.12.1.2
		zhoneTacTestResultsTimeEnded OBJECT-TYPE
			SYNTAX TimeTicks
			MAX-ACCESS read-only
			STATUS current
			DESCRIPTION
				"Description."
			::= { zhoneTacTestResultsEntry 2 }

		
		-- 1.3.6.1.4.1.5504.3.3.12.1.3
		zhoneTacTestResultStatus OBJECT-TYPE
			SYNTAX INTEGER
				{
				testNotStarted(1),
				testInProgress(2),
				testCompleted(3),
				testAborted(4),
				testNotSupported(5)
				}
			MAX-ACCESS read-only
			STATUS current
			DESCRIPTION
				"Contains test results."
			REFERENCE
				"Contains the test status."
			::= { zhoneTacTestResultsEntry 3 }

		
		-- 1.3.6.1.4.1.5504.3.3.12.1.4
		zhoneTacTestResultsOutput OBJECT-TYPE
			SYNTAX OCTET STRING (SIZE (1..8000))
			MAX-ACCESS read-only
			STATUS current
			DESCRIPTION
				"For Legerity Test Suite, results of test(s) are
				output to this object as one string, separated by
				UNIX '/n' for newline characters and terminated by
				the NULL character.
				
				This test results will persist until the next test
				is run or until tac card reboot."
			::= { zhoneTacTestResultsEntry 4 }

		
		-- 1.3.6.1.4.1.5504.3.3.13
		zhoneTacTestTraps OBJECT-IDENTITY
			STATUS current
			DESCRIPTION 
				"Traps for the tac system."
			::= { zhoneCard 13 }

		
		-- 1.3.6.1.4.1.5504.3.3.13.0
		zhoneRingerTraps OBJECT-IDENTITY
			STATUS current
			DESCRIPTION 
				"Traps associated with ring generator. 
				Traps should be added below - the .0 
				on this entry is required."
			::= { zhoneTacTestTraps 0 }

		
		-- 1.3.6.1.4.1.5504.3.3.13.0.1
		zhoneRingerStatusAlarm NOTIFICATION-TYPE
			STATUS current
			DESCRIPTION 
				"This trap occurs when a ring signal fails to be detected,
				or when it re-starts after failure."
			::= { zhoneRingerTraps 1 }

		
		-- 1.3.6.1.4.1.5504.3.3.13.0.2
		zhoneRingerBusFaultAlarm NOTIFICATION-TYPE
			STATUS current
			DESCRIPTION 
				"This trap occurs when a fault in the ringer power bus is 
				detected.  Such fault may be caused by the possible shortage 
				in the POTS or DSL line."
			::= { zhoneRingerTraps 2 }

		
		-- 1.3.6.1.4.1.5504.6.11.1
		zhoneCardDiagObjects OBJECT-GROUP
			OBJECTS { zhoneCardDiagNextIndex, zhoneCardDiagType, zhoneCardDiagAction, zhoneCardDiagRepetition, zhoneCardDiagDuration, 
				zhoneCardDiagResult, zhoneCardDiagPassCount, zhoneCardDiagFailCount, zhoneCardDiagDetails, zhoneCardDiagStartTime, 
				zhoneCardDiagEndTime, zhoneCardDiagRowStatus }
			STATUS current
			DESCRIPTION 
				"This group contains objects associated with Zhone Card
				Diagnostics"
			::= { zhoneCardDiagnosticsModule 1 }

		
		-- 1.3.6.1.4.1.5504.6.11.2
		zhoneTacTestObjects OBJECT-GROUP
			OBJECTS { zhoneTacInterfaceIndex, zhoneTacTestMode, zhoneTacTestId, zhoneTacTestResultsTimeStarted, zhoneTacTestResultsTimeEnded, 
				zhoneTacTestResultStatus, zhoneTacTestResultsOutput }
			STATUS current
			DESCRIPTION 
				"This group contains objects associated with initiating
				tac tests"
			::= { zhoneCardDiagnosticsModule 2 }

		
	
	END

--
-- genCardDiagnostics.mib
--
