LEA-SMART-SPLITTER-MIB DEFINITIONS ::= BEGIN

IMPORTS
    MODULE-IDENTITY, OBJECT-TYPE, Integer32 FROM SNMPv2-SMI
    SnmpAdminString                         FROM SNMP-FRAMEWORK-MIB
    leaSplitters                            FROM LEA-MIB;


leaSmartSplitter MODULE-IDENTITY
        LAST-UPDATED "200210040000Z"
        ORGANIZATION "www.leacom.fr"
        CONTACT-INFO
                "postal:   Regis Urvoy
                        52/54 rue du capitaine Guynemer
                        92415 Courbevoie Cedex
                        France

                email:    regis.urvoy@leacom.fr"
        DESCRIPTION
                "LEA Smart Splitter Management Information Base"
        REVISION     "200209260000Z"
        DESCRIPTION
                "Beta 1"
        ::= { leaSplitters 1 }

--
-- top level structure
--
splitterRelay       OBJECT IDENTIFIER ::= { leaSmartSplitter 1 }

relayActiveDuration OBJECT-TYPE
    SYNTAX      INTEGER (1..300)
    MAX-ACCESS  read-write
    STATUS      current
    DESCRIPTION 
      "Duration that a bypass relay is active in seconds. As a fail-safe
      mechanism, the relay will automatically return a line back to normal
      operational mode when this timer has expired. The same relay timer value
      will be used for every port."
    DEFVAL { 60 }
    ::= { splitterRelay 1 }

numberOfActiveRelays OBJECT-TYPE
    SYNTAX      INTEGER(1..15)
    MAX-ACCESS  read-only
    STATUS      current
    DESCRIPTION
      "Total count of active relays. The agent controls the number of active
      relays so that the maximum is not exceeded in order to keep power
      consumption down."
    DEFVAL { 0 }
    ::= { splitterRelay 2 }

heartBeat OBJECT-TYPE
    SYNTAX      INTEGER { ack (1) }
    MAX-ACCESS  read-only
    STATUS      current
    DESCRIPTION
	"This parameter returns a simply acknowledge following a request from
        the manager. "
    DEFVAL { 1 }
    ::= { splitterRelay 3 }

relayTable OBJECT-TYPE
    SYNTAX      SEQUENCE OF RelayTableEntry
    MAX-ACCESS  not-accessible
    STATUS      current
    DESCRIPTION
	"Table of relay status"
    ::= { splitterRelay 4 }

relayTableEntry OBJECT-TYPE
    SYNTAX      RelayTableEntry
    MAX-ACCESS  not-accessible
    STATUS      current
    DESCRIPTION
	"A row describing a relay status"
    INDEX   { relayIndex }
    ::= { relayTable 1 }

RelayTableEntry ::= SEQUENCE {
	relayIndex	Integer32,
        relaySlot	INTEGER,
        relayPort	INTEGER,
	relayStatus	INTEGER
}

relayIndex OBJECT-TYPE
    SYNTAX      Integer32
    MAX-ACCESS  not-accessible
    STATUS      current
    DESCRIPTION
	"The index of the table. Its value is (relaySlot-1)*24+relayPort"
    ::= { relayTableEntry 1 }

relaySlot OBJECT-TYPE
    SYNTAX      INTEGER {
    			Slot-1 (1),
    			Slot-2 (2),
    			Slot-3 (3),
    			Slot-4 (4),
    			Slot-5 (5),
    			Slot-6 (6),
    			Slot-7 (7),
    			Slot-8 (8),
    			Slot-9 (9),
    			Slot-10 (10),
    			Slot-11 (11),
    			Slot-12 (12),
    			Slot-13 (13),
    			Slot-14 (14),
    			Slot-15 (15)
       		}
    MAX-ACCESS  read-only
    STATUS      current
    DESCRIPTION
	"The slot being addressed"
    ::= { relayTableEntry 2 }

relayPort OBJECT-TYPE
    SYNTAX      INTEGER {
    			Port-1 (1),
    			Port-2 (2),
    			Port-3 (3),
    			Port-4 (4),
    			Port-5 (5),
    			Port-6 (6),
    			Port-7 (7),
    			Port-8 (8),
    			Port-9 (9),
    			Port-10 (10),
    			Port-11 (11),
    			Port-12 (12),
    			Port-13 (13),
    			Port-14 (14),
    			Port-15 (15),
    			Port-16 (16),
    			Port-17 (17),
    			Port-18 (18),
    			Port-19 (19),
    			Port-20 (20),
    			Port-21 (21),
    			Port-22 (22),
    			Port-23 (23),
    			Port-24 (24)
		}
    MAX-ACCESS  read-only
    STATUS      current
    DESCRIPTION
	"The port being addressed"
    ::= { relayTableEntry 3 }

relayStatus OBJECT-TYPE
    SYNTAX      INTEGER {
                    normal (1),
                    closed (2)
                }
    MAX-ACCESS  read-write
    STATUS      current
    DESCRIPTION
	"This parameter describes whether a particular POTS line is in a normal
        or closed loop condition. By setting this parameter, the manager can
        switch the relays in order to bypass the LPF (Low Pass Filter) for POTS
        closed loop testing (closed) or force a relay back to normal operation
        mode before the Relay Active Duration timer times out (normal)"
    DEFVAL { 1 }
    ::= { relayTableEntry 4 }

relayResetAll OBJECT-TYPE
    SYNTAX      INTEGER {
                        unchanged (1),
                        reset (2)
       		}
    MAX-ACCESS  read-write
    STATUS      current
    DESCRIPTION
	"This parameter would allow the operator to force a relay back to
        normal operation for all ports."
    DEFVAL { 1 }
    ::= { splitterRelay 5 }

relayChangeNotification OBJECT-TYPE
    SYNTAX      SnmpAdminString
    MAX-ACCESS  accessible-for-notify
    STATUS      current
    DESCRIPTION
        "This notification is sent to the manager after a line status (or
        relay) change.  It takes three parameters : the slot (relaySlot) and
        port (relayPort) of the line, and its new status (relayStatus)"
    ::= { splitterRelay 6 }


END
