NTNTECH-ROOT-MIB DEFINITIONS ::= BEGIN  

--	**************************************************************** 
--  Enterprise:
--   	Paradyne Corporation	
--
--  ContactInfo:
--    	Paradyne Corporation
--     	8545 126th Avenue North
--     	Largo, FL 33773
--     	phone: +1 (727) 530-2000
--     	email: support@paradyne.com 
--		www:   http://www.nettonet.com/support/
--
--  Description:
--    	ntntech-root-MIB.my
--    	Revision: 1.02.02
--    	Part Number: xx-xxxx-xx
--    	Date: November 17, 2004
--    
--    	This module provides explicit definitions for the Net to
--		Net Technologies naming tree below:
--    
--    	nettonettech { enterprises 8059 }
--    
--    	This module will be extended, as additional sub-sections
--    	of this naming tree are defined.
--
--  Disclaimer:
--	   	This is an extremely preliminary MIB module and is subject
--		to change at any time therefore, use at your own risk.
--    
-- 	Copyright (c) 2000 - 2004 by Paradyne Corporation.
-- 	All rights reserved.    
 
-- ****************************************************************
IMPORTS
    MODULE-IDENTITY, enterprises 				FROM SNMPv2-SMI; 
-- ****************************************************************

ntntechRootMIB MODULE-IDENTITY  
    LAST-UPDATED "0411170200Z"  -- November 17, 2004
    ORGANIZATION "Paradyne Corporation"
    CONTACT-INFO
        "Paradyne Corporation
        8545 126th Avenue North
        Largo, FL 33773   
     	
        phone: +1 (727) 530-2000
        email: support@paradyne.com 
        www:   http://www.nettonet.com/support/"
                                              
    DESCRIPTION
    "This module provides explicit definitions for the Paradyne Corporation's
     Net to Net Technologies naming tree.
	  
    Product type: Digital Subscriber Line (DSL)"  
    
    REVISION   "0208281157Z"
    DESCRIPTION
          "New Release - v1.01.00" 
          
    REVISION   "0210220200Z"
    DESCRIPTION
          "New Release - v1.01.01"
         
    REVISION "0410110101Z"
    DESCRIPTION
    	"Updated copyright and references to Paradyne. Added in QoS Mib branch for
    	future mib support.  Added in a new Textual-Convention NTNTruthValue"    
    	
    	REVISION "0411171009Z"
    	DESCRIPTION
    		"New Release -- version 1.02.01"
		  
 ::= { enterprises 8059 }  
             
             
 --	Textual-Conventions           
NtnIpAddress ::= TEXTUAL-CONVENTION
    DISPLAY-HINT "1x:2x:3x:4x"
    STATUS       current
    DESCRIPTION
    "Represents the value used to define the system Ip address."
    SYNTAX       OCTET STRING (SIZE (4))  
 
NtnDefaultGateway ::= TEXTUAL-CONVENTION
    DISPLAY-HINT "1x:2x:3x:4x"
    STATUS       current
    DESCRIPTION
    "Represents the value used to define the system default gateway."
    SYNTAX       OCTET STRING (SIZE (4))    
    
NtnSubnetMask ::= TEXTUAL-CONVENTION
    DISPLAY-HINT "1x:2x:3x:4x"
    STATUS       current
    DESCRIPTION
    "Represents the value used to define the subnet address."
    SYNTAX       OCTET STRING (SIZE (4))      
    
NtnDisplayString ::= TEXTUAL-CONVENTION
    DISPLAY-HINT "255a"
    STATUS       current
    DESCRIPTION
    "Represents textual information taken from the NVT ASCII
    character set, as defined in pages 4, 10-11 of RFC 854.

    To summarize RFC 854, the NVT ASCII repertoire specifies:

       - the use of character codes 0-127 (decimal)

       - the graphics characters (32-126) are interpreted as
         US ASCII

       - NUL, LF, CR, BEL, BS, HT, VT and FF have the special
         meanings specified in RFC 854

       - the other 25 codes have no standard interpretation

       - the sequence 'CR LF' means newline

       - the sequence 'CR NUL' means carriage-return

       - an 'LF' not preceded by a 'CR' means moving to the
         same column on the next line.
 
       - the sequence 'CR x' for any x other than LF or NUL is
         illegal.  (Note that this also means that a string may
         end with either 'CR LF' or 'CR NUL', but not with CR.)

         Any object defined using this syntax may not exceed 128
         characters in length."
    SYNTAX       OCTET STRING (SIZE (0..127))     
    
NtnMacAddress ::= TEXTUAL-CONVENTION
    DISPLAY-HINT "1x:"
    STATUS       current
    DESCRIPTION
    "Represents an 802 MAC address represented in the
     'canonical' order defined by IEEE 802.1a, i.e., as if it
     were transmitted least significant bit first, even though
     802.5 (in contrast to other 802.x protocols) requires MAC
     addresses to be transmitted most significant bit first."
    SYNTAX       OCTET STRING (SIZE (6))

NtnTimeTicks ::= TEXTUAL-CONVENTION
    STATUS       current
    DESCRIPTION
    "The TimeTicks type represents a non-negative integer which represents
    the time, modulo 2^32 (4294967296 decimal), in hundredths of a second
    between two epochs.  When objects are defined which use this ASN.1
    type, the description of the object identifies both of the reference
    epochs."
    SYNTAX       INTEGER (0..4294967295)
                                                
NtnCounter32 ::= TEXTUAL-CONVENTION
    STATUS       current
    DESCRIPTION
    "The NtnCounter32 type represents a non-negative integer which
    monotonically increases until it reaches a maximum value of 2^32-1
    (4294967295 decimal), when it wraps around and starts increasing
    again from zero.

    Discontinuities in the monotonically increasing value normally 
    occur at re-initialization of the management system."
    SYNTAX       INTEGER ( 0..4294967295 )

NtnGauge32 ::= TEXTUAL-CONVENTION
    STATUS       current
    DESCRIPTION
    "The Gauge32 type represents a non-negative integer, which may
    increase or decrease, but shall never exceed a maximum value.  The
    maximum value can not be greater than 2^32-1 (4294967295 decimal).
    The value of a Gauge has its maximum value whenever the information
    being modeled is greater or equal to that maximum value; if the
    information being modeled subsequently decreases below the maximum
    value, the Gauge also decreases."
    SYNTAX       INTEGER ( 0..4294967295 )  
  
  	
NtnTruthValue ::= TEXTUAL-CONVENTION
STATUS current
DESCRIPTION " Represents the boolean yes (1) or no (2) "
SYNTAX INTEGER { yes(1), no(2) }
  
	 
-- Objects
         
ntntechNamingTree OBJECT IDENTIFIER ::= { ntntechRootMIB 1 }
-- OBJECT-IDENTITY
--  Status
--    current
--  Description
--    Net to Net Technologies, Inc. object identifiers.  
      
ntntechChassis OBJECT IDENTIFIER ::= { ntntechNamingTree 1 }
-- OBJECT-IDENTITY
--  Status
--    current
--  Description
--    Net to Net Technologies, Inc. object identifiers.      

ntntechChassisConfigurationMIB OBJECT IDENTIFIER ::= { ntntechChassis 1 }
-- OBJECT-IDENTITY
--  Status
--    current
--  Description
--    Net to Net Technologies, Inc. object identifiers.  
-- 	  All chassis parameter settings (configuration) are
--    defined here.          

ntntechChassisStatusMIB OBJECT IDENTIFIER ::= { ntntechChassis 2 }
-- OBJECT-IDENTITY
--  Status
--    current
--  Description
--    Net to Net Technologies, Inc. object identifiers.  
--	  All chassis statistics and state values are defined
--	  here.    

ntntechInterfaceModule OBJECT IDENTIFIER ::= { ntntechNamingTree 2 } 
-- OBJECT-IDENTITY
--  Status
--    mandatory
--  Description
--    Net to Net Technologies, Inc. object identifiers.    

ntntechInterfaceModuleConfigurationMIB OBJECT IDENTIFIER ::= { ntntechInterfaceModule 1 }
-- OBJECT-IDENTITY
--  Status
--    current
--  Description
--    Net to Net Technologies, Inc. object identifiers.  
-- 	  All Interface port parameter settings are 
-- 	  defined here.  
     
ntntechInterfaceModuleStatusMIB OBJECT IDENTIFIER ::= { ntntechInterfaceModule 2 }
-- OBJECT-IDENTITY
--  Status
--    current
--  Description
--    Net to Net Technologies, Inc. object identifiers.   
-- 	  All Interface port statistic and state 
--	  values are defined here.  

ntntechQoSMIB OBJECT IDENTIFIER ::= { ntntechInterfaceModule 3 }
-- OBJECT-IDENTITY
--  Status
--    current
--  Description
--	  Net to Net Technologies, Inc. object identifiers.
-- 	  All Interface port QOS attributes are defined here.

ntntechNMSTraps OBJECT IDENTIFIER ::= { ntntechNamingTree 3 }
-- OBJECT-IDENTITY
--  Status
--    current
--  Description
--    Net to Net Technologies, Inc. object identifiers. 

ntntechNMSTrapsMIB OBJECT IDENTIFIER ::= { ntntechNMSTraps 1 }
-- OBJECT-IDENTITY
--  Status
--    current
--  Description
--    Net to Net Technologies, Inc. object identifiers.
-- 	  All NMS trap values are defined here.  
   

ntntechSystemObjects OBJECT IDENTIFIER ::= { ntntechNamingTree 4 }
-- OBJECT-IDENTITY
--  Status
--    current
--  Description
--    Net to Net Technologies, Inc. object identifiers. 

ntntechSystemObjectsIdentifierMIB OBJECT IDENTIFIER ::= { ntntechSystemObjects 1 }
-- OBJECT-IDENTITY
--  Status
--    current
--  Description
--    Net to Net Technologies, Inc. object identifiers.  
-- 	  All system object identification values (OID) are defined here.  
 

 
   
END
