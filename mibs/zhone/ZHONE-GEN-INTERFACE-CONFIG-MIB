--
-- genIntfConfig.mib
-- MIB generated by MG-SOFT Visual MIB Builder Version 3.0 Build 285
-- Friday, December 17, 2010 at 10:44:00
--

    ZHONE-GEN-INTERFACE-CONFIG-MIB DEFINITIONS ::= BEGIN
 
        IMPORTS
            ifIndex            
                FROM IF-MIB            
            Integer32, OBJECT-TYPE, MODULE-IDENTITY, OBJECT-IDENTITY, NOTIFICATION-TYPE            
                FROM SNMPv2-SMI            
            TruthValue            
                FROM SNMPv2-TC            
            zhoneInterfaceConfig, zhoneModules            
                FROM Zhone            
            ZhoneAlarmSeverity, ZhoneRowStatus            
                FROM Zhone-TC;
    
    
-- To create the Profile files:
-- /vob/zhonetools/bin/pahrser.pl Zhone-TC.mib genIntfConfig.mib 
-- 
-- To create the mib handler files:
-- /vob/EPILOGUE/binaries/emissary/solaris/mibcomp iftype.mib rfc1907.mib rfc2233.mib Zhone.mib Zhone-TC.mib genIntfConfig.mib -stub -o alarmConfigMibHdlr.c
-- 
-- To create the css files:
-- /vob/zhonetools/bin/pahrser.pl -css Zhone-TC.mib genIntfConfig.mib
--  
-- 
        -- 1.3.6.1.4.1.5504.3.13.1
        alarmConfigMib MODULE-IDENTITY 
            LAST-UPDATED "201012071714Z"		-- December 07, 2010 at 17:14 GMT
            ORGANIZATION 
                "Organization."
            CONTACT-INFO 
                "Contact-info."
            DESCRIPTION 
                "Description."
            REVISION "201012070237Z"		-- December 07, 2010 at 02:37 GMT
            DESCRIPTION 
                "V01.00.02 - Added alarmSeverity"
            REVISION "200802260625Z"		-- February 26, 2008 at 06:25 GMT
            DESCRIPTION 
                "V01.00.01 - adding alarmConfigTraps"
            ::= { zhoneInterfaceConfig 1 }

        
    
    
--
-- Node definitions
--
    
        -- 1.3.6.1.4.1.5504.3.13.1.1
        alarmConfigTable OBJECT-TYPE
            SYNTAX SEQUENCE OF AlarmConfigEntry
            MAX-ACCESS not-accessible
            STATUS current
            DESCRIPTION
                "The alarm configuration table"
            ::= { alarmConfigMib 1 }

        
        -- 1.3.6.1.4.1.5504.3.13.1.1.1
        alarmConfigEntry OBJECT-TYPE
            SYNTAX AlarmConfigEntry
            MAX-ACCESS not-accessible
            STATUS current
            DESCRIPTION
                "An entry in the alarm configuration table."
            INDEX { ifIndex }
            ::= { alarmConfigTable 1 }

        
        AlarmConfigEntry ::=
            SEQUENCE { 
                alarmConfigBitRateThreshold
                    TruthValue,
                alarmConfigBitRateThresholdValue
                    Integer32,
                alarmConfigBitRateThresholdHoldtime
                    Integer32,
                alarmConfigStatusTrap
                    TruthValue,
                alarmConfigAdminUp
                    TruthValue,
                alarmConfigAlarmSeverity
                    ZhoneAlarmSeverity,
                alarmConfigRowStatus
                    ZhoneRowStatus
             }

        -- 1.3.6.1.4.1.5504.3.13.1.1.1.1
        alarmConfigBitRateThreshold OBJECT-TYPE
            SYNTAX TruthValue
            MAX-ACCESS read-create
            STATUS current
            DESCRIPTION
                "This field describes the enable status of the 
                Bit Rate Threshold Alarm.  If this field is 
                true (1) then the Bit Rate Threshold alarm is 
                enabled.  If this field is false (2) then the 
                Bit Rate Threshold Alarm is disabled."
            ::= { alarmConfigEntry 1 }

        
        -- 1.3.6.1.4.1.5504.3.13.1.1.1.2
        alarmConfigBitRateThresholdValue OBJECT-TYPE
            SYNTAX Integer32
            MAX-ACCESS read-create
            STATUS current
            DESCRIPTION
                "This field indicates the Bit Rate Threshold 
                Value which will generate an alarm if the Bit 
                Rate Threshold Alarm is enabled and the Bit
                Rate of this ifIndex drops below this value."
            ::= { alarmConfigEntry 2 }

        
        -- 1.3.6.1.4.1.5504.3.13.1.1.1.3
        alarmConfigBitRateThresholdHoldtime OBJECT-TYPE
            SYNTAX Integer32
            MAX-ACCESS read-create
            STATUS current
            DESCRIPTION
                "This field indicates the Bit Rate Threshold 
                Holdtime in seconds for which the Bit Rate of 
                the ifIndex must remain below the Bit Rate
                Threshold Value before an alarm will be 
                generated if the Bit Rate Threshold Alarm is
                enabled. "
            ::= { alarmConfigEntry 3 }

        
        -- 1.3.6.1.4.1.5504.3.13.1.1.1.4
        alarmConfigStatusTrap OBJECT-TYPE
            SYNTAX TruthValue
            MAX-ACCESS read-create
            STATUS current
            DESCRIPTION
                "This field describes the enable status of the 
                Status Trap Alarm.  If this field is 
                true (1) then the Status Trap alarm is 
                enabled.  If this field is false (2) then the 
                Status Trap Alarm is disabled."
            ::= { alarmConfigEntry 4 }

        
        -- 1.3.6.1.4.1.5504.3.13.1.1.1.5
        alarmConfigAdminUp OBJECT-TYPE
            SYNTAX TruthValue
            MAX-ACCESS read-create
            STATUS current
            DESCRIPTION
                "This field describes the enable status of the 
                Admin Up Alarm.  If this field is 
                true (1) then the Admin Up alarm is enabled.  
                If this field is false (2) then the 
                Admin Up Alarm is disabled."
            ::= { alarmConfigEntry 5 }

        
        -- 1.3.6.1.4.1.5504.3.13.1.1.1.6
        alarmConfigAlarmSeverity OBJECT-TYPE
            SYNTAX ZhoneAlarmSeverity
            MAX-ACCESS read-create
            STATUS current
            DESCRIPTION
                "This object is used to override Trap, Central Alarm Manager and CLI 'LineAlarm' severity levels for the specified interface. "
            ::= { alarmConfigEntry 6 }

        
        -- 1.3.6.1.4.1.5504.3.13.1.1.1.7
        alarmConfigRowStatus OBJECT-TYPE
            SYNTAX ZhoneRowStatus
            MAX-ACCESS read-create
            STATUS current
            DESCRIPTION
                "This object is used to create, delete or modify a row in this table. "
            ::= { alarmConfigEntry 7 }

        
        -- 1.3.6.1.4.1.5504.3.13.1.2
        alarmConfigTraps OBJECT IDENTIFIER ::= { alarmConfigMib 2 }

        
        -- 1.3.6.1.4.1.5504.3.13.1.2.0
        alarmConfigTrapPrefix OBJECT-IDENTITY
            STATUS current
            DESCRIPTION 
                "Description."
            ::= { alarmConfigTraps 0 }

        
        -- 1.3.6.1.4.1.5504.3.13.1.2.0.1
        zhoneAlarmConfigThresholdTrap NOTIFICATION-TYPE
            STATUS current
            DESCRIPTION 
                "This Trap is generated when this ifIndex bandwidth drops
                below the alarmConfigBitRateThresholdValue for the time
                specified in alarmConfigBitRateThesholdHoldtime."
            ::= { alarmConfigTrapPrefix 1 }

        
        -- 1.3.6.1.4.1.5504.3.13.1.2.0.2
        zhoneAlarmConfigThresholdClearTrap NOTIFICATION-TYPE
            STATUS current
            DESCRIPTION 
                "This trap is generated when this ifIndex bandwidth
                goes above the alarmConfigBitRateThresholdValue for
                the time specified in alarmConfigBitRateThresholdHoldtime."
            ::= { alarmConfigTrapPrefix 2 }

        
    
    END

--
-- genIntfConfig.mib
--
