--
-- comPtp.mib
-- MIB generated by MG-SOFT Visual MIB Builder Version 3.0 Build 285
-- Thursday, May 16, 2013 at 13:21:18
--

	Zhone-PTP-MIB DEFINITIONS ::= BEGIN
 
		IMPORTS
			InterfaceIndex			
				FROM IF-MIB			
			OBJECT-GROUP			
				FROM SNMPv2-CONF			
			IpAddress, Integer32, Unsigned32, OBJECT-TYPE, MODULE-IDENTITY			
				FROM SNMPv2-SMI			
			MacAddress			
				FROM SNMPv2-TC			
			zhonePtp, zhoneModules, zhoneGroups, zhoneShelfSlotGroup			
				FROM Zhone			
			ZhoneRowStatus			
				FROM Zhone-TC;
	
	
-- /vob/zhonetools/bin/pahrser.pl rfc2233.mib Zhone.mib Zhone-TC.mib comPtp.mib
-- 
-- /vob/EPILOGUE/binaries/emissary/solaris/mibcomp rfc1907.mib iftype.mib
-- rfc2233.mib Zhone.mib Zhone-TC.mib -stub -o ptpHdlrs.c comPtp.mib
-- 
-- 
		-- 1.3.6.1.4.1.5504.6.119
		zhonePtpModule MODULE-IDENTITY 
			LAST-UPDATED "201205091450Z"		-- May 09, 2012 at 14:50 GMT
			ORGANIZATION 
				"Zhone Technologies."
			CONTACT-INFO 
				"Contact-info."
			DESCRIPTION 
				"Managed data objects for Zhone's 1588 Precision Timing Protocol."
			REVISION "201305091515Z"		-- May 09, 2013 at 15:15 GMT
			DESCRIPTION 
				"Add ipIfindex & acceptable master fields to ptp"
			REVISION "201201131450Z"		-- January 13, 2012 at 14:50 GMT
			DESCRIPTION 
				"Initial Revision."
			::= { zhoneModules 119 }

		
	
	
--
-- Node definitions
--
	
		-- 1.3.6.1.4.1.5504.4.17.1
		zhonePtpObjectID OBJECT IDENTIFIER ::= { zhonePtp 1 }

		
		-- 1.3.6.1.4.1.5504.4.17.1.1
		zhonePtpConfigTable OBJECT-TYPE
			SYNTAX SEQUENCE OF ZhonePtpConfigEntry
			MAX-ACCESS not-accessible
			STATUS current
			DESCRIPTION
				"Table of configuration values for the Precision Timing Protocol."
			::= { zhonePtpObjectID 1 }

		
		-- 1.3.6.1.4.1.5504.4.17.1.1.1
		zhonePtpConfigEntry OBJECT-TYPE
			SYNTAX ZhonePtpConfigEntry
			MAX-ACCESS not-accessible
			STATUS current
			DESCRIPTION
				"Row in the PtpConfigTable"
			INDEX { zhonePtpConfigIfIndex }
			::= { zhonePtpConfigTable 1 }

		
		ZhonePtpConfigEntry ::=
			SEQUENCE { 
				zhonePtpConfigIfIndex
					InterfaceIndex,
				zhonePtpConfigClockMode
					INTEGER,
				zhonePtpConfigSyncMsgInterval
					Integer32,
				zhonePtpConfigAnnounceInterval
					Integer32,
				zhonePtpConfigDelayReqInterval
					Integer32,
				zhonePtpConfigDomain1MS
					Unsigned32,
				zhonePtpConfigVariance
					Unsigned32,
				zhonePtpConfigPriority1
					Unsigned32,
				zhonePtpConfigPriority2
					Unsigned32,
				zhonePtpConfigDomain2M
					Integer32,
				zhonePtpConfigRowStatus
					ZhoneRowStatus,
				zhonePtpConfigIpIfIndex
					InterfaceIndex,
				zhonePtpConfigAcceptableMaster1
					IpAddress,
				zhonePtpConfigAcceptableMaster2
					IpAddress
			 }

		-- 1.3.6.1.4.1.5504.4.17.1.1.1.1
		zhonePtpConfigIfIndex OBJECT-TYPE
			SYNTAX InterfaceIndex
			MAX-ACCESS not-accessible
			STATUS current
			DESCRIPTION
				"Index for this table."
			::= { zhonePtpConfigEntry 1 }

		
		-- 1.3.6.1.4.1.5504.4.17.1.1.1.2
		zhonePtpConfigClockMode OBJECT-TYPE
			SYNTAX INTEGER
				{
				master(1),
				slave(2),
				boundary(3),
				transparent(4),
				forward(5)
				}
			MAX-ACCESS read-create
			STATUS current
			DESCRIPTION
				"Describes the mode and function of this clock."
			DEFVAL { slave }
			::= { zhonePtpConfigEntry 2 }

		
		-- 1.3.6.1.4.1.5504.4.17.1.1.1.3
		zhonePtpConfigSyncMsgInterval OBJECT-TYPE
			SYNTAX Integer32 (-128..127)
			MAX-ACCESS read-create
			STATUS current
			DESCRIPTION
				"Log of mean time interval between successive Sync 
				messages when transmitted as multicast messages."
			DEFVAL { -5 }
			::= { zhonePtpConfigEntry 3 }

		
		-- 1.3.6.1.4.1.5504.4.17.1.1.1.4
		zhonePtpConfigAnnounceInterval OBJECT-TYPE
			SYNTAX Integer32 (-128..127)
			MAX-ACCESS read-create
			STATUS current
			DESCRIPTION
				"Log of time, in seconds, to send announce messages."
			DEFVAL { 1 }
			::= { zhonePtpConfigEntry 4 }

		
		-- 1.3.6.1.4.1.5504.4.17.1.1.1.5
		zhonePtpConfigDelayReqInterval OBJECT-TYPE
			SYNTAX Integer32 (-128..127)
			MAX-ACCESS read-create
			STATUS current
			DESCRIPTION
				"Log of minimum permitted mean time between successive
				Delay_Req messages sent by a slave to a specific port
				on the master."
			::= { zhonePtpConfigEntry 5 }

		
		-- 1.3.6.1.4.1.5504.4.17.1.1.1.6
		zhonePtpConfigDomain1MS OBJECT-TYPE
			SYNTAX Unsigned32 (0..255)
			MAX-ACCESS read-create
			STATUS current
			DESCRIPTION
				"The domain for this PTP. If clockMode is boundary, then this 
				is the domain for the slave port."
			DEFVAL { 0 }
			::= { zhonePtpConfigEntry 6 }

		
		-- 1.3.6.1.4.1.5504.4.17.1.1.1.7
		zhonePtpConfigVariance OBJECT-TYPE
			SYNTAX Unsigned32 (0..65535)
			MAX-ACCESS read-create
			STATUS current
			DESCRIPTION
				"Log of variance used in determination of the best master clock."
			DEFVAL { 32767 }
			::= { zhonePtpConfigEntry 7 }

		
		-- 1.3.6.1.4.1.5504.4.17.1.1.1.8
		zhonePtpConfigPriority1 OBJECT-TYPE
			SYNTAX Unsigned32 (0..255)
			MAX-ACCESS read-create
			STATUS current
			DESCRIPTION
				"Precedence value used in best master algorithm, if master."
			DEFVAL { 128 }
			::= { zhonePtpConfigEntry 8 }

		
		-- 1.3.6.1.4.1.5504.4.17.1.1.1.9
		zhonePtpConfigPriority2 OBJECT-TYPE
			SYNTAX Unsigned32 (0..255)
			MAX-ACCESS read-create
			STATUS current
			DESCRIPTION
				"Precedence used in best master determination, if master"
			DEFVAL { 128 }
			::= { zhonePtpConfigEntry 9 }

		
		-- 1.3.6.1.4.1.5504.4.17.1.1.1.10
		zhonePtpConfigDomain2M OBJECT-TYPE
			SYNTAX Integer32 (0..255)
			MAX-ACCESS read-create
			STATUS current
			DESCRIPTION
				"If clockMode is boundary, then this is the domain for the
				master port. Otherwise, it is unused."
			DEFVAL { 0 }
			::= { zhonePtpConfigEntry 10 }

		
		-- 1.3.6.1.4.1.5504.4.17.1.1.1.11
		zhonePtpConfigRowStatus OBJECT-TYPE
			SYNTAX ZhoneRowStatus
			MAX-ACCESS read-create
			STATUS current
			DESCRIPTION
				"Row status for this table."
			::= { zhonePtpConfigEntry 11 }

		
		-- 1.3.6.1.4.1.5504.4.17.1.1.1.12
		zhonePtpConfigIpIfIndex OBJECT-TYPE
			SYNTAX InterfaceIndex
			MAX-ACCESS read-create
			STATUS current
			DESCRIPTION
				"The management ip index on this system."
			::= { zhonePtpConfigEntry 12 }

		
		-- 1.3.6.1.4.1.5504.4.17.1.1.1.13
		zhonePtpConfigAcceptableMaster1 OBJECT-TYPE
			SYNTAX IpAddress
			MAX-ACCESS read-create
			STATUS current
			DESCRIPTION
				"First acceptable PTP master."
			DEFVAL { '00000000'h }
			::= { zhonePtpConfigEntry 13 }

		
		-- 1.3.6.1.4.1.5504.4.17.1.1.1.14
		zhonePtpConfigAcceptableMaster2 OBJECT-TYPE
			SYNTAX IpAddress
			MAX-ACCESS read-create
			STATUS current
			DESCRIPTION
				"Second acceptable PTP master."
			DEFVAL { '00000000'h }
			::= { zhonePtpConfigEntry 14 }

		
		-- 1.3.6.1.4.1.5504.4.17.1.2
		zhonePtpStatusTable OBJECT-TYPE
			SYNTAX SEQUENCE OF ZhonePtpStatusEntry
			MAX-ACCESS not-accessible
			STATUS current
			DESCRIPTION
				"The read-only attributes associated with the 1588 module."
			::= { zhonePtpObjectID 2 }

		
		-- 1.3.6.1.4.1.5504.4.17.1.2.1
		zhonePtpStatusEntry OBJECT-TYPE
			SYNTAX ZhonePtpStatusEntry
			MAX-ACCESS not-accessible
			STATUS current
			DESCRIPTION
				"A row in the zhonePtpStatusTable"
			INDEX { zhonePtpConfigIfIndex }
			::= { zhonePtpStatusTable 1 }

		
		ZhonePtpStatusEntry ::=
			SEQUENCE { 
				zhonePtpStatusMacAddress
					MacAddress,
				zhonePtpConfigTimeSource
					INTEGER,
				zhonePtpConfigClockStratum
					INTEGER,
				zhonePtpConfigClockAccuracy
					INTEGER,
				zhonePtpStatusTxMode
					INTEGER
			 }

		-- 1.3.6.1.4.1.5504.4.17.1.2.1.1
		zhonePtpStatusMacAddress OBJECT-TYPE
			SYNTAX MacAddress
			MAX-ACCESS read-only
			STATUS current
			DESCRIPTION
				"The ptpMacAddr is used to set the PTP ClockIdentifier defined
				in the PTP standard. It identifies the clock in the PTP network 
				and as such should be unique within the PTP network.
				 "
			::= { zhonePtpStatusEntry 1 }

		
		-- 1.3.6.1.4.1.5504.4.17.1.2.1.2
		zhonePtpConfigTimeSource OBJECT-TYPE
			SYNTAX INTEGER
				{
				atom(1),
				gps(2),
				radio(3),
				ptp(4),
				ntp(5),
				handSet(6),
				other(7),
				internalOscillator(8)
				}
			MAX-ACCESS read-only
			STATUS current
			DESCRIPTION
				"Time source for the PTP."
			DEFVAL { internalOscillator }
			::= { zhonePtpStatusEntry 2 }

		
		-- 1.3.6.1.4.1.5504.4.17.1.2.1.3
		zhonePtpConfigClockStratum OBJECT-TYPE
			SYNTAX INTEGER
				{
				force(1),
				primaryReference(2),
				secondaryReference(3),
				bestClockStratumThatCanBeSlave(4),
				stratum3(5),
				stratum4(6),
				defaultStratum(7)
				}
			MAX-ACCESS read-only
			STATUS current
			DESCRIPTION
				"Indicates the stratum level of the local clock."
			DEFVAL { defaultStratum }
			::= { zhonePtpStatusEntry 3 }

		
		-- 1.3.6.1.4.1.5504.4.17.1.2.1.4
		zhonePtpConfigClockAccuracy OBJECT-TYPE
			SYNTAX INTEGER
				{
				nSec25(1),
				nSec100(2),
				nSec250(3),
				uSec1(4),
				uSec2point5(5),
				uSec10(6),
				uSec25(7),
				uSec100(8),
				uSec250(9),
				mSec1(10),
				mSec2point5(11),
				mSec10(12),
				mSec25(13),
				mSec100(14),
				mSec250(15),
				sec1(16),
				sec10(17),
				gT10S(18),
				accUnknown(19)
				}
			MAX-ACCESS read-only
			STATUS current
			DESCRIPTION
				"Accuracy of this clock. Used in determining best master clock."
			DEFVAL { accUnknown }
			::= { zhonePtpStatusEntry 4 }

		
		-- 1.3.6.1.4.1.5504.4.17.1.2.1.5
		zhonePtpStatusTxMode OBJECT-TYPE
			SYNTAX INTEGER
				{
				standard(1),
				uniOnly(2),
				multiOnly(3)
				}
			MAX-ACCESS read-only
			STATUS current
			DESCRIPTION
				"By default, Semtech sends multicast messages (e.g. Announce Messages) if they
				are meant for more than one node. Messages destined to a single node are sent 
				as unicast messages. If we want to support Acceptable Master and Slave tables, 
				we need the uniOnly option."
			DEFVAL { standard }
			::= { zhonePtpStatusEntry 5 }

		
		-- 1.3.6.1.4.1.5504.9.1.52
		zhonePtpGroup OBJECT-GROUP
			OBJECTS { zhonePtpConfigClockMode, zhonePtpConfigIpIfIndex, zhonePtpConfigSyncMsgInterval, zhonePtpConfigAnnounceInterval, zhonePtpConfigDelayReqInterval, 
				zhonePtpConfigTimeSource, zhonePtpConfigClockStratum, zhonePtpConfigClockAccuracy, zhonePtpConfigVariance, zhonePtpConfigPriority1, 
				zhonePtpConfigPriority2, zhonePtpConfigRowStatus, zhonePtpStatusTxMode, zhonePtpStatusMacAddress, zhonePtpConfigDomain2M, 
				zhonePtpConfigDomain1MS, zhonePtpConfigAcceptableMaster1, zhonePtpConfigAcceptableMaster2 }
			STATUS current
			DESCRIPTION 
				"Object groups for ptp objects."
			::= { zhoneGroups 52 }

		
	
	END

--
-- comPtp.mib
--
