--
-- genMasterAgent.mib
-- MIB generated by MG-SOFT Visual MIB Builder Version 2.0 Build 187
-- Tuesday, September 12, 2000 at 11:16:40
--

	ZhoneMasterAgent-MIB DEFINITIONS ::= BEGIN

		IMPORTS 
			Integer32, Counter32, OBJECT-TYPE, MODULE-IDENTITY			
				FROM SNMPv2-SMI			
			zhoneMasterAgent, zhoneModules			
				FROM Zhone;
	
	
-- 
-- 
		zhoneMasterAgentMIB MODULE-IDENTITY
			LAST-UPDATED "200009121459Z"
			ORGANIZATION
				"Zhone Technogogies, Inc."
			CONTACT-INFO
				"   Postal: 
				           Zhone Technologies, Inc.
				           @ Zhone Way
				           7001 Oakport Street
				           Oakland, CA  94621
				           USA
				Toll-Free: +1 877-ZHONE20 (+1 877-946-6320)
				      Tel: +1-510-777-7000
				      Fax: +1-510-777-7001
				   E-mail: support@zhone.com"
			DESCRIPTION
				"The MIB module to describe the Zhone specific
				implementation of the Master Agent. These fields 
				go beyond those defined in RFC1907 (snmp)."
			REVISION "200009121116Z"
			DESCRIPTION
				"V01.00.00 - Initial Release"
			::= { zhoneModules 10 }
		
	
--
-- Node definitions
--
	
		maRequestPort OBJECT-TYPE
			SYNTAX Integer32 (0..65535)
			MAX-ACCESS read-write
			STATUS current
			DESCRIPTION
				"The IP Port number that should be used by 
				the SNMP manager when sending/receiving messages.
				
				This will not be used in the initial release.
				
				The default value for this field is 161."
			::= { zhoneMasterAgent 1 }
		
		maTrapPort OBJECT-TYPE
			SYNTAX Integer32 (0..65535)
			MAX-ACCESS read-write
			STATUS current
			DESCRIPTION
				"The IP port number that should be used when 
				sending traps to any Fault Manager Service."
			::= { zhoneMasterAgent 2 }
		
		maPerfSaRequests OBJECT-TYPE
			SYNTAX Counter32
			MAX-ACCESS read-only
			STATUS current
			DESCRIPTION
				"Number of requests sent by the Master Agent to any
				Sub-Agent in the device. In a single SNMP PDU, multiple 
				Sub-Agents may be required to process the individual
				VarBinds. This count will increment for each of these
				individual messages and therefore is not a 1:1 
				relationship with the number of SNMP PDU's requiring
				Sub-Agent Processing. "
			::= { zhoneMasterAgent 3 }
		
		maPerfSaResponses OBJECT-TYPE
			SYNTAX Counter32
			MAX-ACCESS read-only
			STATUS current
			DESCRIPTION
				"Number of Sub-Agent responses to the requests issued.
				Unless there are internal errors, this should match the
				maSARequestCount"
			::= { zhoneMasterAgent 4 }
		
		maPerfSnmpErrors OBJECT-TYPE
			SYNTAX Counter32
			MAX-ACCESS read-only
			STATUS current
			DESCRIPTION
				"The number of Master-Agent errors detected on SNMP
				PDU's received. Examples are parsing errors but does
				not include such items as community table invalid and
				noSuchInstance cases."
			::= { zhoneMasterAgent 5 }
		
		maPerfSaTimeouts OBJECT-TYPE
			SYNTAX Counter32
			MAX-ACCESS read-only
			STATUS current
			DESCRIPTION
				"The number of timeouts that have occurred due to a lack
				of response from a sub-agent to a request."
			::= { zhoneMasterAgent 6 }
		
	
	END

--
-- genMasterAgent.mib
--
