-- Copyright (C) 2003 Paradyne Corporation.        
PDN-IF-EXT-CONFIG-MIB DEFINITIONS ::= BEGIN

IMPORTS
	MODULE-IDENTITY, OBJECT-TYPE
	 FROM SNMPv2-SMI
	TEXTUAL-CONVENTION
	 FROM SNMPv2-TC
        ifIndex
	 FROM IF-MIB
        MODULE-COMPLIANCE, OBJECT-GROUP
	 FROM SNMPv2-CONF
        pdnIfExt
	 FROM PDN-HEADER-MIB
	pdnIfExtConfig
	 FROM PDN-IFEXT-MIB
        ;	

pdnIfExtEncapConfig MODULE-IDENTITY
	LAST-UPDATED "200312160900Z"
	ORGANIZATION "Paradyne Networks
		      MIB Working Group"

 	CONTACT-INFO "Paradyne Networks, Inc.
		      8545 126th Ave North
		      Largo, FL 33733
		      www.paradyne.com

		      General Comments to:
	mibwg_team@eng.paradyne.com

		      Editors
		      Dragana Gough,
		      Jesus Pinto" 

	DESCRIPTION
             "This Mib is created to facilitate  
	      configuration of interface related objects."

	REVISION "200312160900Z"
	DESCRIPTION " Jesus Pinto
            o Added LinkRole TEXTUAL-CONVENTION
	    o Added pdnIfXLinkConfigTable."

	REVISION "200111130000Z"
	DESCRIPTION " Dragana Gough
            o updated object name for
	      pdnIfMultiprotocolEncapConfigIPBridgedPDUs
	      to pdnIfMultiprotocolEncapConfigBridgedPDUs."

	REVISION "200111120000Z"
	DESCRIPTION " Dragana Gough
            o updated comment for
	      pdnIfMultiprotocolEncapConfigIPRoutedPDUs
	      to fix description field
	    o added new object
	      pdnIfMultiprotocolEncapConfigIPBridgedPDUs
	      to supported bridged pdus configuration"

	REVISION "200005110000Z"
	DESCRIPTION " Dragana Gough
	    o updated after mibwg meeting
	    o changed table name
	    o rearranged enum values in pdnIfExtConfigIPRoutedPDU
	    o define groups for compliance "

        REVISION "200005030000Z"
	DESCRIPTION " Dragana Gough
	    o changed enum names "

	REVISION "200005020000Z"
	DESCRIPTION " Dragana Gough
            o Initial Version "

	::= { pdnIfExt 3 }

--
-- Textual Conventions
--
-- Note: Although 'other' is a vague value, we want to leave it like
--	 that for now for flexibility. We'll refine that later.
--	 
PdnLinkRole ::= TEXTUAL-CONVENTION
	STATUS	current
	DESCRIPTION
		"Objects defined with this textual convention 	
		are used to indicate the usage of the link.

		uplink   (1) :  interface is used as uplink
		other    (2) :  interface is used for something other
			        than uplink (e.g, subtending).
		"

	SYNTAX  INTEGER { 
			uplink   (1),
			other    (2)
			}
	
--
--  Interface Configuration Group 
--
  pdnIfMultiprotocolEncapConfigTable  OBJECT-TYPE
    SYNTAX  SEQUENCE OF PdnIfMultiprotocolEncapConfigEntry 
    MAX-ACCESS  not-accessible
    STATUS current 
    DESCRIPTION
	    " This table that contains additional  
	      interface configuration information. "
    ::= { pdnIfExtEncapConfig 1 }

 pdnIfMultiprotocolEncapConfigEntry OBJECT-TYPE
    SYNTAX   PdnIfMultiprotocolEncapConfigEntry
    MAX-ACCESS   not-accessible
    STATUS  current 
    DESCRIPTION
	     " There will be one of these rows for each interface that 
	       supports RFC1483. "
    INDEX { ifIndex }
    ::= { pdnIfMultiprotocolEncapConfigTable 1 }

 PdnIfMultiprotocolEncapConfigEntry ::=
    SEQUENCE {
         pdnIfMultiprotocolEncapConfigIPRoutedPDUs	   INTEGER,
         pdnIfMultiprotocolEncapConfigBridgedPDUs	   INTEGER
            }

 pdnIfMultiprotocolEncapConfigIPRoutedPDUs   OBJECT-TYPE
     SYNTAX     INTEGER { none    (1), 
			  llcSnap (2),
			  vcBasedMultiplexing (3) 
			}
     MAX-ACCESS	read-write
     STATUS     current	
     DESCRIPTION
	"In the upstream direction user can configure the IP 
	routed PDUs in the LLC SNAP encapsulation or VC Based
	Multiplexing encapsulation (RFC1483). If neither is 
	configured 'none' is used. The direction is determined
	by the transmit direction. Initialy this object was
	developed for the endpoint use where the transmit direction
	is upstream. This object could be used for CO type equipment
	where the direction would be downstream."
     ::= { pdnIfMultiprotocolEncapConfigEntry 1 }

 pdnIfMultiprotocolEncapConfigBridgedPDUs   OBJECT-TYPE
     SYNTAX     INTEGER { none    (1), 
			  llcSnap (2),
			  vcBasedMultiplexing (3) 
			}
     MAX-ACCESS	read-write
     STATUS     current	
     DESCRIPTION
	 "In the transmit direction user can configure the IP
	 routed PDUs in the LLC SNAP encapsulation or VC Based
	 Multiplexing encapsulation (RFC1483). If neither is
	 configured 'none' is used."
     ::= { pdnIfMultiprotocolEncapConfigEntry 2 }

--
--  ifXLinkConfig Table
--
--  	This table allows configuration of interfaces
--	that are capable of switching roles at run-time.
--
--	Right now, the primary usage of this table is
--	to configure the uplink role among interfaces.
--

pdnIfXLinkConfigTable  OBJECT-TYPE
    SYNTAX      SEQUENCE OF PdnIfXLinkConfigEntry
    MAX-ACCESS  not-accessible
    STATUS 	current
    DESCRIPTION
	 "This table contains configuration information
	 for interfaces that are capable of switch roles
	 at run-time.
	"
    ::= { pdnIfExtConfig 3 }

pdnIfXLinkConfigEntry OBJECT-TYPE
    SYNTAX       PdnIfXLinkConfigEntry
    MAX-ACCESS   not-accessible
    STATUS       current 
    DESCRIPTION
	"An entry in this table represents an interface
      	that is capable of being used as an uplink.

	Typically, this table will contain entries only
	for interfaces that are capable of switching roles.
	"
    INDEX { ifIndex }	
    ::= { pdnIfXLinkConfigTable 1 }

PdnIfXLinkConfigEntry ::=
    SEQUENCE {
         	pdnIfXLinkConfigRole	PdnLinkRole
	     }

pdnIfXLinkConfigRole   OBJECT-TYPE
     SYNTAX     PdnLinkRole
     MAX-ACCESS	read-write
     STATUS     current	
     DESCRIPTION
	"This object allows users to configure the role
	(e.g., uplink) intended for this interface.
	"
     ::= { pdnIfXLinkConfigEntry 1 }

-- =============================================================================
-- ==                  Conformance Information                                ==
-- =============================================================================
pdnIfMultiprotocolEncapMIBConformance	OBJECT IDENTIFIER 
	::= {pdnIfExtEncapConfig 2 }

pdnIfMultiprotocolEncapMIBGroups	OBJECT IDENTIFIER 
	::= {pdnIfMultiprotocolEncapMIBConformance 1}

pdnIfMultiprotocolEncapCompliances      OBJECT IDENTIFIER 
	::= {pdnIfMultiprotocolEncapMIBConformance 2}

pdnIfXConfigMIBConformance		OBJECT IDENTIFIER
	::= {pdnIfExt 4}

pdnIfXConfigMIBGroups			OBJECT IDENTIFIER
	::= {pdnIfXConfigMIBConformance 1}


-- ===========================
-- == Compliance Statements ==
-- ===========================
pdnIfMultiprotocolEncapCompliance	MODULE-COMPLIANCE
   STATUS   current
   DESCRIPTION	
      " The compliance statement for SNMP entities which support
        RFC1483 Multiprotocol Encapsulation over ATM adaptation layer 5."

   MODULE -- this module

   GROUP pdnIfMultiprotocolEncapsulationOptionalGroup
   DESCRIPTION
    	"This optional group is used for the configuration of
      	interfaces that support RFC1483."
   OBJECT pdnIfMultiprotocolEncapConfigIPRoutedPDUs
   MIN-ACCESS  read-only
   DESCRIPTION 
	"Write access is not required. "

   OBJECT pdnIfMultiprotocolEncapConfigBridgedPDUs
   MIN-ACCESS  read-only
   DESCRIPTION 
	" Write access is not required. "

   GROUP pdnIfXLinkConfigOptionalGroup
   DESCRIPTION
	"This optional group is used for configuration of
	interfaces used as uplink or downlinks."
   OBJECT pdnIfXLinkConfigRole
   MIN-ACCESS read-only
   DESCRIPTION
	"Write access is not required."

   ::= { pdnIfMultiprotocolEncapCompliances 1 }

pdnIfMultiprotocolEncapsulationOptionalGroup   OBJECT-GROUP
   OBJECTS {
	    pdnIfMultiprotocolEncapConfigIPRoutedPDUs,
	    pdnIfMultiprotocolEncapConfigBridgedPDUs 
	   }
   STATUS  current
   DESCRIPTION
	"A collection of objects providing optional configuration information
	about multiprotocol interface link."
   ::= { pdnIfMultiprotocolEncapMIBGroups 1 }

pdnIfXLinkConfigOptionalGroup	OBJECT-GROUP
   OBJECTS {
	    pdnIfXLinkConfigRole
	   }
   STATUS  current
   DESCRIPTION
	"configuration information for this optional group."
   ::= { pdnIfXConfigMIBGroups 1 }

END
