IPAD-DHCP-MIB DEFINITIONS ::= BEGIN

IMPORTS IpAddress, TimeTicks,OBJECT-TYPE, MODULE-IDENTITY  FROM SNMPv2-SMI
	DisplayString                                  FROM SNMPv2-TC
	ipad                                           FROM IPADv2-MIB;

ipadDhcp MODULE-IDENTITY
         LAST-UPDATED "0005290001Z"
         ORGANIZATION "Verilink Corporation"
         CONTACT-INFO
             "support@verilink.com
             1-800-926-0085"
         DESCRIPTION
            "The IPAD DHCP MIB."
         ::= { ipad 27 }

ipadDhcpParms          			OBJECT IDENTIFIER ::= { ipadDhcp 1 }
ipadDhcpPortParms 		    	OBJECT IDENTIFIER ::= { ipadDhcp 2 }

ipadDhcpEnable    OBJECT-TYPE
    SYNTAX  INTEGER {
		    other(1),
		    disable(2),
		    enable(3)
		    }
    MAX-ACCESS  read-write
    STATUS  current
    DESCRIPTION
        ""
    ::= { ipadDhcpParms 1 }

ipadDhcpNumberPorts    OBJECT-TYPE
    SYNTAX  INTEGER
    MAX-ACCESS  read-write
    STATUS  current
    DESCRIPTION
        ""
    ::= { ipadDhcpParms 2 }

ipadDhcpTTL    OBJECT-TYPE
    SYNTAX  INTEGER
    MAX-ACCESS  read-write
    STATUS  current
    DESCRIPTION
        ""
    ::= { ipadDhcpParms 3 }

ipadDhcpServiceType    OBJECT-TYPE
    SYNTAX  INTEGER
    MAX-ACCESS  read-write
    STATUS  current
    DESCRIPTION
        ""
    ::= { ipadDhcpParms 4 }

ipadDhcpLeaseTime    OBJECT-TYPE
    SYNTAX  INTEGER 
    MAX-ACCESS  read-write
    STATUS  current
    DESCRIPTION
        ""
    ::= { ipadDhcpParms 5 }

ipadDhcpServerDatabasePrimaryDnsIpAddress    OBJECT-TYPE
    SYNTAX  IpAddress 
    MAX-ACCESS  read-write
    STATUS  current
    DESCRIPTION
        ""
    ::= { ipadDhcpParms 6 }

ipadDhcpServerDatabaseSecondaryDnsIpAddress    OBJECT-TYPE
    SYNTAX  IpAddress 
    MAX-ACCESS  read-write
    STATUS  current
    DESCRIPTION
        ""
    ::= { ipadDhcpParms 7 }

ipadDhcpServerDatabaseDomainName    OBJECT-TYPE
    SYNTAX  DisplayString 
    MAX-ACCESS  read-write
    STATUS  current
    DESCRIPTION
        ""
    ::= { ipadDhcpParms 8 }

ipadDhcpServerDatabaseRouterIpAddress    OBJECT-TYPE
    SYNTAX  IpAddress 
    MAX-ACCESS  read-write
    STATUS  current
    DESCRIPTION
        ""
    ::= { ipadDhcpParms 9 }

ipadDhcpServerHostNameTable OBJECT-TYPE
    SYNTAX    SEQUENCE OF IpadDhcpServerHostNameTableEntry
    MAX-ACCESS  not-accessible
    STATUS    current
    DESCRIPTION
        "Table of DHCP Server Host Entries."
    ::= { ipadDhcpParms 10 }

ipadDhcpServerHostNameTableEntry OBJECT-TYPE
    SYNTAX  IpadDhcpServerHostNameTableEntry
    MAX-ACCESS  not-accessible
    STATUS  current
    DESCRIPTION
        "An entry in the DHCP Server Host table."
    INDEX   { ipadDhcpServerHostIndex }
    ::= { ipadDhcpServerHostNameTable 1 }

IpadDhcpServerHostNameTableEntry ::=
    SEQUENCE
    {
    ipadDhcpServerHostIndex			INTEGER,
    ipadDhcpServerHostName			DisplayString
    }

ipadDhcpServerHostIndex       OBJECT-TYPE
    SYNTAX  INTEGER
    MAX-ACCESS  read-only
    STATUS  current
    DESCRIPTION
        "The index into the DHCP Server Host  table."
    ::= { ipadDhcpServerHostNameTableEntry 1 }

ipadDhcpServerHostName       OBJECT-TYPE
    SYNTAX  DisplayString
    MAX-ACCESS  read-write
    STATUS  current
    DESCRIPTION
        ""
    ::= { ipadDhcpServerHostNameTableEntry 2 }

ipadDhcpServerHostAdd    OBJECT-TYPE
    SYNTAX  INTEGER {  
    		     other(1),
    		     addnew(2)
    		    }
    MAX-ACCESS  read-write
    STATUS  current
    DESCRIPTION
        ""
    ::= { ipadDhcpParms 11 }

ipadDhcpServerHostDelete    OBJECT-TYPE
    SYNTAX  INTEGER
    MAX-ACCESS  read-write
    STATUS  current
    DESCRIPTION
        ""
    ::= { ipadDhcpParms 12 }


ipadDhcpStaticEntryTable OBJECT-TYPE
    SYNTAX    SEQUENCE OF IpadDhcpStaticEntryTableEntry
    MAX-ACCESS  not-accessible
    STATUS    current
    DESCRIPTION
        "Table of DHCP Static Entries."
    ::= { ipadDhcpParms 13 }

ipadDhcpStaticEntryTableEntry OBJECT-TYPE
    SYNTAX  IpadDhcpStaticEntryTableEntry
    MAX-ACCESS  not-accessible
    STATUS  current
    DESCRIPTION
        "An entry in the DHCP Static Entry table."
    INDEX   { ipadDhcpStaticEntryIndex }
    ::= { ipadDhcpStaticEntryTable 1 }

IpadDhcpStaticEntryTableEntry ::=
    SEQUENCE
    {
    ipadDhcpStaticEntryIndex  		INTEGER,
    ipadDhcpStaticEntryMacAddress	OCTET STRING,
    ipadDhcpStaticEntryIpAddress	IpAddress,
    ipadDhcpStaticEntryMaskAddress	IpAddress,
    ipadDhcpStaticEntryHostName		DisplayString

    }

ipadDhcpStaticEntryIndex       OBJECT-TYPE
    SYNTAX  INTEGER
    MAX-ACCESS  read-only
    STATUS  current
    DESCRIPTION
        "The index into the DHCP Static Entry table."
    ::= { ipadDhcpStaticEntryTableEntry 1 }

ipadDhcpStaticEntryMacAddress       OBJECT-TYPE
    SYNTAX  OCTET STRING
    MAX-ACCESS  read-write
    STATUS  current
    DESCRIPTION
        ""
    ::= { ipadDhcpStaticEntryTableEntry 2 }

ipadDhcpStaticEntryIpAddress       OBJECT-TYPE
    SYNTAX  IpAddress
    MAX-ACCESS  read-write
    STATUS  current
    DESCRIPTION
        ""
    ::= { ipadDhcpStaticEntryTableEntry 3 }

ipadDhcpStaticEntryMaskAddress       OBJECT-TYPE
    SYNTAX  IpAddress
    MAX-ACCESS  read-write
    STATUS  current
    DESCRIPTION
        ""
    ::= { ipadDhcpStaticEntryTableEntry 4 }


ipadDhcpStaticEntryHostName       OBJECT-TYPE
    SYNTAX  DisplayString
    MAX-ACCESS  read-write
    STATUS  current
    DESCRIPTION
        ""
    ::= { ipadDhcpStaticEntryTableEntry 5 }


ipadDhcpStaticEntryAdd    OBJECT-TYPE
    SYNTAX  INTEGER {  
    		     other(1),
    		     addnew(2)
    		    }
    MAX-ACCESS  read-write
    STATUS  current
    DESCRIPTION
        ""
    ::= { ipadDhcpParms 14 }

ipadDhcpStaticEntryDelete    OBJECT-TYPE
    SYNTAX  INTEGER 
    MAX-ACCESS  read-write
    STATUS  current
    DESCRIPTION
        ""
    ::= { ipadDhcpParms 15 }

ipadDhcpAddressListTable OBJECT-TYPE
    SYNTAX    SEQUENCE OF IpadDhcpAddressListTableEntry
    MAX-ACCESS  not-accessible
    STATUS    current
    DESCRIPTION
        "Table of DHCP Addresses."
    ::= { ipadDhcpParms 16 }

ipadDhcpAddressListTableEntry OBJECT-TYPE
    SYNTAX  IpadDhcpAddressListTableEntry
    MAX-ACCESS  not-accessible
    STATUS  current
    DESCRIPTION
        "An entry in the DHCP Address List table."
    INDEX   { ipadDhcpAddressListIndex }
    ::= { ipadDhcpAddressListTable 1 }

IpadDhcpAddressListTableEntry ::=
    SEQUENCE
    {
    ipadDhcpAddressListIndex  		INTEGER,
    ipadDhcpAddressListIpStart		IpAddress,
    ipadDhcpAddressListIpEnd		IpAddress,
    ipadDhcpAddressListSubnetMask	IpAddress,
    ipadDhcpAddressListIpExcludeStart	IpAddress,
    ipadDhcpAddressListIpExcludeEnd	IpAddress

    }

ipadDhcpAddressListIndex       OBJECT-TYPE
    SYNTAX  INTEGER
    MAX-ACCESS  read-only
    STATUS  current
    DESCRIPTION
        "The index into the DHCP Static Entry table."
    ::= { ipadDhcpAddressListTableEntry 1 }

ipadDhcpAddressListIpStart       OBJECT-TYPE
    SYNTAX  IpAddress
    MAX-ACCESS  read-write
    STATUS  current
    DESCRIPTION
        ""
    ::= { ipadDhcpAddressListTableEntry 2 }

ipadDhcpAddressListIpEnd       OBJECT-TYPE
    SYNTAX  IpAddress
    MAX-ACCESS  read-write
    STATUS  current
    DESCRIPTION
        ""
    ::= { ipadDhcpAddressListTableEntry 3 }

ipadDhcpAddressListSubnetMask       OBJECT-TYPE
    SYNTAX  IpAddress
    MAX-ACCESS  read-write
    STATUS  current
    DESCRIPTION
        ""
    ::= { ipadDhcpAddressListTableEntry 4 }

ipadDhcpAddressListIpExcludeStart       OBJECT-TYPE
    SYNTAX  IpAddress
    MAX-ACCESS  read-write
    STATUS  current
    DESCRIPTION
        ""
    ::= { ipadDhcpAddressListTableEntry 5 }

ipadDhcpAddressListIpExcludeEnd       OBJECT-TYPE
    SYNTAX  IpAddress
    MAX-ACCESS  read-write
    STATUS  current
    DESCRIPTION
        ""
    ::= { ipadDhcpAddressListTableEntry 6 }


ipadDhcpAddressListAdd    OBJECT-TYPE
    SYNTAX  INTEGER {  
    		     other(1),
    		     addnew(2)
    		    }
    MAX-ACCESS  read-write
    STATUS  current
    DESCRIPTION
        ""
    ::= { ipadDhcpParms 17 }

ipadDhcpAddressListDelete    OBJECT-TYPE
    SYNTAX  INTEGER 
    MAX-ACCESS  read-write
    STATUS  current
    DESCRIPTION
        ""
    ::= { ipadDhcpParms 18 }

ipadDhcpAddressStatusTable OBJECT-TYPE
    SYNTAX    SEQUENCE OF IpadDhcpAddressStatusTableEntry
    MAX-ACCESS  not-accessible
    STATUS    current
    DESCRIPTION
        "Status Table of DHCP Addresses."
    ::= { ipadDhcpParms 19 }

ipadDhcpServerDatabaseWinsPrimary    OBJECT-TYPE
    SYNTAX  IpAddress 
    MAX-ACCESS  read-write
    STATUS  current
    DESCRIPTION
        "WINS Primary Server IP Address"
    ::= { ipadDhcpParms 20 }

ipadDhcpServerDatabaseWinsSecondary  OBJECT-TYPE
    SYNTAX  IpAddress 
    MAX-ACCESS  read-write
    STATUS  current
    DESCRIPTION
        "WINS Secondary Server IP Address."
    ::= { ipadDhcpParms 21 }

ipadDhcpAddressStatusTableEntry OBJECT-TYPE
    SYNTAX  IpadDhcpAddressStatusTableEntry
    MAX-ACCESS  not-accessible
    STATUS  current
    DESCRIPTION
        "An entry in the DHCP Address Status table."
    INDEX   { ipadDhcpAddressStatusIndex }
    ::= { ipadDhcpAddressStatusTable 1 }

IpadDhcpAddressStatusTableEntry ::=
    SEQUENCE
    {
    ipadDhcpAddressStatusIndex 		INTEGER,
    ipadDhcpAddressStatusMacAddress	OCTET STRING,
    ipadDhcpAddressStatusIpAddress	IpAddress,
    ipadDhcpAddressStatusStatus		INTEGER
    }

ipadDhcpAddressStatusIndex       OBJECT-TYPE
    SYNTAX  INTEGER
    MAX-ACCESS  read-only
    STATUS  current
    DESCRIPTION
        "The index into the DHCP Static Entry table."
    ::= { ipadDhcpAddressStatusTableEntry 1 }

ipadDhcpAddressStatusMacAddress       OBJECT-TYPE
    SYNTAX  OCTET STRING
    MAX-ACCESS  read-only
    STATUS  current
    DESCRIPTION
        ""
    ::= { ipadDhcpAddressStatusTableEntry 2 }

ipadDhcpAddressStatusIpAddress       OBJECT-TYPE
    SYNTAX  IpAddress
    MAX-ACCESS  read-only
    STATUS  current
    DESCRIPTION
        ""
    ::= { ipadDhcpAddressStatusTableEntry 3 }

ipadDhcpAddressStatusStatus       OBJECT-TYPE
    SYNTAX  INTEGER{  
    		     other(1),
    		     available(2),
		     assigned(3)
    		    }
    MAX-ACCESS  read-only
    STATUS  current
    DESCRIPTION
        ""
    ::= { ipadDhcpAddressStatusTableEntry 4 }

ipadDhcpPortTable OBJECT-TYPE
    SYNTAX    SEQUENCE OF IpadDhcpPortTableEntry
    MAX-ACCESS  not-accessible
    STATUS    current
    DESCRIPTION
        "Table of DHCP Port Entries."
    ::= { ipadDhcpPortParms 1 }

ipadDhcpPortTableEntry OBJECT-TYPE
    SYNTAX  IpadDhcpPortTableEntry
    MAX-ACCESS  not-accessible
    STATUS  current
    DESCRIPTION
        "An entry in the DHCP Server Host table."
    INDEX   { ipadDhcpPortIndex }
    ::= { ipadDhcpPortTable 1 }

IpadDhcpPortTableEntry ::=
    SEQUENCE
    {
    ipadDhcpPortIndex			INTEGER,
    ipadDhcpPortIpAddress		IpAddress,
    ipadDhcpPortEnable			INTEGER

    }

ipadDhcpPortIndex       OBJECT-TYPE
    SYNTAX  INTEGER
    MAX-ACCESS  read-only
    STATUS  current
    DESCRIPTION
        "The index into the DHCP Port table."
    ::= { ipadDhcpPortTableEntry 1 }

ipadDhcpPortIpAddress       OBJECT-TYPE
    SYNTAX  IpAddress
    MAX-ACCESS  read-write
    STATUS  current
    DESCRIPTION
        ""
    ::= { ipadDhcpPortTableEntry 2 }

ipadDhcpPortEnable       OBJECT-TYPE
    SYNTAX  INTEGER{
		    other(1),
		    disable(2),
		    enable(3)
		    }
    MAX-ACCESS  read-write
    STATUS  current
    DESCRIPTION
        ""
    ::= { ipadDhcpPortTableEntry 3 }


ipadDhcpPortAdd    OBJECT-TYPE
    SYNTAX  INTEGER    MAX-ACCESS  read-write
    STATUS  current
    DESCRIPTION
        ""
    ::= { ipadDhcpPortParms 2 }

ipadDhcpPortDelete    OBJECT-TYPE
    SYNTAX  INTEGER 
    MAX-ACCESS  read-write
    STATUS  current
    DESCRIPTION
        ""
    ::= { ipadDhcpPortParms 3 }


END
