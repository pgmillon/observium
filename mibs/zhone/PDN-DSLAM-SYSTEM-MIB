PDN-DSLAM-SYSTEM-MIB DEFINITIONS ::= BEGIN

-- Version :  1.1 APPROVED
-- Enterprise pdn DSLAM mib
-- Copyright (C) 2002 Paradyne Corporation.

 
 IMPORTS
 TAddress,
 RowStatus,DisplayString
 FROM SNMPv2-TC
 IdslClockMode, SwitchState
 FROM PDN-TC
 Counter32,IpAddress,TimeTicks,
 Integer32, OBJECT-TYPE, NOTIFICATION-TYPE,
 MODULE-IDENTITY
 FROM SNMPv2-SMI
 OBJECT-GROUP, NOTIFICATION-GROUP
 FROM SNMPv2-CONF
 ifIndex, sysObjectID
 FROM RFC1213-MIB
 entPhysicalIndex
 FROM ENTITY-MIB
 pdn-common
 FROM PDN-HEADER-MIB 
 ;


pdn-dslam MODULE-IDENTITY

   LAST-UPDATED    "0206050000Z"
   ORGANIZATION    "Paradyne Corporation
		    MIB Working Group"

   CONTACT-INFO    "Paradyne Corporation
		    8545 126th Avenue North
		    Largo, FL 33733
		    www.paradyne.com

		    General Comments to: mibwg_team@paradyne.com

		    Editors
		    Prakash Easwar
		    Jesus Pinto
		    Dragana Gough"

   DESCRIPTION
    	"The DSLAM MIB. This MIB is specific to portcards and
 	DSLAM configuration/stats for MCC and the portcards.
 	The objects defined in this mib are specific to some
 	products and donot apply to all paradyne devices."

   REVISION "0206200000Z"
   DESCRIPTION "J. Pinto
    o Added IMPLIED modifier to the INDEX clause in:
	entCommunityTableEntry and sysDevUserAccountEntry.
   "

   REVISION "0206050000Z"
   DESCRIPTION "J. Pinto
    o Changed  sysDevUserAccountUserPassword to read-create
    o Expanded sysDevUserAccountPrivilege options
   "

   REVISION "0202220000Z"
   DESCRIPTION "Initial Release"


   ::= { pdn-common 24 }

sysDevDslamMIBObjects OBJECT IDENTIFIER ::= { pdn-dslam 1 }
sysDevDslamMIBTraps   OBJECT IDENTIFIER ::= { pdn-dslam 2 }


sysDevStats 				OBJECT IDENTIFIER ::= { sysDevDslamMIBObjects 1 }
sysDevConfig				OBJECT IDENTIFIER ::= { sysDevDslamMIBObjects 2 }

-- The statistics group. The implementation of this group
-- is mandatory.
 
 loginHistTable OBJECT-TYPE
   SYNTAX SEQUENCE OF LoginHistTableEntry
   MAX-ACCESS  not-accessible
   STATUS current
   DESCRIPTION
     "This table shows the most recent 10 logins and all active users 
	  currently accessing the device. It is indexed by userId
	  and loginTime."
 ::= { sysDevStats 1 }

 loginHistTableEntry OBJECT-TYPE
   SYNTAX  LoginHistTableEntry
   MAX-ACCESS  not-accessible
   STATUS  current
   DESCRIPTION
   		"This object corresponds to an entry in the login history table."
   INDEX { loginUserId, loginTime }
 ::= { loginHistTable 1 }

 LoginHistTableEntry ::=
   SEQUENCE {
   loginUserId 		DisplayString,
   loginTime 	TimeTicks,
   loginAccessApp 	INTEGER,
   loginAccessHost	IpAddress,
   loginUserPriv	 	INTEGER,
   loginStatus 	INTEGER
   }
 
 loginUserId OBJECT-TYPE
   SYNTAX DisplayString
   MAX-ACCESS read-only
   STATUS current
   DESCRIPTION
     "This object containes the user login id."
 ::= { loginHistTableEntry 1 }
 
 loginTime OBJECT-TYPE
   SYNTAX TimeTicks 
   MAX-ACCESS read-only
   STATUS current
   DESCRIPTION
     "This object containes the login time in seconds 
	 when the login session is established."
 ::= { loginHistTableEntry 2 }

 loginAccessApp OBJECT-TYPE
   SYNTAX INTEGER {
	console (1),
	telnet (2),
	ftp (3),
	web (4),
	modem (5)
   }
   MAX-ACCESS read-only
   STATUS current
   DESCRIPTION
     "This object describes the access application used 
	 by the end user to access the device. This can be 
	 done through console, using telnet, modem, web, or using ftp."
 ::= { loginHistTableEntry 3 }

 loginAccessHost OBJECT-TYPE
   SYNTAX IpAddress
   MAX-ACCESS read-only
   STATUS current
   DESCRIPTION
     "This object containes the ip address of the network
	 management station when the access application is
	 telnet or ftp. In case of console, this object contains
	 0.0.0.0."
 ::= { loginHistTableEntry 4 }

 loginUserPriv OBJECT-TYPE
   SYNTAX INTEGER {
	administrator (1),
	operator (2)
   }
   MAX-ACCESS read-only
   STATUS current
   DESCRIPTION
     "This object containes the access privileges of the user."
 ::= { loginHistTableEntry 5 }

 loginStatus OBJECT-TYPE
   SYNTAX INTEGER {
	active (1),
	inactive (2)
   }
   MAX-ACCESS read-only
   STATUS current
   DESCRIPTION
     "This object indicates whether the user is still accessing the
	 device."
 ::= { loginHistTableEntry 6 }

 loginFailureCountTable OBJECT-TYPE
   SYNTAX SEQUENCE OF LoginFailureCountTableEntry
   MAX-ACCESS  not-accessible
   STATUS current
   DESCRIPTION
     "This table containes the statistics for login failures. It
	  is indexed by access type i.e console, telnet or ftp."
 ::= { sysDevStats 2 }

 loginFailureCountTableEntry OBJECT-TYPE
   SYNTAX  LoginFailureCountTableEntry
   MAX-ACCESS  not-accessible
   STATUS  current
   DESCRIPTION
   "This object corresponds to an entry in the login failure count table."
   INDEX {loginFailureAccessApp}
 ::= { loginFailureCountTable 1 }

 LoginFailureCountTableEntry ::=
   SEQUENCE {
   loginFailureAccessApp INTEGER,
   loginFailureCount Counter32
   }

 loginFailureAccessApp OBJECT-TYPE
   SYNTAX INTEGER {
	console (1),
	telnet (2),
	ftp (3)
   }
   MAX-ACCESS read-only
   STATUS current
   DESCRIPTION
     "This object describes the access application used 
	 by the end user to access the device. This can be 
	 done through console, using telnet or using ftp."
 ::= { loginFailureCountTableEntry 1 }

 loginFailureCount OBJECT-TYPE
   SYNTAX Counter32
   MAX-ACCESS read-only
   STATUS current
   DESCRIPTION
     "This object containes the number of unsuccesful logins for console,
	 ftp or telnet."
 ::= { loginFailureCountTableEntry 2 }

 -- The configuration group. The implementation of this group
 -- is optional.

 enablePowerSourceFailureAlarm OBJECT-TYPE
   SYNTAX INTEGER {
     disable (1),
     enable (2)
   }
   MAX-ACCESS read-write
   STATUS current
   DESCRIPTION
     "This objects corresponds to enabling/disabling the 
      power source failure alarm - for both A and B power sources
      This object is for the MCC only.
      The default value of this object should be 1."
    ::= {sysDevConfig 1 }

 devIfTable OBJECT-TYPE
   SYNTAX SEQUENCE OF DevIfTableEntry
   MAX-ACCESS  not-accessible
   STATUS current
   DESCRIPTION
       "This table is used to configure information  for a
    particular interface"
    ::= {sysDevConfig 2 }

devIfTableEntry OBJECT-TYPE
    SYNTAX  DevIfTableEntry
    MAX-ACCESS  not-accessible
    STATUS  current
    DESCRIPTION
      "This object corresponds to an entry in the DevifTable "
    INDEX { ifIndex }
    ::= { devIfTable 1 }
 
DevIfTableEntry ::=
    SEQUENCE {
      devPacketDiscardPolicy INTEGER,
      devLinkIntegrity        INTEGER
      }
devPacketDiscardPolicy OBJECT-TYPE
    SYNTAX INTEGER {
	 noOp (1),
     mrrp (2),
     lrrp (3)
   }
   MAX-ACCESS read-create
   STATUS current
   DESCRIPTION
     "This object corresponds to the policy for packet discards
      during periods of congestion :
      mrrp - most recently received packets are discarded.
      lrrp - least recently received packets are discarded.
      The default value of this object should be 2"
    ::= { devIfTableEntry 1 }

devLinkIntegrity OBJECT-TYPE
     SYNTAX INTEGER {
     enable (1),
     disable (2),
     none (3)
       }
     MAX-ACCESS read-create
     STATUS current
     DESCRIPTION
         "This object corresponds to the enabling or disabling of
          the ethernet link integrity :
           enable - enable link integrity
           disable - disable link integrity
           none - for interfaces that do not support link integrity
           The default value of this object should be 1"
    ::= { devIfTableEntry 2 }

communityTrapAddressInfoTable OBJECT-TYPE
      SYNTAX SEQUENCE OF CommunityTrapAddressInfoTableEntry
      MAX-ACCESS  not-accessible
      STATUS current
      DESCRIPTION
        "This table is used to set the trap destination address
         for a particular community."
    ::= {sysDevConfig 3 }
 
communityTrapAddressInfoTableEntry OBJECT-TYPE
   SYNTAX  CommunityTrapAddressInfoTableEntry
   MAX-ACCESS  not-accessible
   STATUS current
   DESCRIPTION
     "This object corresponds to an entry in the community
      trap address info table."
   INDEX { trapCommunityName, trapDestAndPort}
 ::= { communityTrapAddressInfoTable 1 }
 
CommunityTrapAddressInfoTableEntry ::=
   SEQUENCE {
     trapCommunityName DisplayString (SIZE(1..32)),
     trapDestAndPort   TAddress,
     trapsEnable       INTEGER,
     trapRowStatus     RowStatus
 }
 
trapCommunityName OBJECT-TYPE
   SYNTAX  DisplayString (SIZE(1..32))
   MAX-ACCESS not-accessible
   STATUS current
   DESCRIPTION
     "This object corresponds to the name of the SNMP Community."
   ::= { communityTrapAddressInfoTableEntry 1 }
    
trapDestAndPort OBJECT-TYPE
   SYNTAX TAddress
   MAX-ACCESS not-accessible
   STATUS current
   DESCRIPTION
     "The IP Address and Port of the destination to which a trap
      must be sent."
   ::= { communityTrapAddressInfoTableEntry 2 }
 
trapsEnable OBJECT-TYPE
   SYNTAX INTEGER {
     enable (1),
     disable (2)
   }
   MAX-ACCESS read-create
   STATUS current
   DESCRIPTION
     "This object corresponds to turning traps on/off for a
      particular destination.
      enable (1) - traps will be sent to the specified destination.
      disable (2)- traps will not be sent to the specified 
      destination.
      The default value of this object should be 2."
 ::= { communityTrapAddressInfoTableEntry 3 }

trapRowStatus OBJECT-TYPE
   SYNTAX RowStatus 
   MAX-ACCESS read-only
   STATUS current
   DESCRIPTION
     "This object is used to add or delete a
       a row from the table."
   ::= { communityTrapAddressInfoTableEntry 4 }

entCommunityTable OBJECT-TYPE
   SYNTAX SEQUENCE OF EntCommunityTableEntry
   MAX-ACCESS  not-accessible
   STATUS current
   DESCRIPTION
     "This table is used to set the various configuration
      parameters for a particular community."
    ::= { sysDevConfig 4 }

entCommunityTableEntry OBJECT-TYPE
   SYNTAX  EntCommunityTableEntry
   MAX-ACCESS  not-accessible
   STATUS  current
   DESCRIPTION
     "This object corresponds to an entry in the community
      table."
   INDEX { IMPLIED entCommunityName }
   ::= { entCommunityTable 1 }

EntCommunityTableEntry ::=
   SEQUENCE {
     entCommunityName
       DisplayString (SIZE(1..32)),
     entCommunityType
       INTEGER,
     entCommunityRowStatus
	    RowStatus
 }
 
entCommunityName OBJECT-TYPE
   SYNTAX  DisplayString (SIZE(1..32))
   MAX-ACCESS not-accessible
   STATUS current
   DESCRIPTION
     "This object corresponds to the name of the SNMP Community"
 ::= { entCommunityTableEntry 1 }

entCommunityType OBJECT-TYPE
   SYNTAX INTEGER {
     readOnly (1),
     readWrite (2)
   }
   MAX-ACCESS read-create
   STATUS current
   DESCRIPTION
     "The type of the community
       readOnly - this community is only allowed to do get's
       readWrite - this community is allowed to do get's and 
                   set's
      The default value of this object should be 1"
 ::= { entCommunityTableEntry 2 }

entCommunityRowStatus OBJECT-TYPE
   SYNTAX RowStatus 
   MAX-ACCESS read-create
   STATUS current
   DESCRIPTION
     "This object is used to add or delete a
       a row from the table."
   ::= { entCommunityTableEntry 3 }


-- MCC-rq 200-210: A new user account group is added into the Hotwire System MIB
 
sysDevUserAccountTable OBJECT-TYPE
    SYNTAX  SEQUENCE OF SysDevUserAccountEntry
    MAX-ACCESS  not-accessible
    STATUS current
    DESCRIPTION
        "This table contains the user accounts."
    ::= { sysDevConfig 5}
 
sysDevUserAccountEntry OBJECT-TYPE
    SYNTAX  SysDevUserAccountEntry
    MAX-ACCESS  not-accessible
    STATUS  current
    DESCRIPTION
        "An entry containing user account information."
    INDEX { IMPLIED sysDevUserAccountUserId }
    ::= { sysDevUserAccountTable 1 }
 
SysDevUserAccountEntry  ::= SEQUENCE {
    sysDevUserAccountUserId   DisplayString (SIZE(6..15)),
    sysDevUserAccountPrivilege INTEGER,
    sysDevUserAccountUserPassword DisplayString (SIZE(6..15)),
    sysDevUserAccountAccessPartition DisplayString (SIZE(0..50)),
    sysDevUserAccountRowStatus RowStatus
	}
 
sysDevUserAccountUserId OBJECT-TYPE
    SYNTAX  DisplayString (SIZE(6..15))
    MAX-ACCESS  not-accessible
    STATUS  current
    DESCRIPTION
        "This object corresponds to the login ID of the
         user account."
    ::= { sysDevUserAccountEntry 1 }
 
sysDevUserAccountPrivilege OBJECT-TYPE
    SYNTAX  INTEGER {
        operator (1),
        administrator (2),
	maintenance (3),
	provisioning (4),
	manufacturing (5)
    }
    MAX-ACCESS  read-create
    STATUS  current
    DESCRIPTION
        "This object corresponds to the access privilege
         of the user account.  1 = Operator, 2 = Administrator,
	 3 = maintenance, 4 = provisioning, 5 = manufacturing."
    ::= { sysDevUserAccountEntry 2 }

sysDevUserAccountUserPassword OBJECT-TYPE
    SYNTAX  DisplayString (SIZE(6..15))
    MAX-ACCESS  read-create
    STATUS  current
    DESCRIPTION
        "This object corresponds to the password of the
         user account."
    ::= { sysDevUserAccountEntry 3 }
 
sysDevUserAccountAccessPartition  OBJECT-TYPE
    SYNTAX  DisplayString (SIZE(0..50))
    MAX-ACCESS  read-create
    STATUS current
    DESCRIPTION
    "This object corresponds to the access partition of the
     user account. The default value of this object is 'all'"
    ::= { sysDevUserAccountEntry 4 }

sysDevUserAccountRowStatus OBJECT-TYPE
	SYNTAX  RowStatus
	MAX-ACCESS  read-create
	STATUS current
	DESCRIPTION
	"This object corresponds to create or delete a row in
	sysDevUserAccountTable."
    ::= {sysDevUserAccountEntry 5 }

-- A new user account config group is added
 
sysDevConfigUserAccountTable OBJECT-TYPE
    SYNTAX  SEQUENCE OF SysDevConfigUserAccountEntry
    MAX-ACCESS  not-accessible
    STATUS current
    DESCRIPTION
        "This table contains the user accounts."
    ::= { sysDevConfig 8}
 
sysDevConfigUserAccountEntry OBJECT-TYPE
    SYNTAX  SysDevConfigUserAccountEntry
    MAX-ACCESS  not-accessible
    STATUS  current
    DESCRIPTION
        "An entry containing user account information."
    INDEX { sysDevConfigUserAccountIndex }
    ::= { sysDevConfigUserAccountTable 1 }
 
SysDevConfigUserAccountEntry  ::= SEQUENCE {
    sysDevConfigUserAccountIndex   Integer32,
    sysDevConfigUserAccountUserId   DisplayString (SIZE(1..15)),
    sysDevConfigUserAccountPrivilegedPassword DisplayString (SIZE(0..15)),
    sysDevConfigUserAccountUserPassword DisplayString (SIZE(0..15)),
    sysDevConfigUserAccountRowStatus RowStatus
	}
 

 sysDevConfigUserAccountIndex OBJECT-TYPE
   SYNTAX Integer32
   MAX-ACCESS not-accessible
   STATUS current
   DESCRIPTION
     "The value of this object is an index of the account config
      table. This object is used by sysDevConfigUserAccountTable
      to identify the row in the table. When creating new
      row of this table the value of this object may be
      obtained by retreiving the value of
      sysDevConfigUserAccountIndexNext."
 ::= { sysDevConfigUserAccountEntry 1 }

sysDevConfigUserAccountUserId OBJECT-TYPE
    SYNTAX  DisplayString (SIZE(1..15))
    MAX-ACCESS  read-create
    STATUS current
    DESCRIPTION
        "This object corresponds to the login ID of the
         user account."
    ::= { sysDevConfigUserAccountEntry 2 }
 
sysDevConfigUserAccountPrivilegedPassword OBJECT-TYPE
    SYNTAX  DisplayString (SIZE(0..15))
    MAX-ACCESS  read-create
    STATUS current
    DESCRIPTION
        "This object corresponds to the access privilege password
         of the user account.  If user is configured
	 with this password in addition to a UserPassword 
	 than the user is Administrator. In a case that user
	 is Operator and does not supply this password 
	 upon user configuration this value should be null string"
    ::= { sysDevConfigUserAccountEntry 3 }

sysDevConfigUserAccountUserPassword OBJECT-TYPE
    SYNTAX  DisplayString (SIZE(0..15))
    MAX-ACCESS  read-create
    STATUS  current
    DESCRIPTION
        "This object corresponds to the password of the
         user account."
    ::= { sysDevConfigUserAccountEntry 4 }
 
sysDevConfigUserAccountRowStatus OBJECT-TYPE
	SYNTAX  RowStatus
	MAX-ACCESS  read-create
	STATUS  current
	DESCRIPTION
	"This object corresponds to create or delete a row in
	sysDevConfigUserAccountTable."
    ::= {sysDevConfigUserAccountEntry 5 }

 sysDevConfigUserAccountIndexNext OBJECT-TYPE
   SYNTAX  Integer32
   MAX-ACCESS  read-only 
   STATUS current
   DESCRIPTION
	" This object contains an appropriate value to be
	  used for sysDevConfigUserAccountTable.
	  The value of 0 indicates that no unassigned 
	  entries are available.  To obtain 
	  sysDevConfigUserAccountIndex value for the new entry 
	  the manager issues a management protocol retrieval 
	  operation to obtain a current value of this object.
	  After each retrieval, the agent should modify the value
	  to the next unassigned index.  "
 ::= { sysDevConfig 9 }

-- the sysDevIDSLConfig group on the MCC

sysDevIDSLConfigTable OBJECT-TYPE
   SYNTAX  SEQUENCE OF SysDevIDSLConfigEntry
   MAX-ACCESS  not-accessible
   STATUS  current
    DESCRIPTION
         "A table that contains configuration information about
          IDSL Card."
    ::= { sysDevConfig 6 }

sysDevIDSLConfigEntry OBJECT-TYPE
   SYNTAX  SysDevIDSLConfigEntry
   MAX-ACCESS  not-accessible
   STATUS current
   DESCRIPTION
         "A list of information for IDSL device Configuration."
   INDEX  { entPhysicalIndex }
    ::= { sysDevIDSLConfigTable 1 }

SysDevIDSLConfigEntry ::=
    SEQUENCE {
            sysDevIDSLConfigPrimaryNetClockMode  IdslClockMode,
            sysDevIDSLConfigSecondaryNetClockMode  IdslClockMode
             }

sysDevIDSLConfigPrimaryNetClockMode  OBJECT-TYPE
    SYNTAX IdslClockMode
    MAX-ACCESS read-create
    STATUS current
    DESCRIPTION
        "This object indicates the network clock mode set
    for the primary network clock. IDSL portcards with a
    port configured as an NT will be set to
    portCardDriveClockOnboard(4), both driving the backplane
    and using the clock for the other Local Timing transceivers
    on the card. Port cards with only LT ports configured will
    receive a clock from the backplane using portCardSinkClock(2).
    portCardDriveClock(3) will drive the backplane alone. The 
    default value of this object is triState(1)."
    DEFVAL { triState }
::= { sysDevIDSLConfigEntry 1 }

sysDevIDSLConfigSecondaryNetClockMode  OBJECT-TYPE
    SYNTAX IdslClockMode
    MAX-ACCESS read-create
    STATUS current
    DESCRIPTION
        "This object indicates the network clock mode set
    for the secondary network clock. IDSL portcards with a
    port configured as an NT will be set to
    portCardDriveClockOnboard(4), both driving the backplane
    and using the clock for the other Local Timing transceivers
    on the card. Port cards with only LT ports configured will
    receive a clock from the backplane using portCardSinkClock(2).
    portCardDriveClock(3) will drive the backplane alone. The 
    default value of this object is triState(1)."
    DEFVAL { triState }
::= { sysDevIDSLConfigEntry 2 }

-- The syslog Group
sysDevDslamSyslog OBJECT IDENTIFIER ::= { sysDevConfig 7 }

sysDevSyslogFtpServerXferStatsEnable OBJECT-TYPE
  SYNTAX SwitchState
  MAX-ACCESS read-write
  STATUS current
  DESCRIPTION
    "This object allows the network manager to enable and disable 
     syslog messages for FTP server file transfer statistics"
  DEFVAL { disabled }
::= { sysDevDslamSyslog 1 }

sysDevSyslogTftpServerXferStatsEnable OBJECT-TYPE
  SYNTAX SwitchState
  MAX-ACCESS read-write
  STATUS current
  DESCRIPTION
    "This object allows the network manager to enable and disable 
     syslog messages for TFTP server file transfer statistics"
  DEFVAL { disabled }
::= { sysDevDslamSyslog 2 }




--Traps

cCN NOTIFICATION-TYPE
  OBJECTS { ifIndex }
  STATUS		current
  DESCRIPTION
    "This trap signifies a Configuration change  or 
     software upgrade in the xDSL card. This trap 
     is of 'warning' class"
 ::= { sysDevDslamMIBTraps 7}

authenticationFailureTrap NOTIFICATION-TYPE
 OBJECTS { loginFailureAccessApp, loginFailureCount }
 STATUS		current
 DESCRIPTION 
  "This trap signifies an authentication  failure. 
   Authentication failures can be telnet based or 
  terminal based. This trap is in addition to the
  SNMP based authentication failure trap, which
  is a generic trap."
  ::= { sysDevDslamMIBTraps 8}

-- the following traps are sent by the MCC *******

 fanModuleFailure NOTIFICATION-TYPE
  STATUS		current
   DESCRIPTION
   "This trap indicates the indicates the failure of 
    the fan module on the device." 
 ::= {sysDevDslamMIBTraps 9}

 fanModuleOperational NOTIFICATION-TYPE
  STATUS		current
   DESCRIPTION
   "This trap indicates the indicates the fan module on the 
    device is operational."  
 ::=  {sysDevDslamMIBTraps 109}



 powerSourceAFailure NOTIFICATION-TYPE
   STATUS		current
   DESCRIPTION
     "This trap indicates that power source A
      has failed. This is sent only by the MCC card. This 
      trap is of 'minor' class."
 ::= {sysDevDslamMIBTraps 10}

 powerSourceAOperational NOTIFICATION-TYPE
   STATUS		current
   DESCRIPTION
     "This trap indicates that the power source A
      is operational. This is sent only by the MCC card. 
      This trap is of 'minor' class. This trap compliments
      powerSourceAFailure trap."
 ::={ sysDevDslamMIBTraps 110}

slotPollFailure NOTIFICATION-TYPE
  OBJECTS { entPhysicalIndex }
  STATUS		current
  DESCRIPTION
   "This trap indicates a slot poll failure.
    This is sent only by the MCC card. this trap is
    of 'major' class."
 ::=  { sysDevDslamMIBTraps 11}

 newCardDetected NOTIFICATION-TYPE
   OBJECTS { entPhysicalIndex }
   STATUS		current
   DESCRIPTION
   "This trap indicates that a new card was detected 
    in a slot. This is sent only by the MCC card. this trap
    is of 'warning' class."
 ::=  {sysDevDslamMIBTraps 111}

-- ****************************

 ethernetJabber NOTIFICATION-TYPE
   OBJECTS { ifIndex }
   STATUS		current
   DESCRIPTION
     "This trap indicates that a jabber condition  has been 
      detected on the ethernet interface. This trap is of 
      'major' class."
 ::=  { sysDevDslamMIBTraps 12}

 ethernetJabberClear NOTIFICATION-TYPE
 
   OBJECTS { ifIndex }
   STATUS		current
   DESCRIPTION
     "This trap indicates that the jabber condition that was 
      detected no longer exists. This trap is of 'major' 
      class."
 ::= { sysDevDslamMIBTraps 112}

 ethernetJumbos NOTIFICATION-TYPE
   OBJECTS { ifIndex }
   STATUS		current
   DESCRIPTION
     "This trap indicates ethernet jumbos. this trap
      is of 'minor' class"
 ::=   { sysDevDslamMIBTraps 13}

 ethernetRunts NOTIFICATION-TYPE
   OBJECTS { ifIndex }
   STATUS		current
   DESCRIPTION
     "This trap indicates ethernet runts. this trap is of 'minor'"
 ::=  {sysDevDslamMIBTraps 14}

 powerSourceBFailure NOTIFICATION-TYPE
   STATUS		current
   DESCRIPTION
     "This trap indicates that power source B
      has failed. This is sent only by the MCC card. This 
      trap is of 'minor' class."
 ::= { sysDevDslamMIBTraps 17}

 powerSourceBOperational NOTIFICATION-TYPE
   STATUS		current
   DESCRIPTION
     "This trap indicates that the power source B
      is operational. This is sent only by the MCC card. 
      This trap is of 'minor' class. This trap compliments
      powerSourceBFailure trap."
 ::=  {sysDevDslamMIBTraps 117}

 nonIpConservativeCardDetected NOTIFICATION-TYPE
   OBJECTS { entPhysicalIndex }
   STATUS		current
   DESCRIPTION
     "This trap indicates that a non ip conservative DSL card
      exist in the chassis at the slot 'slotNumber'.This is
      sent only by the MCC card. This trap is of warning class."
 ::={ sysDevDslamMIBTraps 18}

nonSupportedMCC NOTIFICATION-TYPE
  OBJECTS { sysObjectID }
  STATUS		current
  DESCRIPTION
    "AN has detected MCC firmware release too low to support
     this device"
::={ sysDevDslamMIBTraps 20 }

nonSupportedChassis NOTIFICATION-TYPE
  OBJECTS { sysObjectID }
  STATUS		current
  DESCRIPTION
    "AN in slot xx has been installed in a chassis that cannot
     support one or more of its features. "
::=  {sysDevDslamMIBTraps 21}

 fanEntityModuleFailure NOTIFICATION-TYPE
   OBJECTS { entPhysicalIndex }
  STATUS		current
   DESCRIPTION
   "This trap indicates the indicates the failure of 
    the fan module on the device." 
 ::= {sysDevDslamMIBTraps 22}

 fanEntityModuleOperational NOTIFICATION-TYPE
   OBJECTS { entPhysicalIndex }
  STATUS		current
   DESCRIPTION
   "This trap indicates the indicates the fan module on the 
    device is operational."  
 ::=  {sysDevDslamMIBTraps 122}
END
