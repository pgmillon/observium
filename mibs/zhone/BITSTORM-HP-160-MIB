-- File Name : BITSTORM-HP-160.my
-- Date      : Thu Dec 13 08:59:41 CST 2006
-- Author    : AdventNet Agent Toolkit Java Edition - MIB Editor 6


-- *****************************************************************
-- Zhone Enterprise MIB
-- Product Name: BITSTORM-HP-160
-- Version: 4.6
--
-- Update and Release Notes:
--  Data(Y/M/D) | MIB version |   Note
--  2006-12-27      V1.0        1.First Release
--  2007-01-16      V1.1        1.remove BITSTORM-HP-160CfgClusterStatusTable
--                              2.add BITSTORM-HP-160CfgClusterState
--                                add BITSTORM-HP-160CfgClusterMemberState
--  2007-01-19      V1.2        1.remove events: GBE-LINKUP(201),
--     	                                         GBE-LINKDOWN(202),
--                              2.add alarm : GBE-LOS(201)
--                              3.remove event trap :BITSTORM-HP-160TrapEvtGBELinkUp
--                                                   BITSTORM-HP-160TrapEvtGBELinkDown
--
--                              4.add alarm trap :  BITSTORM-HP-160TrapAlmGBELOS
--                              5.rename   BITSTORM-HP-160TrapEvtVDSLPerf-NE-DAY-ESE to BITSTORM-HP-160TrapEvtVDSLPerf-NE-DAY-SES
--                                         BITSTORM-HP-160TrapEvtVDSLPerf-FE-DAY-ESE to  BITSTORM-HP-160TrapEvtVDSLPerf-FE-DAY-SES
--
--  2007-01-24      V1.3        1.add BITSTORM-HP-160MtnSyslogService
--                              2.remove BITSTORM-HP-160BridgevlanCrossConnectTable
--  2007-01-26      V1.4        1.update BITSTORM-HP-160LineTestResult value list
--  2007 01-30      V1.5        1.update syntax of BITSTORM-HP-160CfgPppoeVsaMode
--  2007 01-31      V1.5        1.update syntax of BITSTORM-HP-160SysAlmStatus and BITSTORM-HP-160CfgCLIFlags
--  2007 02-01      V1.6        1.add column BITSTORM-HP-160CfgAtmTrafficType
--                                           BITSTORM-HP-160CfgEnetTrafficPCR
--                                           BITSTORM-HP-160CfgEnetTrafficCDVT
--                              2.update syntax of BITSTORM-HP-160CfgEnetTrafficDescrIndex
--  2007 02-06      V1.7        1.define column range of BITSTORM-HP-160CfgEnetTrafficDescrTable
--  2007 02-13      V1.8        1.remove BITSTORM-HP-160CfgIgmpAclProfileBank-
--                              2.remove BITSTORM-HP-160CfgCLIFlags
--  2007 02-14      V1.9        1.remove BITSTORM-HP-160CfgIgmpAclProfileBank
--                              2.rename BITSTORM-HP-160CfgIgmpAclProfileMcMumber to BITSTORM-HP-160CfgIgmpAclProfileMcCount
--  2007 03-02      V2.0        1.update syntax of BITSTORM-HP-160SysAlmStatus
--  2007 03-06      V2.1        1.update syntax of BITSTORM-HP-160CfgCLITimeout  (range 1..59 is not allowed)
--
--
--
--  2007 03-26      V2.2        1.add Column BITSTORM-HP-160CfgIgmpAclProfileUsedCount
--                              2.add Column BITSTORM-HP-160IwPolicerUsedCount
--                              3.add Column BITSTORM-HP-160CfgEnetTrafficUsedCount
--  2007 03-27      V2.3        1.update syntax of BITSTORM-HP-160CfgDhcpCircuitIdType 0..4
--  2007 03-29      V2.4        1.add new table  BITSTORM-HP-160BportVlanRateLimitTable
--                                add BITSTORM-HP-160CfgVpmtGroup and three tables
--                                     BITSTORM-HP-160CfgVpmtTrunkTable
--                                     BITSTORM-HP-160CfgVpmtBportProfileTable
--                                     BITSTORM-HP-160CfgVpmtBridgePortBindTable
--
--                              2.update table BITSTORM-HP-160BportRateLimitTable   add BITSTORM-HP-160BportRateLimitEgressIwPolicerIdx and BITSTORM-HP-160BportRateLimitIngressIwPolicerIdx
--                                update table BITSTORM-HP-160CfgIgmpAclProfileTable   add BITSTORM-HP-160CfgIgmpAclProfileVlanEgressMap
--  2007 03-30      V2.5        1.remove  BITSTORM-HP-160MtnFlashBackupInfoTable
--                                        BITSTORM-HP-160MtnFlashBackupEntryCount
--                                        BITSTORM-HP-160MtnFlashBackupEntryType
--                                        BITSTORM-HP-160MtnFlashBackupActiveIndex
--                                and add BITSTORM-HP-160MtnFlashBackupInbandTable
--                                 BITSTORM-HP-160MtnFlashBackupGeneralTable
--                                 BITSTORM-HP-160MtnFlashBackupInbandActiveIndex
--                                 BITSTORM-HP-160MtnFlashBackupGeneralActiveIndex
--  2007 04-04      V2.6        1.file name size 32->64      (BITSTORM-HP-160MtnRemoteFTPFileName and BITSTORM-HP-160MtnCliCfgFTPFileName)
--  2007 04-11      V2.7        1.update BITSTORM-HP-160CfgEnetTrafficWeight range 1..10000
--                              2.add BITSTORM-HP-160CfgSystemConfiguration
--                                add BITSTORM-HP-160CfgSystemAclMode
--                                add BITSTORM-HP-160CfgSystemExtEtherType
--  2007 04-25      V2.8        1.remove BITSTORM-HP-160PhyEnetAdminStatus and BITSTORM-HP-160PhyEnetOperStatus
--  2007 04-26      V2.9        1.update syntax of BITSTORM-HP-160MtnActivePartition
--                              2.update value range of BITSTORM-HP-160CfgInbandManageVlanId
--  2007 05-02      V3.0        1.update syntax of BITSTORM-HP-160CfgBridgeProtocolFilter
--                              2.remove BITSTORM-HP-160CfgIgmpSourceTable
--  2007 05-09      V3.1        1.add BITSTORM-HP-160CfgBridgeNetBiosFilterTable and BITSTORM-HP-160CfgBridgeArpBcastFilterTable
--                              2.move the location of BITSTORM-HP-160CfgBridgePrioTagFilterTable   from 1.3.6.1.4.1.5833.18.2.4.3.4 to 1.3.6.1.4.1.5833.18.2.4.2.7.8
--  2007 05-24      V3.2        1.remove BITSTORM-HP-160CfgFdbCurrentCount
--  2007 06-05      V3.3        1.rename BITSTORM-HP-160CfgDefaultGateway to BITSTORM-HP-160CfgOutbandDefaultGateway
--  2007 06-08      V3.4        1.add BITSTORM-HP-160CfgIgmpAclProfileMsgCount
--
--  2007 06-21      V3.5        1.add BITSTORM-HP-160SysTemperatureDslValue read-only
--                                add BITSTORM-HP-160AgingTimeTable
--                                add BITSTORM-HP-160SnoopArpRequestTable
--                              2.BITSTORM-HP-160CfgSystemConfiguration add
--                                BITSTORM-HP-160CfgSystemAllowDownstreamBc
--                                BITSTORM-HP-160CfgSystemAllowIpFilter
--                                BITSTORM-HP-160CfgSystemAddAllowIpBySnoopDHCP
--                                BITSTORM-HP-160CfgSystemAgingTimePerPort
--                                BITSTORM-HP-160CfgSystemReplaceArpMac
--                                BITSTORM-HP-160CfgSystemSnoopArpDefaultGatewayMac
--                              3.BITSTORM-HP-160MtnCliCfgActionType add CLICONFIG-CHANGE-DETECT(21)
--                                add BITSTORM-HP-160MtnCliCfgConfigUnsaved
--                              4.change oid of BITSTORM-HP-160MtnFlashBackup	from BITSTORM-HP-160MtnCliConfig   to  BITSTORM-HP-160MtnMgt
--                              5.add BITSTORM-HP-160MtnImageProfileDisplayName
--                              6.add BITSTORM-HP-160BportPortBcRateLimitTable
--                              7.add BITSTORM-HP-160CfgBridgeAllowedIpFilterTable
--  2007 07-09      V3.6        1.add BITSTORM-HP-160SNTPSynchronize
--  2007 07-17      V3.7        1.update range (1..4095)
--                                  BITSTORM-HP-160BridgePortDefaultVlan
--                                  BITSTORM-HP-160CfgIgmpGroupVlan
--                                  BITSTORM-HP-160CfgIgmpRouterPortVlanId
--                                  BITSTORM-HP-160McBcRateLimitVlanId
--                                  BITSTORM-HP-160McFldRateLimitVlanId
--  2007 07-23      V3.8        1.add BITSTORM-HP-160SysInvCardType
--  2007 07-26      for Phase II
--  2007 07-26      V3.9        1.remove vsamode
--                              2.BITSTORM-HP-160CfgSystemConfiguration add
--                                BITSTORM-HP-160CfgSystemArpSpoofing
--                                BITSTORM-HP-160CfgSystemAntiMacSpoofing
--                              3.update the syntax of BITSTORM-HP-160CfgDhcpMode
--                              4.update the syntax of BITSTORM-HP-160CfgDslCircuitID and BITSTORM-HP-160CfgDslRemoteID
--                              5.remove BITSTORM-HP-160CfgDslIdForwardMode
--                              6.add BITSTORM-HP-160CfgDslpppoeMode
--                              7.remove BITSTORM-HP-160BridgePortVlanStacking
--                              8.add new table  BITSTORM-HP-160BportVlanTranslationTable
--                                               BITSTORM-HP-160BridgeArpSpoofingTable
--                                               BITSTORM-HP-160CfgDhcpServerProfileTable
--                                               BITSTORM-HP-160CfgDhcpServerProfileBindTable
--                                               BITSTORM-HP-160CfgDhcpQueryClientTable
--                                               BITSTORM-HP-160CfgDhcpStaticIPTable
--                                               BITSTORM-HP-160CfgBridgeL4SrcPortFilterTable
--                                               BITSTORM-HP-160CfgBridgeDstMacFilterTable
--                              9.add BITSTORM-HP-160CfgIgmpRouterPortRouterIp and BITSTORM-HP-160CfgIgmpRouterPortRouterReportIp  on BITSTORM-HP-160CfgIgmpRouterPortTable
--                              10.update syntax of BITSTORM-HP-160AtmTrafficType
--  2007 08-01      V4.0        1.remove BITSTORM-HP-160CfgSystemAclMode and BITSTORM-HP-160CfgSystemAllowIpFilter
--                              2.add BITSTORM-HP-160CfgLayerIIServiceOption
--                                add  BITSTORM-HP-160CfgAclService;
--                                     BITSTORM-HP-160CfgPppoeService;
--                                     BITSTORM-HP-160CfgDhcpService;
--                                     BITSTORM-HP-160CfgRateLimitService;
--                                     BITSTORM-HP-160CfgStackVlanService;
--                                     BITSTORM-HP-160BITSTORM-HP-160CfgAllowIpService;
--  2007 08-08      V4.1        1.remove BITSTORM-HP-160CfgDhcpService and BITSTORM-HP-160CfgAllowIpService
--                              2.add BITSTORM-HP-160CfgFilterAndPriorityRemarkService and BITSTORM-HP-160CfgNetBiosDenialService
--  2007 08-10      V4.2        1.add BITSTORM-HP-160StpBridgeID
--                              2.remove VDSL-CONFIG-INIT-FAILURE(606),
--		                         VDSL-PROTOCOL-INIT-FAILURE(607),
--                                remove BITSTORM-HP-160TrapAlmVdslConfigInitFailure and BITSTORM-HP-160TrapAlmVdslProtocolInitFailure
--                              3.update VDSL-DATA-INIT-FAILURE(605) to VDSL-INIT-FAILURE(605)
--                                update BITSTORM-HP-160TrapAlmVdslDataInitFailure to BITSTORM-HP-160TrapAlmVdslInitFailure
--                              4.update syntax of BITSTORM-HP-160CfgBridgeTpFdbStatus
--  2007 08-14      V4.3        1.add BITSTORM-HP-160CfgAllowIpService
--  2007 08-17      V4.4        1.update BITSTORM-HP-160CfgEnetTrafficWeight     SYNTAX      Unsigned32 (1..127)
--  2007 09-06      V4.5        1.update syntax of BITSTORM-HP-160MtnFlashWrite
--                                remove BITSTORM-HP-160MtnDlStatus
--                                add BITSTORM-HP-160MtnBootLoaderUpdate
--  2007 09-06      V4.5        1.add BITSTORM-HP-160SysInvBootLoaderVersion
--                                    BITSTORM-HP-160SysInvPortCount
--                                    BITSTORM-HP-160SysSysFanSupported
--                              2.update BITSTORM-HP-160CfgEnetTrafficWeight     SYNTAX      Unsigned32 (1..42)
--  2007 09-19      V4.6        1.add BITSTORM-HP-160CfgIgmpLeaveMode
--*****************************************************************

BITSTORM-HP-160-MIB	DEFINITIONS ::= BEGIN
	IMPORTS
		PhysicalIndex, entPhysicalIndex
			FROM ENTITY-MIB
		PhysAddress, RowStatus, TAddress, TEXTUAL-CONVENTION, TruthValue
			FROM SNMPv2-TC
		OBJECT-TYPE
			FROM RFC-1212
		ifIndex, InterfaceIndex
			FROM IF-MIB
		Integer32, IpAddress, Unsigned32, NOTIFICATION-TYPE, enterprises, MODULE-IDENTITY, OBJECT-TYPE
			FROM SNMPv2-SMI;
--	  zhone
--			FROM Zhone;

  org OBJECT IDENTIFIER
    ::=  {  iso  3  }

  dod OBJECT IDENTIFIER
    ::=  {  org  6  }

  internet  OBJECT IDENTIFIER
    ::=  {  dod  1  }

  private OBJECT IDENTIFIER
    ::=  {  internet  4  }

  enterprises OBJECT IDENTIFIER
    ::=  {  private  1  }

  Zhone OBJECT IDENTIFIER
    ::=  {  enterprises  5504  }

	BITSTORM-HP-160	MODULE-IDENTITY
		LAST-UPDATED	"200608100000Z"
		ORGANIZATION	"Zhone"
		CONTACT-INFO	"Zhone"
		DESCRIPTION		"Zhone IP-DSLAM root MIB module."
		REVISION		"200608100000Z"
		DESCRIPTION		"The modified revision : v4.4"
		::=  { Zhone 18 }

-- TEXTUAL-CONVENTIONS --
   VdslLineEntity ::= TEXTUAL-CONVENTION
       STATUS       current
       DESCRIPTION
           "Identifies a transceiver as being either Vtuc or Vtur.
           A VDSL line consists of two transceivers, a Vtuc and a
           Vtur.  Attributes with this syntax reference the two sides
           of a line.  Specified as an INTEGER, the two values are:

           vtuc(1)  -- central site transceiver
           vtur(2)  -- remote site transceiver"
       SYNTAX  INTEGER
           {
           vtuc(1),
           vtur(2)
           }

	BITSTORM-HP-160EventType ::= TEXTUAL-CONVENTION
		DISPLAY-HINT	""
		STATUS			current
		DESCRIPTION
			"The event type identifier number."
		SYNTAX 			INTEGER  {
		SYSTEMRESTART(1),
		SYSTEMDOWNLOADBEGIN(2),
		SYSTEMDOWNLOADSUCCESS(3),
		SYSTEMDOWNLOADFAIL(4),
		SYSTEMPROVISIONDATAEXPORT(5),
		SYSTEMPROVISIONDATAIMPORT(6),
		SYSTEMPROVISIONDATASETDEFAULT(7),
		SYSTEMALARMLOGCLEAR(9),
		SYSTEMEVENTLOGCLEAR(10),
		SYSTEMRTCDATETIMECHANGE(11),
		SYSTEMSOFTWAREACOBUTTONSET(12),
		SYSTEMSOFTWAREACOBUTTONCLEAR(13),
		SYSTEMALARMLEVELMASKFLAGCHANGE(14),
		SYSTEMSNMPAUTHFAIL(15),
		SYSTEMFTPRECEPTIONSTART(17),
		SYSTEMFTPRECEPTIONCOMPLETE(18),
		SYSTEMFTPRECEPTIONINCOMPLETE(19),
		SYSTEMSNTPTIMEZONECHANGE(21),
		SYSTEMSNTPPROVISIONCHANGED(23),
		SYSTEMDATABASESAVINGFAILED(25),
		ATMCREATEVCL(102),
		ATMMODIFYVCL(103),
		ATMDELETEVCL(104),
		ATMOAMCREATELOOPBACK(105),
		ATMOAMDELETELOOPBACK(106),
		--GBE-LINKUP(201),
		--GBE-LINKDOWN(202),
		XDSL-PORT-INFO-CHANGED(501),
		VDSL-PORT-BINDING-CHANGED(601),
		VDSL-PORT-ENABLED(602),
		VDSL-PORT-DISABLED(603),
		VDSL-PORT-REENABLED(604),
		VDSL-PORT-LINKUP(605),
		VDSL-PORT-LINKDOWN(606),
		VDSL-LINE-CONF-PROFILE-CREATED(607),
		VDSL-LINE-CONF-PROFILE-DELETED(608),
		VDSL-LINE-CONF-PROFILE-CHANGED(609),
		VDSL-LINE-ALARM-CONF-PROFILE-CREATED(610),
		VDSL-LINE-ALARM-CONF-PROFILE-DELETED(611),
		VDSL-LINE-ALARM-CONF-PROFILE-CHANGED(612),
		VDSL-PORT-PROFILE-TRANSFER-FAILED(613),

                VDSL-LOOPBACK-SET(614),
                VDSL-DELT-SET(615),
                VDSL-DELT-DONE(616),

		VDSL-PERF-NE-ES(651),
		VDSL-PERF-NE-SES(652),
		VDSL-PERF-NE-UAS(653),
		VDSL-PERF-FE-ES(654),
		VDSL-PERF-FE-SES(655),
		VDSL-PERF-FE-UAS(656),
		VDSL-PERF-NE-DAY-ES(657),
		VDSL-PERF-NE-DAY-SES(658),
		VDSL-PERF-NE-DAY-UAS(659),
		VDSL-PERF-FE-DAY-ES(660),
		VDSL-PERF-FE-DAY-SES(661),
		VDSL-PERF-FE-DAY-UAS(662),
		VDSL-DOWN-MAX-SNR-MGN(663),
		VDSL-DOWN-MIN-SNR-MGN(664),
		VDSL-UP-MAX-SNR-MGN(665),
		VDSL-UP-MIN-SNR-MGN(666),
		VDSL-INIT-FAILURE-TRAP(667)
		}

	MacAddress ::= TEXTUAL-CONVENTION
		DISPLAY-HINT	""
		STATUS			current
		DESCRIPTION
			""
		SYNTAX 			OCTET STRING  ( SIZE ( 6  ) )

	BITSTORM-HP-160LedType ::= TEXTUAL-CONVENTION
		DISPLAY-HINT	""
		STATUS			current
		DESCRIPTION
			"LED status"
		SYNTAX 			INTEGER  { BITSTORM-HP-160LedOff ( 0 ) , BITSTORM-HP-160LedRed ( 1 ) , BITSTORM-HP-160LedGreen ( 2 ) , BITSTORM-HP-160LedYellow ( 3 ) , BITSTORM-HP-160LedRedFlash ( 5 ) , BITSTORM-HP-160LedGreenFlash ( 6 ) , BITSTORM-HP-160LedYellowFlash ( 7 ) }

         BITSTORM-HP-160EnetTrafficType ::= TEXTUAL-CONVENTION
                DISPLAY-HINT	""
                STATUS    current
                DESCRIPTION
                        "Traffic Descriptor Type"
                SYNTAX    INTEGER
                {
                  ENETPKTSHAPINGWFQ(1),
                  ENETPKTSHAPINGPPR(2),
                  ENETPKTSHAPINGCIR(3),
                  ENETPKTSHAPINGCIREIR(4)
                 }

         BITSTORM-HP-160AtmTrafficType ::= TEXTUAL-CONVENTION
                DISPLAY-HINT	""
                STATUS    current
                DESCRIPTION
                        "Atm Traffic Descriptor Type"
                SYNTAX    INTEGER
                {
                  AtmPolicingCBR(9),
                  AtmPolicingUBR(12)
                 }

	PortList ::= TEXTUAL-CONVENTION
		DISPLAY-HINT	""
		STATUS			current
		DESCRIPTION
			"Each octet within this value specifies a set of eight
        ports, with the first octet specifying ports 1 through
        8, the second octet specifying ports 9 through 16, etc.
        Within each octet, the most significant bit represents
        the lowest numbered port, and the least significant bit
        represents the highest numbered port.  Thus, each port
        of the bridge is represented by a single bit within the
        value of this object.  If that bit has a value of '1'
        then that port is included in the set of ports; the port
        is not included if its bit has a value of '0'."
		SYNTAX 			OCTET STRING

	BITSTORM-HP-160AlmType ::= TEXTUAL-CONVENTION
		DISPLAY-HINT	""
		STATUS			current
		DESCRIPTION
			"The alarm type identifier number."
		SYNTAX 			INTEGER  {
		SYS-HOUSEKEEP1(101),
		SYS-HOUSEKEEP2(102),
		SYS-HOUSEKEEP3(103),
		SYS-HOUSEKEEP4(104),
		SYS-FAN(105),
		SYS-SELFTESTFAILED(106),
		SYS-ABOVETEMP(107),
		SYS-BELOWTEMP(108),
		GBE-LOS(201),
		VDSL-LOF(601),
		VDSL-LOS(602),
		VDSL-LOSQ(603),
		VDSL-LOL(604),
		VDSL-INIT-FAILURE(605),
--		VDSL-CONFIG-INIT-FAILURE(606),
--		VDSL-PROTOCOL-INIT-FAILURE(607),
		VDSL-ESE(608),
		VDSL-NCD-SLOW(609),
		VDSL-LCD-SLOW(610),
		VDSL-NCD-FAST(611),
		VDSL-LCD-FAST(612),
		VDSL-LOF-FE(613),
		VDSL-LOS-FE(614),
		VDSL-LPR-FE(615),
		VDSL-LOSQ-FE(616),
		VDSL-NO-PEER-VTU-PRESENT-FE(617),
		VDSL-ESE-FE(618),
		VDSL-NCD-SLOW-FE(619),
		VDSL-LCD-SLOW-FE(620),
		VDSL-NCD-FAST-FE(621),
		VDSL-LCD-FAST-FE(622)
		}


--	AdslPlusTransmissionModeType ::= TEXTUAL-CONVENTION
--		DISPLAY-HINT	""
--		STATUS			current
--		DESCRIPTION
--			"A set of ADSL line transmission modes, with one bit
  --                 per mode.  The notes (F) and (L) denote Full-Rate
    --               and G.Lite respectively:
      --               Bit 00 : Regional Std. (ANSI T1.413) (F)
      --               Bit 01 : Regional Std. (ETSI DTS/TM06006) (F)
--                     Bit 02 : G.992.1 POTS non-overlapped (F)
--                     Bit 03 : G.992.1 POTS overlapped (F)
--                     Bit 04 : G.992.1 ISDN non-overlapped (F)
--                     Bit 05 : G.992.1 ISDN overlapped (F)
--                     Bit 06 : G.992.1 TCM-ISDN non-overlapped (F)
--                     Bit 07 : G.992.1 TCM-ISDN overlapped (F)
--                     Bit 08 : G.992.2 POTS non-overlapped (L)
--                     Bit 09 : G.992.2 POTS overlapped (L)
--                     Bit 10 : G.992.2 with TCM-ISDN non-overlapped (L)
--                     Bit 11 : G.992.2 with TCM-ISDN overlapped (L)
--                     Bit 12 : G.992.1 TCM-ISDN symmetric (F)
--                     Bit 13 : ADSL plus pots non-overlapped
--                     Bit 14 : G.992.1 Annex I TCM-ISDN non-overlapped
--                     Bit 15 : G.992.1 Annex I TCM-ISDN overlapped
--                     Bit 16 : G.992.2 Annex I TCM-ISDN non-overlapped
--                     Bit 17 : G.992.2 Annex I TCM-ISDN overlapped
--                     Bit 18 : ADSL plus pots overlapped
--                     Bit 22 : G.992.3 Annex READSL2 POTS overlapped
--                     Bit 23 : G.992.3 Annex READSL2 POTS non-overlapped
--                     Bit 26 : G.992.3 Annex ADSL2 Plus POTS non-overlapped
--                     Bit 27 : G.992.3 Annex ADSL2 Plus POTS overlapped
--                     Bit 28 : G.992.3 Annex ADSL2 POTS non-overlapped
--                     Bit 29 : G.992.3 Annex ADSL2 POTS overlapped
 --                    Bit 30 : G.992.1 G.Span Plus POTS overlapped
 --                    Bit 31 : G.992.1 G.Span Plus POTS non-overlapped
 --                 "
--		SYNTAX 			BITS  { ansit1413 ( 0 ) , etsi ( 1 ) , q9921PotsNonOverlapped ( 2 ) , q9921PotsOverlapped ( 3 ) , q9921IsdnNonOverlapped ( 4 ) , q9921IsdnOverlapped ( 5 ) , q9921TcmIsdnNonOverlapped ( 6 ) , q9921TcmIsdnOverlapped ( 7 ) , q9922PotsNonOverlapeed ( 8 ) , q9922PotsOverlapped ( 9 ) , q9922TcmIsdnNonOverlapped ( 10 ) , q9922TcmIsdnOverlapped ( 11 ) , q9921TcmIsdnSymmetric ( 12 ) , adslPlusPotsNonOverlapped ( 13 ) , q9921AnnexItcmIsdnNonOverlapped ( 14 ) , q9921AnnexItcmIsdnOverlapped ( 15 ) , q9922AnnexItcmIsdnNonOverlapped ( 16 ) , q9922AnnexItcmIsdnOverlapped ( 17 ) , adslPlusPotsOverlapped ( 18 ) , q9923AnnexREADSL2PotsOverlapped ( 22 ) , q9923AnnexREADSL2PotsNonOverlapped ( 23 ) , q9923AnnexADSL2PlusPotsNonOverlapped ( 26 ) , q9923AnnexADSL2PlusPotsOverlapped ( 27 ) , q9923AnnexADSL2PotsNonOverlapped ( 28 ) , q9923AnnexADSL2PotsOverlapped ( 29 ) , q9921GSpanPlusPotsOverlapped ( 30 ) , q9921GSpanPlusPotsNonOverlapped ( 31 ) }

--	org	OBJECT IDENTIFIER
--		::=  {  iso  3  }
--
--	dod	OBJECT IDENTIFIER
--		::=  {  org  6  }
--
--	internet	OBJECT IDENTIFIER
--		::=  {  dod  1  }
--
--	private	OBJECT IDENTIFIER
--		::=  {  internet  4  }
--
--	enterprises	OBJECT IDENTIFIER
--		::=  {  private  1  }
--
--	Zhone	OBJECT IDENTIFIER
--		::=  {  enterprises  5504  }

BITSTORM-HP-160MibVersion  OBJECT-TYPE
        SYNTAX  OCTET STRING(SIZE(1..16))
        MAX-ACCESS  read-only
        STATUS  current
        DESCRIPTION
        "This object value presents that current  NE by implementation
         is compliant to which version the enterprise MIB belongs to.
        "
   ::= {BITSTORM-HP-160 1}

	BITSTORM-HP-160CfgMgt	OBJECT IDENTIFIER
		::=  {  BITSTORM-HP-160  2  }

	BITSTORM-HP-160SysMgt	OBJECT IDENTIFIER
		::=  {  BITSTORM-HP-160  3  }

	BITSTORM-HP-160MtnMgt	OBJECT IDENTIFIER
		::=  {  BITSTORM-HP-160  4  }

	BITSTORM-HP-160AlmMgt	OBJECT IDENTIFIER
		::=  {  BITSTORM-HP-160  5  }

	BITSTORM-HP-160PerfMgt	OBJECT IDENTIFIER
		::=  {  BITSTORM-HP-160  6  }

	BITSTORM-HP-160TrapMgt	OBJECT IDENTIFIER
		::=  {  BITSTORM-HP-160  7  }

	BITSTORM-HP-160CfgTime	OBJECT IDENTIFIER
		::=  {  BITSTORM-HP-160CfgMgt  1  }

	BITSTORM-HP-160CfgAddress	OBJECT IDENTIFIER
		::=  {  BITSTORM-HP-160CfgMgt  2  }

	BITSTORM-HP-160CfgPhy	OBJECT IDENTIFIER
		::=  {  BITSTORM-HP-160CfgMgt  3  }

--	BITSTORM-HP-160CfgIfc	OBJECT IDENTIFIER
--		::=  {  BITSTORM-HP-160CfgMgt  4  }

	BITSTORM-HP-160CfgBridge	OBJECT IDENTIFIER
		::=  {  BITSTORM-HP-160CfgMgt  4  }

	BITSTORM-HP-160CfgXdslSetting	OBJECT IDENTIFIER
		::=  {  BITSTORM-HP-160CfgMgt  5  }

	BITSTORM-HP-160CfgCLISettings	OBJECT IDENTIFIER  
		::=  {  BITSTORM-HP-160CfgMgt  6  }

	BITSTORM-HP-160CfgCluster	OBJECT IDENTIFIER
		::=  {  BITSTORM-HP-160CfgMgt  7  }

--	BITSTORM-HP-160CfgEnetTrafficDescrTable	OBJECT IDENTIFIER
--		::=  {  BITSTORM-HP-160CfgMgt  9  }
BITSTORM-HP-160CfgEnetTrafficDescrTable	OBJECT-TYPE
		SYNTAX		SEQUENCE  OF  BITSTORM-HP-160CfgEnetTrafficDescrEntry
		MAX-ACCESS	not-accessible
		STATUS		current
		DESCRIPTION	"Description"
		::=  { BITSTORM-HP-160CfgMgt  8 }

		

	BITSTORM-HP-160SysInventory	OBJECT IDENTIFIER
		::=  {  BITSTORM-HP-160SysMgt  1  }

	BITSTORM-HP-160LED	OBJECT IDENTIFIER
		::=  {  BITSTORM-HP-160SysMgt  2  }

	BITSTORM-HP-160SysTemperature	OBJECT IDENTIFIER
		::=  {  BITSTORM-HP-160SysMgt  3  }

	BITSTORM-HP-160SystemRestart	OBJECT-TYPE
		SYNTAX			INTEGER  { active ( 1 ) , ready ( 0 ) }
		MAX-ACCESS		read-write
		STATUS			current
		DESCRIPTION		"Always use active(1) to restart the system."
		::=  {  BITSTORM-HP-160MtnMgt  1  }

	BITSTORM-HP-160RestartSNMPAgent	OBJECT-TYPE
		SYNTAX			INTEGER  { active ( 1 ) , ready ( 0 ) }
		MAX-ACCESS		read-write
		STATUS			current
		DESCRIPTION		"SNMP Agent Restart.
       active: Restart SNMP Agent"
		::=  {  BITSTORM-HP-160MtnMgt  2  }

--	BITSTORM-HP-160MtnDatabase	OBJECT IDENTIFIER
--		::=  {  BITSTORM-HP-160MtnMgt  3  }

	BITSTORM-HP-160MtnFirmware	OBJECT IDENTIFIER
		::=  {  BITSTORM-HP-160MtnMgt  3  }

	BITSTORM-HP-160MtnSyslog	OBJECT IDENTIFIER
		::=  {  BITSTORM-HP-160MtnMgt  4  }

	BITSTORM-HP-160MtnAtmOamLoopbackTest	OBJECT IDENTIFIER
		::=  {  BITSTORM-HP-160MtnMgt  5  }
         
	BITSTORM-HP-160LineTestResult	OBJECT-TYPE
		SYNTAX			Integer32  (0..4294967295)
		MAX-ACCESS		read-write
		STATUS			current
		DESCRIPTION		"
		bitmap
		POST :    Bit[1..0] --> 0:ALL PASS, 1:TESTING , 2:NO TEST, 3:FATAL ERROR

                <BME-1> <BME-2> <BME-3> <Discription>
                Bit[ 2] Bit[12] Bit[22] BME Status                                  --> 0:READY, 1:NA
                Bit[ 3] Bit[13] Bit[23] HIC Host-BME Connection Test                --> 0:PASS, 1:FAIL
                Bit[ 4] Bit[14] Bit[24] BME Core & Mem Clk, EMI Initialization      --> 0:PASS, 1:FAIL
                Bit[ 5] Bit[15] Bit[25] HIC PIO SDRAM Read/Write Tests              --> 0:PASS, 1:FAIL
                Bit[ 6] Bit[16] Bit[26] SDRAM Address & Data Bus Connection Tests   --> 0:PASS, 1:FAIL
                Bit[ 7] Bit[17] Bit[27] Memory to Memory BME DMA Tests              --> 0:PASS, 1:FAIL
                Bit[ 8] Bit[18] Bit[28] External Memory Interface Test              --> 0:PASS, 1:FAIL
                Bit[ 9] Bit[19] Bit[29] BME-AFE DDR Bus Connection Tests            --> 0:PASS, 1:FAIL
                Bit[10] Bit[20] Bit[30] AFE Register Read/Write Tests               --> 0:PASS, 1:FAIL
                Bit[11] Bit[21] Bit[31] IFE Register Read/Write Tests               --> 0:PASS, 1:FAIL
                "
		::=  {  BITSTORM-HP-160MtnMgt  6  }

	BITSTORM-HP-160MtnCliConfig 	OBJECT IDENTIFIER
		::=  {  BITSTORM-HP-160MtnMgt  7  }
		
	BITSTORM-HP-160AlmMain	OBJECT IDENTIFIER
		::=  {  BITSTORM-HP-160AlmMgt  1  }

	BITSTORM-HP-160AlmProfileTable	OBJECT-TYPE
		SYNTAX		SEQUENCE  OF  BITSTORM-HP-160AlmProfileEntry
		MAX-ACCESS	not-accessible
		STATUS		current
		DESCRIPTION	"Used to specify alarm log critera."
		::=  { BITSTORM-HP-160AlmMgt  2 }

	BITSTORM-HP-160AlmProfileEntry	OBJECT-TYPE
		SYNTAX		BITSTORM-HP-160AlmProfileEntry
		MAX-ACCESS	not-accessible
		STATUS		current
		DESCRIPTION	"An Entry in the alarm profile table."
		INDEX		{  BITSTORM-HP-160AlmProfileTypeId  }
		::=  { BITSTORM-HP-160AlmProfileTable 1 }

	BITSTORM-HP-160AlmProfileEntry  ::=  SEQUENCE {
		BITSTORM-HP-160AlmProfileTypeId  BITSTORM-HP-160AlmType,
		BITSTORM-HP-160AlmMask  INTEGER,
		BITSTORM-HP-160AlmLevelSet  INTEGER
		}


	BITSTORM-HP-160AlmProfileTypeId	OBJECT-TYPE	
		SYNTAX			BITSTORM-HP-160AlmType
		MAX-ACCESS		not-accessible
		STATUS			current
		DESCRIPTION		"The alarm type identifier number."
		::=  {  BITSTORM-HP-160AlmProfileEntry  1  }


	BITSTORM-HP-160AlmMask	OBJECT-TYPE	
		SYNTAX			INTEGER  { almMask ( 0 ) , almNonMask ( 1 ) } 
		MAX-ACCESS		read-write
		STATUS			current
		DESCRIPTION		"This object specifies an alarm for which notification
         generation is enabled or disabled.

         0: Mask the alarm.
         1: Non-mask the alarm. "
		::=  {  BITSTORM-HP-160AlmProfileEntry  2  }


	BITSTORM-HP-160AlmLevelSet	OBJECT-TYPE	
		SYNTAX			INTEGER  { almLevelMinor ( 1 ) , almLevelMajor ( 2 ) } 
		MAX-ACCESS		read-write
		STATUS			current
		DESCRIPTION		"This object specifies the alarm level.

         1: Minor
         2: Major "
		::=  {  BITSTORM-HP-160AlmProfileEntry  3  }

	BITSTORM-HP-160AlmCurrentTable	OBJECT-TYPE
		SYNTAX		SEQUENCE  OF  BITSTORM-HP-160AlmCurrentEntry
		MAX-ACCESS	not-accessible
		STATUS		current
		DESCRIPTION	"The current alarm table."
		::=  { BITSTORM-HP-160AlmMgt  3 }

	BITSTORM-HP-160AlmCurrentEntry	OBJECT-TYPE
		SYNTAX		BITSTORM-HP-160AlmCurrentEntry
		MAX-ACCESS	not-accessible
		STATUS		current
		DESCRIPTION	"An Entry in the current alarm table."
		INDEX		{  BITSTORM-HP-160AlmSeqId  }
		::=  { BITSTORM-HP-160AlmCurrentTable 1 }

	BITSTORM-HP-160AlmCurrentEntry  ::=  SEQUENCE {
		BITSTORM-HP-160AlmCurrentEntPhyIndex  PhysicalIndex,
		BITSTORM-HP-160AlmCurrentIfIndex  InterfaceIndex,
		BITSTORM-HP-160AlmCurrentTypeId  BITSTORM-HP-160AlmType,
		BITSTORM-HP-160AlmCurrentLevel  INTEGER,
		BITSTORM-HP-160AlmCurrentState  INTEGER,
		BITSTORM-HP-160AlmCurrentTime  OCTET STRING
		}


	BITSTORM-HP-160AlmCurrentEntPhyIndex	OBJECT-TYPE	
		SYNTAX			PhysicalIndex  ( 1 .. 2147483647  ) 
		MAX-ACCESS		read-only
		STATUS			current
		DESCRIPTION		"This attribute indicates the suffered entity by the entPhysicalIndex."
		::=  {  BITSTORM-HP-160AlmCurrentEntry  1  }


	BITSTORM-HP-160AlmCurrentIfIndex	OBJECT-TYPE	
		SYNTAX			InterfaceIndex
		MAX-ACCESS		read-only
		STATUS			current
		DESCRIPTION		"This attribute indicates the suffered interface index by ifIndex."
		::=  {  BITSTORM-HP-160AlmCurrentEntry  2  }


	BITSTORM-HP-160AlmCurrentTypeId	OBJECT-TYPE	
		SYNTAX			BITSTORM-HP-160AlmType
		MAX-ACCESS		read-only
		STATUS			current
		DESCRIPTION		"This attribute indicates the suffered alarm type name."
		::=  {  BITSTORM-HP-160AlmCurrentEntry  3  }


	BITSTORM-HP-160AlmCurrentLevel	OBJECT-TYPE	
		SYNTAX			INTEGER  { BITSTORM-HP-160AlmLevelMinor ( 1 ) , BITSTORM-HP-160AlmLevelMajor ( 2 ) } 
		MAX-ACCESS		read-only
		STATUS			current
		DESCRIPTION		"This attribute indicates the alarm level specified by alarm profile.

        1: Minor
        2: Major"
		::=  {  BITSTORM-HP-160AlmCurrentEntry  4  }


	BITSTORM-HP-160AlmCurrentState	OBJECT-TYPE	
		SYNTAX			INTEGER  { BITSTORM-HP-160AlmStateSet ( 1 ) , BITSTORM-HP-160AlmStateClear ( 2 ) } 
		MAX-ACCESS		read-only
		STATUS			current
		DESCRIPTION		"This attribute indicates the alarm occurrence.

        1: Alarm has not occurred
        2: Alarm has occurred-----by current alarm table definition, this attribute will be always this value. "
		::=  {  BITSTORM-HP-160AlmCurrentEntry  5  }


	BITSTORM-HP-160AlmCurrentTime	OBJECT-TYPE	
		SYNTAX			OCTET STRING  ( SIZE ( 32  ) ) 
		MAX-ACCESS		read-only
		STATUS			current
		DESCRIPTION		"This attribute indicates the alarm occurence time of the
        current alarm table."
		::=  {  BITSTORM-HP-160AlmCurrentEntry  6  }

	BITSTORM-HP-160AlmTable	OBJECT-TYPE
		SYNTAX		SEQUENCE  OF  BITSTORM-HP-160AlmEntry
		MAX-ACCESS	not-accessible
		STATUS		current
		DESCRIPTION	"The alarm log table."
		::=  { BITSTORM-HP-160AlmMgt  4 }

	BITSTORM-HP-160AlmEntry	OBJECT-TYPE
		SYNTAX		BITSTORM-HP-160AlmEntry
		MAX-ACCESS	not-accessible
		STATUS		current
		DESCRIPTION	"An Entry in the alarm log table."
		INDEX		{  BITSTORM-HP-160AlmSeqId  }
		::=  { BITSTORM-HP-160AlmTable 1 }

	BITSTORM-HP-160AlmEntry  ::=  SEQUENCE {
		BITSTORM-HP-160AlmSeqId  Integer32,
		BITSTORM-HP-160AlmEntPhyIndex  PhysicalIndex,
		BITSTORM-HP-160AlmIfIndex  InterfaceIndex,
		BITSTORM-HP-160AlmTypeId  BITSTORM-HP-160AlmType,
		BITSTORM-HP-160AlmLevel  INTEGER,
		BITSTORM-HP-160AlmState  INTEGER,
		BITSTORM-HP-160AlmTime  OCTET STRING
		}


	BITSTORM-HP-160AlmSeqId	OBJECT-TYPE	
		SYNTAX			Integer32  ( 1 .. 65535  ) 
		MAX-ACCESS		read-only
		STATUS			current
		DESCRIPTION		"This object is used by the alarm log table
        to identify the row of this table.
        To check new row number for a new alarm occurrence,
        just obtain this value by
        BITSTORM-HP-160AlmSeqIdNext."
		::=  {  BITSTORM-HP-160AlmEntry  1  }


	BITSTORM-HP-160AlmEntPhyIndex	OBJECT-TYPE	
		SYNTAX			PhysicalIndex
		MAX-ACCESS		read-only
		STATUS			current
		DESCRIPTION		"This attribute indicates the suffered entity by its entPhysicalIndex."
		::=  {  BITSTORM-HP-160AlmEntry  2  }


	BITSTORM-HP-160AlmIfIndex	OBJECT-TYPE	
		SYNTAX			InterfaceIndex
		MAX-ACCESS		read-only
		STATUS			current
		DESCRIPTION		"This attribute indicates the suffered interface by its ifIndex."
		::=  {  BITSTORM-HP-160AlmEntry  3  }


	BITSTORM-HP-160AlmTypeId	OBJECT-TYPE	
		SYNTAX			BITSTORM-HP-160AlmType
		MAX-ACCESS		read-only
		STATUS			current
		DESCRIPTION		"This attribute indicates the suffered alarm type name."
		::=  {  BITSTORM-HP-160AlmEntry  4  }


	BITSTORM-HP-160AlmLevel	OBJECT-TYPE	
		SYNTAX			INTEGER  { BITSTORM-HP-160AlmLevelMinor ( 1 ) , BITSTORM-HP-160AlmLevelMajor ( 2 ) }
		MAX-ACCESS		read-only
		STATUS			current
		DESCRIPTION		"This attribute indicates the suffered alarm level defined by the alarm profile.

        1: Minor
        2: Major"
		::=  {  BITSTORM-HP-160AlmEntry  5  }


	BITSTORM-HP-160AlmState	OBJECT-TYPE	
		SYNTAX			INTEGER  { BITSTORM-HP-160AlmStateSet ( 1 ) , BITSTORM-HP-160AlmStateClear ( 2 ) } 
		MAX-ACCESS		read-only
		STATUS			current
		DESCRIPTION		"This attribute indicates the alarm occurrence or disappearance.

        1: Alarm has not occurred
        2: Alarm has occurred "
		::=  {  BITSTORM-HP-160AlmEntry  6  }


	BITSTORM-HP-160AlmTime	OBJECT-TYPE	
		SYNTAX			OCTET STRING  ( SIZE ( 32  ) ) 
		MAX-ACCESS		read-only
		STATUS			current
		DESCRIPTION		"This attributes indicates the alarm occurence time."
		::=  {  BITSTORM-HP-160AlmEntry  7  }

	BITSTORM-HP-160AlmSeqIdNext	OBJECT-TYPE	
		SYNTAX			Integer32  ( 1 .. 65535  ) 
		MAX-ACCESS		read-only
		STATUS			current
		DESCRIPTION		"1. This object contains an appropriate value to
        be used for BITSTORM-HP-160AlmSeqId when creating
        entries in the BITSTORM-HP-160AlmTable by agent itself.
        2.This indicates the next sequential number used by the alarm table.
      "
		::=  {  BITSTORM-HP-160AlmMgt  5  }

	BITSTORM-HP-160AlmEventTable	OBJECT-TYPE
		SYNTAX		SEQUENCE  OF  BITSTORM-HP-160AlmEventEntry
		MAX-ACCESS	not-accessible
		STATUS		current
		DESCRIPTION	"The Event Log table."
		::=  { BITSTORM-HP-160AlmMgt  6 }

	BITSTORM-HP-160AlmEventEntry	OBJECT-TYPE
		SYNTAX		BITSTORM-HP-160AlmEventEntry
		MAX-ACCESS	not-accessible
		STATUS		current
		DESCRIPTION	"An Entry in the Event table."
		INDEX		{  BITSTORM-HP-160AlmEventSeqId  }
		::=  { BITSTORM-HP-160AlmEventTable 1 }

	BITSTORM-HP-160AlmEventEntry  ::=  SEQUENCE {
		BITSTORM-HP-160AlmEventSeqId  Integer32,
		BITSTORM-HP-160AlmEventEntPhyIndex  PhysicalIndex,
		BITSTORM-HP-160AlmEventIfIndex  InterfaceIndex,
		BITSTORM-HP-160AlmEventTypeId  BITSTORM-HP-160EventType,
		BITSTORM-HP-160AlmEventName  OCTET STRING,
		BITSTORM-HP-160AlmEventTime  OCTET STRING
		}


	BITSTORM-HP-160AlmEventSeqId	OBJECT-TYPE	
		SYNTAX			Integer32  ( 1 .. 65535  ) 
		MAX-ACCESS		read-only
		STATUS			current
		DESCRIPTION		"This object is used by the event table
        to identify the row of this table, when creating a new row in the table by SNMP Agent itself."
		::=  {  BITSTORM-HP-160AlmEventEntry  1  }


	BITSTORM-HP-160AlmEventEntPhyIndex	OBJECT-TYPE	
		SYNTAX			PhysicalIndex
		MAX-ACCESS		read-only
		STATUS			current
		DESCRIPTION		"This attribute indicates the occurrence entity by entPhysicalIndex."
		::=  {  BITSTORM-HP-160AlmEventEntry  2  }


	BITSTORM-HP-160AlmEventIfIndex	OBJECT-TYPE	
		SYNTAX			InterfaceIndex
		MAX-ACCESS		read-only
		STATUS			current
		DESCRIPTION		"This attribute indicates the occurrence interface by ifIndex."
		::=  {  BITSTORM-HP-160AlmEventEntry  3  }


	BITSTORM-HP-160AlmEventTypeId	OBJECT-TYPE	
		SYNTAX			BITSTORM-HP-160EventType
		MAX-ACCESS		read-only
		STATUS			current
		DESCRIPTION		"This command indicates the event type name."
		::=  {  BITSTORM-HP-160AlmEventEntry  4  }

	BITSTORM-HP-160AlmEventName	OBJECT-TYPE
		SYNTAX			OCTET STRING  ( SIZE ( 32  ) ) 
		MAX-ACCESS		read-only
		STATUS			current
		DESCRIPTION		"This attribute indicates the event name
        of the event table."
		::=  {  BITSTORM-HP-160AlmEventEntry  5  }

	BITSTORM-HP-160AlmEventTime	OBJECT-TYPE
		SYNTAX			OCTET STRING  ( SIZE ( 32  ) )
		MAX-ACCESS		read-only
		STATUS			current
		DESCRIPTION		"This attribute indicates the event occurence time
        of the event table."
		::=  {  BITSTORM-HP-160AlmEventEntry  6  }

	BITSTORM-HP-160AlmEventSeqIdNext	OBJECT-TYPE	
		SYNTAX			Integer32  ( 0 .. 65535  ) 
		MAX-ACCESS		read-only
		STATUS			current
		DESCRIPTION		"1.This object contains an appropriate value to
          be used for BITSTORM-HP-160AlmEventSeqId when creating
          entries in the BITSTORM-HP-160AlmEventTable.
        2.This indicates the next sequential number used by the Event log table.
        3.When wrote to 0, this indicates almLogTable will be clear."
		::=  {  BITSTORM-HP-160AlmMgt  7  }

	BITSTORM-HP-160AlmClear	OBJECT-TYPE	
		SYNTAX			INTEGER  { active ( 1 ) , ready ( 2 ) } 
		MAX-ACCESS		read-write
		STATUS			current
		DESCRIPTION		"clear syatem alarm log."
		::=  {  BITSTORM-HP-160AlmMgt  8  }

	BITSTORM-HP-160AlmEventClear	OBJECT-TYPE	
		SYNTAX			INTEGER  { active ( 1 ) , ready ( 2 ) } 
		MAX-ACCESS		read-write
		STATUS			current
		DESCRIPTION		"clear syatem event log."
		::=  {  BITSTORM-HP-160AlmMgt  9  }



--BITSTORM-HP-160PerfDataTable OBJECT-TYPE
--    SYNTAX  SEQUENCE OF BITSTORM-HP-160PerfDataEntry
--    MAX-ACCESS  not-accessible
--    STATUS  current
--    DESCRIPTION
--       "PM table"
--     ::= { BITSTORM-HP-160PerfMgt 1 }
--
--BITSTORM-HP-160PerfDataEntry OBJECT-TYPE
--    SYNTAX  BITSTORM-HP-160PerfDataEntry
--    MAX-ACCESS  not-accessible
--    STATUS  current
--    DESCRIPTION
--       "An Entry of PM table."
--    INDEX   { ifIndex,
--            BITSTORM-HP-160vdslPhysSide }
--     ::= { BITSTORM-HP-160PerfDataTable 1 }
--
--BITSTORM-HP-160PerfDataEntry ::=
--    SEQUENCE {
--         BITSTORM-HP-160vdslPhysSide                   VdslLineEntity,
--         BITSTORM-HP-160PerfDataCellCount         INTEGER,
--         BITSTORM-HP-160PerfDataHEC               INTEGER
--    }

--   BITSTORM-HP-160vdslPhysSide OBJECT-TYPE
--       SYNTAX       VdslLineEntity
--       MAX-ACCESS   not-accessible
--       STATUS       current
--       DESCRIPTION
--           "Identifies whether the transceiver is the Vtuc or Vtur."
--       ::= { BITSTORM-HP-160PerfDataEntry 1 }
--BITSTORM-HP-160PerfDataCellCount     OBJECT-TYPE
--    SYNTAX  INTEGER
--    MAX-ACCESS  read-only
--    STATUS  current
--    DESCRIPTION
--        ""
--     ::= { BITSTORM-HP-160PerfDataEntry 2 }
--
--BITSTORM-HP-160PerfDataHEC     OBJECT-TYPE
--    SYNTAX  INTEGER
--    MAX-ACCESS  read-only
--    STATUS  current
--    DESCRIPTION
--        ""
--     ::= { BITSTORM-HP-160PerfDataEntry 3 }


	BITSTORM-HP-160Traps	OBJECT IDENTIFIER
		::=  {  BITSTORM-HP-160TrapMgt  1  }

	BITSTORM-HP-160SysDate	OBJECT-TYPE
		SYNTAX			OCTET STRING  ( SIZE ( 8 .. 10  ) )
		MAX-ACCESS		read-write
		STATUS			current
		DESCRIPTION		"System date.

        Format: YYYY/MM/DD
        YYYY: Year
        MM: Month
        DD: Day

        03/04/2005 is equivalent to 3/4/2005.
        "
		::=  {  BITSTORM-HP-160CfgTime  1  }

	BITSTORM-HP-160SysTime	OBJECT-TYPE	
		SYNTAX			OCTET STRING  ( SIZE ( 8  ) ) 
		MAX-ACCESS		read-write
		STATUS			current
		DESCRIPTION		"System time.

        Format: hh:mm:ss
        hh: hour
        mm: minute
        ss: second

        Use pattern like 13:03:02 instead of 13:3:2
        "
		::=  {  BITSTORM-HP-160CfgTime  2  }

	BITSTORM-HP-160SNTP	OBJECT IDENTIFIER
		::=  {  BITSTORM-HP-160CfgTime  3  }

	BITSTORM-HP-160CfgInband	OBJECT IDENTIFIER
		::=  {  BITSTORM-HP-160CfgAddress  1  }

	BITSTORM-HP-160CfgOutband	OBJECT IDENTIFIER
		::=  {  BITSTORM-HP-160CfgAddress  2  }

	BITSTORM-HP-160CfgInbandRouteTable	OBJECT-TYPE
		SYNTAX		SEQUENCE  OF  BITSTORM-HP-160CfgInbandRouteEntry
		MAX-ACCESS	not-accessible
		STATUS		current
		DESCRIPTION	"The Inband Route table."
		::=  { BITSTORM-HP-160CfgAddress  3 }

	BITSTORM-HP-160CfgInbandRouteEntry	OBJECT-TYPE
		SYNTAX		BITSTORM-HP-160CfgInbandRouteEntry
		MAX-ACCESS	not-accessible
		STATUS		current
		DESCRIPTION	"An Entry in the BITSTORM-HP-160CfgInbandRouteTable."
		INDEX		{  BITSTORM-HP-160CfgInbandRouteIndex  }
		::=  { BITSTORM-HP-160CfgInbandRouteTable 1 }

	BITSTORM-HP-160CfgInbandRouteEntry  ::=  SEQUENCE {
		BITSTORM-HP-160CfgInbandRouteIndex  Integer32,
		BITSTORM-HP-160CfgInbandRouteDstIp  IpAddress,
		BITSTORM-HP-160CfgInbandRouteNetmask  IpAddress,
		BITSTORM-HP-160CfgInbandRouteGateway  IpAddress,
		BITSTORM-HP-160CfgInbandRouteRowStatus  RowStatus
		}


	BITSTORM-HP-160CfgInbandRouteIndex	OBJECT-TYPE	
		SYNTAX			Integer32
		MAX-ACCESS		not-accessible
		STATUS			current
		DESCRIPTION		"Inband Route Index."
		::=  {  BITSTORM-HP-160CfgInbandRouteEntry  1  }


	BITSTORM-HP-160CfgInbandRouteDstIp	OBJECT-TYPE	
		SYNTAX			IpAddress
		MAX-ACCESS		read-create
		STATUS			current
		DESCRIPTION		"Inband Route Dst IP."
		::=  {  BITSTORM-HP-160CfgInbandRouteEntry  2  }


	BITSTORM-HP-160CfgInbandRouteNetmask	OBJECT-TYPE	
		SYNTAX			IpAddress
		MAX-ACCESS		read-create
		STATUS			current
		DESCRIPTION		"Inband Route Netmask."
		::=  {  BITSTORM-HP-160CfgInbandRouteEntry  3  }


	BITSTORM-HP-160CfgInbandRouteGateway	OBJECT-TYPE	
		SYNTAX			IpAddress
		MAX-ACCESS		read-create
		STATUS			current
		DESCRIPTION		"Inband Route Gateway."
		::=  {  BITSTORM-HP-160CfgInbandRouteEntry  4  }


	BITSTORM-HP-160CfgInbandRouteRowStatus	OBJECT-TYPE	
		SYNTAX			RowStatus
		MAX-ACCESS		read-create
		STATUS			current
		DESCRIPTION		"RowStatus."
		::=  {  BITSTORM-HP-160CfgInbandRouteEntry  5  }

	BITSTORM-HP-160CfgOutbandDefaultGateway	OBJECT-TYPE
		SYNTAX			TAddress
		MAX-ACCESS		read-write
		STATUS			current
		DESCRIPTION		"This field change will probably disconnect the current link."
		::=  {  BITSTORM-HP-160CfgAddress  4  }

--
	BITSTORM-HP-160CfgOutbandRouteTable	OBJECT-TYPE
		SYNTAX		SEQUENCE  OF  BITSTORM-HP-160CfgOutbandRouteEntry
		MAX-ACCESS	not-accessible
		STATUS		current
		DESCRIPTION	"The Outband Route table."
		::=  { BITSTORM-HP-160CfgAddress  5 }

	BITSTORM-HP-160CfgOutbandRouteEntry	OBJECT-TYPE
		SYNTAX		BITSTORM-HP-160CfgOutbandRouteEntry
		MAX-ACCESS	not-accessible
		STATUS		current
		DESCRIPTION	"An Entry Out the BITSTORM-HP-160CfgOutbandRouteTable."
		INDEX		{  BITSTORM-HP-160CfgOutbandRouteIndex  }
		::=  { BITSTORM-HP-160CfgOutbandRouteTable 1 }

	BITSTORM-HP-160CfgOutbandRouteEntry  ::=  SEQUENCE {
		BITSTORM-HP-160CfgOutbandRouteIndex  Integer32,
		BITSTORM-HP-160CfgOutbandRouteDstIp  IpAddress,
		BITSTORM-HP-160CfgOutbandRouteNetmask  IpAddress,
		BITSTORM-HP-160CfgOutbandRouteGateway  IpAddress,
		BITSTORM-HP-160CfgOutbandRouteRowStatus  RowStatus
		}


	BITSTORM-HP-160CfgOutbandRouteIndex	OBJECT-TYPE	
		SYNTAX			Integer32
		MAX-ACCESS		not-accessible
		STATUS			current
		DESCRIPTION		"Outband Route Index."
		::=  {  BITSTORM-HP-160CfgOutbandRouteEntry  1  }


	BITSTORM-HP-160CfgOutbandRouteDstIp	OBJECT-TYPE	
		SYNTAX			IpAddress
		MAX-ACCESS		read-create
		STATUS			current
		DESCRIPTION		"Outband Route Dst IP."
		::=  {  BITSTORM-HP-160CfgOutbandRouteEntry  2  }


	BITSTORM-HP-160CfgOutbandRouteNetmask	OBJECT-TYPE	
		SYNTAX			IpAddress
		MAX-ACCESS		read-create
		STATUS			current
		DESCRIPTION		"Outband Route Netmask."
		::=  {  BITSTORM-HP-160CfgOutbandRouteEntry  3  }


	BITSTORM-HP-160CfgOutbandRouteGateway	OBJECT-TYPE	
		SYNTAX			IpAddress
		MAX-ACCESS		read-create
		STATUS			current
		DESCRIPTION		"Outband Route Gateway."
		::=  {  BITSTORM-HP-160CfgOutbandRouteEntry  4  }


	BITSTORM-HP-160CfgOutbandRouteRowStatus	OBJECT-TYPE	
		SYNTAX			RowStatus
		MAX-ACCESS		read-create
		STATUS			current
		DESCRIPTION		"RowStatus."
		::=  {  BITSTORM-HP-160CfgOutbandRouteEntry  5  }
--
	BITSTORM-HP-160CfgPhyEnetTable	OBJECT-TYPE
		SYNTAX		SEQUENCE  OF  BITSTORM-HP-160CfgPhyEnetEntry
		MAX-ACCESS	not-accessible
		STATUS		current
		DESCRIPTION	""
		::=  { BITSTORM-HP-160CfgPhy  1 }

	BITSTORM-HP-160CfgPhyEnetEntry	OBJECT-TYPE
		SYNTAX		BITSTORM-HP-160CfgPhyEnetEntry
		MAX-ACCESS	not-accessible
		STATUS		current
		DESCRIPTION	""
		INDEX		{  BITSTORM-HP-160PhyEnetPortIndex  }
		::=  { BITSTORM-HP-160CfgPhyEnetTable 1 }

	BITSTORM-HP-160CfgPhyEnetEntry  ::=  SEQUENCE {
		BITSTORM-HP-160PhyEnetPortIndex  Integer32,
		BITSTORM-HP-160PhyEnetMode  INTEGER,
		BITSTORM-HP-160PhyEnetLinkStatus  INTEGER,
		BITSTORM-HP-160PhyEnetCopperFiberSelect  INTEGER,
		BITSTORM-HP-160PhyEnetCopperFiberStatus  INTEGER
--		BITSTORM-HP-160PhyEnetAdminStatus  INTEGER,
--		BITSTORM-HP-160PhyEnetOperStatus  INTEGER
		}


	BITSTORM-HP-160PhyEnetPortIndex	OBJECT-TYPE
		SYNTAX			Integer32  ( 1 .. 2  )
		MAX-ACCESS		read-only
		STATUS			current
		DESCRIPTION		""
		::=  {  BITSTORM-HP-160CfgPhyEnetEntry  1  }


	BITSTORM-HP-160PhyEnetMode	OBJECT-TYPE
		SYNTAX			INTEGER  { autoNegotiate ( 1 ) , config10MbpsHalf ( 2 ) , config10MbpsFull ( 3 ) , config100MbpsHalf ( 4 ) , config100MbpsFull ( 5 ) , other ( 6 ) , unknown ( 7 ) , config1000Mbps ( 8 ) }
		MAX-ACCESS		read-write
		STATUS			current
		DESCRIPTION		""
		DEFVAL			{ autoNegotiate }
		::=  {  BITSTORM-HP-160CfgPhyEnetEntry  2  }


	BITSTORM-HP-160PhyEnetLinkStatus	OBJECT-TYPE
		SYNTAX			INTEGER  { link-down ( 1 ) , link-10mbpsfull ( 2 ) , link-10mbpshalf ( 3 ) , link-100mbpsfull ( 4 ) , link-100mbpshalf ( 5 ) , link-1000mbpscopper ( 6 ) , link-1000mbpsfiber ( 7 ) }
		MAX-ACCESS		read-only
		STATUS			current
		DESCRIPTION		""
		::=  {  BITSTORM-HP-160CfgPhyEnetEntry  3  }


	BITSTORM-HP-160PhyEnetCopperFiberSelect	OBJECT-TYPE
		SYNTAX			INTEGER  { fiber-first ( 0 ) , copper-first ( 1 ) }
		MAX-ACCESS		read-write
		STATUS			current
		DESCRIPTION		""
		DEFVAL			{ fiber-first }
		::=  {  BITSTORM-HP-160CfgPhyEnetEntry  4  }


	BITSTORM-HP-160PhyEnetCopperFiberStatus	OBJECT-TYPE
		SYNTAX			INTEGER  { fiber ( 0 ) , copper ( 1 )  }
		MAX-ACCESS		read-only
		STATUS			current
		DESCRIPTION		""
		::=  {  BITSTORM-HP-160CfgPhyEnetEntry  5  }

                                                                    
--	BITSTORM-HP-160PhyEnetAdminStatus	OBJECT-TYPE
--		SYNTAX			INTEGER  { off ( 0 ) , on ( 1 )  }
--		MAX-ACCESS		read-write
--		STATUS			current
--		DESCRIPTION		""
--		DEFVAL			{ on }
--		::=  {  BITSTORM-HP-160CfgPhyEnetEntry  6  }

--	BITSTORM-HP-160PhyEnetOperStatus	OBJECT-TYPE
--		SYNTAX			INTEGER  { on ( 1 ) , off ( 2 ) }
--		MAX-ACCESS		read-only
--		STATUS			current
--		DESCRIPTION		""
--		::=  {  BITSTORM-HP-160CfgPhyEnetEntry  7  }

--	BITSTORM-HP-160CfgIfcTable	OBJECT-TYPE
--		SYNTAX		SEQUENCE  OF  BITSTORM-HP-160CfgIfcEntry
--		MAX-ACCESS	not-accessible
--		STATUS		current
--		DESCRIPTION	""
--		::=  { BITSTORM-HP-160CfgIfc  1 }

--	BITSTORM-HP-160CfgIfcEntry	OBJECT-TYPE
--		SYNTAX		BITSTORM-HP-160CfgIfcEntry
--		MAX-ACCESS	not-accessible
--		STATUS		current
--		DESCRIPTION	""
--		INDEX		{  BITSTORM-HP-160CfgIfcIndex  }
--		::=  { BITSTORM-HP-160CfgIfcTable 1 }

--	BITSTORM-HP-160CfgIfcEntry  ::=  SEQUENCE {
--		BITSTORM-HP-160CfgIfcIndex  InterfaceIndex,
--		BITSTORM-HP-160CfgIfcType  INTEGER,
--		BITSTORM-HP-160CfgIfcDevIndex  Integer32,
--		BITSTORM-HP-160CfgIfcConnectionType  INTEGER,
--		BITSTORM-HP-160CfgIfcRxConnectionIdx  Integer32,
--		BITSTORM-HP-160CfgIfcTxConnectionIdx  Integer32,
--		BITSTORM-HP-160CfgIfcRowStatus  RowStatus
--		}

--	BITSTORM-HP-160CfgIfcIndex	OBJECT-TYPE
--		SYNTAX			InterfaceIndex
--		MAX-ACCESS		read-only
--		STATUS			current
--		DESCRIPTION		""
--		::=  {  BITSTORM-HP-160CfgIfcEntry  1  }

--	BITSTORM-HP-160CfgIfcType	OBJECT-TYPE
--		SYNTAX			INTEGER  { enet1 ( 1 ) , enet2 ( 2 ) , gbi1 ( 3 ) , gbi2 ( 4 ) , atm1 ( 5 ) , atm2 ( 6 ) , imaGroup ( 7 ) }
--		MAX-ACCESS		read-create
--		STATUS			current
--		DESCRIPTION		""
--		DEFVAL			{ atm2 }
--		::=  {  BITSTORM-HP-160CfgIfcEntry  2  }

--	BITSTORM-HP-160CfgIfcDevIndex	OBJECT-TYPE
--		SYNTAX			Integer32  ( 0 .. 123  )
--		MAX-ACCESS		read-create
--		STATUS			current
--		DESCRIPTION		""
--		DEFVAL			{ 0 }
--		::=  {  BITSTORM-HP-160CfgIfcEntry  3  }

--  	BITSTORM-HP-160CfgIfcConnectionType	OBJECT-TYPE
--		SYNTAX			INTEGER  { vpl ( 1 ) , vcl ( 2 ) , la ( 3 ) , multivcl ( 4 ) , none ( 5 ) }
--		MAX-ACCESS		read-create
--		STATUS			current
--		DESCRIPTION		""
--		DEFVAL			{ vcl }
--		::=  {  BITSTORM-HP-160CfgIfcEntry  4  }

-- 	BITSTORM-HP-160CfgIfcRxConnectionIdx	OBJECT-TYPE
--		SYNTAX			Integer32  ( 0 .. 65535  )
--		MAX-ACCESS		read-create
--		STATUS			current
--		DESCRIPTION		""
--		DEFVAL			{ 65535 }
--		::=  {  BITSTORM-HP-160CfgIfcEntry  5  }

--  	BITSTORM-HP-160CfgIfcTxConnectionIdx	OBJECT-TYPE
--		SYNTAX			Integer32  ( 0 .. 65535  )
--		MAX-ACCESS		read-create
--		STATUS			current
--		DESCRIPTION		""
--		DEFVAL			{ 65535 }
--		::=  {  BITSTORM-HP-160CfgIfcEntry  6  }

--	BITSTORM-HP-160CfgIfcRowStatus	OBJECT-TYPE
--		SYNTAX			RowStatus
--		MAX-ACCESS		read-create
--		STATUS			current
--		DESCRIPTION		""
--		DEFVAL			{ createAndGo }
--		::=  {  BITSTORM-HP-160CfgIfcEntry  7  }

--	BITSTORM-HP-160CfgIfcReset	OBJECT-TYPE
--		SYNTAX			INTEGER  { none ( 0 ) , all ( 1 ) , gbi1 ( 2 ) , gbi2 ( 3 ) , gbiLA ( 4 ) }
--		MAX-ACCESS		read-write
--		STATUS			current
--		DESCRIPTION		""
--		::=  {  BITSTORM-HP-160CfgIfc  2  }

	BITSTORM-HP-160BridgePortTable	OBJECT-TYPE
		SYNTAX		SEQUENCE  OF  BITSTORM-HP-160BridgePortEntry
		MAX-ACCESS	not-accessible
		STATUS		current
		DESCRIPTION	""
		::=  { BITSTORM-HP-160CfgBridge  1 }

	BITSTORM-HP-160BridgePortEntry	OBJECT-TYPE
		SYNTAX		BITSTORM-HP-160BridgePortEntry
		MAX-ACCESS	not-accessible
		STATUS		current
		DESCRIPTION	""
		INDEX		{  BITSTORM-HP-160BridgePortIfcIndex  }
		::=  { BITSTORM-HP-160BridgePortTable 1 }

	BITSTORM-HP-160BridgePortEntry  ::=  SEQUENCE {
		BITSTORM-HP-160BridgePortIfcIndex  InterfaceIndex,
		BITSTORM-HP-160BridgePortDefaultVlan  Integer32,
		BITSTORM-HP-160BridgePortVlanPriority  Integer32,
		BITSTORM-HP-160BridgePortDefaultVlanTagging  INTEGER,
		BITSTORM-HP-160BridgePortVpmtMode  INTEGER,
		BITSTORM-HP-160BridgePortnodeLinkAggrMode  INTEGER,
		BITSTORM-HP-160BridgePortIngressMode  INTEGER,
		BITSTORM-HP-160BridgePortLinkMode  INTEGER,
		--BITSTORM-HP-160BridgePortVlanStacking  INTEGER,
		BITSTORM-HP-160BridgePortMaxMac  Integer32,
		BITSTORM-HP-160BridgePortAcceptableFrameType  INTEGER,
		BITSTORM-HP-160BridgePortIsolationMode  INTEGER,
		BITSTORM-HP-160BridgePortRowStatus  RowStatus
		}


	BITSTORM-HP-160BridgePortIfcIndex	OBJECT-TYPE	
		SYNTAX			InterfaceIndex
		MAX-ACCESS		read-only
		STATUS			current
		DESCRIPTION		""
		::=  {  BITSTORM-HP-160BridgePortEntry  1  }


	BITSTORM-HP-160BridgePortDefaultVlan	OBJECT-TYPE
		SYNTAX			Integer32  ( 1 .. 4094  )   --960803
		MAX-ACCESS		read-create
		STATUS			current
		DESCRIPTION		""
		::=  {  BITSTORM-HP-160BridgePortEntry  2  }


	BITSTORM-HP-160BridgePortVlanPriority	OBJECT-TYPE	
		SYNTAX			Integer32  ( 0 .. 7  ) 
		MAX-ACCESS		read-create
		STATUS			current
		DESCRIPTION		""
		::=  {  BITSTORM-HP-160BridgePortEntry  3  }


	BITSTORM-HP-160BridgePortDefaultVlanTagging	OBJECT-TYPE	
		SYNTAX			INTEGER  { tagged ( 1 ) , untagged ( 2 ) } 
		MAX-ACCESS		read-create
		STATUS			current
		DESCRIPTION		""
		DEFVAL			{ tagged }
		::=  {  BITSTORM-HP-160BridgePortEntry  4  }


	BITSTORM-HP-160BridgePortVpmtMode	OBJECT-TYPE	
		SYNTAX			INTEGER  { disabled ( 0 ) , singleVc ( 1 ) , multiVc ( 2 ) } 
		MAX-ACCESS		read-create
		STATUS			current
		DESCRIPTION		""
		DEFVAL			{ disabled }
		::=  {  BITSTORM-HP-160BridgePortEntry  5  }


	BITSTORM-HP-160BridgePortnodeLinkAggrMode	OBJECT-TYPE	
		SYNTAX			INTEGER  { disabled ( 0 ) , enabled ( 1 ) } 
		MAX-ACCESS		read-create
		STATUS			current
		DESCRIPTION		""
		DEFVAL			{ disabled }
		::=  {  BITSTORM-HP-160BridgePortEntry  6  }


	BITSTORM-HP-160BridgePortIngressMode	OBJECT-TYPE	
		SYNTAX			INTEGER  { disabled ( 0 ) , enabled ( 1 ) } 
		MAX-ACCESS		read-create
		STATUS			current
		DESCRIPTION		""
		DEFVAL			{ enabled }
		::=  {  BITSTORM-HP-160BridgePortEntry  7  }


	BITSTORM-HP-160BridgePortLinkMode	OBJECT-TYPE	
		SYNTAX			INTEGER  { user ( 0 ) , uplink ( 1 ) } 
		MAX-ACCESS		read-create
		STATUS			current
		DESCRIPTION		""
		DEFVAL			{ user }
		::=  {  BITSTORM-HP-160BridgePortEntry  8  }


--	BITSTORM-HP-160BridgePortVlanStacking	OBJECT-TYPE
--		SYNTAX			INTEGER  { disabled ( 0 ) , enabled ( 1 ) }
--		MAX-ACCESS		read-create
--		STATUS			current
--		DESCRIPTION		""
--		DEFVAL			{ disabled }
--		::=  {  BITSTORM-HP-160BridgePortEntry  9  }


	BITSTORM-HP-160BridgePortMaxMac	OBJECT-TYPE	
		SYNTAX			Integer32  ( 0 .. 65535  ) 
		MAX-ACCESS		read-create
		STATUS			current
		DESCRIPTION		""
		DEFVAL			{ 128 }
		::=  {  BITSTORM-HP-160BridgePortEntry  10  }


	BITSTORM-HP-160BridgePortAcceptableFrameType	OBJECT-TYPE	
		SYNTAX			INTEGER  { only-vlantagged ( 0 ) , only-untagged ( 1 ) , all ( 2 ) } 
		MAX-ACCESS		read-create
		STATUS			current
		DESCRIPTION		""
		DEFVAL			{ all }
		::=  {  BITSTORM-HP-160BridgePortEntry  11  }


	BITSTORM-HP-160BridgePortIsolationMode	OBJECT-TYPE	
		SYNTAX			INTEGER  { disabled ( 0 ) , same ( 2 ) } 
		MAX-ACCESS		read-create
		STATUS			current
		DESCRIPTION		""
		DEFVAL			{ disabled }
		::=  {  BITSTORM-HP-160BridgePortEntry  12  }


	BITSTORM-HP-160BridgePortRowStatus	OBJECT-TYPE	
		SYNTAX			RowStatus
		MAX-ACCESS		read-create
		STATUS			current
		DESCRIPTION		""
		DEFVAL			{ createAndGo }
		::=  {  BITSTORM-HP-160BridgePortEntry  13  }

	BITSTORM-HP-160CfgVlanGroup	OBJECT IDENTIFIER
		::=  {  BITSTORM-HP-160CfgBridge  2  }

	BITSTORM-HP-160CfgFilterGroup	OBJECT IDENTIFIER
		::=  {  BITSTORM-HP-160CfgBridge  3  }

	BITSTORM-HP-160CfgLacpGroup	OBJECT IDENTIFIER
		::=  {  BITSTORM-HP-160CfgBridge  4  }

	BITSTORM-HP-160CfgIgmpGroup	OBJECT IDENTIFIER
		::=  {  BITSTORM-HP-160CfgBridge  5  }

	BITSTORM-HP-160CfgRstpGroup	OBJECT IDENTIFIER
		::=  {  BITSTORM-HP-160CfgBridge  6  }

	BITSTORM-HP-160CfgRelayGroup	OBJECT IDENTIFIER
		::=  {  BITSTORM-HP-160CfgBridge  7  }

	BITSTORM-HP-160CfgVpmtGroup	OBJECT IDENTIFIER
		::=  {  BITSTORM-HP-160CfgBridge  8  }
		
        BITSTORM-HP-160CfgSystemConfiguration	OBJECT IDENTIFIER
		::=  {  BITSTORM-HP-160CfgBridge  9  }
		
        BITSTORM-HP-160CfgLayerIIServiceOption	OBJECT IDENTIFIER
		::=  {  BITSTORM-HP-160CfgBridge  13  }

		
	BITSTORM-HP-160AgingTimeTable	OBJECT-TYPE
		SYNTAX		SEQUENCE  OF  BITSTORM-HP-160AgingTimeEntry
		MAX-ACCESS	not-accessible
		STATUS		current
		DESCRIPTION	""
		::=  { BITSTORM-HP-160CfgBridge  10 }

	BITSTORM-HP-160AgingTimeEntry	OBJECT-TYPE
		SYNTAX		BITSTORM-HP-160AgingTimeEntry
		MAX-ACCESS	not-accessible
		STATUS		current
		DESCRIPTION	""
		INDEX		{  BITSTORM-HP-160AgingTimeIfcIndex  }
		::=  { BITSTORM-HP-160AgingTimeTable 1 }

	BITSTORM-HP-160AgingTimeEntry  ::=  SEQUENCE {
		BITSTORM-HP-160AgingTimeIfcIndex  InterfaceIndex,
		BITSTORM-HP-160AgingTime  Integer32
		}


	BITSTORM-HP-160AgingTimeIfcIndex	OBJECT-TYPE
		SYNTAX			InterfaceIndex
		MAX-ACCESS		read-only
		STATUS			current
		DESCRIPTION		""
		::=  {  BITSTORM-HP-160AgingTimeEntry  1  }


	BITSTORM-HP-160AgingTime	OBJECT-TYPE
		SYNTAX			Integer32  ( 10 .. 600  )
		MAX-ACCESS		read-create
		STATUS			current
		DESCRIPTION		"10..600 second"
		::=  {  BITSTORM-HP-160AgingTimeEntry  2  }





	BITSTORM-HP-160SnoopArpRequestTable	OBJECT-TYPE
		SYNTAX		SEQUENCE  OF  BITSTORM-HP-160SnoopArpRequestEntry
		MAX-ACCESS	not-accessible
		STATUS		current
		DESCRIPTION	""
		::=  { BITSTORM-HP-160CfgBridge  11 }

	BITSTORM-HP-160SnoopArpRequestEntry	OBJECT-TYPE
		SYNTAX		BITSTORM-HP-160SnoopArpRequestEntry
		MAX-ACCESS	not-accessible
		STATUS		current
		DESCRIPTION	""
		INDEX		{  BITSTORM-HP-160SnoopArpIfcIndex  }
		::=  { BITSTORM-HP-160SnoopArpRequestTable 1 }

	BITSTORM-HP-160SnoopArpRequestEntry  ::=  SEQUENCE {
		BITSTORM-HP-160SnoopArpIfcIndex  InterfaceIndex,
		BITSTORM-HP-160LearnByDhcp  INTEGER,
		BITSTORM-HP-160DefaultGatewayMac  PhysAddress
		}


	BITSTORM-HP-160SnoopArpIfcIndex	OBJECT-TYPE
		SYNTAX			InterfaceIndex
		MAX-ACCESS		read-only
		STATUS			current
		DESCRIPTION		""
		::=  {  BITSTORM-HP-160SnoopArpRequestEntry  1  }


	BITSTORM-HP-160LearnByDhcp	OBJECT-TYPE
		SYNTAX			INTEGER{ false ( 0 ) , true ( 1 ) }
		MAX-ACCESS		read-create
		STATUS			current
		DESCRIPTION		"0:defaultGatewayMac is preconfigured, 1:defaultGatewayMac is learnByDhcp.
                                        Once the value is changed, the defaultGatewayMac will be cleared to FF:FF:FF:FF:FF:FF"
		::=  {  BITSTORM-HP-160SnoopArpRequestEntry  2  }


	BITSTORM-HP-160DefaultGatewayMac	OBJECT-TYPE
		SYNTAX			PhysAddress
		MAX-ACCESS		read-create
		STATUS			current
		DESCRIPTION		"string hex mac format in DB, example->FF:FF:FF:FF:FF:FF
                                        FF:FF:FF:FF:FF:FF means empty entry, the bport doesn't exist."
		::=  {  BITSTORM-HP-160SnoopArpRequestEntry  3  }



--
	BITSTORM-HP-160BridgeArpSpoofingTable	OBJECT-TYPE
		SYNTAX		SEQUENCE  OF  BITSTORM-HP-160BridgeArpSpoofingEntry
		MAX-ACCESS	not-accessible
		STATUS		current
		DESCRIPTION	""
		::=  { BITSTORM-HP-160CfgBridge  12 }

	BITSTORM-HP-160BridgeArpSpoofingEntry	OBJECT-TYPE
		SYNTAX		BITSTORM-HP-160BridgeArpSpoofingEntry
		MAX-ACCESS	not-accessible
		STATUS		current
		DESCRIPTION	""
		INDEX		{  BITSTORM-HP-160ArpSpoofingIndex  }
		::=  { BITSTORM-HP-160BridgeArpSpoofingTable 1 }       		
		
                                                        
	BITSTORM-HP-160BridgeArpSpoofingEntry  ::=  SEQUENCE {
		BITSTORM-HP-160ArpSpoofingIndex  Integer32,
		BITSTORM-HP-160ArpSpoofingBpIndex  Integer32,
		BITSTORM-HP-160ArpSpoofingSrcIp  IpAddress,
		BITSTORM-HP-160ArpSpoofingSrcMac  PhysAddress,
		BITSTORM-HP-160ArpSpoofingRowStatus  RowStatus
		}


	BITSTORM-HP-160ArpSpoofingIndex	OBJECT-TYPE
		SYNTAX			Integer32(0..1536)
		MAX-ACCESS		read-only
		STATUS			current
		DESCRIPTION		""
		::=  {  BITSTORM-HP-160BridgeArpSpoofingEntry  1  }


	BITSTORM-HP-160ArpSpoofingBpIndex	OBJECT-TYPE
		SYNTAX			Integer32(4..219)
		MAX-ACCESS		read-create
		STATUS			current
		DESCRIPTION		""
		::=  {  BITSTORM-HP-160BridgeArpSpoofingEntry  2  }

	BITSTORM-HP-160ArpSpoofingSrcIp	OBJECT-TYPE
		SYNTAX			IpAddress
		MAX-ACCESS		read-create
		STATUS			current
		DESCRIPTION		""
		::=  {  BITSTORM-HP-160BridgeArpSpoofingEntry  3  }

	BITSTORM-HP-160ArpSpoofingSrcMac	OBJECT-TYPE
		SYNTAX			PhysAddress
		MAX-ACCESS		read-create
		STATUS			current
		DESCRIPTION		"string hex mac format in DB, example->FF:FF:FF:FF:FF:FF"
		::=  {  BITSTORM-HP-160BridgeArpSpoofingEntry  4  }
	BITSTORM-HP-160ArpSpoofingRowStatus	OBJECT-TYPE
		SYNTAX			RowStatus
		MAX-ACCESS		read-create
		STATUS			current
		DESCRIPTION		""
		::=  {  BITSTORM-HP-160BridgeArpSpoofingEntry  5  }
--



--	BITSTORM-HP-160CfgAclService	OBJECT-TYPE
--		SYNTAX			INTEGER  { disable ( 0 ) , enable ( 1 ) }
--		MAX-ACCESS		read-write
--		STATUS			current
--		DESCRIPTION		""
--		DEFVAL			{ enable }
--		::=  {  BITSTORM-HP-160CfgBridge  8  }

	BITSTORM-HP-160CfgXdslLineInfoTable	OBJECT-TYPE
		SYNTAX		SEQUENCE  OF  BITSTORM-HP-160CfgXdslLineInfoEntry
		MAX-ACCESS	not-accessible
		STATUS		current
		DESCRIPTION	"The Xdsl Line configuration table."
		::=  { BITSTORM-HP-160CfgXdslSetting  2 }

	BITSTORM-HP-160CfgXdslLineInfoEntry	OBJECT-TYPE
		SYNTAX		BITSTORM-HP-160CfgXdslLineInfoEntry
		MAX-ACCESS	not-accessible
		STATUS		current
		DESCRIPTION	"An Entry in the BITSTORM-HP-160CfgXdslLineInfoTable"
		INDEX		{  BITSTORM-HP-160CfgXdslIfIndex  }
		::=  { BITSTORM-HP-160CfgXdslLineInfoTable 1 }

	BITSTORM-HP-160CfgXdslLineInfoEntry  ::=  SEQUENCE {
		BITSTORM-HP-160CfgXdslIfIndex  InterfaceIndex,
		BITSTORM-HP-160CfgXdslLinePortID  OCTET STRING,
		BITSTORM-HP-160CfgXdslLinePortDescr  OCTET STRING,
		BITSTORM-HP-160CfgXdslLinePortPhoneNbr  OCTET STRING
		}


	BITSTORM-HP-160CfgXdslIfIndex	OBJECT-TYPE	
		SYNTAX			InterfaceIndex
		MAX-ACCESS		not-accessible
		STATUS			current
		DESCRIPTION		"IfIndex."
		::=  {  BITSTORM-HP-160CfgXdslLineInfoEntry  1  }


	BITSTORM-HP-160CfgXdslLinePortID	OBJECT-TYPE	
		SYNTAX			OCTET STRING  ( SIZE ( 0 .. 32  ) )
		MAX-ACCESS		read-write
		STATUS			current
		DESCRIPTION		"The Port Identifier."
		::=  {  BITSTORM-HP-160CfgXdslLineInfoEntry  2  }


	BITSTORM-HP-160CfgXdslLinePortDescr	OBJECT-TYPE	
		SYNTAX			OCTET STRING  ( SIZE ( 0 .. 48  ) ) 
		MAX-ACCESS		read-write
		STATUS			current
		DESCRIPTION		"The Port Description."
		::=  {  BITSTORM-HP-160CfgXdslLineInfoEntry  3  }


	BITSTORM-HP-160CfgXdslLinePortPhoneNbr	OBJECT-TYPE	
		SYNTAX			OCTET STRING  ( SIZE ( 0 .. 32  ) )
		MAX-ACCESS		read-write
		STATUS			current
		DESCRIPTION		"The Port Phone No."
		::=  {  BITSTORM-HP-160CfgXdslLineInfoEntry  4  }

	BITSTORM-HP-160CfgXdslLineTable	OBJECT-TYPE
		SYNTAX		SEQUENCE  OF  BITSTORM-HP-160CfgXdslLineEntry
		MAX-ACCESS	not-accessible
		STATUS		current
		DESCRIPTION	""
		::=  { BITSTORM-HP-160CfgXdslSetting  3 }

	BITSTORM-HP-160CfgXdslLineEntry	OBJECT-TYPE
		SYNTAX		BITSTORM-HP-160CfgXdslLineEntry
		MAX-ACCESS	not-accessible
		STATUS		current
		DESCRIPTION	""
		INDEX		{  BITSTORM-HP-160CfgXdslIfIndex  }
		::=  { BITSTORM-HP-160CfgXdslLineTable 1 }

	BITSTORM-HP-160CfgXdslLineEntry  ::=  SEQUENCE {
		BITSTORM-HP-160CfgXdslIfIndex  InterfaceIndex,
		BITSTORM-HP-160CfgXdslLineAdminStatus  INTEGER,
		BITSTORM-HP-160CfgXdslLineOperStatus  INTEGER
		}

 	BITSTORM-HP-160CfgXdslIfIndex	OBJECT-TYPE
		SYNTAX			InterfaceIndex
		MAX-ACCESS		not-accessible
		STATUS			current
		DESCRIPTION		"IfIndex."
		::=  {  BITSTORM-HP-160CfgXdslLineEntry  1  }


	BITSTORM-HP-160CfgXdslLineAdminStatus	OBJECT-TYPE
		SYNTAX			INTEGER  { up ( 1 ) , down ( 2 ) }
		MAX-ACCESS		read-write
		STATUS			current
		DESCRIPTION		"The desired state of the interface. When a
            managed system initializes, all interfaces start with
            ifAdminStatus in the down(2) state.  "
		::=  {  BITSTORM-HP-160CfgXdslLineEntry  2  }


	BITSTORM-HP-160CfgXdslLineOperStatus	OBJECT-TYPE
		SYNTAX			INTEGER  
		{ idle(0),
                  handshake(1),
                  training(2),
                  data(3),
                  test(4),
                  deltinit(5),
                  deltdone(6) }
		MAX-ACCESS		read-only
		STATUS			current
		DESCRIPTION		""
		::=  {  BITSTORM-HP-160CfgXdslLineEntry  3  }

	BITSTORM-HP-160CfgCLITimeout	OBJECT-TYPE
		SYNTAX			Integer32  (0..65535)
                UNITS        "second"
		MAX-ACCESS		read-write
		STATUS			current
		DESCRIPTION		"60 ~ 65535 seconds, 0 : no timeout
		1 ~ 59 is not allowed."
		::=  {  BITSTORM-HP-160CfgCLISettings  1  }

--	BITSTORM-HP-160CfgCLIFlags	OBJECT-TYPE
--		SYNTAX			BITS {
--                showAlarm(15),
--                showEvent(14)
--		}
--		MAX-ACCESS		read-write
--		STATUS			current
--		DESCRIPTION		"alarm /event notify of all cli interface"
--		::=  {  BITSTORM-HP-160CfgCLISettings  2  }

	BITSTORM-HP-160CfgClusterConfig	OBJECT IDENTIFIER
		::=  {  BITSTORM-HP-160CfgCluster  1  }

--	BITSTORM-HP-160CfgClusterStatusTable	OBJECT-TYPE
--		SYNTAX		SEQUENCE  OF  BITSTORM-HP-160CfgClusterStatusEntry
--		MAX-ACCESS	not-accessible
--		STATUS		current
--		DESCRIPTION	""
--		::=  { BITSTORM-HP-160CfgCluster  2 }
  --
--	BITSTORM-HP-160CfgClusterStatusEntry	OBJECT-TYPE
--		SYNTAX		BITSTORM-HP-160CfgClusterStatusEntry
--		MAX-ACCESS	not-accessible
--		STATUS		current
--		DESCRIPTION	""
--		INDEX		{  BITSTORM-HP-160CfgClusterId  }
--		::=  { BITSTORM-HP-160CfgClusterStatusTable 1 }
  --
--	BITSTORM-HP-160CfgClusterStatusEntry  ::=  SEQUENCE {
--		BITSTORM-HP-160CfgClusterId  Integer32,
--		BITSTORM-HP-160CfgClusterState  INTEGER,
--		}
  --
--	BITSTORM-HP-160CfgClusterId	OBJECT-TYPE
--		SYNTAX			Integer32  ( 1..16  )
--		MAX-ACCESS		read-only
--		STATUS			current
--		DESCRIPTION		""
--		::=  {  BITSTORM-HP-160CfgClusterStatusEntry  1  }
  --

--	BITSTORM-HP-160CfgClusterState	OBJECT-TYPE
--		SYNTAX			INTEGER  {
--		  IDLE(0),
  --		  REINIT(1),
  --		  DISCOVERING(2),
  --		  REQUESTING(3),
--		  VOTING(4),
--		  SLAVE(5),
--		  MASTER(6)
--		 }
--		MAX-ACCESS		read-only
--		STATUS			current
--		DESCRIPTION		""
--		::=  {  BITSTORM-HP-160CfgClusterStatusEntry  2  }
  
	BITSTORM-HP-160CfgClusterMemberInfoTable	OBJECT-TYPE
		SYNTAX		SEQUENCE  OF  BITSTORM-HP-160CfgClusterMemberInfoEntry
		MAX-ACCESS	not-accessible
		STATUS		current
		DESCRIPTION	""
		::=  { BITSTORM-HP-160CfgCluster  2 }

	BITSTORM-HP-160CfgClusterMemberInfoEntry	OBJECT-TYPE
		SYNTAX		BITSTORM-HP-160CfgClusterMemberInfoEntry
		MAX-ACCESS	not-accessible
		STATUS		current
		DESCRIPTION	""
		INDEX		{  BITSTORM-HP-160CfgClusterMemberId  }
		::=  { BITSTORM-HP-160CfgClusterMemberInfoTable 1 }

	BITSTORM-HP-160CfgClusterMemberInfoEntry  ::=  SEQUENCE {
		BITSTORM-HP-160CfgClusterMemberId  Integer32,
		BITSTORM-HP-160CfgClusterMemberIp  TAddress,
		BITSTORM-HP-160CfgClusterMemberName  OCTET STRING,
		BITSTORM-HP-160CfgClusterMemberState INTEGER
		}

	BITSTORM-HP-160CfgClusterMemberId	OBJECT-TYPE
		SYNTAX			Integer32  ( -2147483648 .. 2147483647  )
		MAX-ACCESS		read-only
		STATUS			current
		DESCRIPTION		""
		::=  {  BITSTORM-HP-160CfgClusterMemberInfoEntry  1  }


	BITSTORM-HP-160CfgClusterMemberIp	OBJECT-TYPE
		SYNTAX			TAddress
		MAX-ACCESS		read-only
		STATUS			current
		DESCRIPTION		""
		::=  {  BITSTORM-HP-160CfgClusterMemberInfoEntry  2  }


	BITSTORM-HP-160CfgClusterMemberName	OBJECT-TYPE
		SYNTAX			OCTET STRING  ( SIZE ( 0 .. 32  ) )
		MAX-ACCESS		read-only
		STATUS			current
		DESCRIPTION		""
		::=  {  BITSTORM-HP-160CfgClusterMemberInfoEntry  3  }

	BITSTORM-HP-160CfgClusterMemberState	OBJECT-TYPE
		SYNTAX			INTEGER  { slave ( 0 ) , master ( 1 ) }
		MAX-ACCESS		read-only
		STATUS			current
		DESCRIPTION		""
		::=  {  BITSTORM-HP-160CfgClusterMemberInfoEntry  4  }

	BITSTORM-HP-160SysInvSWVersion	OBJECT-TYPE
		SYNTAX			OCTET STRING  ( SIZE ( 1 .. 30  ) )
		MAX-ACCESS		read-only
		STATUS			current
		DESCRIPTION		"The software version of the system."
		::=  {  BITSTORM-HP-160SysInventory  1  }

	BITSTORM-HP-160SysInvFWVersion	OBJECT-TYPE	
		SYNTAX			OCTET STRING  ( SIZE ( 1 .. 30  ) ) 
		MAX-ACCESS		read-only
		STATUS			current
		DESCRIPTION		"The firmware version of the system."
		::=  {  BITSTORM-HP-160SysInventory  2  }

	BITSTORM-HP-160SysInvHWVersion	OBJECT-TYPE
		SYNTAX			OCTET STRING  ( SIZE ( 1 .. 30  ) )
		MAX-ACCESS		read-only
		STATUS			current
		DESCRIPTION		"The hardware version of the system."
		::=  {  BITSTORM-HP-160SysInventory  3  }

	BITSTORM-HP-160SysInvModelInfo	OBJECT-TYPE
		SYNTAX			OCTET STRING  ( SIZE ( 1 .. 15  ) ) 
		MAX-ACCESS		read-only
		STATUS			current
		DESCRIPTION		"Model information."
		::=  {  BITSTORM-HP-160SysInventory  4  }

	BITSTORM-HP-160SysInvPartNbr	OBJECT-TYPE
		SYNTAX			OCTET STRING  ( SIZE ( 1 .. 15  ) ) 
		MAX-ACCESS		read-only
		STATUS			current
		DESCRIPTION		"Part Nbr."
		::=  {  BITSTORM-HP-160SysInventory  5  }

	BITSTORM-HP-160SysInvHWRev	OBJECT-TYPE
		SYNTAX			OCTET STRING  ( SIZE ( 1 .. 8  ) ) 
		MAX-ACCESS		read-only
		STATUS			current
		DESCRIPTION		"Hardware Rev."
		::=  {  BITSTORM-HP-160SysInventory  6  }

	BITSTORM-HP-160SysInvSerialNum	OBJECT-TYPE
		SYNTAX			OCTET STRING  ( SIZE ( 1 .. 30  ) ) 
		MAX-ACCESS		read-only
		STATUS			current
		DESCRIPTION		"The serial number string for the system."
		::=  {  BITSTORM-HP-160SysInventory  7  }

--	BITSTORM-HP-160SysInvCardType	OBJECT-TYPE
--		SYNTAX			INTEGER  { gbe ( 1 ) }
--		MAX-ACCESS		read-only
--		STATUS			current
--		DESCRIPTION		"The card type of the system card."
--		::=  {  BITSTORM-HP-160SysInventory  8  }

	BITSTORM-HP-160SysInvSplitterType	OBJECT-TYPE
		SYNTAX			INTEGER  { 
	        ETSI270-POTS-Splitter(0),
                ANSI600-POTS-Splitter(1),
                ANSI900-POTS-Splitter(2),
                ISDN-Splitter(4),
                No-Splitter(7)
                }   
		MAX-ACCESS		read-only
		STATUS			current
		DESCRIPTION		
		"
		ETSI270-POTS-Splitter(0),
                ANSI600-POTS-Splitter(1),
                ANSI900-POTS-Splitter(2),
                ISDN-Splitter(4),
                No-Splitter(7)"
		::=  {  BITSTORM-HP-160SysInventory  8  }

	BITSTORM-HP-160SysInvCPLDVersion	OBJECT-TYPE
		SYNTAX			INTEGER
		MAX-ACCESS		read-only
		STATUS			current
		DESCRIPTION		"The cpld version of the system card."
		::=  {  BITSTORM-HP-160SysInventory  9  }

	BITSTORM-HP-160SysInvCardType	OBJECT-TYPE
		SYNTAX			INTEGER
		MAX-ACCESS		read-only
		STATUS			current
		DESCRIPTION		"The card type of the system card."
		::=  {  BITSTORM-HP-160SysInventory  10  }
		
	BITSTORM-HP-160SysInvBootLoaderVersion 	OBJECT-TYPE
		SYNTAX			OCTET STRING  ( SIZE ( 1 .. 16  ) )
		MAX-ACCESS		read-only
		STATUS			current
		DESCRIPTION		"The winmon version."
		::=  {  BITSTORM-HP-160SysInventory  11  }

	BITSTORM-HP-160SysInvPortCount 	OBJECT-TYPE
		SYNTAX			INTEGER
		MAX-ACCESS		read-only
		STATUS			current
		DESCRIPTION		"Port count."
		::=  {  BITSTORM-HP-160SysInventory  12  }
		
	BITSTORM-HP-160SysSysFanSupported 	OBJECT-TYPE
		SYNTAX			INTEGER  { false ( 0 ) , true ( 1 ) }
		MAX-ACCESS		read-only
		STATUS			current
		DESCRIPTION		""
		::=  {  BITSTORM-HP-160SysMgt  4  }


	BITSTORM-HP-160SysLED	OBJECT-TYPE
		SYNTAX			BITSTORM-HP-160LedType
		MAX-ACCESS		read-only
		STATUS			current
		DESCRIPTION		"System LED status of the DSLAM.

        Normal operation: BITSTORM-HP-160LedGreen(2)
        Self-test fail  : BITSTORM-HP-160LedRed(1)
        Power on        : BITSTORM-HP-160LedYellow(3)
       "
		::=  {  BITSTORM-HP-160LED  1  }

	BITSTORM-HP-160AlmLED	OBJECT-TYPE	
		SYNTAX			BITSTORM-HP-160LedType
		MAX-ACCESS		read-only
		STATUS			current
		DESCRIPTION		"Alarm LED status for BITSTORM-HP-160 of the DSLAM.

        Normal operation         : BITSTORM-HP-160LedGreen(2)
        Major alarm set          : BITSTORM-HP-160LedRed(1)
        Minor alarm set          : BITSTORM-HP-160LedYellow(3)
        Major and minor alarm set: BITSTORM-HP-160LedRedFlash(5)
        Power on                 : BITSTORM-HP-160LedYellow(3)"
		::=  {  BITSTORM-HP-160LED  2  }

	BITSTORM-HP-160Gbe1LED	OBJECT-TYPE	
		SYNTAX			BITSTORM-HP-160LedType
		MAX-ACCESS		read-only
		STATUS			current
		DESCRIPTION		"GbE1 LED status for BITSTORM-HP-160 of the DSLAM.

        Normal operation         : BITSTORM-HP-160LedGreen(2)"
		::=  {  BITSTORM-HP-160LED  3  }

	BITSTORM-HP-160Gbe2LED	OBJECT-TYPE	
		SYNTAX			BITSTORM-HP-160LedType
		MAX-ACCESS		read-only
		STATUS			current
		DESCRIPTION		"GbE2 LED status for BITSTORM-HP-160 of the DSLAM.

        Normal operation         : BITSTORM-HP-160LedGreen(2)"
		::=  {  BITSTORM-HP-160LED  4  }

BITSTORM-HP-160XdslChlLEDTable        OBJECT-TYPE
    SYNTAX  SEQUENCE OF BITSTORM-HP-160XdslChlLEDEntry
    MAX-ACCESS  not-accessible
    STATUS  current
    DESCRIPTION
       "The Channel Led table of system.
       "
     ::= {BITSTORM-HP-160LED 5 }


BITSTORM-HP-160XdslChlLEDEntry OBJECT-TYPE
    SYNTAX  BITSTORM-HP-160XdslChlLEDEntry
    MAX-ACCESS  not-accessible
    STATUS  current
    DESCRIPTION
       "An Entry in the Channel Led table. Support 24 channel."
    INDEX   { ifIndex }
     ::= {BITSTORM-HP-160XdslChlLEDTable 1 }




BITSTORM-HP-160XdslChlLEDEntry ::=
    SEQUENCE {
                BITSTORM-HP-160xdslChlLEDStatus     BITSTORM-HP-160LedType
    }


BITSTORM-HP-160xdslChlLEDStatus    OBJECT-TYPE    --04-25
    SYNTAX BITSTORM-HP-160LedType
    MAX-ACCESS  read-only
    STATUS  current
    DESCRIPTION
       "The LED Status of xDSL Channel
        Port Normal operation   : BITSTORM-HP-160LedGreen (2)
        Port training           : BITSTORM-HP-160LedGreenFlash (6)
        Port not provisioned    : BITSTORM-HP-160LedOff (0)
       "
     ::= {BITSTORM-HP-160XdslChlLEDEntry 1 }   

	BITSTORM-HP-160SysTemperatureUpShfThreshold	OBJECT-TYPE	
		SYNTAX			Integer32  ( -55 .. 85  ) 
		MAX-ACCESS		read-write
		STATUS			current
		DESCRIPTION		"If current temperature exceeds BITSTORM-HP-160SysTemperatureUpShfThreshold, Alarm Manager will
        declare that there is a high temperature alarm after BITSTORM-HP-160SysTemperatureUpShfTime
        seconds.

       "
		DEFVAL			{ 65 }
		::=  {  BITSTORM-HP-160SysTemperature  1  }

	BITSTORM-HP-160SysTemperatureDwShfThreshold	OBJECT-TYPE
		SYNTAX			Integer32  ( -55 .. 85  )
		MAX-ACCESS		read-write
		STATUS			current
		DESCRIPTION		"If current temperature descends below to BITSTORM-HP-160SysTemperatureDwShfThreshold, Alarm Manager will
        declare that there is a lower temperature alarm after BITSTORM-HP-160SysTemperatureDwShfTime
        seconds.
       "
		DEFVAL			{ 65 }
		::=  {  BITSTORM-HP-160SysTemperature  2  }

	BITSTORM-HP-160SysTemperatureUpShfTime	OBJECT-TYPE
		SYNTAX			Integer32  ( 1 .. 255  )
		MAX-ACCESS		read-write
		STATUS			current
		DESCRIPTION		"The BITSTORM-HP-160SysTemperatureUpShfTime will start to count when BITSTORM-HP-160SysTemperatureValue
        excessing BITSTORM-HP-160SysTemperatureUpShfThreshold.

       "
		DEFVAL			{ 10 }
		::=  {  BITSTORM-HP-160SysTemperature  3  }

	BITSTORM-HP-160SysTemperatureDwShfTime	OBJECT-TYPE
		SYNTAX			Integer32  ( 1 .. 255  )
		MAX-ACCESS		read-write
		STATUS			current
		DESCRIPTION		"The BITSTORM-HP-160SysTemperatureDwShfTime will start to count when BITSTORM-HP-160SysTemperatureValue
        excessing BITSTORM-HP-160SysTemperatureDwShfThreshold.
       "
		DEFVAL			{ 10 }
		::=  {  BITSTORM-HP-160SysTemperature  4  }

	BITSTORM-HP-160SysTemperatureaFanThreshold	OBJECT-TYPE
		SYNTAX			Integer32  ( -40 .. 15  )
		MAX-ACCESS		read-write
		STATUS			current
		DESCRIPTION		"If Fan temperature exceeds BITSTORM-HP-160SysTemperatureaFanThreshold, Fan will be turned on."
		::=  {  BITSTORM-HP-160SysTemperature  5  }

	BITSTORM-HP-160SysTemperatureValue	OBJECT-TYPE
		SYNTAX			Integer32  ( -55 .. 125  )
		MAX-ACCESS		read-only
		STATUS			current
		DESCRIPTION		"The current temperature value."
		::=  {  BITSTORM-HP-160SysTemperature  6  }   

	BITSTORM-HP-160SysTemperatureDslValue	OBJECT-TYPE
		SYNTAX			Integer32  
		MAX-ACCESS		read-only
		STATUS			current
		DESCRIPTION		"The DSL temperature value."
		::=  {  BITSTORM-HP-160SysTemperature  7  }
		
--	BITSTORM-HP-160MtnRemoteTFTPServer	OBJECT IDENTIFIER
--		::=  {  BITSTORM-HP-160MtnDatabase  1  }

--	BITSTORM-HP-160MtBootCfgPartition	OBJECT-TYPE
--		SYNTAX			INTEGER  { partition0 ( 0 ) , partition1 ( 1 ) }
--		MAX-ACCESS		read-write
--		STATUS			current
--		DESCRIPTION		"The partition of Flash used when system boot."
--		::=  {  BITSTORM-HP-160MtnDatabase  2  }

--	BITSTORM-HP-160MtnCfgPartitionSelect	OBJECT-TYPE
--		SYNTAX			INTEGER  { partition1 ( 1 ) , partition2 ( 2 ) }
--		MAX-ACCESS		read-write
--		STATUS			current
--		DESCRIPTION		"The partition of Flash used when doing import/reload."
--		::=  {  BITSTORM-HP-160MtnDatabase  3  }

--	BITSTORM-HP-160MtnConfigureDownload	OBJECT-TYPE
--		SYNTAX			INTEGER  { ready ( 0 ) , active ( 1 ) , complete ( 2 ) , fail ( 3 ) , inprogress ( 4 ) }
--		MAX-ACCESS		read-write
--		STATUS			current
--		DESCRIPTION		"This object is to notify the system to download a
--         copy of the configuration file. The
--         manager will retrieve the file via tftp-get.
--
--         The values for setting operations are as follows.
--         1: import active
--
--         The value for status/read operations are as follows:
--         2: import complete
--         3: import fail
--         4: import in progress"
--		::=  {  BITSTORM-HP-160MtnDatabase  4  }

--	BITSTORM-HP-160MtnImportConfigureToRunning	OBJECT-TYPE
--		SYNTAX			INTEGER  { ready ( 0 ) , active ( 1 ) , complete ( 2 ) , fail ( 3 ) , inprogress ( 4 ) }
--		MAX-ACCESS		read-write
--		STATUS			current
--		DESCRIPTION		"This object is to notify the system to save a download
--         copy of the configuration file.
--
--         The values for setting operations are as follows.
--         1: active
--
--         The value for status/read operations are as follows:
--         2: complete
--         3: fail
--         4: in progress"
--		::=  {  BITSTORM-HP-160MtnDatabase  5  }
--
--	BITSTORM-HP-160MtnImportConfigureToNvRAM	OBJECT-TYPE
--		SYNTAX			INTEGER  { ready ( 0 ) , active ( 1 ) , complete ( 2 ) , fail ( 3 ) , inprogress ( 4 ) }
--		MAX-ACCESS		read-write
--		STATUS			current
--		DESCRIPTION		"This object is to notify the system to save a download
--         copy of the configuration file.
--
--         The values for setting operations are as follows.
--         1: active
--
--         The value for status/read operations are as follows:
--         2: complete
--         3: fail
--         4: in progress"
--		::=  {  BITSTORM-HP-160MtnDatabase  6  }
--
--	BITSTORM-HP-160MtnExportConfigure	OBJECT-TYPE
--		SYNTAX			INTEGER  { ready ( 0 ) , active ( 1 ) , complete ( 2 ) , fail ( 3 ) , inprogress ( 4 ) }
--		MAX-ACCESS		read-write
--		STATUS			current
--		DESCRIPTION		"This object is to notify the system to make a
--         copy of the current runnung configuration file. The
--         manager will send the file to tftp server.
--
--         The values for setting operations are as follows.
--         1: active
--
--         The value for status/read operations are as follows:
--         2: complete
--         3: fail
--         4: in progress"
--		::=  {  BITSTORM-HP-160MtnDatabase  7  }
--
--	BITSTORM-HP-160MtnSaveRunningCfg	OBJECT-TYPE
--		SYNTAX			INTEGER  { ready ( 0 ) , active ( 1 ) , complete ( 2 ) , fail ( 3 ) , inprogress ( 4 ) }
--		MAX-ACCESS		read-write
--		STATUS			current
--		DESCRIPTION		"Always use avtive(1) to save all configuration data to select partition NvRAM.
--
--         The values for setting operations are as follows.
--         1: active
--
--         The value for status/read operations are as follows:
--         2: complete
--         3: fail
--         4: in progress"
--		::=  {  BITSTORM-HP-160MtnDatabase  8  }
--
--	BITSTORM-HP-160MtnLoadSystemCfg	OBJECT-TYPE
--		SYNTAX			INTEGER  { ready ( 0 ) , active ( 1 ) , complete ( 2 ) , fail ( 3 ) , inprogress ( 4 ) }
--		MAX-ACCESS		read-write
--		STATUS			current
--		DESCRIPTION		"Always use avtive(1) to load select partition NvRAM to running configuration.
--
--         The values for setting operations are as follows.
--         1: active
--
--         The value for status/read operations are as follows:
--         2: complete
--         3: fail
--         4: in progress"
--		::=  {  BITSTORM-HP-160MtnDatabase  9  }

--	BITSTORM-HP-160MtnSetFactoryDefault	OBJECT-TYPE
--		SYNTAX			INTEGER  { ready ( 0 ) , active ( 1 ) , complete ( 2 ) , fail ( 3 ) , inprogress ( 4 ) }
--		MAX-ACCESS		read-write
--		STATUS			current
--		DESCRIPTION		"Always use avtive(1) to set all configuration data to default.
--
--         The values for setting operations are as follows.
--         1: active
--
--         The value for status/read operations are as follows:
--         2: complete
--         3: fail
--         4: in progress"
--		::=  {  BITSTORM-HP-160MtnDatabase  10  }

	BITSTORM-HP-160MtnRemoteFTPServer	OBJECT IDENTIFIER
		::=  {  BITSTORM-HP-160MtnFirmware  1  }

	BITSTORM-HP-160MtnCliCfgFTPServer	OBJECT IDENTIFIER
		::=  {  BITSTORM-HP-160MtnCliConfig  1  }

	BITSTORM-HP-160MtnCliCfgInbandIndex	OBJECT-TYPE
		SYNTAX			INTEGER
		MAX-ACCESS		read-write
		STATUS			current
		DESCRIPTION		""
		::=  {  BITSTORM-HP-160MtnCliConfig  2  }

	BITSTORM-HP-160MtnCliCfgGeneralIndex	OBJECT-TYPE
		SYNTAX			INTEGER
		MAX-ACCESS		read-write
		STATUS			current
		DESCRIPTION		""
		::=  {  BITSTORM-HP-160MtnCliConfig  3  }

	BITSTORM-HP-160MtnCliCfgInbandBackupName	OBJECT-TYPE
		SYNTAX			OCTET STRING  ( SIZE ( 0 .. 32  ) )
		MAX-ACCESS		read-write
		STATUS			current
		DESCRIPTION		""
		::=  {  BITSTORM-HP-160MtnCliConfig  4  }

	BITSTORM-HP-160MtnCliCfgGeneralBackupName	OBJECT-TYPE
		SYNTAX			OCTET STRING  ( SIZE ( 0 .. 32  ) )
		MAX-ACCESS		read-write
		STATUS			current
		DESCRIPTION		""
		::=  {  BITSTORM-HP-160MtnCliConfig  5  }

	BITSTORM-HP-160MtnCliCfgActionType	OBJECT-TYPE
		SYNTAX			INTEGER  {
                CLICONFIG-SAVE(1),
--                CLICONFIG-LOAD-NVRAM(2),
--                CLICONFIG-LOAD-INTERNAL(3),
--                CLICONFIG-RESTORE-BY-NAME(4),
                CLICONFIG-RESTORE-BY-INDEX(5),
                CLICONFIG-CLEAR-ALL(6),
                CLICONFIG-CLEAR-GENERAL(7),
                CLICONFIG-EXPORT-BINARY(8),
--                CLICONFIG-EXPORT-TEXT(9),
                CLICONFIG-EXPORT-CLI(10),
                CLICONFIG-GET-BINARY(11),
                CLICONFIG-GET-CLI(12),
                CLICONFIG-PUT-BINARY(13),
                CLICONFIG-PUT-CLI(14),
--                CLICONFIG-IMPORT-BINARY(15),
--                CLICONFIG-IMPORT-CLI(16),
                CLICONFIG-IMPORT-DOWNLOAD-BINARY(17),
                CLICONFIG-IMPORT-DOWNLOAD-CLI(18),
                CLICONFIG-CHANGE-DETECT(21)
		 }
		MAX-ACCESS		read-write
		STATUS			current
		DESCRIPTION		"
		Action to be taken:

                CLICONFIG-SAVE:
                   Save database to flash
                   Use cliCfgBackupNameInband with MASK_cliCfgBackupNameInband to specify name for inband database.
                   Use cliCfgBackupNameGeneral with MASK_cliCfgBackupNameGeneral to specify name for general database.
--                CLICONFIG-LOAD-NVRAM:
--                   Load database from flash (used by OAMP internally)
--                CLICONFIG-LOAD-INTERNAL:
--                   Load database from flash (used by OAMP internally)
--                CLICONFIG-RESTORE-BY-NAME:
--                   Restore database with the specific names
--                   Use cliCfgBackupNameInband with MASK_cliCfgBackupNameInband to specify name for inband database.
--                   Use cliCfgBackupNameGeneral with MASK_cliCfgBackupNameGeneral to specify name for general database.
                CLICONFIG-RESTORE-BY-INDEX:
                   Restore database with the specific indexes
                   Use cliCfgParam1 with MASK_cliCfgParam1 to specify index for inband database.
                   Use cliCfgParam2 with MASK_cliCfgParam2 to specify index for general database.
                CLICONFIG-CLEAR-ALL:
                   Clear Inband/General database
                CLICONFIG-CLEAR-GENERAL:
                   Clear General database
                CLICONFIG-EXPORT-BINARY:
                   Export database (binary)
--                CLICONFIG-EXPORT-TEXT:
--                   Export database (text)
                CLICONFIG-EXPORT-CLI:
                   Export database as a CLI script
                   (gbe ip/netmask,route not exported)
                CLICONFIG-GET-BINARY:
                   Get binary database image from a FTP server.
                CLICONFIG-GET-CLI:
                   Get CLI script from a FTP server.
                CLICONFIG-PUT-BINARY:
                   Put binary database image to a FTP server.
                CLICONFIG-PUT-CLI:
                   Put CLI script to a FTP server.
--                CLICONFIG-IMPORT-BINARY:
--                   Import from binary database images
--                CLICONFIG-IMPORT-CLI:
--                   Import from a CLI script
                CLICONFIG-IMPORT-DOWNLOAD-BINARY:
                   As previous CLICONFIG-WRITE-DOWNLOAD.
                   Import from downloaded binary images.
                CLICONFIG-IMPORT-DOWNLOAD-CLI:
                   Import from download CLI script.
                CLICONFIG-CHANGE-DETECT
                   Detect database changes, for agents. 
          "
		::=  {  BITSTORM-HP-160MtnCliConfig  6  }

	BITSTORM-HP-160MtnCliCfgStatus	OBJECT-TYPE
		SYNTAX			INTEGER  {
		FTPPUTSUCCESS(1),
		FTPPUTFAIL(2),
		FTPPUTINPROGRESS(3),
		FTPGETSUCCESS(4),
		FTPGETFAIL(5),
		FTPGETINPROGRESS(6),
		MEMORYWRITESUCCESS(7),
		MEMORYWRITEFAIL(8),
		MEMORYWRITEINPROGRESS(9),
		MEMORYREADSUCCESS(10),
		MEMORYREADFAIL(11),
		MEMORYREADINPROGRESS(12)
		}
		MAX-ACCESS		read-only
		STATUS			current
		DESCRIPTION		"This object is to report the cli configuration status aftert config action."
		::=  {  BITSTORM-HP-160MtnCliConfig  7  }

	BITSTORM-HP-160MtnCliCfgConfigUnsaved	OBJECT-TYPE
		SYNTAX			INTEGER  {
		false(0),
		true(1)
		}
		MAX-ACCESS		read-only
		STATUS			current
		DESCRIPTION		"Must set BITSTORM-HP-160MtnCliCfgActionType to CLICONFIG-CHANGE-DETECT(21).
                                         After BITSTORM-HP-160MtnCliCfgStatus is changed to MEMORYWRITESUCCESS(7), this field is non-zero if there are unsaved database changes."
		::=  {  BITSTORM-HP-160MtnCliConfig  8  }

	BITSTORM-HP-160MtnFlashBackup	OBJECT IDENTIFIER
		::=  { BITSTORM-HP-160MtnMgt   8  } 

--	BITSTORM-HP-160MtnFlashBackupInfoTable	OBJECT-TYPE
--		SYNTAX		SEQUENCE  OF  BITSTORM-HP-160MtnFlashBackupInfoEntry
--		MAX-ACCESS	not-accessible
--		STATUS		current
--		DESCRIPTION	""
--		::=  { BITSTORM-HP-160MtnFlashBackup  1 }

--	BITSTORM-HP-160MtnFlashBackupInfoEntry	OBJECT-TYPE
--		SYNTAX		BITSTORM-HP-160MtnFlashBackupInfoEntry
--		MAX-ACCESS	not-accessible
--		STATUS		current
--		DESCRIPTION	""
--		INDEX		{  BITSTORM-HP-160MtnFlashBackupIndex  }
--		::=  { BITSTORM-HP-160MtnFlashBackupInfoTable 1 }
  --
--	BITSTORM-HP-160MtnFlashBackupInfoEntry  ::=  SEQUENCE {
--		BITSTORM-HP-160MtnFlashBackupIndex  INTEGER,
--		BITSTORM-HP-160MtnFlashBackupEntryName  OCTET STRING,
--		BITSTORM-HP-160MtnFlashBackupEntrySize  Integer32
--		}

--	BITSTORM-HP-160MtnFlashBackupIndex	OBJECT-TYPE
--		SYNTAX			INTEGER  (1..16)
--		MAX-ACCESS		not-accessible
--		STATUS			current
--		DESCRIPTION		""
--		::=  {  BITSTORM-HP-160MtnFlashBackupInfoEntry  1  }

--	BITSTORM-HP-160MtnFlashBackupEntryName	OBJECT-TYPE
--		SYNTAX			OCTET STRING
--		MAX-ACCESS		read-only
--		STATUS			current
--		DESCRIPTION		""
--		::=  {  BITSTORM-HP-160MtnFlashBackupInfoEntry  2  }

--	BITSTORM-HP-160MtnFlashBackupEntrySize	OBJECT-TYPE
--		SYNTAX			Integer32
--		MAX-ACCESS		read-only
--		STATUS			current
--		DESCRIPTION		""
--		::=  {  BITSTORM-HP-160MtnFlashBackupInfoEntry  3  }

	BITSTORM-HP-160MtnFlashBackupInbandTable	OBJECT-TYPE
		SYNTAX		SEQUENCE  OF  BITSTORM-HP-160MtnFlashBackupInbandEntry
		MAX-ACCESS	not-accessible
		STATUS		current
		DESCRIPTION	""
		::=  { BITSTORM-HP-160MtnFlashBackup  1 }

	BITSTORM-HP-160MtnFlashBackupInbandEntry	OBJECT-TYPE
		SYNTAX		BITSTORM-HP-160MtnFlashBackupInbandEntry
		MAX-ACCESS	not-accessible
		STATUS		current
		DESCRIPTION	""
		INDEX		{  BITSTORM-HP-160MtnFlashBackupInbandIndex  }
		::=  { BITSTORM-HP-160MtnFlashBackupInbandTable 1 }

	BITSTORM-HP-160MtnFlashBackupInbandEntry  ::=  SEQUENCE {
		BITSTORM-HP-160MtnFlashBackupInbandIndex  INTEGER,
		BITSTORM-HP-160MtnFlashBackupInbandEntryName  OCTET STRING,
		}

	BITSTORM-HP-160MtnFlashBackupInbandIndex	OBJECT-TYPE
		SYNTAX			INTEGER  (1..16)
		MAX-ACCESS		not-accessible
		STATUS			current
		DESCRIPTION		""
		::=  {  BITSTORM-HP-160MtnFlashBackupInbandEntry  1  }

	BITSTORM-HP-160MtnFlashBackupInbandEntryName	OBJECT-TYPE
		SYNTAX			OCTET STRING   ( SIZE ( 1 .. 32  ) )
		MAX-ACCESS		read-only
		STATUS			current
		DESCRIPTION		""
		::=  {  BITSTORM-HP-160MtnFlashBackupInbandEntry  2  }

	BITSTORM-HP-160MtnFlashBackupGeneralTable	OBJECT-TYPE        
		SYNTAX		SEQUENCE  OF  BITSTORM-HP-160MtnFlashBackupGeneralEntry
		MAX-ACCESS	not-accessible
		STATUS		current
		DESCRIPTION	""
		::=  { BITSTORM-HP-160MtnFlashBackup  2 }

	BITSTORM-HP-160MtnFlashBackupGeneralEntry	OBJECT-TYPE
		SYNTAX		BITSTORM-HP-160MtnFlashBackupGeneralEntry
		MAX-ACCESS	not-accessible
		STATUS		current
		DESCRIPTION	""
		INDEX		{  BITSTORM-HP-160MtnFlashBackupGeneralIndex  }
		::=  { BITSTORM-HP-160MtnFlashBackupGeneralTable 1 }

	BITSTORM-HP-160MtnFlashBackupGeneralEntry  ::=  SEQUENCE {
		BITSTORM-HP-160MtnFlashBackupGeneralIndex  INTEGER,
		BITSTORM-HP-160MtnFlashBackupGeneralEntryName  OCTET STRING,
		}

	BITSTORM-HP-160MtnFlashBackupGeneralIndex	OBJECT-TYPE
		SYNTAX			INTEGER  (1..16)
		MAX-ACCESS		not-accessible
		STATUS			current
		DESCRIPTION		""
		::=  {  BITSTORM-HP-160MtnFlashBackupGeneralEntry  1  }

	BITSTORM-HP-160MtnFlashBackupGeneralEntryName	OBJECT-TYPE
		SYNTAX			OCTET STRING   ( SIZE ( 1 .. 32  ) )
		MAX-ACCESS		read-only
		STATUS			current
		DESCRIPTION		""
		::=  {  BITSTORM-HP-160MtnFlashBackupGeneralEntry  2  }

--  	BITSTORM-HP-160MtnFlashBackupActiveIndex	OBJECT-TYPE
--		SYNTAX			Integer32
--		MAX-ACCESS		read-only
--		STATUS			current
--		DESCRIPTION		""
--		::=  {  BITSTORM-HP-160MtnFlashBackup  2  }

  	BITSTORM-HP-160MtnFlashBackupInbandActiveIndex	OBJECT-TYPE
		SYNTAX			Integer32
		MAX-ACCESS		read-only
		STATUS			current
		DESCRIPTION		""
		::=  {  BITSTORM-HP-160MtnFlashBackup  3  }

  	BITSTORM-HP-160MtnFlashBackupGeneralActiveIndex	OBJECT-TYPE
		SYNTAX			Integer32
		MAX-ACCESS		read-only
		STATUS			current
		DESCRIPTION		""
		::=  {  BITSTORM-HP-160MtnFlashBackup  4  }
--	BITSTORM-HP-160MtnFlashBackupEntryCount	OBJECT-TYPE
--		SYNTAX			Integer32
--		MAX-ACCESS		read-only
--		STATUS			current
--		DESCRIPTION		""
--		::=  {  BITSTORM-HP-160MtnFlashBackup  3  }

--	BITSTORM-HP-160MtnFlashBackupEntryType	OBJECT-TYPE
--		SYNTAX			INTEGER {
--		  Inband(1),
  --                General(2)
--		}
--		MAX-ACCESS		read-only
--		STATUS			current
--		DESCRIPTION		""
--		::=  {  BITSTORM-HP-160MtnFlashBackup  4  }

--	BITSTORM-HP-160MtnGeneralTable	OBJECT-TYPE
--		SYNTAX		SEQUENCE  OF  BITSTORM-HP-160MtnGeneralEntry
--		MAX-ACCESS	not-accessible
--		STATUS		current
--		DESCRIPTION	""
--		::=  { BITSTORM-HP-160MtnFlashBackup  2 }

--	BITSTORM-HP-160MtnGeneralEntry	OBJECT-TYPE
--		SYNTAX		BITSTORM-HP-160MtnGeneralEntry
--		MAX-ACCESS	not-accessible
--		STATUS		current
--		DESCRIPTION	""
--		INDEX		{  BITSTORM-HP-160MtnGeneralIndex  }
--		::=  { BITSTORM-HP-160MtnGeneralTable 1 }

--	BITSTORM-HP-160MtnGeneralEntry  ::=  SEQUENCE {
--		BITSTORM-HP-160MtnGeneralIndex  Integer32,
--		BITSTORM-HP-160MtnGeneralEntryName  OCTET STRING,
--		BITSTORM-HP-160MtnGeneralActiveIndex  Integer32,
--		BITSTORM-HP-160MtnGeneralEntryCount  Integer32
--		}

--	BITSTORM-HP-160MtnGeneralIndex	OBJECT-TYPE
--		SYNTAX			Integer32
--		MAX-ACCESS		not-accessible
--		STATUS			current
--		DESCRIPTION		""
--		::=  {  BITSTORM-HP-160MtnGeneralEntry  1  }

--	BITSTORM-HP-160MtnGeneralEntryName	OBJECT-TYPE
--		SYNTAX			OCTET STRING
--		MAX-ACCESS		read-only
--		STATUS			current
--		DESCRIPTION		""
--		::=  {  BITSTORM-HP-160MtnGeneralEntry  2  }

--  	BITSTORM-HP-160MtnGeneralActiveIndex	OBJECT-TYPE
--		SYNTAX			Integer32
--		MAX-ACCESS		read-only
--		STATUS			current
--		DESCRIPTION		""
--		::=  {  BITSTORM-HP-160MtnGeneralEntry  3  }

--	BITSTORM-HP-160MtnGeneralEntryCount	OBJECT-TYPE
--		SYNTAX			Integer32
--		MAX-ACCESS		read-only
--		STATUS			current
--		DESCRIPTION		""
--		::=  {  BITSTORM-HP-160MtnGeneralEntry  4  }

--	BITSTORM-HP-160MtnFirmwareDownload	OBJECT-TYPE
--		SYNTAX			INTEGER  { ready ( 0 ) , active ( 1 ) , complete ( 2 ) , fail ( 3 ) , inprogress ( 4 ) }
--		MAX-ACCESS		read-write
--		STATUS			current
--		DESCRIPTION		"This object is to notify the system to
--       download a new firmware image  file. The
--         manager will retrieve the file via ftp-get.
--
--         The values for setting operations are as follows.
--         1: download active
--
--         The value for status/read operations are as follows:
--         2: download complete
--         3: download fail
--         4: download in progress"
--		::=  {  BITSTORM-HP-160MtnFirmware  2  }

--	BITSTORM-HP-160MtnFlashWrite	OBJECT-TYPE
--		SYNTAX			INTEGER  { ready ( 0 ) , active ( 1 ) }
--		MAX-ACCESS		read-write
--		STATUS			current
--		DESCRIPTION		"Set this object to active,
--		the system will get image file via ftp and then
  --              write the new firmware to the flash and restart itself.
    --      "
--		::=  {  BITSTORM-HP-160MtnFirmware  2  }

	BITSTORM-HP-160MtnFlashWrite	OBJECT-TYPE
		SYNTAX			INTEGER  {
		IDLE(0),
		ACTIVE(1),
		FTPSUCCESS(2),
		FTPFAIL(3),
		FTPINPROGRESS(4),
		FLASHWRITESUCCES(5),
		FLASHWRITEFAIL(6),
		FLASHWRITEINPROG(7) }
		MAX-ACCESS		read-write
		STATUS			current
		DESCRIPTION		"Set this object to active,
		the system will get image file via ftp and then
                write the new firmware to the flash and restart itself.
                Get this object to know the status.
                
                The values for setting operations are as follows.
        	1: ACTIVE(1)
 	
 	        The value for status/read operations are as follows:
 	        2: FTPSUCCESS(2)
 	        3: FTPFAIL(3)
 	        4: FTPINPROGRESS(4)
        	5: FLASHWRITESUCCES(5)
        	6: FLASHWRITEFAIL(6)
        	7: FLASHWRITEINPROG(7)
                "
		::=  {  BITSTORM-HP-160MtnFirmware  2  }

--	BITSTORM-HP-160MtnDlStatus	OBJECT-TYPE
--		SYNTAX			INTEGER  {
--              IDLE(0),
--                FTPSUCCESS(1),
--                FTPFAIL(2),
--                FTPINPROGRESS(3),
--                FLASHWRITESUCCES(4),
--                FLASHWRITEFAIL(5),
--                FLASHWRITEINPROG(6)
--                                }
--		MAX-ACCESS		read-only
--		STATUS			current
--		DESCRIPTION		"This object is to report the remote download status aftert flash write"
--
--		::=  {  BITSTORM-HP-160MtnFirmware  3  }

	BITSTORM-HP-160MtnBootLoaderUpdate	OBJECT-TYPE
		SYNTAX			INTEGER  {
		IDLE(0),
		ACTIVE(1),
		FTPSUCCESS(2),
		FTPFAIL(3),
		FTPINPROGRESS(4),
		BOOTLOADERCODEWRITESUCCES(5),
		BOOTLOADERWRITEFAIL(6),
		BOOTLOADERWRITEINPROG(7) }
		MAX-ACCESS		read-write
		STATUS			current
		DESCRIPTION		"Set this object to active,
		the system will get bootloader file via ftp and then
                write the new bootloader to the flash and restart itself.
                Get this object to know the status.
                
                The values for setting operations are as follows.
        	1: ACTIVE(1)
 	
 	        The value for status/read operations are as follows:
 	        2: FTPSUCCESS(2)
 	        3: FTPFAIL(3)
 	        4: FTPINPROGRESS(4)
        	5: BOOTLOADERWRITESUCCES(5)
        	6: BOOTLOADERWRITEFAIL(6)
        	7: BOOTLOADERWRITEINPROG(7)
                "

		::=  {  BITSTORM-HP-160MtnFirmware  3  }

	BITSTORM-HP-160MtnImageProfileTable	OBJECT-TYPE
		SYNTAX		SEQUENCE  OF  BITSTORM-HP-160MtnImageProfileEntry
		MAX-ACCESS	not-accessible
		STATUS		current
		DESCRIPTION	"The Flash Image Profile table."
		::=  { BITSTORM-HP-160MtnFirmware  4 }

	BITSTORM-HP-160MtnImageProfileEntry	OBJECT-TYPE
		SYNTAX		BITSTORM-HP-160MtnImageProfileEntry
		MAX-ACCESS	not-accessible
		STATUS		current
		DESCRIPTION	"An Entry in the ImageProfile table."
		INDEX		{  BITSTORM-HP-160MtnImageProfileIndex  }
		::=  { BITSTORM-HP-160MtnImageProfileTable 1 }

	BITSTORM-HP-160MtnImageProfileEntry  ::=  SEQUENCE {
		BITSTORM-HP-160MtnImageProfileIndex  Integer32,
		BITSTORM-HP-160MtnImageProfileDate  OCTET STRING,
		BITSTORM-HP-160MtnImageProfileVersion  OCTET STRING,
		BITSTORM-HP-160MtnImageProfileDisplayName  OCTET STRING
		}


	BITSTORM-HP-160MtnImageProfileIndex	OBJECT-TYPE	
		SYNTAX			Integer32  ( 0 .. 1  ) 
		MAX-ACCESS		read-only
		STATUS			current
		DESCRIPTION		"If current temperature exceeds BITSTORM-HP-160SysTemperatureUpShfThreshold, Alarm Manager will
        declare that there is a high temperature alarm after BITSTORM-HP-160SysTemperatureUpShfTime
        seconds.

       "
		::=  {  BITSTORM-HP-160MtnImageProfileEntry  1  }


	BITSTORM-HP-160MtnImageProfileDate	OBJECT-TYPE	
		SYNTAX			OCTET STRING  ( SIZE ( 1 .. 16  ) ) 
		MAX-ACCESS		read-only
		STATUS			current
		DESCRIPTION		"Flash image date."
		::=  {  BITSTORM-HP-160MtnImageProfileEntry  2  }


	BITSTORM-HP-160MtnImageProfileVersion	OBJECT-TYPE
		SYNTAX			OCTET STRING  ( SIZE ( 1 .. 16  ) ) 
		MAX-ACCESS		read-only
		STATUS			current
		DESCRIPTION		"Flash image version."
		::=  {  BITSTORM-HP-160MtnImageProfileEntry  3  }

	BITSTORM-HP-160MtnImageProfileDisplayName	OBJECT-TYPE
		SYNTAX			OCTET STRING  ( SIZE ( 1 .. 32  ) )
		MAX-ACCESS		read-only
		STATUS			current
		DESCRIPTION		"Flash image display name."
		::=  {  BITSTORM-HP-160MtnImageProfileEntry  4  }

	BITSTORM-HP-160MtnActivePartition	OBJECT-TYPE
		SYNTAX			INTEGER  { partition0 ( 0 ) , partition1 ( 1 ) }
		MAX-ACCESS		read-write
		STATUS			current
		DESCRIPTION		"This object is to select the partition which is active."
		::=  {  BITSTORM-HP-160MtnFirmware  5  }

	BITSTORM-HP-160MtnSyslogService	OBJECT-TYPE
		SYNTAX			INTEGER  { enable ( 1 ) , disable ( 2 ) } 
		MAX-ACCESS		read-write
		STATUS			current
		DESCRIPTION		"Syslog Service On/Off.
       enable: service on
       disable: service off"
		::=  {  BITSTORM-HP-160MtnSyslog  1  }
	BITSTORM-HP-160MtnSyslogServerIP	OBJECT-TYPE	
		SYNTAX			TAddress
		MAX-ACCESS		read-write
		STATUS			current
		DESCRIPTION		"The Syslog Server IP."
		::=  {  BITSTORM-HP-160MtnSyslog  2  }
	BITSTORM-HP-160MtnSyslogMaxFileSize	OBJECT-TYPE
		SYNTAX			INTEGER  (16..1024)
		MAX-ACCESS		read-write
		STATUS			current
		DESCRIPTION		"The maximum size of the log file for syslog. (16 ~ 1024 KB)."
		::=  {  BITSTORM-HP-160MtnSyslog  3  }

	BITSTORM-HP-160MtnOAMCellGeneration	OBJECT-TYPE	
		SYNTAX			INTEGER  { enable ( 1 ) , disable ( 0 ) } 
		MAX-ACCESS		read-write
		STATUS			current
		DESCRIPTION		""
		::=  {  BITSTORM-HP-160MtnAtmOamLoopbackTest  1  }

	BITSTORM-HP-160MtnAtmLoopbackTable	OBJECT-TYPE
		SYNTAX		SEQUENCE  OF  BITSTORM-HP-160MtnAtmLoopbackEntry
		MAX-ACCESS	not-accessible
		STATUS		current
		DESCRIPTION	"The Atm Loopback table."
		::=  { BITSTORM-HP-160MtnAtmOamLoopbackTest  2 }

	BITSTORM-HP-160MtnAtmLoopbackEntry	OBJECT-TYPE
		SYNTAX		BITSTORM-HP-160MtnAtmLoopbackEntry
		MAX-ACCESS	not-accessible
		STATUS		current
		DESCRIPTION	"An Entry in the AtmLoopback table."
		INDEX		{  BITSTORM-HP-160MtnAtmLoopbackIfIndex  }
		::=  { BITSTORM-HP-160MtnAtmLoopbackTable 1 }

	BITSTORM-HP-160MtnAtmLoopbackEntry  ::=  SEQUENCE {
		BITSTORM-HP-160MtnAtmLoopbackIfIndex  InterfaceIndex,
		BITSTORM-HP-160MtnAtmLoopbackId  OCTET STRING,
		BITSTORM-HP-160MtnAtmIfTestType  INTEGER,
		BITSTORM-HP-160MtnAtmIfTestState  INTEGER,
		BITSTORM-HP-160MtnAtmRowStatus  RowStatus
		}


	BITSTORM-HP-160MtnAtmLoopbackIfIndex	OBJECT-TYPE	
		SYNTAX			InterfaceIndex
		MAX-ACCESS		not-accessible
		STATUS			current
		DESCRIPTION		"AtmLoopback IfIndex."
		::=  {  BITSTORM-HP-160MtnAtmLoopbackEntry  1  }


	BITSTORM-HP-160MtnAtmLoopbackId	OBJECT-TYPE	
		SYNTAX			OCTET STRING  ( SIZE ( 1 .. 32  ) ) 
		MAX-ACCESS		read-create
		STATUS			current
		DESCRIPTION		"AtmLoopback Id."
		::=  {  BITSTORM-HP-160MtnAtmLoopbackEntry  2  }


	BITSTORM-HP-160MtnAtmIfTestType	OBJECT-TYPE	
		SYNTAX			INTEGER  { vce2e ( 2 ) , vcsegment ( 3 ) } 
		MAX-ACCESS		read-create
		STATUS			current
		DESCRIPTION		"Atm If Test Type."
		::=  {  BITSTORM-HP-160MtnAtmLoopbackEntry  3  }


	BITSTORM-HP-160MtnAtmIfTestState	OBJECT-TYPE	
		SYNTAX			INTEGER  { idle ( 0 ) , inprogess ( 1 ) , fail ( 2 ) , success ( 3 ) } 
		MAX-ACCESS		read-only
		STATUS			current
		DESCRIPTION		"Atm If Test State."
		::=  {  BITSTORM-HP-160MtnAtmLoopbackEntry  4  }


	BITSTORM-HP-160MtnAtmRowStatus	OBJECT-TYPE	
		SYNTAX			RowStatus
		MAX-ACCESS		read-create
		STATUS			current
		DESCRIPTION		"Atm If RowStatus."
		::=  {  BITSTORM-HP-160MtnAtmLoopbackEntry  5  }

	BITSTORM-HP-160SysAlmStatus	OBJECT-TYPE
		SYNTAX			BITS  {
		housekeep1Alarm ( 17 ) ,
		housekeep2Alarm ( 18 ) ,
		housekeep3Alarm ( 19 ) ,
		housekeep4Alarm ( 20 ) ,
		fanAlarm ( 21 ) ,
		selftestFailAlarm ( 22 ) ,
		aboveTempAlarm ( 23 ) ,
		belowTempAlarm ( 24 )
                }
		MAX-ACCESS		read-only
		STATUS			current
		DESCRIPTION		"Indicates current system-level alarm state.  This is a
                 bit-map of possible conditions.  The various bit
                 positions from left to right are:

          17      housekeep1Alarm        Housekeeping pin 1 detect an alarm input.
          18      housekeep2Alarm        Housekeeping pin 2 detect an alarm input.
          19      housekeep3Alarm        Housekeeping pin 3 detect an alarm input.
          20      housekeep4Alarm        Housekeeping pin 4 detect an alarm input.
          21      fanAlarm               Fan module reports fan failure.
          22      selftestFailAlarm      A module reports self-test failure.
          23      aboveTempAlarm         Temperature above normal.
          24      belowTempAlarm         Temperature below normal.
           "
		::=  {  BITSTORM-HP-160AlmMain  1  }

	BITSTORM-HP-160AlmMajorAlmStatus	OBJECT-TYPE	
		SYNTAX			INTEGER  { majorAlmStatusClear ( 0 ) , majorAlmStatusSet ( 1 ) } 
		MAX-ACCESS		read-only
		STATUS			current
		DESCRIPTION		"Major alarm state is detected or not.

       0: No major alarm detected
       1: Major alarms detected "
		::=  {  BITSTORM-HP-160AlmMain  2  }

	BITSTORM-HP-160AlmMinorAlmStatus	OBJECT-TYPE	
		SYNTAX			INTEGER  { minorAlmStatusClear ( 0 ) , minorAlmStatusSet ( 1 ) } 
		MAX-ACCESS		read-only
		STATUS			current
		DESCRIPTION		"Minor alarm state is detected or not.

       0: No minor alarm detected
       1: Minor alarms detected "
		::=  {  BITSTORM-HP-160AlmMain  3  }

	BITSTORM-HP-160AlmCutOff	OBJECT-TYPE	
		SYNTAX			INTEGER  { acoDeactive ( 0 ) , acoActive ( 1 ) } 
		MAX-ACCESS		read-write
		STATUS			current
		DESCRIPTION		"This command allows the ACO to be activated.
 	
 	0: Alarm cutoff deactive (only for read, not for write)
 	1: Alarm cutoff active"
		::=  {  BITSTORM-HP-160AlmMain  4  }

	BITSTORM-HP-160TrapAlarmPrefix	OBJECT IDENTIFIER
		::=  {  BITSTORM-HP-160Traps  1  }

	BITSTORM-HP-160TrapEventPrefix	OBJECT IDENTIFIER
		::=  {  BITSTORM-HP-160Traps  2  }

	BITSTORM-HP-160SNTPTimeZone	OBJECT-TYPE	
		SYNTAX			OCTET STRING  ( SIZE ( 8  ) ) 
		MAX-ACCESS		read-write
		STATUS			current
		DESCRIPTION		"This command is used to set the time zone. The CCT is +8 relative to Greenwich mean time (GMT).

        This field change will probably end up with time change too.
        "
		DEFVAL			{ GMT }
		::=  {  BITSTORM-HP-160SNTP  1  }

	BITSTORM-HP-160SNTPPollingInterval	OBJECT-TYPE	
		SYNTAX			Integer32  ( 60 .. 65535  ) 
		MAX-ACCESS		read-write
		STATUS			current
		DESCRIPTION		"This command sets the SNTP client to automatically send a time synchronization
        request (specific to the mode) to the network at a specific interval. If the
        poll-interval is set to 0, the polling mechanism will be disabled."
		DEFVAL			{ 600 }
		::=  {  BITSTORM-HP-160SNTP  2  }

	BITSTORM-HP-160SNTPServerIP	OBJECT-TYPE	
		SYNTAX			TAddress  ( SIZE ( 1 .. 255  ) ) 
		MAX-ACCESS		read-write
		STATUS			current
		DESCRIPTION		"This command is used to set the dedicated unicast server ipaddress for the SNTP client."
		::=  {  BITSTORM-HP-160SNTP  3  }

	BITSTORM-HP-160SNTPSynchronize	OBJECT-TYPE
		SYNTAX			INTEGER  { active ( 1 ) , ready ( 0 ) }
		MAX-ACCESS		read-write
		STATUS			current
		DESCRIPTION		"Always use active(1) to do SNTP Synchronization."
		::=  {  BITSTORM-HP-160SNTP  4  }
		
	BITSTORM-HP-160CfgInbandIPAddress	OBJECT-TYPE
		SYNTAX			TAddress
		MAX-ACCESS		read-write
		STATUS			current
		DESCRIPTION		"This field change will probably disconnect the current link."
		::=  {  BITSTORM-HP-160CfgInband  1  }

	BITSTORM-HP-160CfgInbandSubnetMask	OBJECT-TYPE
		SYNTAX			TAddress
		MAX-ACCESS		read-write
		STATUS			current
		DESCRIPTION		"This field change will probably disconnect the current link."
		::=  {  BITSTORM-HP-160CfgInband  2  }

	BITSTORM-HP-160CfgInbandMACAddress	OBJECT-TYPE
		SYNTAX			TAddress  ( SIZE ( 1 .. 255  ) ) 
		MAX-ACCESS		read-only
		STATUS			current
		DESCRIPTION		"This field can't be changed."
		::=  {  BITSTORM-HP-160CfgInband  3  }

	BITSTORM-HP-160CfgInbandManageVlanId	OBJECT-TYPE
		SYNTAX			Integer32  ( 0 .. 4094  ) 
		MAX-ACCESS		read-write
		STATUS			current
		DESCRIPTION		""
		::=  {  BITSTORM-HP-160CfgInband  4  }

	BITSTORM-HP-160CfgInbandManagePriority	OBJECT-TYPE
		SYNTAX			Integer32  ( 0 .. 7  )
		MAX-ACCESS		read-write
		STATUS			current
		DESCRIPTION		""
		::=  {  BITSTORM-HP-160CfgInband  5  }

	BITSTORM-HP-160CfgOutbandIPAddress	OBJECT-TYPE
		SYNTAX			TAddress
		MAX-ACCESS		read-write
		STATUS			current
		DESCRIPTION		"This field change will probably disconnect the current link."
		::=  {  BITSTORM-HP-160CfgOutband  1  }

	BITSTORM-HP-160CfgOutbandSubnetMask	OBJECT-TYPE	
		SYNTAX			TAddress
		MAX-ACCESS		read-write
		STATUS			current
		DESCRIPTION		"This field change will probably disconnect the current link."
		::=  {  BITSTORM-HP-160CfgOutband  2  }

--	BITSTORM-HP-160CfgOutbandDhcpStatus	OBJECT-TYPE
--		SYNTAX			INTEGER  { disable ( 0 ) , enable ( 1 ) , renew ( 2 ) }
--		MAX-ACCESS		read-write
--		STATUS			current
--		DESCRIPTION		"The DHCP admin status."
--		::=  {  BITSTORM-HP-160CfgOutband  3  }

--	BITSTORM-HP-160CfgOutbandDhcpTimeOut	OBJECT-TYPE	
--		SYNTAX			Unsigned32
--		MAX-ACCESS		read-write
--		STATUS			current
--		DESCRIPTION		"Dhcp TimeOut"
--		DEFVAL			{ 60 }
--		::=  {  BITSTORM-HP-160CfgOutband  4  }
  
--	BITSTORM-HP-160CfgOutbandDhcpLeaseTime	OBJECT-TYPE
--		SYNTAX			Unsigned32  ( 0 .. 4294967295  )
--		MAX-ACCESS		read-write
--		STATUS			current
--		DESCRIPTION		"DhcpLeaseTime"
--		DEFVAL			{ 600 }
--		::=  {  BITSTORM-HP-160CfgOutband  5  }

	BITSTORM-HP-160CfgBridgeMemberSetTable	OBJECT-TYPE
		SYNTAX		SEQUENCE  OF  BITSTORM-HP-160CfgBridgeMemberSetEntry
		MAX-ACCESS	not-accessible
		STATUS		current
		DESCRIPTION	""
		::=  { BITSTORM-HP-160CfgVlanGroup  1 }

	BITSTORM-HP-160CfgBridgeMemberSetEntry	OBJECT-TYPE
		SYNTAX		BITSTORM-HP-160CfgBridgeMemberSetEntry
		MAX-ACCESS	not-accessible
		STATUS		current
		DESCRIPTION	"the ports for a specific VLAN"
		INDEX		{  BITSTORM-HP-160CfgBridgeMemberSetVlanId  }
		::=  { BITSTORM-HP-160CfgBridgeMemberSetTable 1 }

	BITSTORM-HP-160CfgBridgeMemberSetEntry  ::=  SEQUENCE {
		BITSTORM-HP-160CfgBridgeMemberSetVlanId  Integer32,
		BITSTORM-HP-160CfgBridgeMemberSetEgressPorts  PortList,
		BITSTORM-HP-160CfgBridgeMemberSetUntaggedPorts  PortList,
		BITSTORM-HP-160CfgBridgeMemberSetIsolationPorts  PortList,
		BITSTORM-HP-160CfgBridgeMemberSetDefaultPorts  PortList,
		BITSTORM-HP-160CfgBridgeMemberSetRowStatus  RowStatus
		}


	BITSTORM-HP-160CfgBridgeMemberSetVlanId	OBJECT-TYPE	
		SYNTAX			Integer32
		MAX-ACCESS		read-only
		STATUS			current
		DESCRIPTION		"The identity of MemberSet."
		::=  {  BITSTORM-HP-160CfgBridgeMemberSetEntry  1  }


	BITSTORM-HP-160CfgBridgeMemberSetEgressPorts	OBJECT-TYPE	
		SYNTAX			PortList
		MAX-ACCESS		read-create
		STATUS			current
		DESCRIPTION		"28 Bytes for bridge port 0~219."
		::=  {  BITSTORM-HP-160CfgBridgeMemberSetEntry  2  }


	BITSTORM-HP-160CfgBridgeMemberSetUntaggedPorts	OBJECT-TYPE
		SYNTAX			PortList
		MAX-ACCESS		read-create
		STATUS			current
		DESCRIPTION		"28 Bytes for bridge port 0~219."
		::=  {  BITSTORM-HP-160CfgBridgeMemberSetEntry  3  }


	BITSTORM-HP-160CfgBridgeMemberSetIsolationPorts	OBJECT-TYPE
		SYNTAX			PortList
		MAX-ACCESS		read-create
		STATUS			current
		DESCRIPTION		"28 Bytes for bridge port 0~219."
		::=  {  BITSTORM-HP-160CfgBridgeMemberSetEntry  4  }


	BITSTORM-HP-160CfgBridgeMemberSetDefaultPorts	OBJECT-TYPE
		SYNTAX			PortList
		MAX-ACCESS		read-only
		STATUS			current
		DESCRIPTION		"28 Bytes for bridge port 0~219."
		::=  {  BITSTORM-HP-160CfgBridgeMemberSetEntry  5  }


	BITSTORM-HP-160CfgBridgeMemberSetRowStatus	OBJECT-TYPE
		SYNTAX			RowStatus
		MAX-ACCESS		read-create
		STATUS			current
		DESCRIPTION		""
		DEFVAL			{ createAndGo }
		::=  {  BITSTORM-HP-160CfgBridgeMemberSetEntry  6  }

	BITSTORM-HP-160CfgBridgeVlanListTable	OBJECT-TYPE
		SYNTAX		SEQUENCE  OF  BITSTORM-HP-160CfgBridgeVlanListEntry
		MAX-ACCESS	not-accessible
		STATUS		current
		DESCRIPTION	""
		::=  { BITSTORM-HP-160CfgVlanGroup  2 }

	BITSTORM-HP-160CfgBridgeVlanListEntry	OBJECT-TYPE
		SYNTAX		BITSTORM-HP-160CfgBridgeVlanListEntry
		MAX-ACCESS	not-accessible
		STATUS		current
		DESCRIPTION	"the VLANs for a specific port"
		INDEX		{  BITSTORM-HP-160CfgBridgeVlanListPortIndex  }
		::=  { BITSTORM-HP-160CfgBridgeVlanListTable 1 }

	BITSTORM-HP-160CfgBridgeVlanListEntry  ::=  SEQUENCE {
		BITSTORM-HP-160CfgBridgeVlanListPortIndex  Integer32,
		BITSTORM-HP-160CfgBridgeVlanListVIDs  OCTET STRING
		}


	BITSTORM-HP-160CfgBridgeVlanListPortIndex	OBJECT-TYPE	
		SYNTAX			Integer32
		MAX-ACCESS		read-only
		STATUS			current
		DESCRIPTION		"The identity of VlanList."
		::=  {  BITSTORM-HP-160CfgBridgeVlanListEntry  1  }


	BITSTORM-HP-160CfgBridgeVlanListVIDs	OBJECT-TYPE	
		SYNTAX			OCTET STRING
		MAX-ACCESS		read-only
		STATUS			current
		DESCRIPTION		""
		::=  {  BITSTORM-HP-160CfgBridgeVlanListEntry  2  }

	BITSTORM-HP-160CfgBridgeTpFdbTable	OBJECT-TYPE
		SYNTAX		SEQUENCE  OF  BITSTORM-HP-160CfgBridgeTpFdbEntry
		MAX-ACCESS	not-accessible
		STATUS		current
		DESCRIPTION	"A table containing filtering information for Unicast
        MAC addresses for each Filtering Database, configured
        into the device by (local or network) management
        specifying the set of ports to which frames received
        from specific ports and containing specific unicast
        destination addresses are allowed to be forwarded.  A
        value of zero in this table as the port number from
        which frames with a specific destination address are
        received, is used to specify all ports for which there
        is no specific entry in this table for that particular
        destination address.  Entries are valid for unicast
        addresses only."
		::=  { BITSTORM-HP-160CfgVlanGroup  3 }

	BITSTORM-HP-160CfgBridgeTpFdbEntry	OBJECT-TYPE
		SYNTAX		BITSTORM-HP-160CfgBridgeTpFdbEntry
		MAX-ACCESS	not-accessible
		STATUS		current
		DESCRIPTION	"Filtering information configured into the device by
        (local or network) management specifying the set of
        ports to which frames received from a specific port and
        containing a specific unicast destination address are
        allowed to be forwarded."
		INDEX		{  BITSTORM-HP-160CfgBridgeTpFdbId  }
		::=  { BITSTORM-HP-160CfgBridgeTpFdbTable 1 }

	BITSTORM-HP-160CfgBridgeTpFdbEntry  ::=  SEQUENCE {
		BITSTORM-HP-160CfgBridgeTpFdbId  Unsigned32,
		BITSTORM-HP-160CfgBridgeTpFdbMacAddress  PhysAddress,
		BITSTORM-HP-160CfgBridgeTpFdbReceivePort  Integer32,
		BITSTORM-HP-160CfgBridgeTpFdbVlan  Integer32,
		BITSTORM-HP-160CfgBridgeTpFdbStatus  INTEGER,
		BITSTORM-HP-160CfgBridgeTpFdbAgingBit  INTEGER,
		BITSTORM-HP-160CfgBridgeTpFdbProcessMode  INTEGER,
		BITSTORM-HP-160CfgBridgeTpFdbUnknownMacMode  INTEGER
		}


	BITSTORM-HP-160CfgBridgeTpFdbId	OBJECT-TYPE	
		SYNTAX			Unsigned32
		MAX-ACCESS		read-only
		STATUS			current
		DESCRIPTION		"The identity of this Filtering Database."
		::=  {  BITSTORM-HP-160CfgBridgeTpFdbEntry  1  }


	BITSTORM-HP-160CfgBridgeTpFdbMacAddress	OBJECT-TYPE	
		SYNTAX			PhysAddress
		MAX-ACCESS		read-only
		STATUS			current
		DESCRIPTION		"The destination MAC address in a frame to which this
        entry's filtering information applies.  This object must
        take the value of a unicast address."
		::=  {  BITSTORM-HP-160CfgBridgeTpFdbEntry  2  }


	BITSTORM-HP-160CfgBridgeTpFdbReceivePort	OBJECT-TYPE	
		SYNTAX			Integer32  ( 0 .. 65535  ) 
		MAX-ACCESS		read-only
		STATUS			current
		DESCRIPTION		"Either the value '0', or the port number of the port
        from which a frame must be received in order for this
        entry's filtering information to apply.  A value of zero
        indicates that this entry applies on all ports of the
        device for which there is no other applicable entry."
		::=  {  BITSTORM-HP-160CfgBridgeTpFdbEntry  3  }


	BITSTORM-HP-160CfgBridgeTpFdbVlan	OBJECT-TYPE	
		SYNTAX			Integer32  ( 0 .. 4094  )   --960803 
		MAX-ACCESS		read-only
		STATUS			current
		DESCRIPTION		""
		::=  {  BITSTORM-HP-160CfgBridgeTpFdbEntry  4  }


	BITSTORM-HP-160CfgBridgeTpFdbStatus	OBJECT-TYPE          
		SYNTAX			INTEGER  { Static ( 0 ) , Dynamic ( 1 ) , Admin ( 2 )  }
		MAX-ACCESS		read-only
		STATUS			current
		DESCRIPTION		""   		
		::=  {  BITSTORM-HP-160CfgBridgeTpFdbEntry  5  }


	BITSTORM-HP-160CfgBridgeTpFdbAgingBit	OBJECT-TYPE	
		SYNTAX			INTEGER  { false ( 0 ) , true ( 1 ) } 
		MAX-ACCESS		read-only
		STATUS			current
		DESCRIPTION		""
		::=  {  BITSTORM-HP-160CfgBridgeTpFdbEntry  6  }


	BITSTORM-HP-160CfgBridgeTpFdbProcessMode	OBJECT-TYPE	
		SYNTAX			INTEGER  { pass ( 0 ) , deny ( 1 ) , direct-term ( 2 ) , res-mc-term ( 3 ) , svl-uc-pass ( 4 ) } 
		MAX-ACCESS		read-only
		STATUS			current
		DESCRIPTION		""
		::=  {  BITSTORM-HP-160CfgBridgeTpFdbEntry  7  }


	BITSTORM-HP-160CfgBridgeTpFdbUnknownMacMode	OBJECT-TYPE	
		SYNTAX			INTEGER  { disabled ( 0 ) , unitcast ( 1 ) , multicast ( 2 ) } 
		MAX-ACCESS		read-only
		STATUS			current
		DESCRIPTION		""
		::=  {  BITSTORM-HP-160CfgBridgeTpFdbEntry  8  }

	BITSTORM-HP-160CfgBridgeFdbStaticTable	OBJECT-TYPE
		SYNTAX		SEQUENCE  OF  BITSTORM-HP-160CfgBridgeFdbStaticEntry
		MAX-ACCESS	not-accessible
		STATUS		current
		DESCRIPTION	"A table containing filtering information for Multicast
        and Broadcast MAC addresses for each VLAN, configured
        into the device by (local or network) management
        specifying the set of ports to which frames received
        from specific ports and containing specific Multicast
        and Broadcast destination addresses are allowed to be
        forwarded.  A value of zero in this table as the port
        number from which frames with a specific destination
        address are received, is used to specify all ports for
        which there is no specific entry in this table for that
        particular destination address.  Entries are valid for
        Multicast and Broadcast addresses only."
		::=  { BITSTORM-HP-160CfgVlanGroup  4 }

	BITSTORM-HP-160CfgBridgeFdbStaticEntry	OBJECT-TYPE
		SYNTAX		BITSTORM-HP-160CfgBridgeFdbStaticEntry
		MAX-ACCESS	not-accessible
		STATUS		current
		DESCRIPTION	"Filtering information configured into the device by
        (local or network) management specifying the set of
        ports to which frames received from this specific port
        for this VLAN and containing this Multicast or Broadcast
        destination address are allowed to be forwarded."
		INDEX		{  BITSTORM-HP-160CfgBridgeFdbStaticId  }
		::=  { BITSTORM-HP-160CfgBridgeFdbStaticTable 1 }

	BITSTORM-HP-160CfgBridgeFdbStaticEntry  ::=  SEQUENCE {
		BITSTORM-HP-160CfgBridgeFdbStaticId  Unsigned32,
		BITSTORM-HP-160CfgBridgeFdbStaticAddress  OCTET STRING,
		BITSTORM-HP-160CfgBridgeFdbStaticOutPort  Integer32,
		BITSTORM-HP-160CfgBridgeFdbStaticVlan  Integer32,
		BITSTORM-HP-160CfgBridgeFdbStaticrProcessMode  INTEGER,
		BITSTORM-HP-160CfgBridgeFdbStaticrRowStatus  RowStatus
		}


	BITSTORM-HP-160CfgBridgeFdbStaticId	OBJECT-TYPE	
		SYNTAX			Unsigned32
		MAX-ACCESS		read-only
		STATUS			current
		DESCRIPTION		"The identity of this Filtering Database."
		::=  {  BITSTORM-HP-160CfgBridgeFdbStaticEntry  1  }


	BITSTORM-HP-160CfgBridgeFdbStaticAddress	OBJECT-TYPE	
		SYNTAX			OCTET STRING  ( SIZE ( 17  ) )
		MAX-ACCESS		read-create
		STATUS			current
		DESCRIPTION		"The destination MAC address in a frame to which this
        entry's filtering information applies.  This object must
        take the value of a Multicast or Broadcast address."
		::=  {  BITSTORM-HP-160CfgBridgeFdbStaticEntry  2  }


	BITSTORM-HP-160CfgBridgeFdbStaticOutPort	OBJECT-TYPE	
		SYNTAX			Integer32  ( 0 .. 65535  ) 
		MAX-ACCESS		read-create
		STATUS			current
		DESCRIPTION		"Either the value '0', or the port number of the port
        from which a frame must be received in order for this
        entry's filtering information to apply.  A value of zero
        indicates that this entry applies on all ports of the
        device for which there is no other applicable entry."
		::=  {  BITSTORM-HP-160CfgBridgeFdbStaticEntry  3  }


	BITSTORM-HP-160CfgBridgeFdbStaticVlan	OBJECT-TYPE	
		SYNTAX			Integer32  ( 0 .. 4094  )   --960803 
		MAX-ACCESS		read-create
		STATUS			current
		DESCRIPTION		""
		::=  {  BITSTORM-HP-160CfgBridgeFdbStaticEntry  4  }


	BITSTORM-HP-160CfgBridgeFdbStaticrProcessMode	OBJECT-TYPE	
		SYNTAX			INTEGER  { deny ( 0 ) , pass ( 1 ) } 
		MAX-ACCESS		read-create
		STATUS			current
		DESCRIPTION		""
		::=  {  BITSTORM-HP-160CfgBridgeFdbStaticEntry  5  }


	BITSTORM-HP-160CfgBridgeFdbStaticrRowStatus	OBJECT-TYPE	
		SYNTAX			RowStatus
		MAX-ACCESS		read-create
		STATUS			current
		DESCRIPTION		"The status of this 
          BITSTORM-HP-160CfgBridgeFdbStaticEntry entry."
		::=  {  BITSTORM-HP-160CfgBridgeFdbStaticEntry  6  }

	BITSTORM-HP-160CfgRateLimitGroup	OBJECT IDENTIFIER
		::=  {  BITSTORM-HP-160CfgVlanGroup  6  }

	BITSTORM-HP-160CfgVlanPriorityGroup	OBJECT IDENTIFIER
		::=  {  BITSTORM-HP-160CfgVlanGroup  7  }


	BITSTORM-HP-160CfgBridgeProtocolFilterTable	OBJECT-TYPE
		SYNTAX		SEQUENCE  OF  BITSTORM-HP-160CfgBridgeProtocolFilterEntry
		MAX-ACCESS	not-accessible
		STATUS		current
		DESCRIPTION	"The Protocol filter configuration table."
		::=  { BITSTORM-HP-160CfgFilterGroup  1 }

	BITSTORM-HP-160CfgBridgeProtocolFilterEntry	OBJECT-TYPE
		SYNTAX		BITSTORM-HP-160CfgBridgeProtocolFilterEntry
		MAX-ACCESS	not-accessible
		STATUS		current
		DESCRIPTION	"An Entry in the BITSTORM-HP-160CfgBridgeProtocolFilterTable"
		INDEX		{  BITSTORM-HP-160CfgBridgeProtocolFilterIndex  }
		::=  { BITSTORM-HP-160CfgBridgeProtocolFilterTable 1 }

	BITSTORM-HP-160CfgBridgeProtocolFilterEntry  ::=  SEQUENCE {
		BITSTORM-HP-160CfgBridgeProtocolFilterIndex  Integer32,
		BITSTORM-HP-160CfgBridgeProtocolFilterInputBridgePort  InterfaceIndex,
		BITSTORM-HP-160CfgBridgeProtocolFilter  INTEGER,
		BITSTORM-HP-160CfgBridgeProtocolFilterRowStatus  RowStatus
		}


	BITSTORM-HP-160CfgBridgeProtocolFilterIndex	OBJECT-TYPE	
		SYNTAX			Integer32
		MAX-ACCESS		read-only
		STATUS			current
		DESCRIPTION		""
		::=  {  BITSTORM-HP-160CfgBridgeProtocolFilterEntry  1  }


	BITSTORM-HP-160CfgBridgeProtocolFilterInputBridgePort	OBJECT-TYPE	
		SYNTAX			InterfaceIndex
		MAX-ACCESS		read-create
		STATUS			current
		DESCRIPTION		""
		::=  {  BITSTORM-HP-160CfgBridgeProtocolFilterEntry  2  }


	BITSTORM-HP-160CfgBridgeProtocolFilter	OBJECT-TYPE
		SYNTAX			INTEGER  { 
		UDP(17),
                TCP(6),
                OSPF(89),
                IGMP(2),
                IGP(9),
                EIGRP(88),
                IPinIP(4),
                GRE(47),
                ICMP(1)
                }
		MAX-ACCESS		read-create
		STATUS			current
		DESCRIPTION		""
		::=  {  BITSTORM-HP-160CfgBridgeProtocolFilterEntry  3  }


	BITSTORM-HP-160CfgBridgeProtocolFilterRowStatus	OBJECT-TYPE	
		SYNTAX			RowStatus
		MAX-ACCESS		read-create
		STATUS			current
		DESCRIPTION		""
		::=  {  BITSTORM-HP-160CfgBridgeProtocolFilterEntry  4  }

	BITSTORM-HP-160CfgBridgeL4DstPortFilterTable	OBJECT-TYPE
		SYNTAX		SEQUENCE  OF  BITSTORM-HP-160CfgBridgeL4DstPortFilterEntry
		MAX-ACCESS	not-accessible
		STATUS		current
		DESCRIPTION	"The L4 dst filter configuration table."
		::=  { BITSTORM-HP-160CfgFilterGroup  2 }

	BITSTORM-HP-160CfgBridgeL4DstPortFilterEntry	OBJECT-TYPE
		SYNTAX		BITSTORM-HP-160CfgBridgeL4DstPortFilterEntry
		MAX-ACCESS	not-accessible
		STATUS		current
		DESCRIPTION	"An Entry in the BITSTORM-HP-160CfgBridgeL4DstPortFilterTable"
		INDEX		{  BITSTORM-HP-160CfgBridgeL4DstPortFilterIndex  }
		::=  { BITSTORM-HP-160CfgBridgeL4DstPortFilterTable 1 }

	BITSTORM-HP-160CfgBridgeL4DstPortFilterEntry  ::=  SEQUENCE {
		BITSTORM-HP-160CfgBridgeL4DstPortFilterIndex  Integer32,
		BITSTORM-HP-160CfgBridgeL4DstPortFilterInputBridgePort  InterfaceIndex,
		BITSTORM-HP-160CfgBridgeL4DstPortFilterDestinationPort  Integer32,
		BITSTORM-HP-160CfgBridgeL4DstPortFilterRowStatus  RowStatus
		}


	BITSTORM-HP-160CfgBridgeL4DstPortFilterIndex	OBJECT-TYPE	
		SYNTAX			Integer32
		MAX-ACCESS		read-only
		STATUS			current
		DESCRIPTION		""
		::=  {  BITSTORM-HP-160CfgBridgeL4DstPortFilterEntry  1  }


	BITSTORM-HP-160CfgBridgeL4DstPortFilterInputBridgePort	OBJECT-TYPE	
		SYNTAX			InterfaceIndex
		MAX-ACCESS		read-create
		STATUS			current
		DESCRIPTION		""
		::=  {  BITSTORM-HP-160CfgBridgeL4DstPortFilterEntry  2  }


	BITSTORM-HP-160CfgBridgeL4DstPortFilterDestinationPort	OBJECT-TYPE	
		SYNTAX			Integer32
		MAX-ACCESS		read-create
		STATUS			current
		DESCRIPTION		""
		::=  {  BITSTORM-HP-160CfgBridgeL4DstPortFilterEntry  3  }


	BITSTORM-HP-160CfgBridgeL4DstPortFilterRowStatus	OBJECT-TYPE	
		SYNTAX			RowStatus
		MAX-ACCESS		read-create
		STATUS			current
		DESCRIPTION		""
		::=  {  BITSTORM-HP-160CfgBridgeL4DstPortFilterEntry  4  }

	BITSTORM-HP-160CfgBridgeSrcMacFilterTable	OBJECT-TYPE
		SYNTAX		SEQUENCE  OF  BITSTORM-HP-160CfgBridgeSrcMacFilterEntry
		MAX-ACCESS	not-accessible
		STATUS		current
		DESCRIPTION	""
		::=  { BITSTORM-HP-160CfgFilterGroup  3 }

	BITSTORM-HP-160CfgBridgeSrcMacFilterEntry	OBJECT-TYPE
		SYNTAX		BITSTORM-HP-160CfgBridgeSrcMacFilterEntry
		MAX-ACCESS	not-accessible
		STATUS		current
		DESCRIPTION	""
		INDEX		{  BITSTORM-HP-160BridgeSrcMacFilterIndex  }
		::=  { BITSTORM-HP-160CfgBridgeSrcMacFilterTable 1 }

	BITSTORM-HP-160CfgBridgeSrcMacFilterEntry  ::=  SEQUENCE {
		BITSTORM-HP-160BridgeSrcMacFilterIndex  Integer32,
		BITSTORM-HP-160BridgeSrcMacFilterBpIndex  InterfaceIndex,
		BITSTORM-HP-160BridgeSrcMacFilterSrcMac  PhysAddress,
		BITSTORM-HP-160BridgeSrcMacFilterRowStatus  RowStatus
		}


	BITSTORM-HP-160BridgeSrcMacFilterIndex	OBJECT-TYPE	
		SYNTAX			Integer32  ( 1 .. 4095  ) 
		MAX-ACCESS		read-only
		STATUS			current
		DESCRIPTION		""
		::=  {  BITSTORM-HP-160CfgBridgeSrcMacFilterEntry  1  }


	BITSTORM-HP-160BridgeSrcMacFilterBpIndex	OBJECT-TYPE	
		SYNTAX			InterfaceIndex
		MAX-ACCESS		read-create
		STATUS			current
		DESCRIPTION		""
		::=  {  BITSTORM-HP-160CfgBridgeSrcMacFilterEntry  2  }


	BITSTORM-HP-160BridgeSrcMacFilterSrcMac	OBJECT-TYPE	
		SYNTAX			PhysAddress
		MAX-ACCESS		read-create
		STATUS			current
		DESCRIPTION		""
		::=  {  BITSTORM-HP-160CfgBridgeSrcMacFilterEntry  3  }


	BITSTORM-HP-160BridgeSrcMacFilterRowStatus	OBJECT-TYPE	
		SYNTAX			RowStatus
		MAX-ACCESS		read-create
		STATUS			current
		DESCRIPTION		""
		DEFVAL			{ createAndGo }
		::=  {  BITSTORM-HP-160CfgBridgeSrcMacFilterEntry  4  }
		
--
	BITSTORM-HP-160CfgBridgeL4SrcPortFilterTable	OBJECT-TYPE
		SYNTAX		SEQUENCE  OF  BITSTORM-HP-160CfgBridgeL4SrcPortFilterEntry
		MAX-ACCESS	not-accessible
		STATUS		current
		DESCRIPTION	"The L4 Src filter configuration table."
		::=  { BITSTORM-HP-160CfgFilterGroup  4 }

	BITSTORM-HP-160CfgBridgeL4SrcPortFilterEntry	OBJECT-TYPE
		SYNTAX		BITSTORM-HP-160CfgBridgeL4SrcPortFilterEntry
		MAX-ACCESS	not-accessible
		STATUS		current
		DESCRIPTION	"An Entry in the BITSTORM-HP-160CfgBridgeL4SrcPortFilterTable"
		INDEX		{  BITSTORM-HP-160CfgBridgeL4SrcPortFilterIndex  }
		::=  { BITSTORM-HP-160CfgBridgeL4SrcPortFilterTable 1 }

	BITSTORM-HP-160CfgBridgeL4SrcPortFilterEntry  ::=  SEQUENCE {
		BITSTORM-HP-160CfgBridgeL4SrcPortFilterIndex  Integer32,
		BITSTORM-HP-160CfgBridgeL4SrcPortFilterInputBridgePort  InterfaceIndex,
		BITSTORM-HP-160CfgBridgeL4SrcPortFilterDestinationPort  Integer32,
		BITSTORM-HP-160CfgBridgeL4SrcPortFilterRowStatus  RowStatus
		}


	BITSTORM-HP-160CfgBridgeL4SrcPortFilterIndex	OBJECT-TYPE	
		SYNTAX			Integer32
		MAX-ACCESS		read-only
		STATUS			current
		DESCRIPTION		""
		::=  {  BITSTORM-HP-160CfgBridgeL4SrcPortFilterEntry  1  }


	BITSTORM-HP-160CfgBridgeL4SrcPortFilterInputBridgePort	OBJECT-TYPE	
		SYNTAX			InterfaceIndex
		MAX-ACCESS		read-create
		STATUS			current
		DESCRIPTION		""
		::=  {  BITSTORM-HP-160CfgBridgeL4SrcPortFilterEntry  2  }


	BITSTORM-HP-160CfgBridgeL4SrcPortFilterDestinationPort	OBJECT-TYPE	
		SYNTAX			Integer32
		MAX-ACCESS		read-create
		STATUS			current
		DESCRIPTION		""
		::=  {  BITSTORM-HP-160CfgBridgeL4SrcPortFilterEntry  3  }


	BITSTORM-HP-160CfgBridgeL4SrcPortFilterRowStatus	OBJECT-TYPE	
		SYNTAX			RowStatus
		MAX-ACCESS		read-create
		STATUS			current
		DESCRIPTION		""
		::=  {  BITSTORM-HP-160CfgBridgeL4SrcPortFilterEntry  4  }
--		

--	BITSTORM-HP-160CfgBridgePrioTagFilterTable	OBJECT-TYPE
--		SYNTAX		SEQUENCE  OF  BITSTORM-HP-160CfgBridgePrioTagFilterEntry
--		MAX-ACCESS	not-accessible
--		STATUS		current
--		DESCRIPTION	""
--		::=  { BITSTORM-HP-160CfgFilterGroup  4 }

--	BITSTORM-HP-160CfgBridgePrioTagFilterEntry	OBJECT-TYPE
--		SYNTAX		BITSTORM-HP-160CfgBridgePrioTagFilterEntry
--		MAX-ACCESS	not-accessible
--		STATUS		current
--		DESCRIPTION	""
--		INDEX		{  BITSTORM-HP-160BridgePrioTagFilterIndex  }
--		::=  { BITSTORM-HP-160CfgBridgePrioTagFilterTable 1 }

--	BITSTORM-HP-160CfgBridgePrioTagFilterEntry  ::=  SEQUENCE {
--		BITSTORM-HP-160BridgePrioTagFilterIndex  Integer32,
--		BITSTORM-HP-160BridgePrioTagInputBridgePort  InterfaceIndex,
--		BITSTORM-HP-160BridgePrioTagOutgoingVlanPriority  Integer32,
--		BITSTORM-HP-160BridgePrioTagIncomingVlanPriority  Integer32,
--		BITSTORM-HP-160BridgePrioTagFilterRowStatus  RowStatus
--		}


--	BITSTORM-HP-160BridgePrioTagFilterIndex	OBJECT-TYPE
--		SYNTAX			Integer32  ( 1 .. 4095  )
--		MAX-ACCESS		read-only
--		STATUS			current
--		DESCRIPTION		""
--		::=  {  BITSTORM-HP-160CfgBridgePrioTagFilterEntry  1  }


--	BITSTORM-HP-160BridgePrioTagInputBridgePort	OBJECT-TYPE
--		SYNTAX			InterfaceIndex
--		MAX-ACCESS		read-create
--		STATUS			current
--		DESCRIPTION		""
--		::=  {  BITSTORM-HP-160CfgBridgePrioTagFilterEntry  2  }


--	BITSTORM-HP-160BridgePrioTagOutgoingVlanPriority	OBJECT-TYPE
--		SYNTAX			Integer32  ( 0 .. 7  )
--		MAX-ACCESS		read-create
--		STATUS			current
--		DESCRIPTION		""
--		DEFVAL			{ 0 }
--		::=  {  BITSTORM-HP-160CfgBridgePrioTagFilterEntry  3  }


--	BITSTORM-HP-160BridgePrioTagIncomingVlanPriority	OBJECT-TYPE
--		SYNTAX			Integer32  ( 0 .. 7  )
--		MAX-ACCESS		read-create
--		STATUS			current
--		DESCRIPTION		""
--		DEFVAL			{ 0 }
--		::=  {  BITSTORM-HP-160CfgBridgePrioTagFilterEntry  4  }


--	BITSTORM-HP-160BridgePrioTagFilterRowStatus	OBJECT-TYPE
--		SYNTAX			RowStatus
--		MAX-ACCESS		read-create
--		STATUS			current
--		DESCRIPTION		""
--		DEFVAL			{ createAndGo }
--		::=  {  BITSTORM-HP-160CfgBridgePrioTagFilterEntry  5  }

	BITSTORM-HP-160CfgBridgeSrcIpFilterTable	OBJECT-TYPE
		SYNTAX		SEQUENCE  OF  BITSTORM-HP-160CfgBridgeSrcIpFilterEntry
		MAX-ACCESS	not-accessible
		STATUS		current
		DESCRIPTION	""
		::=  { BITSTORM-HP-160CfgFilterGroup  5 }

	BITSTORM-HP-160CfgBridgeSrcIpFilterEntry	OBJECT-TYPE
		SYNTAX		BITSTORM-HP-160CfgBridgeSrcIpFilterEntry
		MAX-ACCESS	not-accessible
		STATUS		current
		DESCRIPTION	""
		INDEX		{  BITSTORM-HP-160BridgeSrcIpFilterIndex  }
		::=  { BITSTORM-HP-160CfgBridgeSrcIpFilterTable 1 }

	BITSTORM-HP-160CfgBridgeSrcIpFilterEntry  ::=  SEQUENCE {
		BITSTORM-HP-160BridgeSrcIpFilterIndex  Integer32,
		BITSTORM-HP-160BridgeSrcIpFilterBpIndex  InterfaceIndex,
		BITSTORM-HP-160BridgeSrcIpFilterSrcIpStart  IpAddress,
		BITSTORM-HP-160BridgeSrcIpFilterSrcIpEnd  IpAddress,
		BITSTORM-HP-160BridgeSrcIpFilterRowStatus  RowStatus
		}


	BITSTORM-HP-160BridgeSrcIpFilterIndex	OBJECT-TYPE	
		SYNTAX			Integer32  ( 1 .. 4095  ) 
		MAX-ACCESS		read-only
		STATUS			current
		DESCRIPTION		""
		::=  {  BITSTORM-HP-160CfgBridgeSrcIpFilterEntry  1  }


	BITSTORM-HP-160BridgeSrcIpFilterBpIndex	OBJECT-TYPE	
		SYNTAX			InterfaceIndex
		MAX-ACCESS		read-create
		STATUS			current
		DESCRIPTION		""
		::=  {  BITSTORM-HP-160CfgBridgeSrcIpFilterEntry  2  }


	BITSTORM-HP-160BridgeSrcIpFilterSrcIpStart	OBJECT-TYPE	
		SYNTAX			IpAddress
		MAX-ACCESS		read-create
		STATUS			current
		DESCRIPTION		""
		::=  {  BITSTORM-HP-160CfgBridgeSrcIpFilterEntry  3  }


	BITSTORM-HP-160BridgeSrcIpFilterSrcIpEnd	OBJECT-TYPE	
		SYNTAX			IpAddress
		MAX-ACCESS		read-create
		STATUS			current
		DESCRIPTION		""
		::=  {  BITSTORM-HP-160CfgBridgeSrcIpFilterEntry  4  }


	BITSTORM-HP-160BridgeSrcIpFilterRowStatus	OBJECT-TYPE	
		SYNTAX			RowStatus
		MAX-ACCESS		read-create
		STATUS			current
		DESCRIPTION		""
		DEFVAL			{ createAndGo }
		::=  {  BITSTORM-HP-160CfgBridgeSrcIpFilterEntry  5  }

	BITSTORM-HP-160CfgBridgeDstIpFilterTable	OBJECT-TYPE
		SYNTAX		SEQUENCE  OF  BITSTORM-HP-160CfgBridgeDstIpFilterEntry
		MAX-ACCESS	not-accessible
		STATUS		current
		DESCRIPTION	""
		::=  { BITSTORM-HP-160CfgFilterGroup  6 }   

	BITSTORM-HP-160CfgBridgeDstIpFilterEntry	OBJECT-TYPE
		SYNTAX		BITSTORM-HP-160CfgBridgeDstIpFilterEntry
		MAX-ACCESS	not-accessible
		STATUS		current
		DESCRIPTION	""
		INDEX		{  BITSTORM-HP-160BridgeDstIpFilterIndex  }
		::=  { BITSTORM-HP-160CfgBridgeDstIpFilterTable 1 }

	BITSTORM-HP-160CfgBridgeDstIpFilterEntry  ::=  SEQUENCE {
		BITSTORM-HP-160BridgeDstIpFilterIndex  Integer32,
		BITSTORM-HP-160BridgeDstIpFilterBpIndex  InterfaceIndex,
		BITSTORM-HP-160BridgeDstIpFilterSrcIpStart  IpAddress,
		BITSTORM-HP-160BridgeDstIpFilterSrcIpEnd  IpAddress,
		BITSTORM-HP-160BridgeDstIpFilterRowStatus  RowStatus
		}


	BITSTORM-HP-160BridgeDstIpFilterIndex	OBJECT-TYPE
		SYNTAX			Integer32  ( 1 .. 4095  )
		MAX-ACCESS		read-only
		STATUS			current
		DESCRIPTION		""
		::=  {  BITSTORM-HP-160CfgBridgeDstIpFilterEntry  1  }


	BITSTORM-HP-160BridgeDstIpFilterBpIndex	OBJECT-TYPE
		SYNTAX			InterfaceIndex
		MAX-ACCESS		read-create
		STATUS			current
		DESCRIPTION		""
		::=  {  BITSTORM-HP-160CfgBridgeDstIpFilterEntry  2  }


	BITSTORM-HP-160BridgeDstIpFilterSrcIpStart	OBJECT-TYPE
		SYNTAX			IpAddress
		MAX-ACCESS		read-create
		STATUS			current
		DESCRIPTION		""
		::=  {  BITSTORM-HP-160CfgBridgeDstIpFilterEntry  3  }


	BITSTORM-HP-160BridgeDstIpFilterSrcIpEnd	OBJECT-TYPE
		SYNTAX			IpAddress
		MAX-ACCESS		read-create
		STATUS			current
		DESCRIPTION		""
		::=  {  BITSTORM-HP-160CfgBridgeDstIpFilterEntry  4  }


	BITSTORM-HP-160BridgeDstIpFilterRowStatus	OBJECT-TYPE
		SYNTAX			RowStatus
		MAX-ACCESS		read-create
		STATUS			current
		DESCRIPTION		""
		DEFVAL			{ createAndGo }
		::=  {  BITSTORM-HP-160CfgBridgeDstIpFilterEntry  5  }








	BITSTORM-HP-160CfgBridgeNetBiosFilterTable	OBJECT-TYPE
		SYNTAX		SEQUENCE  OF  BITSTORM-HP-160CfgBridgeNetBiosFilterEntry
		MAX-ACCESS	not-accessible
		STATUS		current
		DESCRIPTION	""
		::=  { BITSTORM-HP-160CfgFilterGroup  7 }

	BITSTORM-HP-160CfgBridgeNetBiosFilterEntry	OBJECT-TYPE
		SYNTAX		BITSTORM-HP-160CfgBridgeNetBiosFilterEntry
		MAX-ACCESS	not-accessible
		STATUS		current
		DESCRIPTION	"An Entry in the BITSTORM-HP-160CfgBridgeNetBiosFilterTable"
		INDEX		{  BITSTORM-HP-160CfgBridgeNetBiosFilterInputBridgePort  }
		::=  { BITSTORM-HP-160CfgBridgeNetBiosFilterTable 1 }

	BITSTORM-HP-160CfgBridgeNetBiosFilterEntry  ::=  SEQUENCE {
		BITSTORM-HP-160CfgBridgeNetBiosFilterInputBridgePort  InterfaceIndex,
		BITSTORM-HP-160CfgBridgeNetBiosFilterStatus  INTEGER,
		BITSTORM-HP-160CfgBridgeNetBiosFilterRowStatus  RowStatus
		}


	BITSTORM-HP-160CfgBridgeNetBiosFilterInputBridgePort	OBJECT-TYPE
		SYNTAX			InterfaceIndex
		MAX-ACCESS		read-only
		STATUS			current
		DESCRIPTION		""
		::=  {  BITSTORM-HP-160CfgBridgeNetBiosFilterEntry  1  }


	BITSTORM-HP-160CfgBridgeNetBiosFilterStatus	OBJECT-TYPE
		SYNTAX			INTEGER  { enable ( 1 ) , disable ( 0 ) }
		MAX-ACCESS		read-create
		STATUS			current
		DESCRIPTION		""
		::=  {  BITSTORM-HP-160CfgBridgeNetBiosFilterEntry  2  }


	BITSTORM-HP-160CfgBridgeNetBiosFilterRowStatus	OBJECT-TYPE
		SYNTAX			RowStatus
		MAX-ACCESS		read-create
		STATUS			current
		DESCRIPTION		""
		::=  {  BITSTORM-HP-160CfgBridgeNetBiosFilterEntry  3  }

                                                                    

	BITSTORM-HP-160CfgBridgeArpBcastFilterTable	OBJECT-TYPE
		SYNTAX		SEQUENCE  OF  BITSTORM-HP-160CfgBridgeArpBcastFilterEntry
		MAX-ACCESS	not-accessible
		STATUS		current
		DESCRIPTION	""
		::=  { BITSTORM-HP-160CfgFilterGroup  8 }

	BITSTORM-HP-160CfgBridgeArpBcastFilterEntry	OBJECT-TYPE
		SYNTAX		BITSTORM-HP-160CfgBridgeArpBcastFilterEntry
		MAX-ACCESS	not-accessible
		STATUS		current
		DESCRIPTION	"An Entry in the BITSTORM-HP-160CfgBridgeArpBcastFilterTable"
		INDEX		{  BITSTORM-HP-160CfgBridgeArpBcastFilterInputBridgePort  }
		::=  { BITSTORM-HP-160CfgBridgeArpBcastFilterTable 1 }

	BITSTORM-HP-160CfgBridgeArpBcastFilterEntry  ::=  SEQUENCE {
		BITSTORM-HP-160CfgBridgeArpBcastFilterInputBridgePort  InterfaceIndex,
		BITSTORM-HP-160CfgBridgeArpBcastFilterStatus  INTEGER,
		BITSTORM-HP-160CfgBridgeArpBcastFilterRowStatus  RowStatus
		}


	BITSTORM-HP-160CfgBridgeArpBcastFilterInputBridgePort	OBJECT-TYPE
		SYNTAX			InterfaceIndex
		MAX-ACCESS		read-only
		STATUS			current
		DESCRIPTION		""
		::=  {  BITSTORM-HP-160CfgBridgeArpBcastFilterEntry  1  }


	BITSTORM-HP-160CfgBridgeArpBcastFilterStatus	OBJECT-TYPE
		SYNTAX			INTEGER  { enable ( 1 ) , disable ( 0 ) }
		MAX-ACCESS		read-create
		STATUS			current
		DESCRIPTION		""
		::=  {  BITSTORM-HP-160CfgBridgeArpBcastFilterEntry  2  }


	BITSTORM-HP-160CfgBridgeArpBcastFilterRowStatus	OBJECT-TYPE
		SYNTAX			RowStatus
		MAX-ACCESS		read-create
		STATUS			current
		DESCRIPTION		""
		::=  {  BITSTORM-HP-160CfgBridgeArpBcastFilterEntry  3  }






  	BITSTORM-HP-160CfgBridgeAllowedIpFilterTable	OBJECT-TYPE
		SYNTAX		SEQUENCE  OF  BITSTORM-HP-160CfgBridgeAllowedIpFilterEntry
		MAX-ACCESS	not-accessible
		STATUS		current
		DESCRIPTION	""
		::=  { BITSTORM-HP-160CfgFilterGroup  9 }

	BITSTORM-HP-160CfgBridgeAllowedIpFilterEntry	OBJECT-TYPE
		SYNTAX		BITSTORM-HP-160CfgBridgeAllowedIpFilterEntry
		MAX-ACCESS	not-accessible
		STATUS		current
		DESCRIPTION	""
		INDEX		{  BITSTORM-HP-160BridgeAllowedIpFilterIndex  }
		::=  { BITSTORM-HP-160CfgBridgeAllowedIpFilterTable 1 }
		

	BITSTORM-HP-160CfgBridgeAllowedIpFilterEntry  ::=  SEQUENCE {
		BITSTORM-HP-160BridgeAllowedIpFilterIndex  Integer32,
		BITSTORM-HP-160BridgeAllowedIpFilterBpIndex  InterfaceIndex,
		BITSTORM-HP-160BridgeAllowedIpFilterIsDynamic  INTEGER,
		BITSTORM-HP-160BridgeAllowedIpFilterSrcIp  IpAddress,
		BITSTORM-HP-160BridgeAllowedIpFilterRowStatus  RowStatus
		}


	BITSTORM-HP-160BridgeAllowedIpFilterIndex	OBJECT-TYPE	
		SYNTAX			Integer32  ( 1 .. 1920  )
		MAX-ACCESS		read-only
		STATUS			current
		DESCRIPTION		""
		::=  {  BITSTORM-HP-160CfgBridgeAllowedIpFilterEntry  1  }


	BITSTORM-HP-160BridgeAllowedIpFilterBpIndex	OBJECT-TYPE	
		SYNTAX			InterfaceIndex
		MAX-ACCESS		read-create
		STATUS			current
		DESCRIPTION		""
		::=  {  BITSTORM-HP-160CfgBridgeAllowedIpFilterEntry  2  }


	BITSTORM-HP-160BridgeAllowedIpFilterIsDynamic	OBJECT-TYPE
		SYNTAX			INTEGER  { manual ( 0 ) , auto-learn ( 1 ) }
		MAX-ACCESS		read-create
		STATUS			current
		DESCRIPTION		""
		::=  {  BITSTORM-HP-160CfgBridgeAllowedIpFilterEntry  3  }


	BITSTORM-HP-160BridgeAllowedIpFilterSrcIp	OBJECT-TYPE	
		SYNTAX			IpAddress
		MAX-ACCESS		read-create
		STATUS			current
		DESCRIPTION		""
		::=  {  BITSTORM-HP-160CfgBridgeAllowedIpFilterEntry  4  }


	BITSTORM-HP-160BridgeAllowedIpFilterRowStatus	OBJECT-TYPE
		SYNTAX			RowStatus
		MAX-ACCESS		read-create
		STATUS			current
		DESCRIPTION		""
		DEFVAL			{ createAndGo }
		::=  {  BITSTORM-HP-160CfgBridgeAllowedIpFilterEntry  5  }



--
	BITSTORM-HP-160CfgBridgeDstMacFilterTable	OBJECT-TYPE
		SYNTAX		SEQUENCE  OF  BITSTORM-HP-160CfgBridgeDstMacFilterEntry
		MAX-ACCESS	not-accessible
		STATUS		current
		DESCRIPTION	""
		::=  { BITSTORM-HP-160CfgFilterGroup  10 }

	BITSTORM-HP-160CfgBridgeDstMacFilterEntry	OBJECT-TYPE
		SYNTAX		BITSTORM-HP-160CfgBridgeDstMacFilterEntry
		MAX-ACCESS	not-accessible
		STATUS		current
		DESCRIPTION	""
		INDEX		{  BITSTORM-HP-160BridgeDstMacFilterIndex  }
		::=  { BITSTORM-HP-160CfgBridgeDstMacFilterTable 1 }

	BITSTORM-HP-160CfgBridgeDstMacFilterEntry  ::=  SEQUENCE {
		BITSTORM-HP-160BridgeDstMacFilterIndex  Integer32,
		BITSTORM-HP-160BridgeDstMacFilterBpIndex  InterfaceIndex,
		BITSTORM-HP-160BridgeDstMacFilterDstMac  PhysAddress,
		BITSTORM-HP-160BridgeDstMacFilterRowStatus  RowStatus
		}


	BITSTORM-HP-160BridgeDstMacFilterIndex	OBJECT-TYPE	
		SYNTAX			Integer32  ( 1 .. 4095  ) 
		MAX-ACCESS		read-only
		STATUS			current
		DESCRIPTION		""
		::=  {  BITSTORM-HP-160CfgBridgeDstMacFilterEntry  1  }


	BITSTORM-HP-160BridgeDstMacFilterBpIndex	OBJECT-TYPE	
		SYNTAX			InterfaceIndex
		MAX-ACCESS		read-create
		STATUS			current
		DESCRIPTION		""
		::=  {  BITSTORM-HP-160CfgBridgeDstMacFilterEntry  2  }


	BITSTORM-HP-160BridgeDstMacFilterDstMac	OBJECT-TYPE
		SYNTAX			PhysAddress
		MAX-ACCESS		read-create
		STATUS			current
		DESCRIPTION		""
		::=  {  BITSTORM-HP-160CfgBridgeDstMacFilterEntry  3  }


	BITSTORM-HP-160BridgeDstMacFilterRowStatus	OBJECT-TYPE	
		SYNTAX			RowStatus
		MAX-ACCESS		read-create
		STATUS			current
		DESCRIPTION		""
		DEFVAL			{ createAndGo }
		::=  {  BITSTORM-HP-160CfgBridgeDstMacFilterEntry  4  }
--






	BITSTORM-HP-160CfgLACPMode	OBJECT-TYPE
		SYNTAX			INTEGER  { on ( 1 ) , off ( 0 ) }
		MAX-ACCESS		read-write
		STATUS			current
		DESCRIPTION		"System ID of LACP port."
		::=  {  BITSTORM-HP-160CfgLacpGroup  1  }

	BITSTORM-HP-160CfgIgmpMode	OBJECT-TYPE
		SYNTAX			INTEGER  { snoopingMode ( 1 ) , proxyMode ( 2 ) }
		MAX-ACCESS		read-write
		STATUS			current
		DESCRIPTION		""
		::=  {  BITSTORM-HP-160CfgIgmpGroup  1  }

	BITSTORM-HP-160CfgIgmpTimeoutQuery	OBJECT-TYPE
		SYNTAX			Integer32  ( 1 .. 500  )
		MAX-ACCESS		read-write
		STATUS			current
		DESCRIPTION		""
		::=  {  BITSTORM-HP-160CfgIgmpGroup  2  }

	BITSTORM-HP-160CfgIgmpTimeoutUri	OBJECT-TYPE
		SYNTAX			Integer32  ( 1 .. 500  )
		MAX-ACCESS		read-write
		STATUS			current
		DESCRIPTION		""
		::=  {  BITSTORM-HP-160CfgIgmpGroup  3  }

	BITSTORM-HP-160CfgIgmpTimeoutBc	OBJECT-TYPE	
		SYNTAX			Integer32  ( 1 .. 500  ) 
		MAX-ACCESS		read-write
		STATUS			current
		DESCRIPTION		""
		::=  {  BITSTORM-HP-160CfgIgmpGroup  4  }

	BITSTORM-HP-160CfgIgmpTimeoutMrt	OBJECT-TYPE	
		SYNTAX			Integer32  ( 1 .. 500  ) 
		MAX-ACCESS		read-write
		STATUS			current
		DESCRIPTION		""
		::=  {  BITSTORM-HP-160CfgIgmpGroup  5  }

	BITSTORM-HP-160CfgIgmpTimeoutLmqt	OBJECT-TYPE	
		SYNTAX			Integer32  ( 1 .. 500  ) 
		MAX-ACCESS		read-write
		STATUS			current
		DESCRIPTION		""
		::=  {  BITSTORM-HP-160CfgIgmpGroup  6  }

	BITSTORM-HP-160CfgIgmpTimeoutGmt	OBJECT-TYPE	
		SYNTAX			Integer32  ( 1 .. 500  ) 
		MAX-ACCESS		read-write
		STATUS			current
		DESCRIPTION		""
		::=  {  BITSTORM-HP-160CfgIgmpGroup  7  }

	BITSTORM-HP-160CfgIgmpVersion	OBJECT-TYPE	
		SYNTAX			INTEGER  { igmpv1 ( 1 ) , igmpv2 ( 2 ) , igmpv3 ( 3 ) } 
		MAX-ACCESS		read-write
		STATUS			current
		DESCRIPTION		""
		::=  {  BITSTORM-HP-160CfgIgmpGroup  8  }

	BITSTORM-HP-160CfgIgmpAclMode	OBJECT-TYPE
		SYNTAX			TruthValue  { true ( 1 ) , false ( 2 ) } 
		MAX-ACCESS		read-write
		STATUS			current
		DESCRIPTION		""
		::=  {  BITSTORM-HP-160CfgIgmpGroup  9  }

	BITSTORM-HP-160CfgIgmpLeaveMode	OBJECT-TYPE
		SYNTAX			INTEGER  { Normal ( 0 ) , Fast ( 1 ) }
		MAX-ACCESS		read-write
		STATUS			current
		DESCRIPTION		""
		::=  {  BITSTORM-HP-160CfgIgmpGroup  10  }

	BITSTORM-HP-160CfgIgmpGroupTable	OBJECT-TYPE
		SYNTAX		SEQUENCE  OF  BITSTORM-HP-160IgmpGroupEntry
		MAX-ACCESS	not-accessible
		STATUS		current
		DESCRIPTION	""
		::=  { BITSTORM-HP-160CfgIgmpGroup  13 }

	BITSTORM-HP-160CfgIgmpGroupEntry	OBJECT-TYPE
		SYNTAX		BITSTORM-HP-160IgmpGroupEntry
		MAX-ACCESS	not-accessible
		STATUS		current
		DESCRIPTION	""
		INDEX		{  BITSTORM-HP-160CfgIgmpGroupIp, BITSTORM-HP-160CfgIgmpGroupVlan  }
		::=  { BITSTORM-HP-160CfgIgmpGroupTable 1 }

	BITSTORM-HP-160IgmpGroupEntry  ::=  SEQUENCE {
		BITSTORM-HP-160CfgIgmpGroupIp  IpAddress,
		BITSTORM-HP-160CfgIgmpGroupVlan  Integer32,
		BITSTORM-HP-160CfgIgmpGroupAddActions  Integer32,
		BITSTORM-HP-160CfgIgmpGroupNumOfEntries  Integer32,
		BITSTORM-HP-160CfgIgmpGroupInclude  Integer32,
		BITSTORM-HP-160CfgIgmpGroupBitmap  OCTET STRING
		}


	BITSTORM-HP-160CfgIgmpGroupIp	OBJECT-TYPE	
		SYNTAX			IpAddress
		MAX-ACCESS		read-only
		STATUS			current
		DESCRIPTION		""
		::=  {  BITSTORM-HP-160CfgIgmpGroupEntry  1  }


	BITSTORM-HP-160CfgIgmpGroupVlan	OBJECT-TYPE
		SYNTAX			Integer32  ( 1 .. 4094  )   --960803
		MAX-ACCESS		read-only
		STATUS			current
		DESCRIPTION		""
		::=  {  BITSTORM-HP-160CfgIgmpGroupEntry  2  }


	BITSTORM-HP-160CfgIgmpGroupAddActions	OBJECT-TYPE	
		SYNTAX			Integer32
		MAX-ACCESS		read-only
		STATUS			current
		DESCRIPTION		""
		::=  {  BITSTORM-HP-160CfgIgmpGroupEntry  3  }


	BITSTORM-HP-160CfgIgmpGroupNumOfEntries	OBJECT-TYPE	
		SYNTAX			Integer32
		MAX-ACCESS		read-only
		STATUS			current
		DESCRIPTION		""
		::=  {  BITSTORM-HP-160CfgIgmpGroupEntry  4  }


	BITSTORM-HP-160CfgIgmpGroupInclude	OBJECT-TYPE	
		SYNTAX			Integer32
		MAX-ACCESS		read-only
		STATUS			current
		DESCRIPTION		""
		::=  {  BITSTORM-HP-160CfgIgmpGroupEntry  5  }


	BITSTORM-HP-160CfgIgmpGroupBitmap	OBJECT-TYPE	
		SYNTAX			OCTET STRING  ( SIZE ( 0 .. 513  ) )
		MAX-ACCESS		read-only
		STATUS			current
		DESCRIPTION		""
		::=  {  BITSTORM-HP-160CfgIgmpGroupEntry  6  }

	BITSTORM-HP-160CfgIgmpSource	OBJECT IDENTIFIER
		::=  {  BITSTORM-HP-160CfgIgmpGroup  14  }

	BITSTORM-HP-160CfgIgmpRouterPortTable	OBJECT-TYPE
		SYNTAX		SEQUENCE  OF  BITSTORM-HP-160CfgIgmpRouterPortEntry
		MAX-ACCESS	not-accessible
		STATUS		current
		DESCRIPTION	""
		::=  { BITSTORM-HP-160CfgIgmpGroup  15 }

	BITSTORM-HP-160CfgIgmpRouterPortEntry	OBJECT-TYPE
		SYNTAX		BITSTORM-HP-160CfgIgmpRouterPortEntry
		MAX-ACCESS	not-accessible
		STATUS		current
		DESCRIPTION	""
		INDEX		{  BITSTORM-HP-160CfgIgmpRouterPortVlanId, BITSTORM-HP-160CfgIgmpRouterPortBportIndex  }
		::=  { BITSTORM-HP-160CfgIgmpRouterPortTable 1 }

	BITSTORM-HP-160CfgIgmpRouterPortEntry  ::=  SEQUENCE {
		BITSTORM-HP-160CfgIgmpRouterPortVlanId  Integer32,
		BITSTORM-HP-160CfgIgmpRouterPortBportIndex  InterfaceIndex,
		BITSTORM-HP-160CfgIgmpRouterPortBitmap  InterfaceIndex,
		BITSTORM-HP-160CfgIgmpRouterPortRouterIp  OCTET STRING,
		BITSTORM-HP-160CfgIgmpRouterPortRouterReportIp  OCTET STRING,
		BITSTORM-HP-160CfgIgmpRouterPortRowStatus  RowStatus
		}

	BITSTORM-HP-160CfgIgmpRouterPortVlanId	OBJECT-TYPE
		SYNTAX			Integer32  ( 1 .. 4094  )   --960803
		MAX-ACCESS		read-only
		STATUS			current
		DESCRIPTION		""
		::=  {  BITSTORM-HP-160CfgIgmpRouterPortEntry  1  }


	BITSTORM-HP-160CfgIgmpRouterPortBportIndex	OBJECT-TYPE	
		SYNTAX			InterfaceIndex
		MAX-ACCESS		read-only
		STATUS			current
		DESCRIPTION		""
		::=  {  BITSTORM-HP-160CfgIgmpRouterPortEntry  2  }


	BITSTORM-HP-160CfgIgmpRouterPortBitmap	OBJECT-TYPE	
		SYNTAX			InterfaceIndex
		MAX-ACCESS		read-create
		STATUS			current
		DESCRIPTION		""
		::=  {  BITSTORM-HP-160CfgIgmpRouterPortEntry  3  }


	BITSTORM-HP-160CfgIgmpRouterPortRouterIp	OBJECT-TYPE
		SYNTAX			OCTET STRING  ( SIZE ( 0 .. 15  ) )
		MAX-ACCESS		read-create
		STATUS			current
		DESCRIPTION		""
		::=  {  BITSTORM-HP-160CfgIgmpRouterPortEntry  4  }

	BITSTORM-HP-160CfgIgmpRouterPortRouterReportIp	OBJECT-TYPE
		SYNTAX			OCTET STRING  ( SIZE ( 0 .. 15  ) )
		MAX-ACCESS		read-create
		STATUS			current
		DESCRIPTION		""
		::=  {  BITSTORM-HP-160CfgIgmpRouterPortEntry  5  }

	BITSTORM-HP-160CfgIgmpRouterPortRowStatus	OBJECT-TYPE
		SYNTAX			RowStatus
		MAX-ACCESS		read-create
		STATUS			current
		DESCRIPTION		""
		DEFVAL			{ createAndGo }
		::=  {  BITSTORM-HP-160CfgIgmpRouterPortEntry  6  }

	BITSTORM-HP-160CfgIgmpAclProfileTable	OBJECT-TYPE
		SYNTAX		SEQUENCE  OF  BITSTORM-HP-160CfgIgmpAclProfileEntry
		MAX-ACCESS	not-accessible
		STATUS		current
		DESCRIPTION	""
		::=  { BITSTORM-HP-160CfgIgmpGroup  16 }

	BITSTORM-HP-160CfgIgmpAclProfileEntry	OBJECT-TYPE
		SYNTAX		BITSTORM-HP-160CfgIgmpAclProfileEntry
		MAX-ACCESS	not-accessible
		STATUS		current
		DESCRIPTION	""
		INDEX		{  BITSTORM-HP-160CfgIgmpAclProfileIndex  }
		::=  { BITSTORM-HP-160CfgIgmpAclProfileTable 1 }

	BITSTORM-HP-160CfgIgmpAclProfileEntry  ::=  SEQUENCE {
		BITSTORM-HP-160CfgIgmpAclProfileIndex  Integer32,
		BITSTORM-HP-160CfgIgmpAclProfileChMap  OCTET STRING,
		BITSTORM-HP-160CfgIgmpAclProfileVlanMap  OCTET STRING,
		BITSTORM-HP-160CfgIgmpAclProfileVlanEgressMap  OCTET STRING,   --20070329
--		BITSTORM-HP-160CfgIgmpAclProfileBank  Integer32,
		BITSTORM-HP-160CfgIgmpAclProfileMcCount  Integer32,
		BITSTORM-HP-160CfgIgmpAclProfileRowStatus  RowStatus,
		BITSTORM-HP-160CfgIgmpAclProfileUsedCount  INTEGER,
		BITSTORM-HP-160CfgIgmpAclProfileMsgCount  Integer32
		}

	BITSTORM-HP-160CfgIgmpAclProfileIndex	OBJECT-TYPE	
		SYNTAX			Integer32  (1..24)
		MAX-ACCESS		not-accessible
		STATUS			current
		DESCRIPTION		""
		::=  {  BITSTORM-HP-160CfgIgmpAclProfileEntry  1  }


	BITSTORM-HP-160CfgIgmpAclProfileChMap	OBJECT-TYPE	
		SYNTAX			OCTET STRING
		MAX-ACCESS		read-create
		STATUS			current
		DESCRIPTION		"IP address
		total 1024 bytes.
		byte 1~256 for bank1 (64 ip address)
		byte 257~512 for bank2 (64 ip address)
		byte 513~768 for bank3 (64 ip address)
		byte 769~1024 for bank4 (64 ip address)
		"
		::=  {  BITSTORM-HP-160CfgIgmpAclProfileEntry  2  }


	BITSTORM-HP-160CfgIgmpAclProfileVlanMap	OBJECT-TYPE
		SYNTAX			OCTET STRING
		MAX-ACCESS		read-create
		STATUS			current
		DESCRIPTION		"User (packet) VLAN id
		total 512 bytes.
		byte 1~128 for bank1 (64 vlan id)
		byte 129~256 for bank2 (64 vlan id)
		byte 257~384 for bank3 (64 vlan id)
		byte 385~512 for bank4 (64 vlan id)
		"
		::=  {  BITSTORM-HP-160CfgIgmpAclProfileEntry  3  }


	BITSTORM-HP-160CfgIgmpAclProfileVlanEgressMap	OBJECT-TYPE
		SYNTAX			OCTET STRING
		MAX-ACCESS		read-create
		STATUS			current
		DESCRIPTION		"VlanEgressMap
		total 256 bytes.
		1: tag, 2 : untag
		"
		::=  {  BITSTORM-HP-160CfgIgmpAclProfileEntry  4  }

--	BITSTORM-HP-160CfgIgmpAclProfileBank	OBJECT-TYPE
--		SYNTAX			Integer32  ( 0 .. 3  )
--		MAX-ACCESS		read-create
--		STATUS			current
--		DESCRIPTION		"0..3, 0 for ChMap 1~64, 1 for ChMap 65~128 ..."
--		::=  {  BITSTORM-HP-160CfgIgmpAclProfileEntry  4  }

	BITSTORM-HP-160CfgIgmpAclProfileMcCount	OBJECT-TYPE
		SYNTAX			Integer32  ( 0 .. 10  )
		MAX-ACCESS		read-create
		STATUS			current
		DESCRIPTION		"Max Channel Count"
		::=  {  BITSTORM-HP-160CfgIgmpAclProfileEntry  5  }

	BITSTORM-HP-160CfgIgmpAclProfileRowStatus	OBJECT-TYPE
		SYNTAX			RowStatus  { active ( 1 ) , notInService ( 2 ) , notReady ( 3 ) , createAndGo ( 4 ) , createAndWait ( 5 ) , destroy ( 6 ) }
		MAX-ACCESS		read-create
		STATUS			current
		DESCRIPTION		""
		::=  {  BITSTORM-HP-160CfgIgmpAclProfileEntry  6  }

	BITSTORM-HP-160CfgIgmpAclProfileUsedCount	OBJECT-TYPE
		SYNTAX			INTEGER
		MAX-ACCESS		read-only
		STATUS			current
		DESCRIPTION		"The value is not zero means the profile is in used,then the profile can't be delete."
		::=  {  BITSTORM-HP-160CfgIgmpAclProfileEntry  7  }

	BITSTORM-HP-160CfgIgmpAclProfileMsgCount	OBJECT-TYPE
		SYNTAX			Integer32  ( 0 .. 65535  )
		MAX-ACCESS		read-create
		STATUS			current
		DESCRIPTION		"Max IGMP Message Count. Default value is 128."
		::=  {  BITSTORM-HP-160CfgIgmpAclProfileEntry  8  }
		
	BITSTORM-HP-160CfgIgmpBridgePortBindTable	OBJECT-TYPE
		SYNTAX		SEQUENCE  OF  BITSTORM-HP-160CfgIgmpBridgePortBindEntry
		MAX-ACCESS	not-accessible
		STATUS		current
		DESCRIPTION	""
		::=  { BITSTORM-HP-160CfgIgmpGroup  17 }

	BITSTORM-HP-160CfgIgmpBridgePortBindEntry	OBJECT-TYPE
		SYNTAX		BITSTORM-HP-160CfgIgmpBridgePortBindEntry
		MAX-ACCESS	not-accessible
		STATUS		current
		DESCRIPTION	""
		INDEX		{  BITSTORM-HP-160CfgIgmpBindBpId  }
		::=  { BITSTORM-HP-160CfgIgmpBridgePortBindTable 1 }

	BITSTORM-HP-160CfgIgmpBridgePortBindEntry  ::=  SEQUENCE {
		BITSTORM-HP-160CfgIgmpBindBpId  Integer32,
		BITSTORM-HP-160CfgIgmpBindProfileId  Integer32
--		BITSTORM-HP-160CfgIgmpAclProfileBank-  Integer32
		}


	BITSTORM-HP-160CfgIgmpBindBpId	OBJECT-TYPE	
		SYNTAX			Integer32
		MAX-ACCESS		not-accessible
		STATUS			current
		DESCRIPTION		""
		::=  {  BITSTORM-HP-160CfgIgmpBridgePortBindEntry  1  }


	BITSTORM-HP-160CfgIgmpBindProfileId	OBJECT-TYPE
		SYNTAX			Integer32
		MAX-ACCESS		read-write
		STATUS			current
		DESCRIPTION		""
		::=  {  BITSTORM-HP-160CfgIgmpBridgePortBindEntry  2  }


--	BITSTORM-HP-160CfgIgmpAclProfileBank-	OBJECT-TYPE
--		SYNTAX			Integer32 (0..3)
--		MAX-ACCESS		read-write
--		STATUS			current
--		DESCRIPTION		""
--		::=  {  BITSTORM-HP-160CfgIgmpBridgePortBindEntry  3  }

	BITSTORM-HP-160CfgRstpForceVersion	OBJECT-TYPE	
		SYNTAX			INTEGER  { STP ( 0 ) , RSTP ( 2 ) } 
		MAX-ACCESS		read-write
		STATUS			current
		DESCRIPTION		""
		DEFVAL			{ RSTP }
		::=  {  BITSTORM-HP-160CfgRstpGroup  1  }

	BITSTORM-HP-160StpEnable	OBJECT-TYPE
		SYNTAX			INTEGER  { disabled ( 0 ) , enabled ( 1 ) }
		MAX-ACCESS		read-write
		STATUS			current
		DESCRIPTION		""
		DEFVAL			{ disabled }
		::=  {  BITSTORM-HP-160CfgRstpGroup  2  }

	BITSTORM-HP-160CfgRstpPortTable	OBJECT-TYPE
		SYNTAX		SEQUENCE  OF  BITSTORM-HP-160CfgRstpPortEntry
		MAX-ACCESS	not-accessible
		STATUS		current
		DESCRIPTION	""
		::=  { BITSTORM-HP-160CfgRstpGroup  3 }

	BITSTORM-HP-160CfgRstpPortEntry	OBJECT-TYPE
		SYNTAX		BITSTORM-HP-160CfgRstpPortEntry
		MAX-ACCESS	not-accessible
		STATUS		current
		DESCRIPTION	""
		INDEX		{  BITSTORM-HP-160CfgRstpPortIndex  }
		::=  { BITSTORM-HP-160CfgRstpPortTable 1 }

	BITSTORM-HP-160CfgRstpPortEntry  ::=  SEQUENCE {
		BITSTORM-HP-160CfgRstpPortIndex  Integer32,
		BITSTORM-HP-160CfgRstpPortAdminEdge  INTEGER,
		BITSTORM-HP-160CfgRstpPortAdminPoint2Point  INTEGER,
		BITSTORM-HP-160CfgRstpPortAdminNonSTP  INTEGER
		}


	BITSTORM-HP-160CfgRstpPortIndex	OBJECT-TYPE
		SYNTAX			Integer32
		MAX-ACCESS		read-only
		STATUS			current
		DESCRIPTION		""
		::=  {  BITSTORM-HP-160CfgRstpPortEntry  1  }


	BITSTORM-HP-160CfgRstpPortAdminEdge	OBJECT-TYPE
		SYNTAX			INTEGER  { false ( 0 ) , true ( 1 ) }
		MAX-ACCESS		read-write
		STATUS			current
		DESCRIPTION		""
		DEFVAL			{ false }
		::=  {  BITSTORM-HP-160CfgRstpPortEntry  2  }


	BITSTORM-HP-160CfgRstpPortAdminPoint2Point	OBJECT-TYPE
		SYNTAX			INTEGER  { true ( 0 ) , false ( 1 ) , auto ( 2 ) }
		MAX-ACCESS		read-write
		STATUS			current
		DESCRIPTION		""
		DEFVAL			{ false }
		::=  {  BITSTORM-HP-160CfgRstpPortEntry  3  }


	BITSTORM-HP-160CfgRstpPortAdminNonSTP	OBJECT-TYPE
		SYNTAX			INTEGER  { false ( 0 ) , true ( 1 ) }
		MAX-ACCESS		read-write
		STATUS			current
		DESCRIPTION		""
		DEFVAL			{ false }
		::=  {  BITSTORM-HP-160CfgRstpPortEntry  4  }

--
	BITSTORM-HP-160StpBridgeID	OBJECT-TYPE
		SYNTAX			OCTET STRING (SIZE (8))
		MAX-ACCESS		read-only
		STATUS			current
		DESCRIPTION		""
		::=  {  BITSTORM-HP-160CfgRstpGroup  4  }
--
	BITSTORM-HP-160CfgDhcpMode	OBJECT-TYPE
		SYNTAX			INTEGER  { transparent ( 0 ) , relay ( 1 ) , server ( 3 )}
		MAX-ACCESS		read-write
		STATUS			current
		DESCRIPTION		""
		::=  {  BITSTORM-HP-160CfgRelayGroup  1  }

	BITSTORM-HP-160CfgDhcpSubOptMode	OBJECT-TYPE
		SYNTAX			INTEGER  { circuitID ( 1 ) , remoteID ( 2 ) , both ( 3 ) }
		MAX-ACCESS		read-write
		STATUS			current
		DESCRIPTION		""
		::=  {  BITSTORM-HP-160CfgRelayGroup  2  }

	BITSTORM-HP-160CfgDhcpCircuitIdType	OBJECT-TYPE
		SYNTAX			INTEGER  { DEFAULT(0),
		                                   SCBV(1),
		                                   SCV(2),
		                                   SC(3),
		                                   CUSTOMER(4) }		
		MAX-ACCESS		read-write
		STATUS			current
		DESCRIPTION		"
		default               Set circuit default type
		scbv                  Set circuit scbv type
		scv                   Set circuit scv type
		sc                    Set circuit sc type
		customer              Set circuit customer type"
		::=  {  BITSTORM-HP-160CfgRelayGroup  3  }

--	BITSTORM-HP-160CfgDhcpRemoteIdType	OBJECT-TYPE	
--		SYNTAX			INTEGER  { default ( 0 ) , id ( 1 ) , descr ( 2 ) , phonenum ( 3 ) , customer ( 4 ) }
--		MAX-ACCESS		read-write
--		STATUS			current
--		DESCRIPTION		"
--		default            Set circuit default type
--		id                Set remote line id
--		descr                  Set remote line description
--		phonenum                    Set remote line phone number
--		customer       Set remote customer type"
--		::=  {  BITSTORM-HP-160CfgRelayGroup  4  }

	BITSTORM-HP-160CfgDhcpName	OBJECT-TYPE
		SYNTAX			OCTET STRING
		MAX-ACCESS		read-write
		STATUS			current
		DESCRIPTION		""
		::=  {  BITSTORM-HP-160CfgRelayGroup  4  }

--	BITSTORM-HP-160CfgPppoeVsaMode	OBJECT-TYPE
--		SYNTAX			INTEGER  { disable ( 0 ) , enable ( 1 )  }
--		MAX-ACCESS		read-write
--		STATUS			current
--		DESCRIPTION		""
--		::=  {  BITSTORM-HP-160CfgRelayGroup  5  }

	BITSTORM-HP-160CfgPppoeAcName	OBJECT-TYPE
		SYNTAX			OCTET STRING
		MAX-ACCESS		read-write
		STATUS			current
		DESCRIPTION		""
		::=  {  BITSTORM-HP-160CfgRelayGroup  5  }

	BITSTORM-HP-160CfgPppoeSrvName	OBJECT-TYPE	
		SYNTAX			OCTET STRING
		MAX-ACCESS		read-write
		STATUS			current
		DESCRIPTION		""
		::=  {  BITSTORM-HP-160CfgRelayGroup  6  }

	BITSTORM-HP-160CfgDhcpDslIdConfigTable	OBJECT-TYPE
		SYNTAX		SEQUENCE  OF  BITSTORM-HP-160CfgDhcpDslIdConfigEntry
		MAX-ACCESS	not-accessible
		STATUS		current
		DESCRIPTION	""
		::=  { BITSTORM-HP-160CfgRelayGroup  8 }

	BITSTORM-HP-160CfgDhcpDslIdConfigEntry	OBJECT-TYPE
		SYNTAX		BITSTORM-HP-160CfgDhcpDslIdConfigEntry
		MAX-ACCESS	not-accessible
		STATUS		current
		DESCRIPTION	""
		INDEX		{  BITSTORM-HP-160CfgDhcpDslIfIndex  }
		::=  { BITSTORM-HP-160CfgDhcpDslIdConfigTable 1 }

	BITSTORM-HP-160CfgDhcpDslIdConfigEntry  ::=  SEQUENCE {
		BITSTORM-HP-160CfgDhcpDslIfIndex  InterfaceIndex,
		BITSTORM-HP-160CfgDslCircuitID  OCTET STRING,
		BITSTORM-HP-160CfgDslRemoteID  OCTET STRING,
		BITSTORM-HP-160CfgDslIdTrusted  TruthValue,
		--BITSTORM-HP-160CfgDslIdForwardMode  INTEGER,
		BITSTORM-HP-160CfgDslpppoeMode  INTEGER
		}


	BITSTORM-HP-160CfgDhcpDslIfIndex	OBJECT-TYPE	
		SYNTAX			InterfaceIndex
		MAX-ACCESS		not-accessible
		STATUS			current
		DESCRIPTION		"IfIndex."
		::=  {  BITSTORM-HP-160CfgDhcpDslIdConfigEntry  1  }


	BITSTORM-HP-160CfgDslCircuitID	OBJECT-TYPE
		SYNTAX			OCTET STRING  ( SIZE ( 0 .. 63  ) ) 
		MAX-ACCESS		read-write
		STATUS			current
		DESCRIPTION		""
		::=  {  BITSTORM-HP-160CfgDhcpDslIdConfigEntry  2  }


	BITSTORM-HP-160CfgDslRemoteID	OBJECT-TYPE	
		SYNTAX			OCTET STRING  ( SIZE ( 0 .. 63  ) ) 
		MAX-ACCESS		read-write
		STATUS			current
		DESCRIPTION		""
		::=  {  BITSTORM-HP-160CfgDhcpDslIdConfigEntry  3  }


	BITSTORM-HP-160CfgDslIdTrusted	OBJECT-TYPE
		SYNTAX			TruthValue  { true ( 1 ) , false ( 2 ) } 
		MAX-ACCESS		read-write
		STATUS			current
		DESCRIPTION		""
		::=  {  BITSTORM-HP-160CfgDhcpDslIdConfigEntry  4  }


--	BITSTORM-HP-160CfgDslIdForwardMode	OBJECT-TYPE
--		SYNTAX			INTEGER  { default ( 0 ) , append ( 1 ) , replace ( 2 ) , forward ( 3 ) , discard ( 4 ) , chaddr ( 5 ) }
--		MAX-ACCESS		read-write
--		STATUS			current
--		DESCRIPTION		""
--		::=  {  BITSTORM-HP-160CfgDhcpDslIdConfigEntry  5  }
		
	BITSTORM-HP-160CfgDslpppoeMode	OBJECT-TYPE
		SYNTAX			INTEGER  { transparent ( 0 ) , relay ( 1 ) }
		MAX-ACCESS		read-write
		STATUS			current
		DESCRIPTION		""
		::=  {  BITSTORM-HP-160CfgDhcpDslIdConfigEntry  5  }
		


--
	BITSTORM-HP-160CfgDhcpServerProfileTable	OBJECT-TYPE
		SYNTAX		SEQUENCE  OF  BITSTORM-HP-160CfgDhcpServerProfileEntry
		MAX-ACCESS	not-accessible
		STATUS		current
		DESCRIPTION	""
		::=  { BITSTORM-HP-160CfgRelayGroup  9 }

	BITSTORM-HP-160CfgDhcpServerProfileEntry	OBJECT-TYPE
		SYNTAX		BITSTORM-HP-160CfgDhcpServerProfileEntry
		MAX-ACCESS	not-accessible
		STATUS		current
		DESCRIPTION	""
		INDEX		{  BITSTORM-HP-160CfgDhcpServerPrfIndex  }
		::=  { BITSTORM-HP-160CfgDhcpServerProfileTable 1 }
		

	BITSTORM-HP-160CfgDhcpServerProfileEntry  ::=  SEQUENCE {
		BITSTORM-HP-160CfgDhcpServerPrfIndex  Integer32,
		BITSTORM-HP-160CfgDhcpServerPrfStartIp  OCTET STRING,
		BITSTORM-HP-160CfgDhcpServerPrfEndIp  OCTET STRING,

		BITSTORM-HP-160CfgDhcpServerPrfIpMsk  OCTET STRING,
		BITSTORM-HP-160CfgDhcpServerPrfDefGatewayIp  OCTET STRING,
		BITSTORM-HP-160CfgDhcpServerPrfDNS1Ip  OCTET STRING,
		BITSTORM-HP-160CfgDhcpServerPrfDNS2Ip  OCTET STRING,
		BITSTORM-HP-160CfgDhcpServerPrfLeaseTime  Integer32,
		BITSTORM-HP-160CfgDhcpServerPrfUsedCount  INTEGER,
		BITSTORM-HP-160CfgDhcpServerPrfRowStatus  RowStatus
		}



	BITSTORM-HP-160CfgDhcpServerPrfIndex	OBJECT-TYPE
		SYNTAX			Integer32(1..24)
		MAX-ACCESS		not-accessible
		STATUS			current
		DESCRIPTION		""
		::=  {  BITSTORM-HP-160CfgDhcpServerProfileEntry  1  }


	BITSTORM-HP-160CfgDhcpServerPrfStartIp	OBJECT-TYPE
		SYNTAX			OCTET STRING  ( SIZE ( 0 .. 15  ) )
		MAX-ACCESS		read-create
		STATUS			current
		DESCRIPTION		""
		::=  {  BITSTORM-HP-160CfgDhcpServerProfileEntry  2  }

	BITSTORM-HP-160CfgDhcpServerPrfEndIp	OBJECT-TYPE
		SYNTAX			OCTET STRING  ( SIZE ( 0 .. 15  ) )
		MAX-ACCESS		read-create
		STATUS			current
		DESCRIPTION		""
		::=  {  BITSTORM-HP-160CfgDhcpServerProfileEntry  3  }
		
	BITSTORM-HP-160CfgDhcpServerPrfIpMsk	OBJECT-TYPE
		SYNTAX			OCTET STRING  ( SIZE ( 0 .. 15  ) )
		MAX-ACCESS		read-create
		STATUS			current
		DESCRIPTION		""
		::=  {  BITSTORM-HP-160CfgDhcpServerProfileEntry  4  }
	BITSTORM-HP-160CfgDhcpServerPrfDefGatewayIp	OBJECT-TYPE
		SYNTAX			OCTET STRING  ( SIZE ( 0 .. 15  ) )
		MAX-ACCESS		read-create
		STATUS			current
		DESCRIPTION		""
		::=  {  BITSTORM-HP-160CfgDhcpServerProfileEntry  5  }
		
	BITSTORM-HP-160CfgDhcpServerPrfDNS1Ip	OBJECT-TYPE
		SYNTAX			OCTET STRING  ( SIZE ( 0 .. 15  ) )
		MAX-ACCESS		read-create
		STATUS			current
		DESCRIPTION		""
		::=  {  BITSTORM-HP-160CfgDhcpServerProfileEntry  6  }
		
	BITSTORM-HP-160CfgDhcpServerPrfDNS2Ip	OBJECT-TYPE
		SYNTAX			OCTET STRING  ( SIZE ( 0 .. 15  ) )
		MAX-ACCESS		read-create
		STATUS			current
		DESCRIPTION		""
		::=  {  BITSTORM-HP-160CfgDhcpServerProfileEntry  7  }

	BITSTORM-HP-160CfgDhcpServerPrfLeaseTime	OBJECT-TYPE
		SYNTAX			Integer32 (300..86400)
		MAX-ACCESS		read-create
		STATUS			current
		DESCRIPTION		"seconds"
		::=  {  BITSTORM-HP-160CfgDhcpServerProfileEntry  8  }
	BITSTORM-HP-160CfgDhcpServerPrfUsedCount	OBJECT-TYPE
		SYNTAX			INTEGER
		MAX-ACCESS		read-only
		STATUS			current
		DESCRIPTION		""
		::=  {  BITSTORM-HP-160CfgDhcpServerProfileEntry  9  }
	BITSTORM-HP-160CfgDhcpServerPrfRowStatus	OBJECT-TYPE
		SYNTAX			RowStatus
		MAX-ACCESS		read-create
		STATUS			current
		DESCRIPTION		""
		::=  {  BITSTORM-HP-160CfgDhcpServerProfileEntry  10  }



--
--
	BITSTORM-HP-160CfgDhcpServerProfileBindTable	OBJECT-TYPE
		SYNTAX		SEQUENCE  OF  BITSTORM-HP-160CfgDhcpServerProfileBindEntry
		MAX-ACCESS	not-accessible
		STATUS		current
		DESCRIPTION	""
		::=  { BITSTORM-HP-160CfgRelayGroup  10 }

	BITSTORM-HP-160CfgDhcpServerProfileBindEntry	OBJECT-TYPE
		SYNTAX		BITSTORM-HP-160CfgDhcpServerProfileBindEntry
		MAX-ACCESS	not-accessible
		STATUS		current
		DESCRIPTION	""
		INDEX		{  BITSTORM-HP-160ServerBindBpIndex  }
		::=  { BITSTORM-HP-160CfgDhcpServerProfileBindTable 1 }

	BITSTORM-HP-160CfgDhcpServerProfileBindEntry  ::=  SEQUENCE {
		BITSTORM-HP-160ServerBindBpIndex  Integer32,
		BITSTORM-HP-160ServerBindPrfIndex  Integer32,
		}

	BITSTORM-HP-160ServerBindBpIndex	OBJECT-TYPE	
		SYNTAX			Integer32 (4..219)
		MAX-ACCESS		not-accessible
		STATUS			current
		DESCRIPTION		""
		::=  {  BITSTORM-HP-160CfgDhcpServerProfileBindEntry  1  }

	BITSTORM-HP-160ServerBindPrfIndex	OBJECT-TYPE
		SYNTAX			Integer32  (1..24)
		MAX-ACCESS		read-write
		STATUS			current
		DESCRIPTION		""
		::=  {  BITSTORM-HP-160CfgDhcpServerProfileBindEntry  2  }
--
		
--
	BITSTORM-HP-160CfgDhcpQueryClientTable	OBJECT-TYPE
		SYNTAX		SEQUENCE  OF  BITSTORM-HP-160CfgDhcpQueryClientEntry
		MAX-ACCESS	not-accessible
		STATUS		current
		DESCRIPTION	""
		::=  { BITSTORM-HP-160CfgRelayGroup  11 }

	BITSTORM-HP-160CfgDhcpQueryClientEntry	OBJECT-TYPE
		SYNTAX		BITSTORM-HP-160CfgDhcpQueryClientEntry
		MAX-ACCESS	not-accessible
		STATUS		current
		DESCRIPTION	""
		INDEX		{  BITSTORM-HP-160ServerQueryBpIndex,BITSTORM-HP-160ServerQueryClientIndex  }
		::=  { BITSTORM-HP-160CfgDhcpQueryClientTable 1 }

	BITSTORM-HP-160CfgDhcpQueryClientEntry  ::=  SEQUENCE {
		BITSTORM-HP-160ServerQueryBpIndex  Integer32,
		BITSTORM-HP-160ServerQueryClientIndex  Integer32,
		BITSTORM-HP-160ServerQueryIp  OCTET STRING,       
		BITSTORM-HP-160ServerQueryMac  PhysAddress,   
		BITSTORM-HP-160ServerQueryExpTime  OCTET STRING,
		BITSTORM-HP-160ServerQueryLeaseTime  Integer32
		}

	BITSTORM-HP-160ServerQueryBpIndex	OBJECT-TYPE
		SYNTAX			Integer32 (4..219)
		MAX-ACCESS		not-accessible
		STATUS			current
		DESCRIPTION		""
		::=  {  BITSTORM-HP-160CfgDhcpQueryClientEntry  1  }


	BITSTORM-HP-160ServerQueryClientIndex	OBJECT-TYPE
		SYNTAX			Integer32  (1..10)
		MAX-ACCESS		read-only
		STATUS			current
		DESCRIPTION		""
		::=  {  BITSTORM-HP-160CfgDhcpQueryClientEntry  2  }
	BITSTORM-HP-160ServerQueryIp	OBJECT-TYPE
		SYNTAX			OCTET STRING
		MAX-ACCESS		read-only
		STATUS			current
		DESCRIPTION		""
		::=  {  BITSTORM-HP-160CfgDhcpQueryClientEntry  3  }
	BITSTORM-HP-160ServerQueryMac	OBJECT-TYPE
		SYNTAX			PhysAddress
		MAX-ACCESS		read-only
		STATUS			current
		DESCRIPTION		""
		::=  {  BITSTORM-HP-160CfgDhcpQueryClientEntry  4  }
	BITSTORM-HP-160ServerQueryExpTime	OBJECT-TYPE
		SYNTAX			OCTET STRING
		MAX-ACCESS		read-only
		STATUS			current
		DESCRIPTION		""
		::=  {  BITSTORM-HP-160CfgDhcpQueryClientEntry  5  }
        BITSTORM-HP-160ServerQueryLeaseTime	OBJECT-TYPE
		SYNTAX			Integer32
		MAX-ACCESS		read-only
		STATUS			current
		DESCRIPTION		""
		::=  {  BITSTORM-HP-160CfgDhcpQueryClientEntry  6  }
--

--
	BITSTORM-HP-160CfgDhcpStaticIPTable	OBJECT-TYPE
		SYNTAX		SEQUENCE  OF  BITSTORM-HP-160CfgDhcpStaticIPEntry
		MAX-ACCESS	not-accessible
		STATUS		current
		DESCRIPTION	""
		::=  { BITSTORM-HP-160CfgRelayGroup  12 }

	BITSTORM-HP-160CfgDhcpStaticIPEntry	OBJECT-TYPE
		SYNTAX		BITSTORM-HP-160CfgDhcpStaticIPEntry
		MAX-ACCESS	not-accessible
		STATUS		current
		DESCRIPTION	""
		INDEX		{  BITSTORM-HP-160StaticIndex  }
		::=  { BITSTORM-HP-160CfgDhcpStaticIPTable 1 }
		
		
	BITSTORM-HP-160CfgDhcpStaticIPEntry  ::=  SEQUENCE {
		BITSTORM-HP-160StaticIndex  Integer32,
		BITSTORM-HP-160StaticIPBpIndex  Integer32,
		BITSTORM-HP-160StaticIp  OCTET STRING,
		BITSTORM-HP-160StaticMac  PhysAddress,
		BITSTORM-HP-160StaticRowStatus  RowStatus
		}

	BITSTORM-HP-160StaticIndex	OBJECT-TYPE
		SYNTAX			Integer32 (1..438)
		MAX-ACCESS		not-accessible
		STATUS			current
		DESCRIPTION		""
		::=  {  BITSTORM-HP-160CfgDhcpStaticIPEntry  1  }


	BITSTORM-HP-160StaticIPBpIndex	OBJECT-TYPE
		SYNTAX			Integer32  
		MAX-ACCESS		read-create
		STATUS			current
		DESCRIPTION		""
		::=  {  BITSTORM-HP-160CfgDhcpStaticIPEntry  2  }
	BITSTORM-HP-160StaticIp	OBJECT-TYPE
		SYNTAX			OCTET STRING  ( SIZE ( 0 .. 15  ) )
		MAX-ACCESS		read-create
		STATUS			current
		DESCRIPTION		""
		::=  {  BITSTORM-HP-160CfgDhcpStaticIPEntry  3  }
	BITSTORM-HP-160StaticMac	OBJECT-TYPE
		SYNTAX			PhysAddress
		MAX-ACCESS		read-create
		STATUS			current
		DESCRIPTION		""
		::=  {  BITSTORM-HP-160CfgDhcpStaticIPEntry  4  }
	BITSTORM-HP-160StaticRowStatus	OBJECT-TYPE
		SYNTAX			RowStatus
		MAX-ACCESS		read-create
		STATUS			current
		DESCRIPTION		""
		::=  {  BITSTORM-HP-160CfgDhcpStaticIPEntry  5  }
--


   	BITSTORM-HP-160CfgVpmtTrunkTable	OBJECT-TYPE
		SYNTAX		SEQUENCE  OF  BITSTORM-HP-160CfgVpmtTrunkEntry
		MAX-ACCESS	not-accessible                      
		STATUS		current
		DESCRIPTION	""
		::=  { BITSTORM-HP-160CfgVpmtGroup  1 }

	BITSTORM-HP-160CfgVpmtTrunkEntry	OBJECT-TYPE
		SYNTAX		BITSTORM-HP-160CfgVpmtTrunkEntry
		MAX-ACCESS	not-accessible
		STATUS		current
		DESCRIPTION	""
		INDEX		{  BITSTORM-HP-160CfgVpmtIndex  }
		::=  { BITSTORM-HP-160CfgVpmtTrunkTable 1 }

	BITSTORM-HP-160CfgVpmtTrunkEntry  ::=  SEQUENCE {
		BITSTORM-HP-160CfgVpmtIndex     INTEGER,
		BITSTORM-HP-160CfgVpmtPriority  OCTET STRING,
		BITSTORM-HP-160CfgVpmtDenyMode  OCTET STRING,
--                BITSTORM-HP-160CfgVpmtRowStatus RowStatus,
		}


	BITSTORM-HP-160CfgVpmtIndex	OBJECT-TYPE
		SYNTAX			INTEGER (1..3)
		MAX-ACCESS		not-accessible
		STATUS			current
		DESCRIPTION		"1..3"
		::=  {  BITSTORM-HP-160CfgVpmtTrunkEntry  1  }


	BITSTORM-HP-160CfgVpmtPriority	OBJECT-TYPE
		SYNTAX			OCTET STRING  ( SIZE ( 16  ) )
		MAX-ACCESS		read-write
		STATUS			current
		DESCRIPTION		"for priority 0..7
		                         Queue No : 0 .. 3
	                                  0 .. 2 for shaping Queue(0 : High prio, 1 : Medium prio, 2 : Low prio)
	                                         , the enetTrafficDescrType bind to this prio should be CIR/CIREIR/PPR.
	                                  3      only for WFQ Quese(Lowest prio of these 4 Queses)
	                                         , the enetTrafficDescrType bind to this prio should be WFQ.
	                                  It isn't allowed that a shaping Queue maps to enetTrafficDescrType WFQ
	                                  It isn't allowed that a WFQ Queue maps to enetTrafficDescrType CIR/CIREIR/PPR
	                                  OAMP Layer 2 will check the relationship of Queue mapping and enetTrafficDescrType."
		::=  {  BITSTORM-HP-160CfgVpmtTrunkEntry  2  }


	BITSTORM-HP-160CfgVpmtDenyMode	OBJECT-TYPE
		SYNTAX			OCTET STRING  ( SIZE ( 8  ) )
		MAX-ACCESS		read-write
		STATUS			current
		DESCRIPTION		"0:pass, 1:deny"
		::=  {  BITSTORM-HP-160CfgVpmtTrunkEntry  3  }


--	BITSTORM-HP-160CfgVpmtRowStatus	OBJECT-TYPE
--                SYNTAX  RowStatus
--                MAX-ACCESS  read-create
--                STATUS  current
--                DESCRIPTION
--                           "BITSTORM-HP-160CfgVpmtRowStatus."
--		::=  {  BITSTORM-HP-160CfgVpmtTrunkEntry  4  }



   	BITSTORM-HP-160CfgVpmtBportProfileTable	OBJECT-TYPE
		SYNTAX		SEQUENCE  OF  BITSTORM-HP-160CfgVpmtBportProfileEntry
		MAX-ACCESS	not-accessible                      
		STATUS		current
		DESCRIPTION	""
		::=  { BITSTORM-HP-160CfgVpmtGroup  2 }

	BITSTORM-HP-160CfgVpmtBportProfileEntry	OBJECT-TYPE
		SYNTAX		BITSTORM-HP-160CfgVpmtBportProfileEntry
		MAX-ACCESS	not-accessible
		STATUS		current
		DESCRIPTION	""
		INDEX		{  BITSTORM-HP-160CfgVpmtProfileIndex  }
		::=  { BITSTORM-HP-160CfgVpmtBportProfileTable 1 }

	BITSTORM-HP-160CfgVpmtBportProfileEntry  ::=  SEQUENCE {
		BITSTORM-HP-160CfgVpmtProfileIndex     INTEGER,
		BITSTORM-HP-160CfgVpmtProfilePriority  OCTET STRING,
		BITSTORM-HP-160CfgVpmtProfileDenyMode  OCTET STRING,
		BITSTORM-HP-160CfgVpmtProfileEnetProfileIndex OCTET STRING,
		BITSTORM-HP-160CfgVpmtProfileUsedCount        INTEGER,
                BITSTORM-HP-160CfgVpmtProfileRowStatus RowStatus,
		}


	BITSTORM-HP-160CfgVpmtProfileIndex	OBJECT-TYPE
		SYNTAX			INTEGER (1..24)
		MAX-ACCESS		not-accessible
		STATUS			current
		DESCRIPTION		"1..3"
		::=  {  BITSTORM-HP-160CfgVpmtBportProfileEntry  1  }


	BITSTORM-HP-160CfgVpmtProfilePriority	OBJECT-TYPE
		SYNTAX			OCTET STRING  ( SIZE ( 8  ) )
		MAX-ACCESS		read-create
		STATUS			current
		DESCRIPTION		"for priority 0..7 
		                         Queue No : 0 .. 3
	                                  0 .. 2 for shaping Queue(0 : High prio, 1 : Medium prio, 2 : Low prio)
	                                         , the enetTrafficDescrType bind to this prio should be CIR/CIREIR/PPR.
	                                  3      only for WFQ Quese(Lowest prio of these 4 Queses)
	                                         , the enetTrafficDescrType bind to this prio should be WFQ.
	                                  It isn't allowed that a shaping Queue maps to enetTrafficDescrType WFQ
	                                  It isn't allowed that a WFQ Queue maps to enetTrafficDescrType CIR/CIREIR/PPR
	                                  OAMP Layer 2 will check the relationship of Queue mapping and enetTrafficDescrType."
		::=  {  BITSTORM-HP-160CfgVpmtBportProfileEntry  2  }


	BITSTORM-HP-160CfgVpmtProfileDenyMode	OBJECT-TYPE
		SYNTAX			OCTET STRING  ( SIZE ( 8  ) )
		MAX-ACCESS		read-create
		STATUS			current
		DESCRIPTION		"0:pass, 1:deny"
		::=  {  BITSTORM-HP-160CfgVpmtBportProfileEntry  3  }


	BITSTORM-HP-160CfgVpmtProfileEnetProfileIndex	OBJECT-TYPE
                SYNTAX  OCTET STRING  ( SIZE ( 8  ) )
                MAX-ACCESS  read-create
                STATUS  current
                DESCRIPTION
                           "enet traffic descriptor index."
		::=  {  BITSTORM-HP-160CfgVpmtBportProfileEntry  4  }
	BITSTORM-HP-160CfgVpmtProfileUsedCount	OBJECT-TYPE
                SYNTAX  INTEGER
                MAX-ACCESS  read-only
                STATUS  current
                DESCRIPTION
                           ""
		::=  {  BITSTORM-HP-160CfgVpmtBportProfileEntry  5  }
	BITSTORM-HP-160CfgVpmtProfileRowStatus	OBJECT-TYPE
                SYNTAX  RowStatus
                MAX-ACCESS  read-create
                STATUS  current
                DESCRIPTION
                           "BITSTORM-HP-160CfgVpmtRowStatus."
		::=  {  BITSTORM-HP-160CfgVpmtBportProfileEntry  6  }

	BITSTORM-HP-160CfgVpmtBridgePortBindTable	OBJECT-TYPE
		SYNTAX		SEQUENCE  OF  BITSTORM-HP-160CfgVpmtBridgePortBindEntry
		MAX-ACCESS	not-accessible
		STATUS		current
		DESCRIPTION	""
		::=  { BITSTORM-HP-160CfgVpmtGroup  3 }

	BITSTORM-HP-160CfgVpmtBridgePortBindEntry	OBJECT-TYPE
		SYNTAX		BITSTORM-HP-160CfgVpmtBridgePortBindEntry
		MAX-ACCESS	not-accessible
		STATUS		current
		DESCRIPTION	""
		INDEX		{  BITSTORM-HP-160CfgVpmtBindBpId  }
		::=  { BITSTORM-HP-160CfgVpmtBridgePortBindTable 1 }

	BITSTORM-HP-160CfgVpmtBridgePortBindEntry  ::=  SEQUENCE {
		BITSTORM-HP-160CfgVpmtBindBpId  Integer32,
		BITSTORM-HP-160CfgVpmtBindProfileId  Integer32
		}


	BITSTORM-HP-160CfgVpmtBindBpId	OBJECT-TYPE	
		SYNTAX			Integer32 (196..219)
		MAX-ACCESS		not-accessible
		STATUS			current
		DESCRIPTION		""
		::=  {  BITSTORM-HP-160CfgVpmtBridgePortBindEntry  1  }


	BITSTORM-HP-160CfgVpmtBindProfileId	OBJECT-TYPE
		SYNTAX			Integer32  (1..24)
		MAX-ACCESS		read-write
		STATUS			current
		DESCRIPTION		""
		::=  {  BITSTORM-HP-160CfgVpmtBridgePortBindEntry  2  }
		
		
--	BITSTORM-HP-160CfgSystemAclMode	OBJECT-TYPE
--		SYNTAX			INTEGER { Disable(0),Enable(1) }
--		MAX-ACCESS		read-write
--		STATUS			current
--		DESCRIPTION		""
--		::=  {  BITSTORM-HP-160CfgSystemConfiguration  1  }

	BITSTORM-HP-160CfgSystemExtEtherType	OBJECT-TYPE
		SYNTAX			Integer32  (0..65535)
		MAX-ACCESS		read-write
		STATUS			current
		DESCRIPTION		""
		::=  {  BITSTORM-HP-160CfgSystemConfiguration  1  }

	BITSTORM-HP-160CfgSystemAllowDownstreamBc	OBJECT-TYPE
		SYNTAX			INTEGER { Disable(0),Enable(1) }
		MAX-ACCESS		read-write
		STATUS			current
		DESCRIPTION		"0:disable(only ARP,DHCP are allowed), 1:enable(ALL bccast are allowed)"
		::=  {  BITSTORM-HP-160CfgSystemConfiguration  2  }

--	BITSTORM-HP-160CfgSystemAllowIpFilter	OBJECT-TYPE
--		SYNTAX			INTEGER { Disable(0),Enable(1) }
--		MAX-ACCESS		read-write
--		STATUS			current
--		DESCRIPTION		"0:disable, 1:enable"
--		::=  {  BITSTORM-HP-160CfgSystemConfiguration  4  }


	BITSTORM-HP-160CfgSystemAddAllowIpBySnoopDHCP	OBJECT-TYPE
		SYNTAX			INTEGER { Disable(0),Enable(1) }
		MAX-ACCESS		read-write
		STATUS			current
		DESCRIPTION		"0:disable, 1:enable,
	                                allowIpFilter should be enabled first."
		::=  {  BITSTORM-HP-160CfgSystemConfiguration  3  }


	BITSTORM-HP-160CfgSystemAgingTimePerPort	OBJECT-TYPE
		SYNTAX			INTEGER { Disable(0),Enable(1) }
		MAX-ACCESS		read-write
		STATUS			current
		DESCRIPTION		"1:enable, 0:disable->Old mechanism, referecne to TpAgingTime."
		::=  {  BITSTORM-HP-160CfgSystemConfiguration  4  }

	BITSTORM-HP-160CfgSystemReplaceArpMac	OBJECT-TYPE
		SYNTAX			INTEGER { Disable(0),Enable(1) }
		MAX-ACCESS		read-write
		STATUS			current
		DESCRIPTION		"0:disable, 1:enable(mac of arp will be replaced)"
		::=  {  BITSTORM-HP-160CfgSystemConfiguration  5  }


	BITSTORM-HP-160CfgSystemSnoopArpDefaultGatewayMac	OBJECT-TYPE
		SYNTAX			PhysAddress
		MAX-ACCESS		read-create
		STATUS			current
		DESCRIPTION		"string hex mac format in DB, example->FF:FF:FF:FF:FF:FF"
		::=  {  BITSTORM-HP-160CfgSystemConfiguration  6  }


	BITSTORM-HP-160CfgSystemArpSpoofing	OBJECT-TYPE
		SYNTAX			INTEGER { Disable(0),Enable(1) }
		MAX-ACCESS		read-write
		STATUS			current
		DESCRIPTION		"0:disable this arp spoof function, L2 will not check the arp reply packet from line side.
                                         1:enable this arp spoof function, L2 will check the arp reply packet from line side."
		::=  {  BITSTORM-HP-160CfgSystemConfiguration  7  }

	BITSTORM-HP-160CfgSystemAntiMacSpoofing	OBJECT-TYPE
		SYNTAX			INTEGER { Disable(0),Enable(1) }
		MAX-ACCESS		read-write
		STATUS			current
		DESCRIPTION		"0:able to provide service to users with duplicate MAC addresses (by default)
                                         1:able to deny service to users with duplicate MAC addresses."
		::=  {  BITSTORM-HP-160CfgSystemConfiguration  8  }

--
	BITSTORM-HP-160CfgAclService	OBJECT-TYPE
		SYNTAX			INTEGER { Disable(0),Enable(1) }
		MAX-ACCESS		read-write
		STATUS			current
		DESCRIPTION		""
		::=  {  BITSTORM-HP-160CfgLayerIIServiceOption  1  }

	BITSTORM-HP-160CfgPppoeService	OBJECT-TYPE
		SYNTAX			INTEGER { Disable(0),Enable(1) }
		MAX-ACCESS		read-write
		STATUS			current
		DESCRIPTION		""
		::=  {  BITSTORM-HP-160CfgLayerIIServiceOption  2  }

	BITSTORM-HP-160CfgFilterAndPriorityRemarkService	OBJECT-TYPE     
		SYNTAX			INTEGER { Disable(0),Enable(1) }
		MAX-ACCESS		read-write
		STATUS			current
		DESCRIPTION		""
		::=  {  BITSTORM-HP-160CfgLayerIIServiceOption  3  }

	BITSTORM-HP-160CfgRateLimitService	OBJECT-TYPE
		SYNTAX			INTEGER { Disable(0),Enable(1) }
		MAX-ACCESS		read-write
		STATUS			current
		DESCRIPTION		""
		::=  {  BITSTORM-HP-160CfgLayerIIServiceOption  4  }


	BITSTORM-HP-160CfgStackVlanService	OBJECT-TYPE
		SYNTAX			INTEGER { Disable(0),Enable(1) }
		MAX-ACCESS		read-write
		STATUS			current
		DESCRIPTION		""
		::=  {  BITSTORM-HP-160CfgLayerIIServiceOption  5  }

	BITSTORM-HP-160CfgNetBiosDenialService	OBJECT-TYPE
		SYNTAX			INTEGER { Disable(0),Enable(1) }
		MAX-ACCESS		read-write
		STATUS			current
		DESCRIPTION		""
		::=  {  BITSTORM-HP-160CfgLayerIIServiceOption  6  }
		
	BITSTORM-HP-160CfgAllowIpService	OBJECT-TYPE
		SYNTAX			INTEGER { Disable(0),Enable(1) }
		MAX-ACCESS		read-write
		STATUS			current
		DESCRIPTION		""
		::=  {  BITSTORM-HP-160CfgLayerIIServiceOption  7  }
		
--


	BITSTORM-HP-160CfgClusterName	OBJECT-TYPE
		SYNTAX			OCTET STRING  ( SIZE ( 0 .. 32  ) ) 
		MAX-ACCESS		read-write
		STATUS			current
		DESCRIPTION		""
		::=  {  BITSTORM-HP-160CfgClusterConfig  1  }

	BITSTORM-HP-160CfgClusterDomain	OBJECT-TYPE
		SYNTAX			OCTET STRING  ( SIZE ( 0 .. 32  ) )
		MAX-ACCESS		read-write
		STATUS			current
		DESCRIPTION		""
		::=  {  BITSTORM-HP-160CfgClusterConfig  2  }

	BITSTORM-HP-160CfgClusterManagementIp	OBJECT-TYPE	
		SYNTAX			TAddress
		MAX-ACCESS		read-write
		STATUS			current
		DESCRIPTION		""
		::=  {  BITSTORM-HP-160CfgClusterConfig  3  }

	BITSTORM-HP-160CfgClusterManagementNetmask	OBJECT-TYPE	
		SYNTAX			TAddress
		MAX-ACCESS		read-write
		STATUS			current
		DESCRIPTION		""
		::=  {  BITSTORM-HP-160CfgClusterConfig  4  }

	BITSTORM-HP-160CfgClusterManagementGateway	OBJECT-TYPE	
		SYNTAX			TAddress
		MAX-ACCESS		read-write
		STATUS			current
		DESCRIPTION		""
		::=  {  BITSTORM-HP-160CfgClusterConfig  5  }

	BITSTORM-HP-160CfgClusterPriority	OBJECT-TYPE	
		SYNTAX			Integer32
		MAX-ACCESS		read-write
		STATUS			current
		DESCRIPTION		""
		::=  {  BITSTORM-HP-160CfgClusterConfig  6  }

	BITSTORM-HP-160CfgClusterClustered	OBJECT-TYPE
		SYNTAX			INTEGER { Disabled(0),Enabled(1) }  
		MAX-ACCESS		read-write
		STATUS			current
		DESCRIPTION		""
		::=  {  BITSTORM-HP-160CfgClusterConfig  7  }

	BITSTORM-HP-160CfgClusterSlaveOnly	OBJECT-TYPE
		SYNTAX			INTEGER { MasterSlave(0),SlaveOnly(1) }
		MAX-ACCESS		read-write
		STATUS			current
		DESCRIPTION		""
		::=  {  BITSTORM-HP-160CfgClusterConfig  8  }
		
	BITSTORM-HP-160CfgClusterState	OBJECT-TYPE
		SYNTAX			INTEGER  {
		  IDLE(0),               
  		  REINIT(1),
  		  DISCOVERING(2),
  		  REQUESTING(3),
		  VOTING(4),
		  SLAVE(5),
		  MASTER(6)
		 }
		MAX-ACCESS		read-only
		STATUS			current
		DESCRIPTION		""
		::=  {  BITSTORM-HP-160CfgClusterConfig  9  }
		
		
BITSTORM-HP-160CfgEnetTrafficDescrEntry OBJECT-TYPE
    SYNTAX      BITSTORM-HP-160CfgEnetTrafficDescrEntry
    MAX-ACCESS  not-accessible
    STATUS      current
    DESCRIPTION
        ""
    INDEX   { BITSTORM-HP-160CfgEnetTrafficDescrIndex }
    ::= { BITSTORM-HP-160CfgEnetTrafficDescrTable 1 }

BITSTORM-HP-160CfgEnetTrafficDescrEntry ::=
    SEQUENCE {
             BITSTORM-HP-160CfgEnetTrafficDescrIndex         Integer32,
             BITSTORM-HP-160CfgEnetTrafficType               BITSTORM-HP-160EnetTrafficType,
             BITSTORM-HP-160CfgEnetTrafficWeight             Unsigned32,
--             BITSTORM-HP-160CfgEnetTrafficWeightFraction     Unsigned32,
             BITSTORM-HP-160CfgEnetTrafficPPR                Unsigned32,
             BITSTORM-HP-160CfgEnetTrafficCIR                Unsigned32,
             BITSTORM-HP-160CfgEnetTrafficEIR                Unsigned32,
             BITSTORM-HP-160CfgEnetTrafficCBS                Unsigned32,
             BITSTORM-HP-160CfgEnetTrafficEBS                Unsigned32,
             BITSTORM-HP-160CfgEnetTrafficPPRPollingSpeed    Unsigned32,
             BITSTORM-HP-160CfgEnetTrafficCIRPollingSpeed    Unsigned32,
             BITSTORM-HP-160CfgEnetTrafficEIRPollingSpeed    Unsigned32,
             BITSTORM-HP-160CfgAtmTrafficType                BITSTORM-HP-160AtmTrafficType,
             BITSTORM-HP-160CfgEnetTrafficPCR                Unsigned32,
             BITSTORM-HP-160CfgEnetTrafficCDVT               Unsigned32,
                                               
             BITSTORM-HP-160CfgEnetTrafficRowStatus          RowStatus,
             BITSTORM-HP-160CfgEnetTrafficUsedCount           INTEGER
    }

BITSTORM-HP-160CfgEnetTrafficDescrIndex  OBJECT-TYPE
    SYNTAX      Integer32 (1..16)
    MAX-ACCESS  not-accessible
    STATUS  current
    DESCRIPTION
       "1..16"
     ::= { BITSTORM-HP-160CfgEnetTrafficDescrEntry 1 }

BITSTORM-HP-160CfgEnetTrafficType OBJECT-TYPE
    SYNTAX      BITSTORM-HP-160EnetTrafficType
    MAX-ACCESS  read-write
    STATUS  current
    DESCRIPTION
        "
           ENETPKTSHAPINGWFQ(1),
           ENETPKTSHAPINGPPR(2),
           ENETPKTSHAPINGCIR(3),
           ENETPKTSHAPINGCIREIR(4)
        "
     ::= { BITSTORM-HP-160CfgEnetTrafficDescrEntry 2 }

BITSTORM-HP-160CfgEnetTrafficWeight  OBJECT-TYPE
    SYNTAX      Unsigned32 (1..42)
    MAX-ACCESS  read-write
    STATUS  current
    DESCRIPTION
       ""
     ::= { BITSTORM-HP-160CfgEnetTrafficDescrEntry 3 }

--BITSTORM-HP-160CfgEnetTrafficWeightFraction  OBJECT-TYPE
--    SYNTAX      Unsigned32
--    MAX-ACCESS  read-write
--    STATUS  current
--    DESCRIPTION
--       ""
--     ::= { BITSTORM-HP-160CfgEnetTrafficDescrEntry 4 }

BITSTORM-HP-160CfgEnetTrafficPPR  OBJECT-TYPE
    SYNTAX      Unsigned32 (1000000..100000000)
    MAX-ACCESS  read-write
    STATUS  current
    DESCRIPTION
       "Peak packet Rate.[bits/second]"
     ::= { BITSTORM-HP-160CfgEnetTrafficDescrEntry 4 }

BITSTORM-HP-160CfgEnetTrafficCIR  OBJECT-TYPE
    SYNTAX      Unsigned32 (1000000..100000000)
    MAX-ACCESS  read-write
    STATUS  current
    DESCRIPTION
       "Committed Information Rate expressed as bits/sec"
     ::= { BITSTORM-HP-160CfgEnetTrafficDescrEntry 5 }

BITSTORM-HP-160CfgEnetTrafficEIR  OBJECT-TYPE
    SYNTAX      Unsigned32 (1000000..100000000)
    MAX-ACCESS  read-write
    STATUS  current
    DESCRIPTION
       "Committed Excess Rate expressed as bits/sec"
     ::= { BITSTORM-HP-160CfgEnetTrafficDescrEntry 6 }

BITSTORM-HP-160CfgEnetTrafficCBS  OBJECT-TYPE
    SYNTAX      Unsigned32 (1..4294967295)
    MAX-ACCESS  read-write
    STATUS  current
    DESCRIPTION
       "Committed Burst Size in bits"
     ::= { BITSTORM-HP-160CfgEnetTrafficDescrEntry 7 }

BITSTORM-HP-160CfgEnetTrafficEBS  OBJECT-TYPE
    SYNTAX      Unsigned32 (1..4294967295)
    MAX-ACCESS  read-write
    STATUS  current
    DESCRIPTION
       "Excess Burst Size in bits"
     ::= { BITSTORM-HP-160CfgEnetTrafficDescrEntry 8 }

BITSTORM-HP-160CfgEnetTrafficPPRPollingSpeed  OBJECT-TYPE
    SYNTAX      Unsigned32 (1000000..2147483648)
    MAX-ACCESS  read-write
    STATUS  current
    DESCRIPTION
       "Vaule range:1000000-100000000.
        2147483648 means Auto Deactivation Mode.
       "
     ::= { BITSTORM-HP-160CfgEnetTrafficDescrEntry 9 }

BITSTORM-HP-160CfgEnetTrafficCIRPollingSpeed  OBJECT-TYPE
    SYNTAX      Unsigned32 (1000000..2147483648)
    MAX-ACCESS  read-write
    STATUS  current
    DESCRIPTION
       "Vaule range:1000000-100000000..
        2147483648 means Auto Deactivation Mode.

        Currently, Auto Deactivation is not supported.
       "
     ::= { BITSTORM-HP-160CfgEnetTrafficDescrEntry 10 }

BITSTORM-HP-160CfgEnetTrafficEIRPollingSpeed  OBJECT-TYPE
    SYNTAX      Unsigned32 (1000000..2147483648)
    MAX-ACCESS  read-write
    STATUS  current
    DESCRIPTION
       "Vaule range:1000000-100000000.
        2147483648 means Auto Deactivation Mode.

        Currently only Auto-deactivation mode is permitted.
       "
     ::= { BITSTORM-HP-160CfgEnetTrafficDescrEntry 11 }

BITSTORM-HP-160CfgAtmTrafficType OBJECT-TYPE
    SYNTAX      BITSTORM-HP-160AtmTrafficType
    MAX-ACCESS  read-write
    STATUS  current
    DESCRIPTION
        "
           AtmPolicingCBR(9),
           AtmPolicingUBR2(11)
        "
     ::= { BITSTORM-HP-160CfgEnetTrafficDescrEntry 12 }

BITSTORM-HP-160CfgEnetTrafficPCR  OBJECT-TYPE
    SYNTAX      Unsigned32 (1..65536)
    MAX-ACCESS  read-write
    STATUS  current
    DESCRIPTION
       "0-65536, Specified in units of cells/second"
     ::= { BITSTORM-HP-160CfgEnetTrafficDescrEntry 13 }
     
BITSTORM-HP-160CfgEnetTrafficCDVT  OBJECT-TYPE
    SYNTAX      Unsigned32 (1..65536)
    MAX-ACCESS  read-write
    STATUS  current
    DESCRIPTION
       "0-65536, Specified in units of 10 ns increments, this field is used by the PCR policing algorithm"
     ::= { BITSTORM-HP-160CfgEnetTrafficDescrEntry 14 }
     
BITSTORM-HP-160CfgEnetTrafficRowStatus  OBJECT-TYPE
    SYNTAX  RowStatus
    MAX-ACCESS  read-create
    STATUS  current
    DESCRIPTION
       "BITSTORM-HP-160CfgEnetTrafficRowStatus."
     ::= { BITSTORM-HP-160CfgEnetTrafficDescrEntry 15 }

BITSTORM-HP-160CfgEnetTrafficUsedCount	OBJECT-TYPE
    SYNTAX			INTEGER
    MAX-ACCESS		read-only
    STATUS			current
    DESCRIPTION		"The value is not zero means the profile is in used,then the profile can't be delete."
     ::=  {  BITSTORM-HP-160CfgEnetTrafficDescrEntry  16  }
		
--BITSTORM-HP-160CfgEnetTrafficUseCount  OBJECT-TYPE
--    SYNTAX  Unsigned32
--    MAX-ACCESS  read-only
--    STATUS  current
--    DESCRIPTION
--       "BITSTORM-HP-160CfgEnetTrafficUseCount."
--     ::= { BITSTORM-HP-160CfgEnetTrafficDescrEntry 14 }


--	BITSTORM-HP-160MtnRemoteTFTPServerIP	OBJECT-TYPE
--		SYNTAX			TAddress
--		MAX-ACCESS		read-write
--		STATUS			current
--		DESCRIPTION		""
--		::=  {  BITSTORM-HP-160MtnRemoteTFTPServer  1  }

--	BITSTORM-HP-160MtnRemoteTFTPFileName	OBJECT-TYPE
--		SYNTAX			OCTET STRING  ( SIZE ( 32  ) )
--		MAX-ACCESS		read-write
--		STATUS			current
--		DESCRIPTION		""
--		::=  {  BITSTORM-HP-160MtnRemoteTFTPServer  2  }

	BITSTORM-HP-160MtnRemoteFTPServerIP	OBJECT-TYPE
		SYNTAX			TAddress
		MAX-ACCESS		read-write
		STATUS			current
		DESCRIPTION		""
		::=  {  BITSTORM-HP-160MtnRemoteFTPServer  1  }

	BITSTORM-HP-160MtnRemoteFTPUserName	OBJECT-TYPE
		SYNTAX			OCTET STRING  ( SIZE ( 32  ) )
		MAX-ACCESS		read-write
		STATUS			current
		::=  {  BITSTORM-HP-160MtnRemoteFTPServer  2  }

	BITSTORM-HP-160MtnRemoteFTPPassword	OBJECT-TYPE
		SYNTAX			OCTET STRING  ( SIZE ( 32  ) )
		MAX-ACCESS		read-write
		STATUS			current
		DESCRIPTION		""
		::=  {  BITSTORM-HP-160MtnRemoteFTPServer  3  }

	BITSTORM-HP-160MtnRemoteFTPFileName	OBJECT-TYPE
		SYNTAX			OCTET STRING  ( SIZE ( 64  ) )
		MAX-ACCESS		read-write
		STATUS			current
		DESCRIPTION		""
		::=  {  BITSTORM-HP-160MtnRemoteFTPServer  4  }




	BITSTORM-HP-160MtnCliCfgFTPServerIP	OBJECT-TYPE
		SYNTAX			TAddress
		MAX-ACCESS		read-write
		STATUS			current
		DESCRIPTION		""
		::=  {  BITSTORM-HP-160MtnCliCfgFTPServer  1  }

	BITSTORM-HP-160MtnCliCfgFTPUserName	OBJECT-TYPE
		SYNTAX			OCTET STRING  ( SIZE ( 32  ) )
		MAX-ACCESS		read-write
		STATUS			current
		::=  {  BITSTORM-HP-160MtnCliCfgFTPServer  2  }

	BITSTORM-HP-160MtnCliCfgFTPPassword	OBJECT-TYPE
		SYNTAX			OCTET STRING  ( SIZE ( 32  ) )
		MAX-ACCESS		read-write
		STATUS			current
		DESCRIPTION		""
		::=  {  BITSTORM-HP-160MtnCliCfgFTPServer  3  }

	BITSTORM-HP-160MtnCliCfgFTPFileName	OBJECT-TYPE           
		SYNTAX			OCTET STRING  ( SIZE ( 64  ) )
		MAX-ACCESS		read-write
		STATUS			current
		DESCRIPTION		""
		::=  {  BITSTORM-HP-160MtnCliCfgFTPServer  4  }
		
	BITSTORM-HP-160SystemAlarmTrap	OBJECT IDENTIFIER
		::=  {  BITSTORM-HP-160TrapAlarmPrefix  1  }
		
        BITSTORM-HP-160GBEAlarmTrap	OBJECT IDENTIFIER
		::=  {  BITSTORM-HP-160TrapAlarmPrefix  2  }

	BITSTORM-HP-160VDSLAlarmTrap	OBJECT IDENTIFIER
		::=  {  BITSTORM-HP-160TrapAlarmPrefix  3  }

	BITSTORM-HP-160SystemEventTrap	OBJECT IDENTIFIER
		::=  {  BITSTORM-HP-160TrapEventPrefix  1  }

	BITSTORM-HP-160ATMEventTrap	OBJECT IDENTIFIER
		::=  {  BITSTORM-HP-160TrapEventPrefix  2  }

--	BITSTORM-HP-160GBEEventTrap	OBJECT IDENTIFIER
--		::=  {  BITSTORM-HP-160TrapEventPrefix  3  }

	BITSTORM-HP-160XDSLEventTrap	OBJECT IDENTIFIER
		::=  {  BITSTORM-HP-160TrapEventPrefix  3  }

	BITSTORM-HP-160VDSLEventTrap	OBJECT IDENTIFIER
		::=  {  BITSTORM-HP-160TrapEventPrefix  4  }

	BITSTORM-HP-160McBcRateLimitTable	OBJECT-TYPE
		SYNTAX		SEQUENCE  OF  BITSTORM-HP-160McBcRateLimitEntry
		MAX-ACCESS	not-accessible
		STATUS		current
		DESCRIPTION	""
		::=  { BITSTORM-HP-160CfgRateLimitGroup  1 }

	BITSTORM-HP-160McBcRateLimitEntry	OBJECT-TYPE
		SYNTAX		BITSTORM-HP-160McBcRateLimitEntry
		MAX-ACCESS	not-accessible
		STATUS		current
		DESCRIPTION	""
		INDEX		{  BITSTORM-HP-160McBcRateLimitVlanId  }
		::=  { BITSTORM-HP-160McBcRateLimitTable 1 }

	BITSTORM-HP-160McBcRateLimitEntry  ::=  SEQUENCE {
		BITSTORM-HP-160McBcRateLimitVlanId  Integer32,
		BITSTORM-HP-160McBcRateLimitCIR  Unsigned32,
		BITSTORM-HP-160McBcRateLimitLbSl  Unsigned32,
		BITSTORM-HP-160McBcRateLimitRowStatus  RowStatus
		}


	BITSTORM-HP-160McBcRateLimitVlanId	OBJECT-TYPE
		SYNTAX			Integer32  ( 1 .. 4094  )   --960803
		MAX-ACCESS		read-only
		STATUS			current
		DESCRIPTION		""
		::=  {  BITSTORM-HP-160McBcRateLimitEntry  1  }


	BITSTORM-HP-160McBcRateLimitCIR	OBJECT-TYPE	
		SYNTAX			Unsigned32  ( 1 .. 4294967295  ) 
		MAX-ACCESS		read-create
		STATUS			current
		DESCRIPTION		""
		::=  {  BITSTORM-HP-160McBcRateLimitEntry  2  }


	BITSTORM-HP-160McBcRateLimitLbSl	OBJECT-TYPE	
		SYNTAX			Unsigned32  ( 1 .. 4294967295  ) 
		MAX-ACCESS		read-create
		STATUS			current
		DESCRIPTION		""
		::=  {  BITSTORM-HP-160McBcRateLimitEntry  3  }


	BITSTORM-HP-160McBcRateLimitRowStatus	OBJECT-TYPE	
		SYNTAX			RowStatus
		MAX-ACCESS		read-create
		STATUS			current
		DESCRIPTION		""
		DEFVAL			{ createAndGo }
		::=  {  BITSTORM-HP-160McBcRateLimitEntry  4  }

	BITSTORM-HP-160McFldRateLimitTable	OBJECT-TYPE
		SYNTAX		SEQUENCE  OF  BITSTORM-HP-160McFldRateLimitEntry
		MAX-ACCESS	not-accessible
		STATUS		current
		DESCRIPTION	""
		::=  { BITSTORM-HP-160CfgRateLimitGroup  2 }

	BITSTORM-HP-160McFldRateLimitEntry	OBJECT-TYPE
		SYNTAX		BITSTORM-HP-160McFldRateLimitEntry
		MAX-ACCESS	not-accessible
		STATUS		current
		DESCRIPTION	""
		INDEX		{  BITSTORM-HP-160McFldRateLimitVlanId  }
		::=  { BITSTORM-HP-160McFldRateLimitTable 1 }

	BITSTORM-HP-160McFldRateLimitEntry  ::=  SEQUENCE {
		BITSTORM-HP-160McFldRateLimitVlanId  Integer32,
		BITSTORM-HP-160McFldRateLimitCIR  Unsigned32,
		BITSTORM-HP-160McFldRateLimitLbSl  Unsigned32,
		BITSTORM-HP-160McFldRateLimitRowStatus  RowStatus
		}


	BITSTORM-HP-160McFldRateLimitVlanId	OBJECT-TYPE
		SYNTAX			Integer32  ( 1 .. 4094  )   --960803
		MAX-ACCESS		read-only
		STATUS			current
		DESCRIPTION		""
		::=  {  BITSTORM-HP-160McFldRateLimitEntry  1  }


	BITSTORM-HP-160McFldRateLimitCIR	OBJECT-TYPE	
		SYNTAX			Unsigned32  ( 1 .. 4294967295  ) 
		MAX-ACCESS		read-create
		STATUS			current
		DESCRIPTION		""
		::=  {  BITSTORM-HP-160McFldRateLimitEntry  2  }


	BITSTORM-HP-160McFldRateLimitLbSl	OBJECT-TYPE	
		SYNTAX			Unsigned32  ( 1 .. 4294967295  ) 
		MAX-ACCESS		read-create
		STATUS			current
		DESCRIPTION		""
		::=  {  BITSTORM-HP-160McFldRateLimitEntry  3  }


	BITSTORM-HP-160McFldRateLimitRowStatus	OBJECT-TYPE	
		SYNTAX			RowStatus
		MAX-ACCESS		read-create
		STATUS			current
		DESCRIPTION		""
		DEFVAL			{ createAndGo }
		::=  {  BITSTORM-HP-160McFldRateLimitEntry  4  }

	BITSTORM-HP-160IwPolicerTable	OBJECT-TYPE
		SYNTAX		SEQUENCE  OF  BITSTORM-HP-160IwPolicerEntry
		MAX-ACCESS	not-accessible
		STATUS		current
		DESCRIPTION	""
		::=  { BITSTORM-HP-160CfgRateLimitGroup  3 }

	BITSTORM-HP-160IwpolicerEntry	OBJECT-TYPE
		SYNTAX		BITSTORM-HP-160IwPolicerEntry
		MAX-ACCESS	not-accessible
		STATUS		current
		DESCRIPTION	""
		INDEX		{  BITSTORM-HP-160IwPolicerIndex  }
		::=  { BITSTORM-HP-160IwPolicerTable 1 }

	BITSTORM-HP-160IwPolicerEntry  ::=  SEQUENCE {
		BITSTORM-HP-160IwPolicerIndex  Integer32,
		BITSTORM-HP-160IwPolicerCIR  Unsigned32,
		BITSTORM-HP-160IwPolicerLbSl  Unsigned32,
		BITSTORM-HP-160IwPolicerRowStatus  RowStatus,
		BITSTORM-HP-160IwPolicerUsedCount  INTEGER 		
		}


	BITSTORM-HP-160IwPolicerIndex	OBJECT-TYPE	
		SYNTAX			Integer32  ( 1 .. 128  ) 
		MAX-ACCESS		not-accessible
		STATUS			current
		DESCRIPTION		""
		::=  {  BITSTORM-HP-160IwpolicerEntry  1  }


	BITSTORM-HP-160IwPolicerCIR	OBJECT-TYPE	
		SYNTAX			Unsigned32
		MAX-ACCESS		read-create
		STATUS			current
		DESCRIPTION		""
		::=  {  BITSTORM-HP-160IwpolicerEntry  2  }


	BITSTORM-HP-160IwPolicerLbSl	OBJECT-TYPE	
		SYNTAX			Unsigned32  ( 1 .. 4294967295  ) 
		MAX-ACCESS		read-create
		STATUS			current
		DESCRIPTION		""
		::=  {  BITSTORM-HP-160IwpolicerEntry  3  }


	BITSTORM-HP-160IwPolicerRowStatus	OBJECT-TYPE
		SYNTAX			RowStatus
		MAX-ACCESS		read-create
		STATUS			current
		DESCRIPTION		""
		::=  {  BITSTORM-HP-160IwpolicerEntry  4  }

	BITSTORM-HP-160IwPolicerUsedCount	OBJECT-TYPE
		SYNTAX			INTEGER
		MAX-ACCESS		read-only
		STATUS			current
		DESCRIPTION		"The value is not zero means the profile is in used,then the profile can't be delete."
		::=  {  BITSTORM-HP-160IwpolicerEntry  5  }

	BITSTORM-HP-160BportRateLimitTable	OBJECT-TYPE
		SYNTAX		SEQUENCE  OF  BITSTORM-HP-160BportRateLimitEntry
		MAX-ACCESS	not-accessible
		STATUS		current
		DESCRIPTION	""
		::=  { BITSTORM-HP-160CfgRateLimitGroup  4 }

	BITSTORM-HP-160BportRateLimitEntry	OBJECT-TYPE
		SYNTAX		BITSTORM-HP-160BportRateLimitEntry
		MAX-ACCESS	not-accessible
		STATUS		current
		DESCRIPTION	""
		INDEX		{  BITSTORM-HP-160BportIfcIndex  }
		::=  { BITSTORM-HP-160BportRateLimitTable 1 }

	BITSTORM-HP-160BportRateLimitEntry  ::=  SEQUENCE {
		BITSTORM-HP-160BportIfcIndex  Integer32,
		--BITSTORM-HP-160BportRateLimitIwPolicerIdx  Unsigned32,
		BITSTORM-HP-160BportRateLimitEgressIwPolicerIdx  Unsigned32,   --20070329 add
		BITSTORM-HP-160BportRateLimitIngressIwPolicerIdx  Unsigned32,   --20070329 add
--		BITSTORM-HP-160BportRateLimitRowStatus  RowStatus
		}


	BITSTORM-HP-160BportIfcIndex	OBJECT-TYPE
		SYNTAX			Integer32  ( 1 .. 219  )
		MAX-ACCESS		not-accessible
		STATUS			current
		DESCRIPTION		""
		::=  {  BITSTORM-HP-160BportRateLimitEntry  1  }


	BITSTORM-HP-160BportRateLimitEgressIwPolicerIdx	OBJECT-TYPE
		SYNTAX			Unsigned32  ( 1 .. 4294967295  )
		MAX-ACCESS		read-write
		STATUS			current
		DESCRIPTION		""
		::=  {  BITSTORM-HP-160BportRateLimitEntry  2  }


	BITSTORM-HP-160BportRateLimitIngressIwPolicerIdx	OBJECT-TYPE
		SYNTAX			Unsigned32  ( 1 .. 4294967295  )
		MAX-ACCESS		read-write
		STATUS			current
		DESCRIPTION		""
		::=  {  BITSTORM-HP-160BportRateLimitEntry  3  }

--	BITSTORM-HP-160BportRateLimitRowStatus	OBJECT-TYPE
--		SYNTAX			RowStatus
--		MAX-ACCESS		read-create
--		STATUS			current
--		DESCRIPTION		""
--		::=  {  BITSTORM-HP-160BportRateLimitEntry  4  }



	BITSTORM-HP-160BportVlanRateLimitTable	OBJECT-TYPE
		SYNTAX		SEQUENCE  OF  BITSTORM-HP-160BportVlanRateLimitEntry
		MAX-ACCESS	not-accessible
		STATUS		current
		DESCRIPTION	""
		::=  { BITSTORM-HP-160CfgRateLimitGroup  5 }

	BITSTORM-HP-160BportVlanRateLimitEntry	OBJECT-TYPE
		SYNTAX		BITSTORM-HP-160BportVlanRateLimitEntry
		MAX-ACCESS	not-accessible
		STATUS		current
		DESCRIPTION	""
		INDEX		{  BITSTORM-HP-160BportVlanRateLimitIndex  }
		::=  { BITSTORM-HP-160BportVlanRateLimitTable 1 }

	BITSTORM-HP-160BportVlanRateLimitEntry  ::=  SEQUENCE {
		BITSTORM-HP-160BportVlanRateLimitIndex  Integer32,
		BITSTORM-HP-160BportVlanRateLimitEgressIwPolicerIdx  Unsigned32,
		BITSTORM-HP-160BportVlanRateLimitIngressIwPolicerIdx  Unsigned32,
		BITSTORM-HP-160BportVlanRateLimitVlanId  Unsigned32,
		BITSTORM-HP-160BportVlanRateLimitIfcIndex  Unsigned32,
		BITSTORM-HP-160BportVlanRateLimitRowStatus  RowStatus
		}


	BITSTORM-HP-160BportVlanRateLimitIndex	OBJECT-TYPE
		SYNTAX			Integer32  ( 1 .. 219  )
		MAX-ACCESS		not-accessible
		STATUS			current
		DESCRIPTION		""
		::=  {  BITSTORM-HP-160BportVlanRateLimitEntry  1  }


	BITSTORM-HP-160BportVlanRateLimitEgressIwPolicerIdx	OBJECT-TYPE
		SYNTAX			Unsigned32  ( 1 .. 4294967295  )
		MAX-ACCESS		read-create
		STATUS			current
		DESCRIPTION		""
		::=  {  BITSTORM-HP-160BportVlanRateLimitEntry  2  }


	BITSTORM-HP-160BportVlanRateLimitIngressIwPolicerIdx	OBJECT-TYPE
		SYNTAX			Unsigned32  ( 1 .. 4294967295  )
		MAX-ACCESS		read-create
		STATUS			current
		DESCRIPTION		""
		::=  {  BITSTORM-HP-160BportVlanRateLimitEntry  3  }

	BITSTORM-HP-160BportVlanRateLimitVlanId	OBJECT-TYPE
		SYNTAX			Unsigned32  ( 1 .. 4094  )   --960803
		MAX-ACCESS		read-create
		STATUS			current
		DESCRIPTION		""
		::=  {  BITSTORM-HP-160BportVlanRateLimitEntry  4  }


	BITSTORM-HP-160BportVlanRateLimitIfcIndex	OBJECT-TYPE
		SYNTAX			Unsigned32  ( 1 .. 219  )
		MAX-ACCESS		read-create
		STATUS			current
		DESCRIPTION		""
		::=  {  BITSTORM-HP-160BportVlanRateLimitEntry  5  }

	BITSTORM-HP-160BportVlanRateLimitRowStatus	OBJECT-TYPE
		SYNTAX			RowStatus
		MAX-ACCESS		read-create
		STATUS			current
		DESCRIPTION		""
		::=  {  BITSTORM-HP-160BportVlanRateLimitEntry  6  }








	BITSTORM-HP-160BportPortBcRateLimitTable	OBJECT-TYPE
		SYNTAX		SEQUENCE  OF  BITSTORM-HP-160BportPortBcRateLimitEntry
		MAX-ACCESS	not-accessible
		STATUS		current
		DESCRIPTION	""
		::=  { BITSTORM-HP-160CfgRateLimitGroup  6 }

	BITSTORM-HP-160BportPortBcRateLimitEntry	OBJECT-TYPE
		SYNTAX		BITSTORM-HP-160BportPortBcRateLimitEntry
		MAX-ACCESS	not-accessible
		STATUS		current
		DESCRIPTION	""
		INDEX		{  BITSTORM-HP-160bcRateBridgePortIfcIndex  }
		::=  { BITSTORM-HP-160BportPortBcRateLimitTable 1 }

	BITSTORM-HP-160BportPortBcRateLimitEntry  ::=  SEQUENCE {
		BITSTORM-HP-160bcRateBridgePortIfcIndex  Integer32,
		BITSTORM-HP-160bcRateLimitIngressIwPolicerIdx  Integer32
		}

	BITSTORM-HP-160bcRateBridgePortIfcIndex	OBJECT-TYPE
		SYNTAX			Integer32  ( 1 .. 219  )
		MAX-ACCESS		not-accessible
		STATUS			current
		DESCRIPTION		""
		::=  {  BITSTORM-HP-160BportPortBcRateLimitEntry  1  }


	BITSTORM-HP-160bcRateLimitIngressIwPolicerIdx	OBJECT-TYPE
		SYNTAX			Integer32  ( 1 .. 128  )
		MAX-ACCESS		read-write
		STATUS			current
		DESCRIPTION		""
		::=  {  BITSTORM-HP-160BportPortBcRateLimitEntry  2  }






--
	BITSTORM-HP-160BportVlanTranslationTable	OBJECT-TYPE
		SYNTAX		SEQUENCE  OF  BITSTORM-HP-160BportVlanTranslationEntry
		MAX-ACCESS	not-accessible
		STATUS		current
		DESCRIPTION	""
		::=  { BITSTORM-HP-160CfgVlanGroup  8 }

	BITSTORM-HP-160BportVlanTranslationEntry	OBJECT-TYPE
		SYNTAX		BITSTORM-HP-160BportVlanTranslationEntry
		MAX-ACCESS	not-accessible
		STATUS		current
		DESCRIPTION	""
		INDEX		{  BITSTORM-HP-160BportVlanTranslationIndex  }
		::=  { BITSTORM-HP-160BportVlanTranslationTable 1 }

	BITSTORM-HP-160BportVlanTranslationEntry  ::=  SEQUENCE {
		BITSTORM-HP-160BportVlanTranslationIndex  Integer32,        --1..512
		BITSTORM-HP-160BportVlanTranslationUserPort  Integer32,    --4..219
		BITSTORM-HP-160BportVlanTranslationUserVlanId  Integer32,   --1..4094
		BITSTORM-HP-160BportVlanTranslationUplinkPort  Integer32,   --1..3
		BITSTORM-HP-160BportVlanTranslationUplinkVlanId  Integer32,  --1..4094
		BITSTORM-HP-160BportVlanTranslationUplinkPriority  Integer32,  --0..7
		BITSTORM-HP-160BportVlanTranslationRowStatus  RowStatus
		}

	BITSTORM-HP-160BportVlanTranslationIndex	OBJECT-TYPE
		SYNTAX			Integer32  ( 1 .. 512  )
		MAX-ACCESS		not-accessible
		STATUS			current
		DESCRIPTION		""
		::=  {  BITSTORM-HP-160BportVlanTranslationEntry  1  }


	BITSTORM-HP-160BportVlanTranslationUserPort	OBJECT-TYPE
		SYNTAX			Integer32  ( 4 .. 219 )
		MAX-ACCESS		read-create
		STATUS			current
		DESCRIPTION		""
		::=  {  BITSTORM-HP-160BportVlanTranslationEntry  2  }


	BITSTORM-HP-160BportVlanTranslationUserVlanId	OBJECT-TYPE
		SYNTAX			Integer32  ( 1 .. 4094  )
		MAX-ACCESS		read-create
		STATUS			current
		DESCRIPTION		""
		::=  {  BITSTORM-HP-160BportVlanTranslationEntry  3  }

	BITSTORM-HP-160BportVlanTranslationUplinkPort	OBJECT-TYPE
		SYNTAX			Integer32  ( 1 .. 3  )
		MAX-ACCESS		read-create
		STATUS			current
		DESCRIPTION		""
		::=  {  BITSTORM-HP-160BportVlanTranslationEntry  4  }


	BITSTORM-HP-160BportVlanTranslationUplinkVlanId	OBJECT-TYPE
		SYNTAX			Integer32  ( 1 .. 4094  )
		MAX-ACCESS		read-create
		STATUS			current
		DESCRIPTION		""
		::=  {  BITSTORM-HP-160BportVlanTranslationEntry  5  }

	BITSTORM-HP-160BportVlanTranslationUplinkPriority	OBJECT-TYPE
		SYNTAX			Integer32  ( 0 .. 7  )
		MAX-ACCESS		read-create
		STATUS			current
		DESCRIPTION		""
		::=  {  BITSTORM-HP-160BportVlanTranslationEntry  6  }

	BITSTORM-HP-160BportVlanTranslationRowStatus	OBJECT-TYPE
		SYNTAX			RowStatus
		MAX-ACCESS		read-create
		STATUS			current
		DESCRIPTION		""
		::=  {  BITSTORM-HP-160BportVlanTranslationEntry  7  }
--

	BITSTORM-HP-160CfgBridgeTosVpmtFilterTable	OBJECT-TYPE
		SYNTAX		SEQUENCE  OF  BITSTORM-HP-160CfgBridgeTosVpmtFilterEntry
		MAX-ACCESS	not-accessible
		STATUS		current
		DESCRIPTION	"The TOS filter configuration table."
		::=  { BITSTORM-HP-160CfgVlanPriorityGroup  1 }

	BITSTORM-HP-160CfgBridgeTosVpmtFilterEntry	OBJECT-TYPE
		SYNTAX		BITSTORM-HP-160CfgBridgeTosVpmtFilterEntry
		MAX-ACCESS	not-accessible
		STATUS		current
		DESCRIPTION	"An Entry in the BITSTORM-HP-160CfgBridgeTosVpmtFilterTable"
		INDEX		{  BITSTORM-HP-160CfgBridgeTosVpmtFilterIndex  }
		::=  { BITSTORM-HP-160CfgBridgeTosVpmtFilterTable 1 }

	BITSTORM-HP-160CfgBridgeTosVpmtFilterEntry  ::=  SEQUENCE {
		BITSTORM-HP-160CfgBridgeTosVpmtFilterIndex  Integer32,
		BITSTORM-HP-160CfgBridgeTosVpmtFilterInputBridgePort  InterfaceIndex,
		BITSTORM-HP-160CfgBridgeTosVpmtFilterIncomingTos  Integer32,
		BITSTORM-HP-160CfgBridgeTosVpmtFilterOutgoingVlanPriority  Integer32,
		BITSTORM-HP-160CfgBridgeTosVpmtFilterRowStatus  RowStatus
		}


	BITSTORM-HP-160CfgBridgeTosVpmtFilterIndex	OBJECT-TYPE	
		SYNTAX			Integer32
		MAX-ACCESS		read-only
		STATUS			current
		DESCRIPTION		""
		::=  {  BITSTORM-HP-160CfgBridgeTosVpmtFilterEntry  1  }


	BITSTORM-HP-160CfgBridgeTosVpmtFilterInputBridgePort	OBJECT-TYPE	
		SYNTAX			InterfaceIndex
		MAX-ACCESS		read-create
		STATUS			current
		DESCRIPTION		""
		::=  {  BITSTORM-HP-160CfgBridgeTosVpmtFilterEntry  2  }


	BITSTORM-HP-160CfgBridgeTosVpmtFilterIncomingTos	OBJECT-TYPE	
		SYNTAX			Integer32  ( 0 .. 7  ) 
		MAX-ACCESS		read-create
		STATUS			current
		DESCRIPTION		""
		::=  {  BITSTORM-HP-160CfgBridgeTosVpmtFilterEntry  3  }


	BITSTORM-HP-160CfgBridgeTosVpmtFilterOutgoingVlanPriority	OBJECT-TYPE	
		SYNTAX			Integer32  ( 0 .. 7  ) 
		MAX-ACCESS		read-create
		STATUS			current
		DESCRIPTION		""
		::=  {  BITSTORM-HP-160CfgBridgeTosVpmtFilterEntry  4  }


	BITSTORM-HP-160CfgBridgeTosVpmtFilterRowStatus	OBJECT-TYPE	
		SYNTAX			RowStatus
		MAX-ACCESS		read-create
		STATUS			current
		DESCRIPTION		""
		::=  {  BITSTORM-HP-160CfgBridgeTosVpmtFilterEntry  5  }

	BITSTORM-HP-160CfgBridgeDSVpmtFilterTable	OBJECT-TYPE
		SYNTAX		SEQUENCE  OF  BITSTORM-HP-160CfgBridgeDSVpmtFilterEntry
		MAX-ACCESS	not-accessible
		STATUS		current
		DESCRIPTION	"The DS filter configuration table."
		::=  { BITSTORM-HP-160CfgVlanPriorityGroup  2 }

	BITSTORM-HP-160CfgBridgeDSVpmtFilterEntry	OBJECT-TYPE
		SYNTAX		BITSTORM-HP-160CfgBridgeDSVpmtFilterEntry
		MAX-ACCESS	not-accessible
		STATUS		current
		DESCRIPTION	"An Entry in the BITSTORM-HP-160CfgBridgeDSVpmtFilterTable"
		INDEX		{  BITSTORM-HP-160CfgBridgeDSVpmtFilterIndex  }
		::=  { BITSTORM-HP-160CfgBridgeDSVpmtFilterTable 1 }

	BITSTORM-HP-160CfgBridgeDSVpmtFilterEntry  ::=  SEQUENCE {
		BITSTORM-HP-160CfgBridgeDSVpmtFilterIndex  Integer32,
		BITSTORM-HP-160CfgBridgeDSVpmtFilterInputBridgePort  InterfaceIndex,
		BITSTORM-HP-160CfgBridgeDSVpmtFilterIncomingDS  Integer32,
		BITSTORM-HP-160CfgBridgeDSVpmtFilterOutgoingVlanPriority  Integer32,
		BITSTORM-HP-160CfgBridgeDSVpmtFilterRowStatus  RowStatus
		}


	BITSTORM-HP-160CfgBridgeDSVpmtFilterIndex	OBJECT-TYPE	
		SYNTAX			Integer32  (1..256)
		MAX-ACCESS		read-only
		STATUS			current
		DESCRIPTION		""
		::=  {  BITSTORM-HP-160CfgBridgeDSVpmtFilterEntry  1  }


	BITSTORM-HP-160CfgBridgeDSVpmtFilterInputBridgePort	OBJECT-TYPE
		SYNTAX			InterfaceIndex
		MAX-ACCESS		read-create
		STATUS			current
		DESCRIPTION		""
		::=  {  BITSTORM-HP-160CfgBridgeDSVpmtFilterEntry  2  }


	BITSTORM-HP-160CfgBridgeDSVpmtFilterIncomingDS	OBJECT-TYPE	
		SYNTAX			Integer32 {
                     DIFFSERV-DEFAULT(0),
                     DIFFSERV-AF11(10),
                     DIFFSERV-AF12(12),
                     DIFFSERV-AF13(14),
                     DIFFSERV-AF21(18),
                     DIFFSERV-AF22(20),
                     DIFFSERV-AF23(22),
                     DIFFSERV-AF31(26),
                     DIFFSERV-AF32(28),
                     DIFFSERV-AF33(30),
                     DIFFSERV-AF41(34),
                     DIFFSERV-AF42(36),
                     DIFFSERV-AF43(38),
                     DIFFSERV-EF(46)
                     }
		MAX-ACCESS		read-create
		STATUS			current
		DESCRIPTION		"
                     DIFFSERV-DEFAULT(0)
                     DIFFSERV-AF11(10)
                     DIFFSERV-AF12(12)
                     DIFFSERV-AF13(14)
                     DIFFSERV-AF21(18)
                     DIFFSERV-AF22(20)
                     DIFFSERV-AF23(22)
                     DIFFSERV-AF31(26)
                     DIFFSERV-AF32(28)
                     DIFFSERV-AF33(30)
                     DIFFSERV-AF41(34)
                     DIFFSERV-AF42(36)
                     DIFFSERV-AF43(38)
                     DIFFSERV-EF(46)
		"
		::=  {  BITSTORM-HP-160CfgBridgeDSVpmtFilterEntry  3  }


	BITSTORM-HP-160CfgBridgeDSVpmtFilterOutgoingVlanPriority	OBJECT-TYPE	
		SYNTAX			Integer32  ( 0 .. 7  ) 
		MAX-ACCESS		read-create
		STATUS			current
		DESCRIPTION		""
		::=  {  BITSTORM-HP-160CfgBridgeDSVpmtFilterEntry  4  }


	BITSTORM-HP-160CfgBridgeDSVpmtFilterRowStatus	OBJECT-TYPE	
		SYNTAX			RowStatus
		MAX-ACCESS		read-create
		STATUS			current
		DESCRIPTION		""
		::=  {  BITSTORM-HP-160CfgBridgeDSVpmtFilterEntry  5  }

	BITSTORM-HP-160CfgBridgeIpSrcVpmtFilterTable	OBJECT-TYPE
		SYNTAX		SEQUENCE  OF  BITSTORM-HP-160CfgBridgeIpSrcVpmtFilterEntry
		MAX-ACCESS	not-accessible
		STATUS		current
		DESCRIPTION	"The IP src filter configuration table."
		::=  { BITSTORM-HP-160CfgVlanPriorityGroup  3 }

	BITSTORM-HP-160CfgBridgeIpSrcVpmtFilterEntry	OBJECT-TYPE
		SYNTAX		BITSTORM-HP-160CfgBridgeIpSrcVpmtFilterEntry
		MAX-ACCESS	not-accessible
		STATUS		current
		DESCRIPTION	"An Entry in the BITSTORM-HP-160CfgBridgeIpSrcVpmtFilterTable"
		INDEX		{  BITSTORM-HP-160CfgBridgeIpSrcVpmtFilterIndex  }
		::=  { BITSTORM-HP-160CfgBridgeIpSrcVpmtFilterTable 1 }

	BITSTORM-HP-160CfgBridgeIpSrcVpmtFilterEntry  ::=  SEQUENCE {
		BITSTORM-HP-160CfgBridgeIpSrcVpmtFilterIndex  Integer32,
		BITSTORM-HP-160CfgBridgeIpSrcVpmtFilterInputBridgePort  InterfaceIndex,
		BITSTORM-HP-160CfgBridgeIpSrcVpmtFilterIncomingIpsrcstart  IpAddress,
		BITSTORM-HP-160CfgBridgeIpSrcVpmtFilterIncomingIpsrcend  IpAddress,
		BITSTORM-HP-160CfgBridgeIpSrcVpmtFilterOutgoingVlanPriority  Integer32,
		BITSTORM-HP-160CfgBridgeIpSrcVpmtFilterRowStatus  RowStatus
		}


	BITSTORM-HP-160CfgBridgeIpSrcVpmtFilterIndex	OBJECT-TYPE	
		SYNTAX			Integer32
		MAX-ACCESS		read-only
		STATUS			current
		DESCRIPTION		""
		::=  {  BITSTORM-HP-160CfgBridgeIpSrcVpmtFilterEntry  1  }


	BITSTORM-HP-160CfgBridgeIpSrcVpmtFilterInputBridgePort	OBJECT-TYPE	
		SYNTAX			InterfaceIndex
		MAX-ACCESS		read-create
		STATUS			current
		DESCRIPTION		""
		::=  {  BITSTORM-HP-160CfgBridgeIpSrcVpmtFilterEntry  2  }


	BITSTORM-HP-160CfgBridgeIpSrcVpmtFilterIncomingIpsrcstart	OBJECT-TYPE	
		SYNTAX			IpAddress
		MAX-ACCESS		read-create
		STATUS			current
		DESCRIPTION		""
		::=  {  BITSTORM-HP-160CfgBridgeIpSrcVpmtFilterEntry  3  }


	BITSTORM-HP-160CfgBridgeIpSrcVpmtFilterIncomingIpsrcend	OBJECT-TYPE	
		SYNTAX			IpAddress
		MAX-ACCESS		read-create
		STATUS			current
		DESCRIPTION		""
		::=  {  BITSTORM-HP-160CfgBridgeIpSrcVpmtFilterEntry  4  }


	BITSTORM-HP-160CfgBridgeIpSrcVpmtFilterOutgoingVlanPriority	OBJECT-TYPE	
		SYNTAX			Integer32  ( 0 .. 7  ) 
		MAX-ACCESS		read-create
		STATUS			current
		DESCRIPTION		""
		::=  {  BITSTORM-HP-160CfgBridgeIpSrcVpmtFilterEntry  5  }


	BITSTORM-HP-160CfgBridgeIpSrcVpmtFilterRowStatus	OBJECT-TYPE	
		SYNTAX			RowStatus
		MAX-ACCESS		read-create
		STATUS			current
		DESCRIPTION		""
		::=  {  BITSTORM-HP-160CfgBridgeIpSrcVpmtFilterEntry  6  }

	BITSTORM-HP-160CfgBridgeIpDstVpmtFilterTable	OBJECT-TYPE
		SYNTAX		SEQUENCE  OF  BITSTORM-HP-160CfgBridgeIpDstVpmtFilterEntry
		MAX-ACCESS	not-accessible
		STATUS		current
		DESCRIPTION	"The IP dst filter configuration table."
		::=  { BITSTORM-HP-160CfgVlanPriorityGroup  4 }

	BITSTORM-HP-160CfgBridgeIpDstVpmtFilterEntry	OBJECT-TYPE
		SYNTAX		BITSTORM-HP-160CfgBridgeIpDstVpmtFilterEntry
		MAX-ACCESS	not-accessible
		STATUS		current
		DESCRIPTION	"An Entry in the BITSTORM-HP-160CfgBridgeIpDstVpmtFilterTable"
		INDEX		{  BITSTORM-HP-160CfgBridgeIpDstVpmtFilterIndex  }
		::=  { BITSTORM-HP-160CfgBridgeIpDstVpmtFilterTable 1 }

	BITSTORM-HP-160CfgBridgeIpDstVpmtFilterEntry  ::=  SEQUENCE {
		BITSTORM-HP-160CfgBridgeIpDstVpmtFilterIndex  Integer32,
		BITSTORM-HP-160CfgBridgeIpDstVpmtFilterInputBridgePort  InterfaceIndex,
		BITSTORM-HP-160CfgBridgeIpDstVpmtFilterIncomingIpDststart  IpAddress,
		BITSTORM-HP-160CfgBridgeIpDstVpmtFilterIncomingIpDstend  IpAddress,
		BITSTORM-HP-160CfgBridgeIpDstVpmtFilterOutgoingVlanPriority  Integer32,
		BITSTORM-HP-160CfgBridgeIpDstVpmtFilterRowStatus  RowStatus
		}


	BITSTORM-HP-160CfgBridgeIpDstVpmtFilterIndex	OBJECT-TYPE	
		SYNTAX			Integer32
		MAX-ACCESS		read-only
		STATUS			current
		DESCRIPTION		""
		::=  {  BITSTORM-HP-160CfgBridgeIpDstVpmtFilterEntry  1  }


	BITSTORM-HP-160CfgBridgeIpDstVpmtFilterInputBridgePort	OBJECT-TYPE	
		SYNTAX			InterfaceIndex
		MAX-ACCESS		read-create
		STATUS			current
		DESCRIPTION		""
		::=  {  BITSTORM-HP-160CfgBridgeIpDstVpmtFilterEntry  2  }


	BITSTORM-HP-160CfgBridgeIpDstVpmtFilterIncomingIpDststart	OBJECT-TYPE	
		SYNTAX			IpAddress
		MAX-ACCESS		read-create
		STATUS			current
		DESCRIPTION		""
		::=  {  BITSTORM-HP-160CfgBridgeIpDstVpmtFilterEntry  3  }


	BITSTORM-HP-160CfgBridgeIpDstVpmtFilterIncomingIpDstend	OBJECT-TYPE	
		SYNTAX			IpAddress
		MAX-ACCESS		read-create
		STATUS			current
		DESCRIPTION		""
		::=  {  BITSTORM-HP-160CfgBridgeIpDstVpmtFilterEntry  4  }


	BITSTORM-HP-160CfgBridgeIpDstVpmtFilterOutgoingVlanPriority	OBJECT-TYPE	
		SYNTAX			Integer32  ( 0 .. 7  ) 
		MAX-ACCESS		read-create
		STATUS			current
		DESCRIPTION		""
		::=  {  BITSTORM-HP-160CfgBridgeIpDstVpmtFilterEntry  5  }


	BITSTORM-HP-160CfgBridgeIpDstVpmtFilterRowStatus	OBJECT-TYPE	
		SYNTAX			RowStatus
		MAX-ACCESS		read-create
		STATUS			current
		DESCRIPTION		""
		::=  {  BITSTORM-HP-160CfgBridgeIpDstVpmtFilterEntry  6  }

	BITSTORM-HP-160CfgBridgeMacSrcVpmtFilterTable	OBJECT-TYPE
		SYNTAX		SEQUENCE  OF  BITSTORM-HP-160CfgBridgeMacSrcVpmtFilterEntry
		MAX-ACCESS	not-accessible
		STATUS		current
		DESCRIPTION	"The MAC src filter configuration table."
		::=  { BITSTORM-HP-160CfgVlanPriorityGroup  5 }

	BITSTORM-HP-160CfgBridgeMacSrcVpmtFilterEntry	OBJECT-TYPE
		SYNTAX		BITSTORM-HP-160CfgBridgeMacSrcVpmtFilterEntry
		MAX-ACCESS	not-accessible
		STATUS		current
		DESCRIPTION	"An Entry in the BITSTORM-HP-160CfgBridgeMacSrcVpmtFilterTable"
		INDEX		{  BITSTORM-HP-160CfgBridgeMacSrcVpmtFilterIndex  }
		::=  { BITSTORM-HP-160CfgBridgeMacSrcVpmtFilterTable 1 }

	BITSTORM-HP-160CfgBridgeMacSrcVpmtFilterEntry  ::=  SEQUENCE {
		BITSTORM-HP-160CfgBridgeMacSrcVpmtFilterIndex  Integer32,
		BITSTORM-HP-160CfgBridgeMacSrcVpmtFilterInputBridgePort  InterfaceIndex,
		BITSTORM-HP-160CfgBridgeMacSrcVpmtFilterIncomingMacsrc  PhysAddress,
		BITSTORM-HP-160CfgBridgeMacSrcVpmtFilterOutgoingVlanPriority  Integer32,
		BITSTORM-HP-160CfgBridgeMacSrcVpmtFilterRowStatus  RowStatus
		}


	BITSTORM-HP-160CfgBridgeMacSrcVpmtFilterIndex	OBJECT-TYPE	
		SYNTAX			Integer32
		MAX-ACCESS		read-only
		STATUS			current
		DESCRIPTION		""
		::=  {  BITSTORM-HP-160CfgBridgeMacSrcVpmtFilterEntry  1  }


	BITSTORM-HP-160CfgBridgeMacSrcVpmtFilterInputBridgePort	OBJECT-TYPE	
		SYNTAX			InterfaceIndex
		MAX-ACCESS		read-create
		STATUS			current
		DESCRIPTION		""
		::=  {  BITSTORM-HP-160CfgBridgeMacSrcVpmtFilterEntry  2  }


	BITSTORM-HP-160CfgBridgeMacSrcVpmtFilterIncomingMacsrc	OBJECT-TYPE	
		SYNTAX			PhysAddress
		MAX-ACCESS		read-create
		STATUS			current
		DESCRIPTION		""
		::=  {  BITSTORM-HP-160CfgBridgeMacSrcVpmtFilterEntry  3  }


	BITSTORM-HP-160CfgBridgeMacSrcVpmtFilterOutgoingVlanPriority	OBJECT-TYPE	
		SYNTAX			Integer32  ( 0 .. 7  ) 
		MAX-ACCESS		read-create
		STATUS			current
		DESCRIPTION		""
		::=  {  BITSTORM-HP-160CfgBridgeMacSrcVpmtFilterEntry  4  }


	BITSTORM-HP-160CfgBridgeMacSrcVpmtFilterRowStatus	OBJECT-TYPE	
		SYNTAX			RowStatus
		MAX-ACCESS		read-create
		STATUS			current
		DESCRIPTION		""
		::=  {  BITSTORM-HP-160CfgBridgeMacSrcVpmtFilterEntry  5  }

	BITSTORM-HP-160CfgBridgeMacDstVpmtFilterTable	OBJECT-TYPE
		SYNTAX		SEQUENCE  OF  BITSTORM-HP-160CfgBridgeMacDstVpmtFilterEntry
		MAX-ACCESS	not-accessible
		STATUS		current
		DESCRIPTION	"The MAC dst filter configuration table."
		::=  { BITSTORM-HP-160CfgVlanPriorityGroup  6 }

	BITSTORM-HP-160CfgBridgeMacDstVpmtFilterEntry	OBJECT-TYPE
		SYNTAX		BITSTORM-HP-160CfgBridgeMacDstVpmtFilterEntry
		MAX-ACCESS	not-accessible
		STATUS		current
		DESCRIPTION	"An Entry in the BITSTORM-HP-160CfgBridgeMacDstVpmtFilterTable"
		INDEX		{  BITSTORM-HP-160CfgBridgeMacDstVpmtFilterIndex  }
		::=  { BITSTORM-HP-160CfgBridgeMacDstVpmtFilterTable 1 }

	BITSTORM-HP-160CfgBridgeMacDstVpmtFilterEntry  ::=  SEQUENCE {
		BITSTORM-HP-160CfgBridgeMacDstVpmtFilterIndex  Integer32,
		BITSTORM-HP-160CfgBridgeMacDstVpmtFilterInputBridgePort  InterfaceIndex,
		BITSTORM-HP-160CfgBridgeMacDstVpmtFilterIncomingMacDst  PhysAddress,
		BITSTORM-HP-160CfgBridgeMacDstVpmtFilterOutgoingVlanPriority  Integer32,
		BITSTORM-HP-160CfgBridgeMacDstVpmtFilterRowStatus  RowStatus
		}


	BITSTORM-HP-160CfgBridgeMacDstVpmtFilterIndex	OBJECT-TYPE	
		SYNTAX			Integer32
		MAX-ACCESS		read-only
		STATUS			current
		DESCRIPTION		""
		::=  {  BITSTORM-HP-160CfgBridgeMacDstVpmtFilterEntry  1  }


	BITSTORM-HP-160CfgBridgeMacDstVpmtFilterInputBridgePort	OBJECT-TYPE	
		SYNTAX			InterfaceIndex
		MAX-ACCESS		read-create
		STATUS			current
		DESCRIPTION		""
		::=  {  BITSTORM-HP-160CfgBridgeMacDstVpmtFilterEntry  2  }


	BITSTORM-HP-160CfgBridgeMacDstVpmtFilterIncomingMacDst	OBJECT-TYPE	
		SYNTAX			PhysAddress
		MAX-ACCESS		read-create
		STATUS			current
		DESCRIPTION		""
		::=  {  BITSTORM-HP-160CfgBridgeMacDstVpmtFilterEntry  3  }


	BITSTORM-HP-160CfgBridgeMacDstVpmtFilterOutgoingVlanPriority	OBJECT-TYPE	
		SYNTAX			Integer32  ( 0 .. 7  ) 
		MAX-ACCESS		read-create
		STATUS			current
		DESCRIPTION		""
		::=  {  BITSTORM-HP-160CfgBridgeMacDstVpmtFilterEntry  4  }


	BITSTORM-HP-160CfgBridgeMacDstVpmtFilterRowStatus	OBJECT-TYPE	
		SYNTAX			RowStatus
		MAX-ACCESS		read-create
		STATUS			current
		DESCRIPTION		""
		::=  {  BITSTORM-HP-160CfgBridgeMacDstVpmtFilterEntry  5  }

	BITSTORM-HP-160CfgBridgeVlanIdVpmtFilterTable	OBJECT-TYPE
		SYNTAX		SEQUENCE  OF  BITSTORM-HP-160CfgBridgeVlanIdVpmtFilterEntry
		MAX-ACCESS	not-accessible
		STATUS		current
		DESCRIPTION	"The Vlan ID filter configuration table."
		::=  { BITSTORM-HP-160CfgVlanPriorityGroup  7 }

	BITSTORM-HP-160CfgBridgeVlanIdVpmtFilterEntry	OBJECT-TYPE
		SYNTAX		BITSTORM-HP-160CfgBridgeVlanIdVpmtFilterEntry
		MAX-ACCESS	not-accessible
		STATUS		current
		DESCRIPTION	"An Entry in the BITSTORM-HP-160CfgBridgeVlanIdVpmtFilterTable"
		INDEX		{  BITSTORM-HP-160CfgBridgeVlanIdVpmtFilterIndex  }
		::=  { BITSTORM-HP-160CfgBridgeVlanIdVpmtFilterTable 1 }

	BITSTORM-HP-160CfgBridgeVlanIdVpmtFilterEntry  ::=  SEQUENCE {
		BITSTORM-HP-160CfgBridgeVlanIdVpmtFilterIndex  Integer32,
		BITSTORM-HP-160CfgBridgeVlanIdVpmtFilterInputBridgePort  InterfaceIndex,
		BITSTORM-HP-160CfgBridgeVlanIdVpmtFilterIncomingVlanid  Integer32,
		BITSTORM-HP-160CfgBridgeVlanIdVpmtFilterOutgoingVlanPriority  Integer32,
		BITSTORM-HP-160CfgBridgeVlanIdVpmtFilterRowStatus  RowStatus
		}


	BITSTORM-HP-160CfgBridgeVlanIdVpmtFilterIndex	OBJECT-TYPE	
		SYNTAX			Integer32
		MAX-ACCESS		read-only
		STATUS			current
		DESCRIPTION		""
		::=  {  BITSTORM-HP-160CfgBridgeVlanIdVpmtFilterEntry  1  }


	BITSTORM-HP-160CfgBridgeVlanIdVpmtFilterInputBridgePort	OBJECT-TYPE	
		SYNTAX			InterfaceIndex
		MAX-ACCESS		read-create
		STATUS			current
		DESCRIPTION		""
		::=  {  BITSTORM-HP-160CfgBridgeVlanIdVpmtFilterEntry  2  }


	BITSTORM-HP-160CfgBridgeVlanIdVpmtFilterIncomingVlanid	OBJECT-TYPE	
		SYNTAX			Integer32  ( 0 .. 4094  )   --960803 
		MAX-ACCESS		read-create
		STATUS			current
		DESCRIPTION		""
		::=  {  BITSTORM-HP-160CfgBridgeVlanIdVpmtFilterEntry  3  }


	BITSTORM-HP-160CfgBridgeVlanIdVpmtFilterOutgoingVlanPriority	OBJECT-TYPE	
		SYNTAX			Integer32  ( 0 .. 7  ) 
		MAX-ACCESS		read-create
		STATUS			current
		DESCRIPTION		""
		::=  {  BITSTORM-HP-160CfgBridgeVlanIdVpmtFilterEntry  4  }


	BITSTORM-HP-160CfgBridgeVlanIdVpmtFilterRowStatus	OBJECT-TYPE	
		SYNTAX			RowStatus
		MAX-ACCESS		read-create
		STATUS			current
		DESCRIPTION		""
		::=  {  BITSTORM-HP-160CfgBridgeVlanIdVpmtFilterEntry  5  }
		
		
		
		
		
	BITSTORM-HP-160CfgBridgePrioTagFilterTable	OBJECT-TYPE
		SYNTAX		SEQUENCE  OF  BITSTORM-HP-160CfgBridgePrioTagFilterEntry
		MAX-ACCESS	not-accessible
		STATUS		current
		DESCRIPTION	""
		::=  { BITSTORM-HP-160CfgVlanPriorityGroup  8 }

	BITSTORM-HP-160CfgBridgePrioTagFilterEntry	OBJECT-TYPE
		SYNTAX		BITSTORM-HP-160CfgBridgePrioTagFilterEntry
		MAX-ACCESS	not-accessible
		STATUS		current
		DESCRIPTION	""
		INDEX		{  BITSTORM-HP-160BridgePrioTagFilterIndex  }
		::=  { BITSTORM-HP-160CfgBridgePrioTagFilterTable 1 }

	BITSTORM-HP-160CfgBridgePrioTagFilterEntry  ::=  SEQUENCE {
		BITSTORM-HP-160BridgePrioTagFilterIndex  Integer32,
		BITSTORM-HP-160BridgePrioTagInputBridgePort  InterfaceIndex,
		BITSTORM-HP-160BridgePrioTagOutgoingVlanPriority  Integer32,
		BITSTORM-HP-160BridgePrioTagIncomingVlanPriority  Integer32,
		BITSTORM-HP-160BridgePrioTagFilterRowStatus  RowStatus
		}


	BITSTORM-HP-160BridgePrioTagFilterIndex	OBJECT-TYPE	
		SYNTAX			Integer32  ( 1 .. 4095  ) 
		MAX-ACCESS		read-only
		STATUS			current
		DESCRIPTION		""
		::=  {  BITSTORM-HP-160CfgBridgePrioTagFilterEntry  1  }


	BITSTORM-HP-160BridgePrioTagInputBridgePort	OBJECT-TYPE	
		SYNTAX			InterfaceIndex
		MAX-ACCESS		read-create
		STATUS			current
		DESCRIPTION		""
		::=  {  BITSTORM-HP-160CfgBridgePrioTagFilterEntry  2  }


	BITSTORM-HP-160BridgePrioTagOutgoingVlanPriority	OBJECT-TYPE	
		SYNTAX			Integer32  ( 0 .. 7  ) 
		MAX-ACCESS		read-create
		STATUS			current
		DESCRIPTION		""
		DEFVAL			{ 0 }
		::=  {  BITSTORM-HP-160CfgBridgePrioTagFilterEntry  3  }


	BITSTORM-HP-160BridgePrioTagIncomingVlanPriority	OBJECT-TYPE	
		SYNTAX			Integer32  ( 0 .. 7  ) 
		MAX-ACCESS		read-create
		STATUS			current
		DESCRIPTION		""
		DEFVAL			{ 0 }
		::=  {  BITSTORM-HP-160CfgBridgePrioTagFilterEntry  4  }


	BITSTORM-HP-160BridgePrioTagFilterRowStatus	OBJECT-TYPE	
		SYNTAX			RowStatus
		MAX-ACCESS		read-create
		STATUS			current
		DESCRIPTION		""
		DEFVAL			{ createAndGo }
		::=  {  BITSTORM-HP-160CfgBridgePrioTagFilterEntry  5  }



		

	BITSTORM-HP-160CfgIgmpSourceGroupIp	OBJECT-TYPE
		SYNTAX			IpAddress
		MAX-ACCESS		read-write
		STATUS			current
		DESCRIPTION		""
		::=  {  BITSTORM-HP-160CfgIgmpSource  1  }

	BITSTORM-HP-160CfgIgmpSourceGroupVlan	OBJECT-TYPE	
		SYNTAX			Integer32  ( 1 .. 4094  )   --960803
		MAX-ACCESS		read-write
		STATUS			current
		DESCRIPTION		""
		::=  {  BITSTORM-HP-160CfgIgmpSource  2  }




	BITSTORM-HP-160TrapAlmSystemHousekeep1	NOTIFICATION-TYPE
		STATUS			current
		DESCRIPTION		"DSLAM system housekeeping1 trap."
		::=  {  BITSTORM-HP-160SystemAlarmTrap  1  }

	BITSTORM-HP-160TrapAlmSystemHousekeep2	NOTIFICATION-TYPE
		STATUS			current
		DESCRIPTION		"DSLAM system housekeeping2 trap."
		::=  {  BITSTORM-HP-160SystemAlarmTrap  2  }

	BITSTORM-HP-160TrapAlmSystemHousekeep3	NOTIFICATION-TYPE
		STATUS			current
		DESCRIPTION		"DSLAM system housekeeping3 trap."
		::=  {  BITSTORM-HP-160SystemAlarmTrap  3  }

	BITSTORM-HP-160TrapAlmSystemHousekeep4	NOTIFICATION-TYPE
		STATUS			current
		DESCRIPTION		"DSLAM system housekeeping4 trap."
		::=  {  BITSTORM-HP-160SystemAlarmTrap  4  }

	BITSTORM-HP-160TrapAlmSystemFanFailure	NOTIFICATION-TYPE
		STATUS			current
		DESCRIPTION		"DSLAM fan failure alarm trap."
		::=  {  BITSTORM-HP-160SystemAlarmTrap  5  }

	BITSTORM-HP-160TrapAlmSystemSelfTestTestFail	NOTIFICATION-TYPE
		STATUS			current
		DESCRIPTION		"DSLAM system module test fail trap."
		::=  {  BITSTORM-HP-160SystemAlarmTrap  6  }

	BITSTORM-HP-160TrapAlmSystemAboveTemperature	NOTIFICATION-TYPE
		STATUS			current
		DESCRIPTION		"The current temperature exceeds BITSTORM-HP-160SysTemperatureUpShfThreshold."
		::=  {  BITSTORM-HP-160SystemAlarmTrap  7  }

	BITSTORM-HP-160TrapAlmSystemBelowTemperature	NOTIFICATION-TYPE
		STATUS			current
		DESCRIPTION		"The current temperature descends below to BITSTORM-HP-160SysTemperatureDwShfThreshold."
		::=  {  BITSTORM-HP-160SystemAlarmTrap  8  }


BITSTORM-HP-160TrapAlmVdslLOF   NOTIFICATION-TYPE
    OBJECTS {
                ifIndex
            }
    STATUS             current
    DESCRIPTION  "Loss of frame of the DSLAM VDSL interface."
   ::= { BITSTORM-HP-160VDSLAlarmTrap 1 }

BITSTORM-HP-160TrapAlmVdslLOS   NOTIFICATION-TYPE
    OBJECTS {
                ifIndex
            }
    STATUS             current
    DESCRIPTION  "Loss of signal of the DSLAM VDSL interface."
   ::= { BITSTORM-HP-160VDSLAlarmTrap 2 }

BITSTORM-HP-160TrapAlmVdslLOSQ   NOTIFICATION-TYPE
    OBJECTS {
                ifIndex
            }
    STATUS             current
    DESCRIPTION  "Loss of signal quality of the DSLAM VDSL interface."
   ::= { BITSTORM-HP-160VDSLAlarmTrap 3 }

BITSTORM-HP-160TrapAlmVdslLOL   NOTIFICATION-TYPE
    OBJECTS {
                ifIndex
            }
    STATUS             current
    DESCRIPTION  "Loss of link of the DSLAM VDSL interface."
   ::= { BITSTORM-HP-160VDSLAlarmTrap 4 }

BITSTORM-HP-160TrapAlmVdslInitFailure   NOTIFICATION-TYPE
    OBJECTS {
                ifIndex
            }
    STATUS             current
    DESCRIPTION  "VDSL Init Failure."
   ::= { BITSTORM-HP-160VDSLAlarmTrap 5 }



BITSTORM-HP-160TrapAlmVdslESE   NOTIFICATION-TYPE
    OBJECTS {
                ifIndex
            }
    STATUS             current
    DESCRIPTION  "VDSL Excessive Severely Errored Seconds of the VDSL interface."
   ::= { BITSTORM-HP-160VDSLAlarmTrap 8 }

BITSTORM-HP-160TrapAlmVdslNCDSlow   NOTIFICATION-TYPE
    OBJECTS {
                ifIndex
            }
    STATUS             current
    DESCRIPTION  "VDSL No Cell Delination on the slow channel"
   ::= { BITSTORM-HP-160VDSLAlarmTrap 9 }

BITSTORM-HP-160TrapAlmVdslLCDSlow   NOTIFICATION-TYPE
    OBJECTS {
                ifIndex
            }
    STATUS             current
    DESCRIPTION  "VDSL Loss of Cell Delination on the slow channel"
   ::= { BITSTORM-HP-160VDSLAlarmTrap 10 }
   
BITSTORM-HP-160TrapAlmVdslNCDFast   NOTIFICATION-TYPE
    OBJECTS {
                ifIndex
            }
    STATUS             current
    DESCRIPTION  "VDSL No Cell Delination on the fast channel"
   ::= { BITSTORM-HP-160VDSLAlarmTrap 11 }

BITSTORM-HP-160TrapAlmVdslLCDFast   NOTIFICATION-TYPE
    OBJECTS {
                ifIndex
            }
    STATUS             current
    DESCRIPTION  "VDSL Loss of Cell Delination on the fast channel"
   ::= { BITSTORM-HP-160VDSLAlarmTrap 12 }

BITSTORM-HP-160TrapAlmVdslLOFFE   NOTIFICATION-TYPE
    OBJECTS {
                ifIndex
            }
    STATUS             current
    DESCRIPTION  "Loss of frame in the downstream direction."
   ::= { BITSTORM-HP-160VDSLAlarmTrap 13 }

BITSTORM-HP-160TrapAlmVdslLOSFE   NOTIFICATION-TYPE
    OBJECTS {
                ifIndex
            }
    STATUS             current
    DESCRIPTION  "Loss of signal in the downstream direction."
   ::= { BITSTORM-HP-160VDSLAlarmTrap 14 }

BITSTORM-HP-160TrapAlmVdslLPRFE   NOTIFICATION-TYPE
    OBJECTS {
                ifIndex
            }
    STATUS             current
    DESCRIPTION  "Loss of power in the downstream direction."
   ::= { BITSTORM-HP-160VDSLAlarmTrap 15 }

BITSTORM-HP-160TrapAlmVdslLOSQFE   NOTIFICATION-TYPE
    OBJECTS {
                ifIndex
            }
    STATUS             current
    DESCRIPTION  "Loss of signal quality in the downstream direction."
   ::= { BITSTORM-HP-160VDSLAlarmTrap 16 }

BITSTORM-HP-160TrapAlmVdslNoPeerVtuPresentFE   NOTIFICATION-TYPE
    OBJECTS {
                ifIndex
            }
    STATUS             current
    DESCRIPTION  "VDSL No Peer Vtu Present in the downstream direction."
   ::= { BITSTORM-HP-160VDSLAlarmTrap 17 }

BITSTORM-HP-160TrapAlmVdslESEFE   NOTIFICATION-TYPE
    OBJECTS {
                ifIndex
            }
    STATUS             current
    DESCRIPTION  "VDSL Excessive Severely Errored Seconds in the downstream direction."
   ::= { BITSTORM-HP-160VDSLAlarmTrap 18 }

BITSTORM-HP-160TrapAlmVdslNCDSlowFE   NOTIFICATION-TYPE
    OBJECTS {
                ifIndex
            }
    STATUS             current
    DESCRIPTION  "VDSL FE No Cell Delination on the slow channel"
   ::= { BITSTORM-HP-160VDSLAlarmTrap 19 }

BITSTORM-HP-160TrapAlmVdslLCDSlowFE   NOTIFICATION-TYPE
    OBJECTS {
                ifIndex
            }
    STATUS             current
    DESCRIPTION  "VDSL FE Loss of Cell Delination on the slow channel"
   ::= { BITSTORM-HP-160VDSLAlarmTrap 20 }
   
BITSTORM-HP-160TrapAlmVdslNCDFastFE   NOTIFICATION-TYPE
    OBJECTS {
                ifIndex
            }
    STATUS             current
    DESCRIPTION  "VDSL FE No Cell Delination on the fast channel"
   ::= { BITSTORM-HP-160VDSLAlarmTrap 21 }

BITSTORM-HP-160TrapAlmVdslLCDFastFE   NOTIFICATION-TYPE
    OBJECTS {
                ifIndex
            }
    STATUS             current
    DESCRIPTION  "VDSL FE Loss of Cell Delination on the fast channel"
   ::= { BITSTORM-HP-160VDSLAlarmTrap 22 }


END
