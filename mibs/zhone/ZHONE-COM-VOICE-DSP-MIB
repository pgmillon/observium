--
-- comVoiceDsp.mib
-- MIB generated by MG-SOFT Visual MIB Builder Version 3.0 Build 271
-- Friday, March 28, 2003 at 10:46:25
--

        ZHONE-COM-VOICE-DSP-MIB DEFINITIONS ::= BEGIN
 
                IMPORTS
                        TimeTicks, Integer32, Unsigned32, Counter32, OBJECT-TYPE, 
                        MODULE-IDENTITY, OBJECT-IDENTITY, NOTIFICATION-TYPE                        
                                FROM SNMPv2-SMI                        
                        zhoneVoice, zhoneShelfIndex, zhoneSlotIndex, zhoneModules, zhoneShelfIndex, 
                        zhoneSlotIndex                        
                                FROM Zhone                        
                        ZhoneShelfValue, ZhoneSlotValue                        
                                FROM Zhone-TC;
        
        
-- profile for objects under voiceDspDefaultConfiguration
-- 
-- 
-- statistic profile for voiceDspStatusTable
-- 
-- 
-- statistic profile for channelStatusTable
-- 
-- 
-- 
                comVoiceDsp MODULE-IDENTITY 
                        LAST-UPDATED "200303281935Z"		-- March 28, 2003 at 19:35 GMT
                        ORGANIZATION 
                                "Zhone Technologies, Inc."
                        CONTACT-INFO 
                                "  Postal: 
                                           Zhone Technologies, Inc.
                                           @ Zhone Way
                                           7001 Oakport Street
                                           Oakland, CA  94621
                                           USA
                                Toll-Free: +1 877-ZHONE20 (+1 877-946-6320)
                                      Tel: +1-510-777-7000
                                      Fax: +1-510-777-7001
                                   E-mail: support@zhone.com"
                        DESCRIPTION 
                                "Voice DSP MIB for Voice Application Specific 
                                Processing cards."
                        REVISION "200303281042Z"		-- March 28, 2003 at 10:42 GMT
                        DESCRIPTION
                                "V01.00.04 - Add echoReturnLoss object."
                        REVISION "200302131935Z"		-- February 13, 2003 at 19:35 GMT
                        DESCRIPTION
                                "V01.00.03 - Made changes in the description of the following objects:
                                 jitterBufferType: dynamic is supported in VoIP only,
                                                   static is supported in both VoATM and VoIP.
                                 jitterBufferSize: Changed the range.
                                Both objects are supported on BAN, S100 and ZEdge.
                                MALC support is not complete yet.
                                 echo-cancellation-type: Identified the ones supported.
                                 silence-supression-type: Identified the ones supported, and swapped
                                 the descriptions of silsuponsidon and silsuponsidconst."
                        REVISION "200110021834Z"		-- October 02, 2001 at 18:34 GMT
                        DESCRIPTION
                                "V01.00.02 - Made changes in the description of the following objects:
                                  redundancyOverSubscriptionType: Supported only on BAN with VASP card(s)
                                  jitterBufferSize: Not supported.
                                  interArrvJitThreshold: Not Supported
                                  pktsLostThreshold: Not Supported"
                        REVISION "200011281356Z"		-- November 28, 2000 at 13:56 GMT
                        DESCRIPTION
                                "V01.00.01 - Corrected MIB import problem for zhoneVoice
                                for the MG-Soft bui file."
                        REVISION "200009201842Z"		-- September 20, 2000 at 18:42 GMT
                        DESCRIPTION
                                "V01.00.00 - Initial Release"
                        ::= { zhoneModules 12 }
                
        
        
--
-- Node definitions
--
        
-- Voice DSP MIB definition
-- 
-- Copyright (C) 2000 by Zhone Technologies, Inc.
-- All rights reserved.
-- 
-- Comments to: <support@zhone.com>
-- Web URL: <http://www.zhone.com>
-- 
-- 
                -- 1.3.6.1.4.1.5504.4.3.3
                zhoneVoiceDsp OBJECT-IDENTITY
                        STATUS current
                        DESCRIPTION 
                                "The MIB module to describe managed objects for Zhone's
                                voice DSP applications.
                                
                                The Voice DSP MIB has the following components:
                                * voiceDspDefaultConfiguration
                                * voiceDspStatusTable
                                * channelStatusTable
                                * voiceDspTraps"
                        ::= { zhoneVoice 3 }
                
                -- 1.3.6.1.4.1.5504.4.3.3.1
                voiceDspDefaultConfiguration OBJECT-IDENTITY
                        STATUS current
                        DESCRIPTION 
                                "System-wide defaults for voice DSP variables. These
                                values will be used by voice DSP to set up default
                                values to be used per call."
                        ::= { zhoneVoiceDsp 1 }
                
-- 
                -- 1.3.6.1.4.1.5504.4.3.3.1.1
                redundancyOverSubscriptionType OBJECT-TYPE
                        SYNTAX INTEGER
                                {
                                none(1),
                                low(2),
                                medium(3),
                                high(4)
                                }
                        MAX-ACCESS read-write
                        STATUS current
                        DESCRIPTION
                                "voice DSP redundancy over-subscription model.
                                
                                It is important to know the concept of active versus 
                                standby resources in order to understand how over-
                                subscription works. For each call that is made on our
                                equipment, resources are used. A resource is active if
                                it is currently in use and it is standby if it is 
                                being held in case of the active's failure. If an 
                                active resourse fails, the standby can take over and 
                                the call continues.
                                
                                On the standby resources in a redundancy configuration
                                can be oversubscribed.
                                 
                                A service provider system administrator can configure
                                a voice DSP system to use one of the following
                                oversubscription models:
                                
                                * none: implies 1:1 (one to one) oversubscription.
                                  When a standby is allocated, the pool of available 
                                  actives is depleted by one.
                                * low: implies 1:2 oversubscription.
                                * medium: implies 1:4 oversubscription.
                                * high: implies infinite oversubscription. Active pool
                                  is never depleted when any standbys are allocated.
                                  If all active resources are used for real calls, no
                                  standby resources will be available to take over a
                                  failed call.
                                
                                The default value of this variable is high.
                                
                                This variable is supported only on BAN with VASP card(s)."
                        ::= { voiceDspDefaultConfiguration 1 }
                
-- 
                -- 1.3.6.1.4.1.5504.4.3.3.1.2
                jitterBufferType OBJECT-TYPE
                        SYNTAX INTEGER
                                {
                                static(1),
                                dynamic(2)
                                }
                        MAX-ACCESS read-write
                        STATUS current
                        DESCRIPTION
                                "Voice DSP channel jitter buffer defaults. 
                                
                                There are two types of jitter algorithms: static and
                                dynamic. Dynamic allows the jitter buffer to grow and
                                shrink as inter-arrival jitter changes. A static
                                jitter buffer does not.
                                
                                Some examples of the voice connection types used for; 
                                Voice Over ATM (VoATM): pots-to-aal2, isdn-to-aal2, 
                                                        aal2-to-gr303, aal2-to-v52.
                                Voice Over IP  (VoIP) : sip-to-ds1, sip-to-gr303, 
                                                        sip-to-v52.
                                
                                Dynamic jitter buffer is not supported in VoATM case.
                                
                                Default jitter buffer type is static for VoATM, and
                                dynamic for VoIP."
                        ::= { voiceDspDefaultConfiguration 2 }
                
-- 
                -- 1.3.6.1.4.1.5504.4.3.3.1.3
                jitterBufferSize OBJECT-TYPE
                        SYNTAX Unsigned32 (0..300)
                        UNITS "milliseconds"
                        MAX-ACCESS read-write
                        STATUS current
                        DESCRIPTION
                                "Voice DSP jitter buffer size in milliseconds. More
                                specifically, it refers to the amount of memory usage
                                that can store certain milliseconds of voice.
                                
                                There are two types of jitter algorithms: static and
                                dynamic. Dynamic allows the jitter buffer to grow and
                                shrink as inter-arrival jitter changes. A static
                                jitter buffer does not.
                                
                                When the jitterBufferType is dynamic, jitterBufferSize
                                is the initial buffer size the jitter buffer can grow
                                to.
                                
                                Some examples of the voice connection types used for; 
                                Voice Over ATM (VoATM): pots-to-aal2, isdn-to-aal2, 
                                                        aal2-to-gr303, aal2-to-v52.
                                Voice Over IP  (VoIP) : sip-to-ds1, sip-to-gr303, 
                                                        sip-to-v52.
                                
                                Valid range is 1 to 33 milliseconds for VoATM case.
                                
                                Valid range is 1 to 100 milliseconds for VoIP case.
                                
                                Default jitter buffer size is 10 milliseconds."
                        ::= { voiceDspDefaultConfiguration 3 }
                
-- 
                -- 1.3.6.1.4.1.5504.4.3.3.1.4
                interArrvJitThreshold OBJECT-TYPE
                        SYNTAX Unsigned32 (0..100)
                        UNITS "milliseconds"
                        MAX-ACCESS read-write
                        STATUS current
                        DESCRIPTION
                                "The inter-arrival jitter threshold per channel used as
                                a trigger value in milliseconds to generate a trap
                                when its value is passed.
                                
                                If this value is 0, the threshold mointoring is
                                disabled for inter-arrival jitter.
                                
                                Valid range is 0 to 100 milliseconds. The default
                                value is 80 milliseconds.
                                
                                This variable is not supported."
                        ::= { voiceDspDefaultConfiguration 4 }
                
-- 
                -- 1.3.6.1.4.1.5504.4.3.3.1.5
                pktsLostThreshold OBJECT-TYPE
                        SYNTAX Unsigned32 (0..10000)
                        MAX-ACCESS read-write
                        STATUS current
                        DESCRIPTION
                                "Voice DSP channel packets lost per minute threshold.
                                A trap will be generated when this value is passed.
                                
                                If this value is 0, the threshold mointoring is
                                disabled for packets lost.
                                
                                Valid range for this value is from 0 to 10000 pkts/
                                min. The default value is 600 pkts/min.
                                
                                This variable is not supported."
                        ::= { voiceDspDefaultConfiguration 5 }
                
-- 
                -- 1.3.6.1.4.1.5504.4.3.3.1.6
                echoCancellationType OBJECT-TYPE
                        SYNTAX INTEGER
                                {
                                off(1),
                                g165EchoTL16(2),
                                g165EchoTL32(3),
                                g165EchoTL48(4),
                                g168EchoTL32(5),
                                g168EchoTL48(6),
                                g168EchoTL64(7),
                                g168EchoTL80(8),
                                g168EchoTL96(9),
                                g168EchoTL112(10),
                                g168EchoTL128(11)
                                }
                        MAX-ACCESS read-write
                        STATUS current
                        DESCRIPTION
                                "This data informs which echo cancellation algorithm to
                                be used by default: 165 or 168 for a particular
                                channel. The numbers 165 and 168 are the ITU 
                                designations for the algorithms. The number following
                                the designation describes the echo tail length in
                                milliseconds.
                                
                                Both G.165 and G.168 are ITU-T recommendations. G.168
                                has slightly stricter technical specs. G.168 defines
                                much better how the tests are performed. If an echo
                                canceller passes the G.165 spec, then it is G.165
                                compliant. If it passes G.168, it is both G.168 and
                                G.165 compliant.
                                
                                The echo tail length required depends on factors such
                                as network configuration, local loop length, line 
                                frequency response, etc. Generally, 16 ms is more than
                                adequate for local loop (ie. Zedge) and 32 ms is a
                                good minimum for Network side. Our products currently
                                support up to 48 ms of echo tail length, MALC supports
                                16 ms of echo tail length.
                                
                                Valid values for the variable are:
                                
                                * off - echo cancellation is off (on all platforms).
                                * g165EchoTL16 - G.165 echo cancellation with echo
                                  tail length of 16ms (on MALC only).
                                * g168EchoTL48 - G.168 echo cancellation with echo
                                  tail length of 48ms (on the other platforms, i.e.:
                                  BAN, Sechtor 100, Z-Edge64).
                                
                                
                                Following values are not supported:
                                
                                * g165EchoTL32 - G.165 echo cancellation with echo
                                  tail length of 32ms.
                                * g165EchoTL48 - G.165 echo cancellation with echo
                                  tail length of 48ms.
                                * g168EchoTL32 - G.168 echo cancellation with echo
                                  tail length of 32ms.
                                * g168EchoTL64 - G.168 echo cancellation with echo
                                  tail length of 64ms.
                                * g168EchoTL80 - G.168 echo cancellation with echo
                                  tail length of 80ms.
                                * g168EchoTL96 - G.168 echo cancellation with echo
                                  tail length of 96ms.
                                * g168EchoTL112 - G.168 echo cancellation with echo
                                  tail length of 112ms.
                                * g168EchoTL128 - G.168 echo cancellation with echo
                                  tail length of 128ms.
                                
                                The default value is g165EchoTL16 for MALC, and 
                                g168EchoTL48 for the other platforms."
                        REFERENCE
                                "ITU-T Rec. G.165 (03/1993) Echo Cancellers
                                ITU-T Rec. G.168 (04/2000) Digital Network Echo
                                Cancellers"
                        ::= { voiceDspDefaultConfiguration 6 }
                
                -- 1.3.6.1.4.1.5504.4.3.3.1.7
                silenceSuppressionType OBJECT-TYPE
                        SYNTAX INTEGER
                                {
                                silSupOff(1),
                                silSupOnSidOff(2),
                                silSupOnSidOn(3),
                                silSupOnSidConst(4)
                                }
                        MAX-ACCESS read-write
                        STATUS current
                        DESCRIPTION
                                "This data informs a voice DSP what type of silence
                                suppression algorithm to use on a channel. Silence
                                suppression is used to suppress packet generation during
                                periods of silence of a voice call.
                                
                                The SID (silence descriptor) frame is generated at the
                                start of a silence period, or periodically, and it is
                                used to characterize the power level of the background
                                noise during silence period on the encode side of the
                                voice path. The SID frame is then passed to the decode
                                side through the packet encoding medium (AAL2 or RTP).
                                The decode side then generates comfort noise at an
                                equivalent power level dictated by the SID frame
                                values.
                                
                                Valid values for the variable are:
                                
                                * silSupOff - silence suppression is off.
                                * silSupOnSidOn - send an SID frame at a specified
                                  constant interval (e.g. 100ms).
                                
                                Following values are not supported:
                                
                                * silSupOnSidOff - discontinue transmission during
                                  silence periods and no SID frame is sent.
                                * silSupOnSidConst - send an initial SID frame and then
                                  discontinue transmission.
                                
                                Silence suppression is not supported on MALC.
                                
                                The default value is silSupOff."
                        ::= { voiceDspDefaultConfiguration 7 }
                
                -- 1.3.6.1.4.1.5504.4.3.3.1.8
                echoReturnLoss OBJECT-TYPE
                        SYNTAX INTEGER
                                {
                                erl0dB(1),
                                erl3dB(2),
                                erl6dB(3)
                                }
                        MAX-ACCESS read-write
                        STATUS current
                        DESCRIPTION
                                "The amount of loss between the transmitted signal
                                and the reflected echo back from the hybrid where
                                the 4-to-2 wire conversion takes place.
                                
                                For MALC: 0dB and 6dB. 6dB is default.
                                
                                For all other platforms: 0dB, 3dB, 6dB. 3db is default."
                        ::= { voiceDspDefaultConfiguration 8 }
                
                -- 1.3.6.1.4.1.5504.4.3.3.2
                voiceDspStatusTable OBJECT-TYPE
                        SYNTAX SEQUENCE OF VoiceDspStatusEntry
                        MAX-ACCESS not-accessible
                        STATUS current
                        DESCRIPTION
                                "Current status information for the voice DSP
                                application. This table gives a current view of how a
                                voice DSP is doing since the voice DSP is started."
                        ::= { zhoneVoiceDsp 2 }
                
                -- 1.3.6.1.4.1.5504.4.3.3.2.1
                voiceDspStatusEntry OBJECT-TYPE
                        SYNTAX VoiceDspStatusEntry
                        MAX-ACCESS not-accessible
                        STATUS current
                        DESCRIPTION
                                "An entry in the voiceDspStatusTable."
                        INDEX { zhoneShelfIndex, zhoneSlotIndex }
                        ::= { voiceDspStatusTable 1 }
                
                VoiceDspStatusEntry ::=
                        SEQUENCE { 
                                voiceDspMaxChannelOnBoard
                                        Unsigned32,
                                voiceDspActiveChannelCount
                                        Unsigned32,
                                voiceDspHiWaterChannelCount
                                        Unsigned32,
                                voiceDspResetCount
                                        Counter32
                         }

-- 
                -- 1.3.6.1.4.1.5504.4.3.3.2.1.1
                voiceDspMaxChannelOnBoard OBJECT-TYPE
                        SYNTAX Unsigned32 (0..1008)
                        MAX-ACCESS read-only
                        STATUS current
                        DESCRIPTION
                                "Maximum number of channels a voice DSP can handle at
                                the present time.
                                
                                The valid range for DSP boards we currently support is
                                0 to 1008."
                        ::= { voiceDspStatusEntry 1 }
                
-- 
                -- 1.3.6.1.4.1.5504.4.3.3.2.1.2
                voiceDspActiveChannelCount OBJECT-TYPE
                        SYNTAX Unsigned32 (0..1008)
                        MAX-ACCESS read-only
                        STATUS current
                        DESCRIPTION
                                "Number of channels currently active.
                                
                                The maximum value of this variable should not exceed
                                voiceDspMaxChannelOnBoard."
                        ::= { voiceDspStatusEntry 2 }
                
-- 
                -- 1.3.6.1.4.1.5504.4.3.3.2.1.3
                voiceDspHiWaterChannelCount OBJECT-TYPE
                        SYNTAX Unsigned32 (0..1008)
                        MAX-ACCESS read-only
                        STATUS current
                        DESCRIPTION
                                "The highest channel count since this voice DSP has
                                 been running.
                                
                                The maximum value of this variable should not exceed
                                voiceDspMaxChannelOnBoard."
                        ::= { voiceDspStatusEntry 3 }
                
-- 
                -- 1.3.6.1.4.1.5504.4.3.3.2.1.4
                voiceDspResetCount OBJECT-TYPE
                        SYNTAX Counter32
                        MAX-ACCESS read-only
                        STATUS current
                        DESCRIPTION
                                "Number of slave DSP resets that have occurred within
                                a voice DSP.
                                
                                A reset occurs when a slave DSP crashes. This counter
                                is incremented each time voice DSP detects a slave
                                DSP crash."
                        ::= { voiceDspStatusEntry 4 }
                
                -- 1.3.6.1.4.1.5504.4.3.3.3
                channelStatusTable OBJECT-TYPE
                        SYNTAX SEQUENCE OF ChannelStatusEntry
                        MAX-ACCESS not-accessible
                        STATUS current
                        DESCRIPTION
                                "This table gives a detailed snapshot view of all the 
                                voice calls the voice DSP is currently processing. 
                                Only the current active calls are reported in this 
                                table and there is no information about call sessions
                                that are already terminated."
                        ::= { zhoneVoiceDsp 3 }
                
                -- 1.3.6.1.4.1.5504.4.3.3.3.1
                channelStatusEntry OBJECT-TYPE
                        SYNTAX ChannelStatusEntry
                        MAX-ACCESS not-accessible
                        STATUS current
                        DESCRIPTION
                                "An entry in the channelStatusTable."
                        INDEX { zhoneShelfIndex, zhoneSlotIndex, channelId }
                        ::= { channelStatusTable 1 }
                
                ChannelStatusEntry ::=
                        SEQUENCE { 
                                channelId
                                        Integer32,
                                channelVoiceSessionIdHigh
                                        Unsigned32,
                                channelVoiceSessionIdLow
                                        Unsigned32,
                                channelCcrpShelf
                                        ZhoneShelfValue,
                                channelCcrpSlot
                                        ZhoneSlotValue,
                                channelTrunkCtrpShelf
                                        ZhoneShelfValue,
                                channelTrunkCtrpSlot
                                        ZhoneSlotValue,
                                channelPktCtrpShelf
                                        ZhoneShelfValue,
                                channelPktCtrpSlot
                                        ZhoneSlotValue,
                                channelActiveCodec
                                        INTEGER,
                                channelTimeAlive
                                        TimeTicks,
                                channelPktsSent
                                        Counter32,
                                channelBytesSent
                                        Counter32,
                                channelPktsReceived
                                        Counter32,
                                channelBytesReceived
                                        Counter32,
                                channelPktsLost
                                        Counter32,
                                channelInterArrvJitter
                                        Unsigned32,
                                channelJitterBufferSize
                                        Unsigned32
                         }

                -- 1.3.6.1.4.1.5504.4.3.3.3.1.1
                channelId OBJECT-TYPE
                        SYNTAX Integer32 (1..65536)
                        MAX-ACCESS read-only
                        STATUS current
                        DESCRIPTION
                                "Logical channel id of a call. The valid range of this
                                id is from 1 to 65536. At any single instance, there
                                should at most one call with the same channel id but
                                over time the same channel id can be used for
                                different calls."
                        ::= { channelStatusEntry 1 }
                
-- 
                -- 1.3.6.1.4.1.5504.4.3.3.3.1.2
                channelVoiceSessionIdHigh OBJECT-TYPE
                        SYNTAX Unsigned32
                        MAX-ACCESS read-only
                        STATUS current
                        DESCRIPTION
                                "The high 32 bits of the session number of a voice call.
                                
                                The session id is used to keep track all resources
                                used by a call. Detailed call performance statistics
                                can be supported in the future with session id
                                uniquely identify each individual call.
                                
                                Voice session id is a unique 64 bit number and it will
                                never be repeated."
                        ::= { channelStatusEntry 2 }
                
-- 
                -- 1.3.6.1.4.1.5504.4.3.3.3.1.3
                channelVoiceSessionIdLow OBJECT-TYPE
                        SYNTAX Unsigned32
                        MAX-ACCESS read-only
                        STATUS current
                        DESCRIPTION
                                "The low 32 bits of the session number of a voice call.
                                
                                The session id is used to keep track all resources
                                used by a call. Detailed call performance statistics
                                can be supported in the future with session id
                                uniquely identify each individual call.
                                
                                Voice session id is a unique 64 bit number and it will
                                never be repeated."
                        ::= { channelStatusEntry 3 }
                
-- 
                -- 1.3.6.1.4.1.5504.4.3.3.3.1.4
                channelCcrpShelf OBJECT-TYPE
                        SYNTAX ZhoneShelfValue
                        MAX-ACCESS read-only
                        STATUS current
                        DESCRIPTION
                                "The shelf where the Call Control Resource Provider 
                                (CCRP) resides. CCRP process acts as a gateway for 
                                call signaling between TDM equipment and the ATM AAL2
                                network.
                                
                                Range of valid values is 1-255. Note 0 is an invalid 
                                value.
                                
                                "
                        ::= { channelStatusEntry 4 }
                
-- 
                -- 1.3.6.1.4.1.5504.4.3.3.3.1.5
                channelCcrpSlot OBJECT-TYPE
                        SYNTAX ZhoneSlotValue
                        MAX-ACCESS read-only
                        STATUS current
                        DESCRIPTION
                                "The slot where the Call Control Resource Provider 
                                (CCRP) resides. CCRP process acts as a gateway for 
                                call signaling between TDM equipment and the ATM AAL2
                                network.
                                
                                Range of valid values is 1-17. Note 0 is an invalid
                                value."
                        ::= { channelStatusEntry 5 }
                
-- 
                -- 1.3.6.1.4.1.5504.4.3.3.3.1.6
                channelTrunkCtrpShelf OBJECT-TYPE
                        SYNTAX ZhoneShelfValue
                        MAX-ACCESS read-only
                        STATUS current
                        DESCRIPTION
                                "The shelf where the Trunk Call Temrination Resource 
                                Provider (TrunkCtrp) resides. TrunkCtrp is a proccess
                                through which call signaling travels to and from TDM 
                                equipment. The CCRP above does not communicate 
                                directly with TDM; it does so through this CTRP.
                                
                                Range of valid values is 1-255. Note 0 is an invalid 
                                value."
                        ::= { channelStatusEntry 6 }
                
-- 
                -- 1.3.6.1.4.1.5504.4.3.3.3.1.7
                channelTrunkCtrpSlot OBJECT-TYPE
                        SYNTAX ZhoneSlotValue
                        MAX-ACCESS read-only
                        STATUS current
                        DESCRIPTION
                                "The slot where the Trunk Call Temrination Resource 
                                Provider (TrunkCtrp) resides. TrunkCtrp is a proccess
                                through which call signaling travels to and from TDM 
                                equipment. The CCRP above does not communicate 
                                directly with TDM; it does so through this CTRP.
                                
                                Range of valid values is 1-17. Note 0 is an invalid
                                value."
                        ::= { channelStatusEntry 7 }
                
-- 
                -- 1.3.6.1.4.1.5504.4.3.3.3.1.8
                channelPktCtrpShelf OBJECT-TYPE
                        SYNTAX ZhoneShelfValue
                        MAX-ACCESS read-only
                        STATUS current
                        DESCRIPTION
                                "The shelf where the Packet Call Temrination Resource 
                                Provider (PktCtrp) resides. PktCtrp is a proccess
                                through which call signaling travels to and from ATM 
                                AAL2 network.
                                
                                Range of valid values is 1-255. Note 0 is an invalid
                                value."
                        ::= { channelStatusEntry 8 }
                
-- 
                -- 1.3.6.1.4.1.5504.4.3.3.3.1.9
                channelPktCtrpSlot OBJECT-TYPE
                        SYNTAX ZhoneSlotValue
                        MAX-ACCESS read-only
                        STATUS current
                        DESCRIPTION
                                "The slot where the Packet Call Temrination Resource 
                                Provider (PktCtrp) resides. PktCtrp is a proccess
                                through which call signaling travels to and from ATM 
                                AAL2 network.
                                
                                Range of valid values is 1-17. Note 0 is an invalid
                                value."
                        ::= { channelStatusEntry 9 }
                
-- 
                -- 1.3.6.1.4.1.5504.4.3.3.3.1.10
                channelActiveCodec OBJECT-TYPE
                        SYNTAX INTEGER
                                {
                                g711Ulaw(1),
                                g711Alaw(2),
                                g726(3),
                                g729A(4),
                                g729B(5),
                                g729E(6),
                                g723R1KBPS5Dot3(7),
                                g723R1KBPS6Dot3(8),
                                g723R1AKBPS5Dot3(9),
                                g723R1AKBPS6Dot3(10)
                                }
                        MAX-ACCESS read-only
                        STATUS current
                        DESCRIPTION
                                "Types of voice codecs on the current call.
                                
                                G.711, G.726, G.729 and G.723 are ITU-T standards for
                                voice and multimedia modulation and digital encoding.
                                
                                Valid values for this variable can be:
                                
                                * g711Ulaw - G.711 Ulaw coding standard at 64 kbps
                                * g711Alaw - G.711 Alaw coding standard at 64 kbps
                                * g726 - G.726 ADPCM coding stardards at 48/56/64 kbps
                                * g729A - G.729 Annex A CS-ACELP coding standard at 8
                                  kbps
                                * g729B - G.729 Annex B CS-ACELP coding standard with
                                  silence suppressionat 8 kbps
                                * g729E - G.729 Annex E CS-ACELP coding standard with
                                  silence suppressionat 11.8 kbps
                                * g723R1KBPS5Dot3 - G.723.1 coding standard at 5.3 kbps
                                * g723R1KBPS6Dot3 - G.723.1 coding standard at 6.3 kbps
                                * g723R1AKBPS5Dot3 - G.723.1 Annex A coding standard at
                                  5.3 kbps
                                * g723R1AKBPS6Dot3 - G.723.1 Annex coding standard at 
                                  6.3 kbps"
                        REFERENCE
                                "ITU-T Recommendation G.711 (11/88) - Pulse code
                                modulation (PCM) of voice frequencies.
                                ITU-T Recommendation G.726 (12/90) - 40, 32, 24, 16
                                kbit/s Adaptive Differential Pulse Code Modulation
                                (ADPCM).
                                ITU-T Recommendation G.729 (03/96) - C source code
                                and test vectors for implementation verification of
                                the G.729 8 kbit/s CS-ACELP speech coder.
                                ITU-T Recommendation G.723.1 (03/96) - Dual rate
                                speech coder for multimedia communications
                                transmitting at 5.3 and 6.3 kbit/s."
                        ::= { channelStatusEntry 10 }
                
-- 
                -- 1.3.6.1.4.1.5504.4.3.3.3.1.11
                channelTimeAlive OBJECT-TYPE
                        SYNTAX TimeTicks
                        MAX-ACCESS read-only
                        STATUS current
                        DESCRIPTION
                                "This indicates how long this channel has been running
                                in TimeTicks. A channel is considered alive when the
                                call parties pick up the phone and data starts to flow
                                and it is no longer alive when the phone is hung up.
                                
                                One TimeTick is one hundredth of a second."
                        ::= { channelStatusEntry 11 }
                
                -- 1.3.6.1.4.1.5504.4.3.3.3.1.12
                channelPktsSent OBJECT-TYPE
                        SYNTAX Counter32
                        MAX-ACCESS read-only
                        STATUS current
                        DESCRIPTION
                                "Number of packets transmitted."
                        ::= { channelStatusEntry 12 }
                
-- 
                -- 1.3.6.1.4.1.5504.4.3.3.3.1.13
                channelBytesSent OBJECT-TYPE
                        SYNTAX Counter32
                        MAX-ACCESS read-only
                        STATUS current
                        DESCRIPTION
                                "Number of bytes transmitted."
                        ::= { channelStatusEntry 13 }
                
-- 
                -- 1.3.6.1.4.1.5504.4.3.3.3.1.14
                channelPktsReceived OBJECT-TYPE
                        SYNTAX Counter32
                        MAX-ACCESS read-only
                        STATUS current
                        DESCRIPTION
                                "Number of packets received."
                        ::= { channelStatusEntry 14 }
                
-- 
                -- 1.3.6.1.4.1.5504.4.3.3.3.1.15
                channelBytesReceived OBJECT-TYPE
                        SYNTAX Counter32
                        MAX-ACCESS read-only
                        STATUS current
                        DESCRIPTION
                                "Number of bytes received."
                        ::= { channelStatusEntry 15 }
                
-- 
                -- 1.3.6.1.4.1.5504.4.3.3.3.1.16
                channelPktsLost OBJECT-TYPE
                        SYNTAX Counter32
                        MAX-ACCESS read-only
                        STATUS current
                        DESCRIPTION
                                "Number of packets lost."
                        ::= { channelStatusEntry 16 }
                
                -- 1.3.6.1.4.1.5504.4.3.3.3.1.17
                channelInterArrvJitter OBJECT-TYPE
                        SYNTAX Unsigned32
                        UNITS "milliseconds"
                        MAX-ACCESS read-only
                        STATUS current
                        DESCRIPTION
                                "The inter arrival jitter in milliseconds."
                        ::= { channelStatusEntry 17 }
                
-- 
                -- 1.3.6.1.4.1.5504.4.3.3.3.1.18
                channelJitterBufferSize OBJECT-TYPE
                        SYNTAX Unsigned32
                        UNITS "milliseconds"
                        MAX-ACCESS read-only
                        STATUS current
                        DESCRIPTION
                                "Size of jitter buffer in milliseconds.
                                
                                The jitter buffer is used to compensate for 
                                inter-arrival packet jitter. It is accomplished by 
                                keeping a buffer of packets to allow continuous
                                playout of voice."
                        ::= { channelStatusEntry 18 }
                
                -- 1.3.6.1.4.1.5504.4.3.3.4
                voiceDspTraps OBJECT-IDENTITY
                        STATUS current
                        DESCRIPTION 
                                "All voice DSP related traps are defined under 
                                voiceDspTraps."
                        ::= { zhoneVoiceDsp 4 }
                
                -- 1.3.6.1.4.1.5504.4.3.3.4.0
                voiceDspTrapsPrefix OBJECT-IDENTITY
                        STATUS current
                        DESCRIPTION 
                                "prefix 0 for voiceDspTraps as required by SNMPv2."
                        ::= { voiceDspTraps 0 }
                
-- zhoneShelfIndex and zhoneSlotIndex are included to 
-- in the VarBind to identify the location of voice DSP.
                -- 1.3.6.1.4.1.5504.4.3.3.4.0.1
                voiceDspReset NOTIFICATION-TYPE
                        OBJECTS { zhoneShelfIndex, zhoneSlotIndex, voiceDspResetCount }
                        STATUS current
                        DESCRIPTION 
                                "Notification that a voice DSP just reset."
                        ::= { voiceDspTrapsPrefix 1 }
                
-- zhoneShelfIndex and zhoneSlotIndex are included to 
-- in the VarBind to identify the location of voice DSP.
                -- 1.3.6.1.4.1.5504.4.3.3.4.0.2
                voiceDspChannelPktsLoss NOTIFICATION-TYPE
                        OBJECTS { zhoneShelfIndex, zhoneSlotIndex, channelId, channelPktsLost }
                        STATUS current
                        DESCRIPTION 
                                "Notification to be generated when channelPktsPktsLost
                                is more than the voice Dsp default pktsLostThreshold."
                        ::= { voiceDspTrapsPrefix 2 }
                
-- zhoneShelfIndex and zhoneSlotIndex are included to 
-- in the VarBind to identify the location of voice DSP.
                -- 1.3.6.1.4.1.5504.4.3.3.4.0.3
                voiceDspChannelInterArrvJitterTrigger NOTIFICATION-TYPE
                        OBJECTS { zhoneShelfIndex, zhoneSlotIndex, channelId, channelInterArrvJitter }
                        STATUS current
                        DESCRIPTION 
                                "Notification to be generated when
                                channelInterArrvJitter is more than the voice Dsp 
                                default interArrvJitThreshold."
                        ::= { voiceDspTrapsPrefix 3 }
                
        
        END

--
-- comVoiceDsp.mib
--
