--
-- phyEnetMauMib.mib
-- MIB generated by MG-SOFT Visual MIB Builder Version 3.0 Build 285
-- Monday, October 14, 2013 at 20:34:49
--

--  ZHONE-MAU-MIB.mib
-- MIB generated by MG-SOFT Visual MIB Builder Version 1.8 Build 150
-- Tuesday, June 20, 2000 at 12:19:16

	ZHONE-MAU-MIB DEFINITIONS ::= BEGIN

		IMPORTS
			ifIndex, ifAdminStatus,	ifOperStatus, ifName, InterfaceIndexOrZero
				FROM IF-MIB
			NOTIFICATION-GROUP
				FROM SNMPv2-CONF
			Integer32, Counter32, OBJECT-TYPE, MODULE-IDENTITY, OBJECT-IDENTITY,
			NOTIFICATION-TYPE
				FROM SNMPv2-SMI
			TruthValue
				FROM SNMPv2-TC
			zhoneEnet, zhoneModules
				FROM Zhone;


-- to generate protection layer:
-- /vob/zhonetools/bin/pahrser.pl rfc2233.mib Zhone.mib
-- Zhone-TC.mib	phyEnetMauMib.mib
--
-- to generate mib handler stubs:
-- /vob/EPILOGUE/binaries/emissary/solaris/mibcomp rfc2514.mib rfc1907.mib
-- iftype.mib rfc2233.mib Zhone.mib Zhone-TC.mib -stub -o ethHdlr.c
-- phyEnetMauMib.mib
--
--
		-- 1.3.6.1.4.1.5504.6.8
		phyEnetMauMib MODULE-IDENTITY
			LAST-UPDATED "201310131500Z"		-- October 13, 2013 at 15:00 GMT
			ORGANIZATION
				"Zhone Technologies, Inc."
			CONTACT-INFO
				"	  Zhone	Technologies. Inc.
				Postal:	 900 Chelmsford	Street
					 Lowell, MA 01851

				Phone:	 +1 877-ZHONE20	(877 946-6320)
					 +1 978	848-3766
				Fax:	 +1 978	848-3796

				Email:	 support@zhone.com"
			DESCRIPTION
				"MIB to	manage the physical interface on Ethernet
				ports.	The MAU	referred to by the MIB refers to
				both integarted	physical interfaces as well as
				the now	rarely used external MAUs.

				Adapted	from RFC 2668 -	Definitions of Managed
				Objects	for 802.3 Media	Attachment Units (MAU).

				"
			REVISION "201310131708Z"		-- October 13, 2013 at 17:08 GMT
			DESCRIPTION
				"Add mazFrameSize"
			REVISION "201205251455Z"		-- May 25, 2012	at 14:55 GMT
			DESCRIPTION
				"Added a value to the pauseControl enum"
			REVISION "200902030139Z"		-- February 03,	2009 at	01:39 GMT
			DESCRIPTION
				"Added new 10gBase Mau Types in	MauTypeListBits."
			REVISION "200901192144Z"		-- January 19, 2009 at 21:44 GMT
			DESCRIPTION
				"Added new mauTypes for	10 Gig ports."
			REVISION "200808140717Z"		-- August 14, 2008 at 07:17 GMT
			DESCRIPTION
				"Added zhoneIfMauEntry.zhoneMauLinkStateMirror field."
			REVISION "200803101203Z"		-- March 10, 2008 at 12:03 GMT
			DESCRIPTION
				"Added profile link-agg"
			REVISION "200711011437Z"		-- November 01,	2007 at	14:37 GMT
			DESCRIPTION
				"Add aggregation mode"
			REVISION "200706242311Z"		-- June	24, 2007 at 23:11 GMT
			DESCRIPTION
				"V01.00.03 - Add zhoneMauPauseFlowControl
				and zhoneMauSetPauseTime."
			REVISION "200705221605Z"		-- May 22, 2007	at 16:05 GMT
			DESCRIPTION
				"V01.00.02 - Added linkAggLink1Trap, linkAggLink2Trap, LinkAggLinkGroup"
			REVISION "200510131655Z"		-- October 13, 2005 at 16:55 GMT
			DESCRIPTION
				"V01.00.01 - Add RPR Traps."
			REVISION "200009121801Z"		-- September 12, 2000 at 18:01 GMT
			DESCRIPTION
				"V01.00.00 - Initial Release"
			::= { zhoneModules 8 }





--
-- Node	definitions
--

		-- 1.3.6.1.4.1.5504.5.1.1
		zhoneIfMauTable	OBJECT-TYPE
			SYNTAX SEQUENCE	OF ZhoneIfMauEntry
			MAX-ACCESS not-accessible
			STATUS current
			DESCRIPTION
				"Table of descriptive and status information
				about the phsyical Enet	interface."
			::= { zhoneEnet	1 }


		-- 1.3.6.1.4.1.5504.5.1.1.1
		zhoneIfMauEntry	OBJECT-TYPE
			SYNTAX ZhoneIfMauEntry
			MAX-ACCESS not-accessible
			STATUS current
			DESCRIPTION
				"An entry in the table,	containing information
				about a	single physical	Enet interface."
			INDEX {	zhoneMauIfIndex	}
			::= { zhoneIfMauTable 1	}


		ZhoneIfMauEntry	::=
			SEQUENCE {
				zhoneMauIfIndex
					Integer32,
				zhoneMauType
					INTEGER,
				zhoneMauOperStatus
					INTEGER,
				zhoneMauMediaAvailable
					INTEGER,
				zhoneMauMediaAvailStateExits
					Counter32,
				zhoneMauJabberState
					INTEGER,
				zhoneMauJabberingStateEnters
					Counter32,
				zhoneMauFalseCarriers
					Counter32,
				zhoneMauDefaultType
					INTEGER,
				zhoneMauAutoNegSupported
					TruthValue,
				zhoneMauTypeListBits
					BITS,
				zhoneMauClkSrc
					INTEGER,
				zhoneMauPauseFlowControl
					INTEGER,
				zhoneMauAggregationMode
					INTEGER,
				zhoneMauLinkStateMirror
					InterfaceIndexOrZero,
				zhoneMauSetPauseTime
					Integer32,
				zhoneMauMaxFrameSize
					Integer32,
				zhoneMauIngressRate
					Integer32,
				zhoneMauIngressBurstSize
					Integer32,
				zhoneMauEgressRate
					Integer32,
				zhoneMauEgressBurstSize
					Integer32
			 }

		-- 1.3.6.1.4.1.5504.5.1.1.1.1
		zhoneMauIfIndex	OBJECT-TYPE
			SYNTAX Integer32 (1..2147483647)
			MAX-ACCESS read-only
			STATUS current
			DESCRIPTION
				"This variable uniquely	identifies the interface
				to which the Ethernet/MAU described by this entry
				is connected."
			REFERENCE
				"RFC 1213, ifIndex"
			::= { zhoneIfMauEntry 1	}


		-- 1.3.6.1.4.1.5504.5.1.1.1.2
		zhoneMauType OBJECT-TYPE
			SYNTAX INTEGER
				{
				mauOther(1),
				mau10BaseT(5),
				mau10BaseTHD(10),
				mau10BaseTFD(11),
				mau100BaseTXHD(15),
				mau100BaseTXFD(16),
				mau1000BaseLXHD(22),
				mau1000BaseLXFD(23),
				mau1000BaseSXHD(25),
				mau1000BaseSXFD(26),
				mau1000BaseTHD(29),
				mau1000BaseTFD(30),
				mau10gBaseX(31),
				mau10gBaseR(32),
				mau10gBaseW(33),
				mau10gBaseLX4(34),
				mau10gBaseSR(35),
				mau10gBaseSW(36),
				mau10gBaseLR(37),
				mau10gBaseLW(38),
				mau10gBaseER(39),
				mau10gBaseEW(40)
				}
			MAX-ACCESS read-write
			STATUS current
			DESCRIPTION
				"Physical Interface Type"
			::= { zhoneIfMauEntry 2	}


		-- 1.3.6.1.4.1.5504.5.1.1.1.3
		zhoneMauOperStatus OBJECT-TYPE
			SYNTAX INTEGER
				{
				other(1),
				unknown(2),
				operational(3),
				standby(4),
				shutdown(5),
				reset(6)
				}
			MAX-ACCESS read-only
			STATUS current
			DESCRIPTION
				"The current operational state of the MAU.

				other(1) is returned if	the MAU	or interface is	in
				a state	other than one of the states 2 through 6.

				unknown(2) is returned when the	true state of the
				MAU is unknown;	for example, when it is	being
				initialized.

				operational(3) state is	fully functional, operates,
				and passes signals to its attached DTE.

				standby(4) state forces	DI and CI to idle and the
				media transmitter or interface to idle or fault,
				if supported.  Standby(4) mode only applies to
				link type MAUs.	 The state of
				zhoneMauMediaAvailable is unaffected.

				A MAU in shutdown(5) state assumes the same
				condition on DI, CI, and the media transmitter
				as though it were powered down or not connected.
				The MAU	MAY return other(1) value for the
				zhoneMauJabberState and	zhoneMauMediaAvailable
				objects	when it	is in this state.  For an AUI,
				this state will	remove power from the AUI.

				Setting	this variable to the value reset(6)
				resets the MAU in the same manner as a
				power-off, power-on cycle of at	least one-half
				second would.  The agent is not	required to
				return the value reset (6)."
			REFERENCE
				"[IEEE 802.3 Std], 30.5.1.1.7, aMAUAdminState,
				30.5.1.2.2, acMAUAdminControl, and 30.5.1.2.1,
				acResetMAU."
			::= { zhoneIfMauEntry 3	}


		-- 1.3.6.1.4.1.5504.5.1.1.1.4
		zhoneMauMediaAvailable OBJECT-TYPE
			SYNTAX INTEGER
				{
				other(1),
				unknown(2),
				available(3),
				notAvailable(4),
				remoteFault(5),
				invalidSignal(6),
				remoteJabber(7),
				remoteLinkLoss(8),
				remoteTest(9),
				offline(10),
				autoNegError(11)
				}
			MAX-ACCESS read-only
			STATUS current
			DESCRIPTION
				"If the	MAU or interface is a link or fiber type
				(FOIRL,	10BASE-T, 10BASE-F) then this is
				equivalent to the link test fail state/low light
				function. For an AUI MAU this indicates	whether
				or not loopback	is detected on the DI circuit.

				other(1) is returned if	the mediaAvailable state
				is not one of 2	through	11.

				unknown(2) is returned when the	MAU's true state
				is unknown; for	example, when it is being
				initialized.  At power-up or following a reset,
				the value of this attribute will be unknown for
				AUI and	10BASE-FP MAUs.	 For these MAUs	loopback
				will be	tested on each transmission during which
				no collision is	detected. If DI	is receiving input
				when DO	returns	to IDL after a transmission and
				there has been no collision during the
				transmission then loopback will	be detected. The
				value of this attribute	will only change during
				non-collided transmissions for AUI and
				10BASE-FP MAUs.

				For 100Mbps and	1000Mbps MAUs, the enumerations
				match the states within	the respective link
				integrity states.  Any MAU which implements
				management of auto-negotiation will map	remote
				fault indication to remote fault.

				available(3) indicates that the	link, light, or
				loopback is normal.  The value notAvailable(4)
				indicates link loss, low light,	or no loopback.

				remoteFault(5) indicates that a	fault has been
				detected at the	remote end of the link.	This
				value applies to 10BASE-FB, 100BASE-T4 Far End
				Fault Indication and non-specified remote
				faults from a system running auto-negotiation.

				remoteJabber(7), remoteLinkLoss(8), and
				remoteTest(9) SHOULD be	used instead of
				remoteFault(5) where the reason	for remote
				fault is identified in the remote signaling
				protocol.

				invalidSignal(6) indicates that	an invalid signal
				has been received from the other end of	the link.
				InvalidSignal(6) applies only to MAUs of type
				10BASE-FB.

				Where an IEEE Std 802.3u-1995 clause 22	MII
				is present, a logic one	in the remote fault bit
				(reference section 22.2.4.2.8 of that document)
				maps to	the value remoteFault(5), and a	logic
				zero in	the link status	bit (reference section
				22.2.4.2.10 of that document) maps to the value
				notAvailable(4).  The value notAvailable(4)
				takes precedence over the value	remoteFault(5).

				Any MAU	that implements	management of clause 37
				Auto-Negotiation will map the received RF1 and
				RF2 bit	values for Offline to offline(10), Link
				Failure	to remoteFault(5) and Auto-Negotiation
				Error to autoNegError(11)."
			REFERENCE
				"[IEEE 802.3 Std], 30.5.1.1.4, aMediaAvailable."
			::= { zhoneIfMauEntry 4	}


		-- 1.3.6.1.4.1.5504.5.1.1.1.5
		zhoneMauMediaAvailStateExits OBJECT-TYPE
			SYNTAX Counter32
			MAX-ACCESS read-only
			STATUS current
			DESCRIPTION
				"A count of the	number of times	that
				zhoneMauMediaAvailable for this	MAU or interface
				instance leaves	the state available(3).

				Discontinuities	in the value of	this counter can
				occur at re-initialization of the management
				system,	and at other times as indicated	by the
				value of ifCounterDiscontinuityTime."
			REFERENCE
				"[IEEE 802.3 Std], 30.5.1.1.5,
				aLoseMediaCounter.
				RFC 2233, ifCounterDiscontinuityTime."
			::= { zhoneIfMauEntry 5	}


		-- 1.3.6.1.4.1.5504.5.1.1.1.6
		zhoneMauJabberState OBJECT-TYPE
			SYNTAX INTEGER
				{
				other(1),
				unknown(2),
				noJabber(3),
				jabbering(4)
				}
			MAX-ACCESS read-only
			STATUS current
			DESCRIPTION
				"The value other(1) is returned	if the jabber
				state is not 2,	3, or 4.

				unknown(2) is returned when the	MAU's true state
				is unknown; e.g. when it is being initialized.

				If the MAU is not jabbering the	agent returns
				noJabber(3).  This is the 'normal' state.

				If the MAU is in jabber	state the agent	returns
				the jabbering(4) value."
			REFERENCE
				"[IEEE 802.3 Std], 30.5.1.1.6,
				aJabber.jabberFlag."
			::= { zhoneIfMauEntry 6	}


		-- 1.3.6.1.4.1.5504.5.1.1.1.7
		zhoneMauJabberingStateEnters OBJECT-TYPE
			SYNTAX Counter32
			MAX-ACCESS read-only
			STATUS current
			DESCRIPTION
				"A count of the	number of times	that
				zhoneMauJabberState for	this MAU or interface
				instance  enters the state jabbering(4). This
				counter	will always indicate zero for MAUs of
				ype dot1MauTypeAUI and those of	speeds above
				10Mbps.

				Discontinuities	in the value of	this counter can
				occur at re-initialization of the management
				system,	and at other times as indicated	by the
				value of ifCounterDiscontinuityTime."
			REFERENCE
				"[IEEE 802.3 Std], 30.5.1.1.6,
				aJabber.jabberCounter.
				RFC 2233, ifCounterDiscontinuityTime."
			::= { zhoneIfMauEntry 7	}


		-- 1.3.6.1.4.1.5504.5.1.1.1.8
		zhoneMauFalseCarriers OBJECT-TYPE
			SYNTAX Counter32
			MAX-ACCESS read-only
			STATUS current
			DESCRIPTION
				"A count of the	number of false	carrier	events
				during IDLE in 100BASE-X and 1000BASE-X	links.

				For all	other MAU or inetrafce types, this counter
				will always indicate zero. This	counter	does not
				increment at the symbol	rate.

				It can increment after a valid carrier
				completion at a	maximum	rate of	once per 100 ms
				for 100BASE-X and once per 10us	for 1000BASE-X
				until the next CarrierEvent.

				Discontinuities	in the value of	this counter can
				occur at re-initialization of the management
				system,	and at other times as indicated	by the
				value of ifCounterDiscontinuityTime."
			REFERENCE
				"[IEEE 802.3 Std], 30.5.1.1.10,	aFalseCarriers.
				RFC 2233, ifCounterDiscontinuityTime."
			::= { zhoneIfMauEntry 8	}


		-- 1.3.6.1.4.1.5504.5.1.1.1.9
		zhoneMauDefaultType OBJECT-TYPE
			SYNTAX INTEGER
				{
				mauOther(1),
				mau10BaseT(5),
				mau10BaseTHD(10),
				mau10BaseTFD(11),
				mau100BaseTXHD(15),
				mau100BaseTXFD(16),
				mau1000BaseLXHD(22),
				mau1000BaseLXFD(23),
				mau1000BaseSXHD(25),
				mau1000BaseSXFD(26),
				mau1000BaseTHD(29),
				mau1000BaseTFD(30),
				mau10gBaseX(31),
				mau10gBaseR(32),
				mau10gBaseW(33),
				mau10gBaseLX4(34),
				mau10gBaseSR(35),
				mau10gBaseSW(36),
				mau10gBaseLR(37),
				mau10gBaseLW(38),
				mau10gBaseER(39),
				mau10gBaseEW(40)
				}
			MAX-ACCESS read-only
			STATUS current
			DESCRIPTION
				"Physical interface type."
			::= { zhoneIfMauEntry 9	}


		-- 1.3.6.1.4.1.5504.5.1.1.1.10
		zhoneMauAutoNegSupported OBJECT-TYPE
			SYNTAX TruthValue
			MAX-ACCESS read-only
			STATUS current
			DESCRIPTION
				"This object indicates whether or not
				auto-negotiation is supported."
			::= { zhoneIfMauEntry 10 }


		-- 1.3.6.1.4.1.5504.5.1.1.1.11
		zhoneMauTypeListBits OBJECT-TYPE
			SYNTAX BITS
				{
				bOther(0),
				bAUI(1),
				b10base5(2),
				bFoirl(3),
				b10base2(4),
				b10baseT(5),
				b10baseFP(6),
				b10baseFB(7),
				b10baseFL(8),
				b10broad36(9),
				b10baseTHD(10),
				b10baseTFD(11),
				b10baseFLHD(12),
				b10baseFLFD(13),
				b100baseT4(14),
				b100baseTXHD(15),
				b100baseTXFD(16),
				b100baseFXHD(17),
				b100baseFXFD(18),
				b100baseT2HD(19),
				b100baseT2FD(20),
				b1000baseXHD(21),
				b1000baseXFD(22),
				b1000baseLXHD(23),
				b1000baseLXFD(24),
				b1000baseSXHD(25),
				b1000baseSXFD(26),
				b1000baseCXHD(27),
				b1000baseCXFD(28),
				b1000baseTHD(29),
				b1000baseTFD(30),
				b10gbaseX(31),
				b10gbaseR(32),
				b10gbaseW(33),
				b10gbaseLX4(34),
				b10gbaseSR(35),
				b10gbaseSW(36),
				b10gbaseLR(37),
				b10gbaseLW(38),
				b10gbaseER(39),
				b10gbaseEW(40)
				}
			MAX-ACCESS read-only
			STATUS current
			DESCRIPTION
				"A value that uniquely identifies the set of
				possible IEEE 802.3 types that the MAU could be.
				If auto-negotiation is present on this MAU, this
				object will map	to ifMauAutoNegCapability.

				Note that this MAU may be capable of operating
				as a MAU type that is beyond the scope of this
				MIB.  This is indicated	by returning the
				bit value bOther in addition to	any bit	values
				for capabilities that are listed above."
			::= { zhoneIfMauEntry 11 }


		-- 1.3.6.1.4.1.5504.5.1.1.1.12
		zhoneMauClkSrc OBJECT-TYPE
			SYNTAX INTEGER
				{
				unused(1),
				automatic(2),
				master(3),
				slave(4)
				}
			MAX-ACCESS read-write
			STATUS current
			DESCRIPTION
				"Clock source for timing.
				Unused - unused
				Automatic - Master/Slave is decided during autonegotiation
				Master -  Clocked from local source
				Slave -	Loop timing from the received data stream"
			::= { zhoneIfMauEntry 12 }


		-- 1.3.6.1.4.1.5504.5.1.1.1.13
		zhoneMauPauseFlowControl OBJECT-TYPE
			SYNTAX INTEGER
				{
				disabled(1),
				asymmetricTx(2),
				asymmetricRx(3),
				symmetric(4),
				passthrough(5)
				}
			MAX-ACCESS read-write
			STATUS current
			DESCRIPTION
				"When autonegotiation is enabled (zhoneMauAutoNegSupported is true),
				this Pause Flow	Control	field is used to program the advertised
				pause capabilities.

				When autonegotiation is	disabled (manual negotiation), this
				Pause Flow Control field is used to program the	local Mac
				as instructed.

				If passthrough is selected the pause frames are	sent to	the host
				for forwarding or discard as the packet	rules dictate."
			::= { zhoneIfMauEntry 13 }


		-- 1.3.6.1.4.1.5504.5.1.1.1.14
		zhoneMauAggregationMode	OBJECT-TYPE
			SYNTAX INTEGER
				{
				on(1),
				off(2),
				passive(3),
				active(4)
				}
			MAX-ACCESS read-write
			STATUS current
			DESCRIPTION
				"On: The link aggregation is forced to be formed without any
				LACP negotiation .In other words, the switch will neither send the
				LACP packet nor	process	any incoming LACP packet. This is similar
				to the on state	for PAgP.

				Off: The link aggregation will not be formed.
				We do not send or understand the LACP packet.
				This is	similar	to the off state for PAgP.

				Passive: The switch does not initiate the channel,
				but does understand incoming LACP packets.
				The peer (in active state) initiates negotiation
				(by sending out	an LACP	packet)	which we receive and reply to,
				eventually forming the aggregation channel with	the peer.
				This is	similar	to the auto mode in PAgP.

				Active:	We are willing to form an aggregate link, and
				initiate the negotiation. The link aggregate will be formed
				if the other end is running in LACP active or passive mode.
				This is	similar	to the desirable mode of PAgP.

				"
			DEFVAL { on }
			::= { zhoneIfMauEntry 14 }


		-- 1.3.6.1.4.1.5504.5.1.1.1.15
		zhoneMauLinkStateMirror	OBJECT-TYPE
			SYNTAX InterfaceIndexOrZero
			MAX-ACCESS read-write
			STATUS current
			DESCRIPTION
				"ifIndex of another physical interface whose link state	will be	mirrored on
				this MAU.  This	is used	to propagate a link fault observed on one physical
				interface onto another interface."
			DEFVAL { 0 }
			::= { zhoneIfMauEntry 15 }
-- Note:  The mirrored interface may be	limited	to a certain type and can be
-- a one to many relationship.	An example could have multiple Ethernet	MAUs
-- mirroring one WAN interface.

		-- 1.3.6.1.4.1.5504.5.1.1.1.16
		zhoneMauSetPauseTime OBJECT-TYPE
			SYNTAX Integer32 (0..65535)
			MAX-ACCESS read-write
			STATUS current
			DESCRIPTION
				"Used to set the pause interval.  Units	are in pause_quanta.

				Currently not supported."
			DEFVAL { 0 }
			::= { zhoneIfMauEntry 16 }


		-- 1.3.6.1.4.1.5504.5.1.1.1.17
		zhoneMauMaxFrameSize OBJECT-TYPE
			SYNTAX Integer32 (0..15360)
			MAX-ACCESS read-write
			STATUS current
			DESCRIPTION
				"Used to set the max frame size	for ethernet ports.
				Units are bytes. Range is 0 15360. 0 is	default	implying 2048 bytes."
			DEFVAL { 0 }
			::= { zhoneIfMauEntry 17 }
-- Used	to set max frame size for ethernet ports. Units	are Bytes.

		-- 1.3.6.1.4.1.5504.5.1.1.1.18
		zhoneMauIngressRate OBJECT-TYPE
			SYNTAX Integer32 (0..10240000)
			UNITS "Kbps"
			MAX-ACCESS read-write
			STATUS current
			DESCRIPTION
				"Used to set the ingress rate for ethernet ports.
				Units are Kbps.	Range is 0 10Gbps. 0 is	default	implying no limit."
			::= { zhoneIfMauEntry 18 }
-- Used	to set max frame size for ethernet ports. Units	are Bytes.

		-- 1.3.6.1.4.1.5504.5.1.1.1.19
		zhoneMauIngressBurstSize OBJECT-TYPE
			SYNTAX Integer32 (0..512000)
			UNITS "Kbits"
			MAX-ACCESS read-write
			STATUS current
			DESCRIPTION
				"Used to set the ingress burst size for	ethernet ports.
				Units are Kbits. Range is 0 512000. 0 is default implying no restriction."
			DEFVAL { 0 }
			::= { zhoneIfMauEntry 19 }
-- Used	to set max frame size for ethernet ports. Units	are Bytes.

		-- 1.3.6.1.4.1.5504.5.1.1.1.20
		zhoneMauEgressRate OBJECT-TYPE
			SYNTAX Integer32 (0..10240000)
			UNITS "Kbps"
			MAX-ACCESS read-write
			STATUS current
			DESCRIPTION
				"Used to set the egress	rate for ethernet ports.
				Units are Kbps.	Range is 0 10Gbps. 0 is	default	implying no limit."
			DEFVAL { 0 }
			::= { zhoneIfMauEntry 20 }
-- Used	to set max frame size for ethernet ports. Units	are Bytes.

		-- 1.3.6.1.4.1.5504.5.1.1.1.21
		zhoneMauEgressBurstSize	OBJECT-TYPE
			SYNTAX Integer32 (0..512000)
			UNITS "Kbits"
			MAX-ACCESS read-write
			STATUS current
			DESCRIPTION
				"Used to set the egress	burst size for ethernet	ports.
				Units are Kbits. Range is 0 512000. 0 is default implying no restriction."
			DEFVAL { 0 }
			::= { zhoneIfMauEntry 21 }
-- Used	to set max frame size for ethernet ports. Units	are Bytes.

		-- 1.3.6.1.4.1.5504.5.1.2
		zhoneMauAutoNegTable OBJECT-TYPE
			SYNTAX SEQUENCE	OF ZhoneMauAutoNegEntry
			MAX-ACCESS not-accessible
			STATUS current
			DESCRIPTION
				"Configuration and status objects for the
				auto-negotiation function of MAUs attached to
				interfaces."
			::= { zhoneEnet	2 }


		-- 1.3.6.1.4.1.5504.5.1.2.1
		zhoneMauAutoNegEntry OBJECT-TYPE
			SYNTAX ZhoneMauAutoNegEntry
			MAX-ACCESS not-accessible
			STATUS current
			DESCRIPTION
				"An entry in the table,	containing configuration
				and status information for the auto-negotiation
				function of a particular MAU."
			INDEX {	zhoneMauIfIndex	}
			::= { zhoneMauAutoNegTable 1 }


		ZhoneMauAutoNegEntry ::=
			SEQUENCE {
				zhoneMauAutoNegAdminStatus
					INTEGER,
				zhoneMauAutoNegRemoteSignaling
					INTEGER,
				zhoneMauAutoNegConfig
					INTEGER,
				zhoneMauAutoNegRestart
					INTEGER,
				zhoneMauAutoNegCapabilityBits
					BITS,
				zhoneMauAutoNegCapAdvertBits
					BITS,
				zhoneMauAutoNegCapRecvBits
					BITS,
				zhoneMauAutoNegRemoteFaultAdvert
					INTEGER,
				zhoneMauAutoNegRemoteFaultRecv
					INTEGER
			 }

		-- 1.3.6.1.4.1.5504.5.1.2.1.1
		zhoneMauAutoNegAdminStatus OBJECT-TYPE
			SYNTAX INTEGER
				{
				enabled(1),
				disabled(2)
				}
			MAX-ACCESS read-write
			STATUS current
			DESCRIPTION
				"Setting this object to	enabled(1) will	cause
				the interface which has	the auto-negotiation
				signaling ability to be	enabled.

				If the value of	this object is disabled(2) then
				the interface will act as it would if it had no
				auto-negotiation signaling.  Under these
				conditions, an IEEE 802.3 MAU will immediately
				be forced to the state indicated by the	value of
				the object zhoneMauDefaultType.

				NOTE TO	IMPLEMENTORS:  When
				ifMauAutoNegAdminStatus	transitions from enabled
				to disabled, the agent implementation MUST
				ensure that the	operational type of the	MAU (as
				reported by zhoneMauType) correctly transitions
				to the value specified by the zhoneMauDefaultType
				object,	rather than continuing to operate at the
				value earlier determined by the	auto-negotiation
				function."
			REFERENCE
				"[IEEE 802.3 Std], 30.6.1.1.2,
				aAutoNegAdminState and 30.6.1.2.2,
				acAutoNegAdminControl."
			::= { zhoneMauAutoNegEntry 1 }


		-- 1.3.6.1.4.1.5504.5.1.2.1.2
		zhoneMauAutoNegRemoteSignaling OBJECT-TYPE
			SYNTAX INTEGER
				{
				detected(1),
				notdetected(2)
				}
			MAX-ACCESS read-only
			STATUS current
			DESCRIPTION
				"A value indicating whether the	remote end of
				the link is using auto-negotiation signaling. It
				takes the value	detected(1) if and only	if,
				during the previous link negotiation, FLP Bursts
				were received."
			REFERENCE
				"[IEEE 802.3 Std], 30.6.1.1.3,
				aAutoNegRemoteSignaling."
			::= { zhoneMauAutoNegEntry 2 }


		-- 1.3.6.1.4.1.5504.5.1.2.1.3
		zhoneMauAutoNegConfig OBJECT-TYPE
			SYNTAX INTEGER
				{
				other(1),
				configuring(2),
				complete(3),
				disabled(4),
				parallelDetectFail(5)
				}
			MAX-ACCESS read-only
			STATUS current
			DESCRIPTION
				"A value indicating the	current	status of the
				auto-negotiation process.  The enumeration
				parallelDetectFail(5) maps to a	failure	in
				parallel detection as defined in 28.2.3.1 of
				[IEEE 802.3 Std]."
			REFERENCE
				"[IEEE 802.3 Std], 30.6.1.1.4,
				aAutoNegAutoConfig."
			::= { zhoneMauAutoNegEntry 3 }


		-- 1.3.6.1.4.1.5504.5.1.2.1.4
		zhoneMauAutoNegRestart OBJECT-TYPE
			SYNTAX INTEGER
				{
				restart(1),
				norestart(2)
				}
			MAX-ACCESS read-write
			STATUS current
			DESCRIPTION
				"If the	value of this object is	set to restart(1)
				then this will force auto-negotiation to begin
				link renegotiation. If auto-negotiation	signaling
				is disabled, a write to	this object
				has no effect.

				Setting	the value of this object to norestart(2)
				has no effect."
			REFERENCE
				"[IEEE 802.3 Std], 30.6.1.2.1,
				acAutoNegRestartAutoConfig."
			::= { zhoneMauAutoNegEntry 4 }


		-- 1.3.6.1.4.1.5504.5.1.2.1.5
		zhoneMauAutoNegCapabilityBits OBJECT-TYPE
			SYNTAX BITS
				{
				bOther(0),
				b10baseT(1),
				b10baseTFD(2),
				b100baseT4(3),
				b100baseTX(4),
				b100baseTXFD(5),
				b100baseT2(6),
				b100baseT2FD(7),
				bfdxPause(8),
				bfdxAPause(9),
				bfdxSPause(10),
				bfdxBPause(11),
				b1000baseX(12),
				b1000baseXFD(13),
				b1000baseT(14),
				b1000baseTFD(15),
				b10gbaseX(16),
				b10gbaseR(17),
				b10gbaseW(18),
				b10gbaseLX4(19),
				b10gbaseSR(20),
				b10gbaseSW(21),
				b10gbaseLR(22),
				b10gbaseLW(23),
				b10gbaseER(24),
				b10gbaseEW(25)
				}
			MAX-ACCESS read-only
			STATUS current
			DESCRIPTION
				"A value that uniquely identifies the set of
				capabilities of	the local auto-negotiation
				entity.	 Note that interfaces that support this
				MIB may	have capabilities that extend beyond the
				scope of this MIB.

				Note that the local auto-negotiation entity may
				support	some capabilities beyond the scope of
				this MIB.  This	is indicated by	returning the
				bit value bOther in addition to	any bit	values
				for capabilities that are listed above."
			REFERENCE
				"[IEEE 802.3 Std], 30.6.1.1.5,
				aAutoNegLocalTechnologyAbility."
			::= { zhoneMauAutoNegEntry 5 }


		-- 1.3.6.1.4.1.5504.5.1.2.1.6
		zhoneMauAutoNegCapAdvertBits OBJECT-TYPE
			SYNTAX BITS
				{
				bOther(0),
				b10baseT(1),
				b10baseTFD(2),
				b100baseT4(3),
				b100baseTX(4),
				b100baseTXFD(5),
				b100baseT2(6),
				b100baseT2FD(7),
				bFdxPause(8),
				bFdxAPause(9),
				bFdxSPause(10),
				bFdxBPause(11),
				b1000baseX(12),
				b1000baseXFD(13),
				b1000baseT(14),
				b1000baseTFD(15),
				b10gbaseX(16),
				b10gbaseR(17),
				b10gbaseW(18),
				b10gbaseLX4(19),
				b10gbaseSR(20),
				b10gbaseSW(21),
				b10gbaseLR(22),
				b10gbaseLW(23),
				b10gbaseER(24),
				b10gbaseEW(25)
				}
			MAX-ACCESS read-write
			STATUS current
			DESCRIPTION
				"A value that uniquely identifies the set of
				capabilities advertised	by the local
				auto-negotiation entity.

				Capabilities in	this object that are not
				available in ifMauAutoNegCapabilityBits	cannot
				be enabled.

				Note that the local auto-negotiation entity may
				advertise some capabilities beyond the scope of
				this MIB.  This	is indicated by	returning the
				bit value bOther in addition to	any bit	values
				for capabilities that are listed above."
			REFERENCE
				"[IEEE 802.3 Std], 30.6.1.1.6,
				aAutoNegAdvertisedTechnologyAbility."
			::= { zhoneMauAutoNegEntry 6 }


		-- 1.3.6.1.4.1.5504.5.1.2.1.7
		zhoneMauAutoNegCapRecvBits OBJECT-TYPE
			SYNTAX BITS
				{
				bOther(0),
				b10baseT(1),
				b10baseTFD(2),
				b100baseT4(3),
				b100baseTX(4),
				b100baseTXFD(5),
				b100baseT2(6),
				b100baseT2FD(7),
				bFdxPause(8),
				bFdxAPause(9),
				bFdxSPause(10),
				bFdxBPause(11),
				b1000baseX(12),
				b1000baseXFD(13),
				b1000baseT(14),
				b1000baseTFD(15),
				b10gbaseX(16),
				b10gbaseR(17),
				b10gbaseW(18),
				b10gbaseLX4(19),
				b10gbaseSR(20),
				b10gbaseSW(21),
				b10gbaseLR(22),
				b10gbaseLW(23),
				b10gbaseER(24),
				b10gbaseEW(25)
				}
			MAX-ACCESS read-only
			STATUS current
			DESCRIPTION
				"A value that uniquely identifies the set of
				capabilities received from the remote
				auto-negotiation entity.

				Note that interfaces that support this MIB may
				be attached to remote auto-negotiation entities
				which have capabilities	beyond the scope of this
				MIB.  This is indicated	by returning the bit
				value bOther(0)	in addition to any bit values for
				capabilities that are listed above."
			REFERENCE
				"[IEEE 802.3 Std], 30.6.1.1.7,
				aAutoNegReceivedTechnologyAbility."
			::= { zhoneMauAutoNegEntry 7 }


		-- 1.3.6.1.4.1.5504.5.1.2.1.8
		zhoneMauAutoNegRemoteFaultAdvert OBJECT-TYPE
			SYNTAX INTEGER
				{
				noError(1),
				offline(2),
				linkFailure(3),
				autoNegError(4)
				}
			MAX-ACCESS read-write
			STATUS current
			DESCRIPTION
				"A value that identifies any local fault
				indications that this MAU has detected and will
				advertise at the next auto-negotiation
				interaction for	1000Mbps MAUs."
			REFERENCE
				"[IEEE 802.3 Std], 30.6.1.1.6,
				aAutoNegAdvertisedTechnologyAbility."
			::= { zhoneMauAutoNegEntry 8 }


		-- 1.3.6.1.4.1.5504.5.1.2.1.9
		zhoneMauAutoNegRemoteFaultRecv OBJECT-TYPE
			SYNTAX INTEGER
				{
				noError(1),
				offline(2),
				linkFailure(3),
				autoNegError(4)
				}
			MAX-ACCESS read-only
			STATUS current
			DESCRIPTION
				"A value that identifies any fault indications
				received from the far end of a link by the
				local auto-negotiation entity for 1000Mbps
				MAUs."
			REFERENCE
				"[IEEE 802.3 Std], 30.6.1.1.7,
				aAutoNegReceivedTechnologyAbility."
			::= { zhoneMauAutoNegEntry 9 }


		-- 1.3.6.1.4.1.5504.5.1.3
		zhoneEnetTraps OBJECT-IDENTITY
			STATUS current
			DESCRIPTION
				"Description."
			::= { zhoneEnet	3 }


		-- 1.3.6.1.4.1.5504.5.1.3.0
		enetV2Traps OBJECT-IDENTITY
			STATUS current
			DESCRIPTION
				"Description."
			::= { zhoneEnetTraps 0 }


		-- 1.3.6.1.4.1.5504.5.1.3.0.1
		rprEastSpanTrap	NOTIFICATION-TYPE
			OBJECTS	{ ifIndex, ifAdminStatus, ifOperStatus,	ifName }
			STATUS current
			DESCRIPTION
				"Resilient Packet Ring (RPR) East Span Trap - indicates
				East span went Up or Down.  RPR	runs over Gigabit
				Ethernet."
			::= { enetV2Traps 1 }


		-- 1.3.6.1.4.1.5504.5.1.3.0.2
		rprWestSpanTrap	NOTIFICATION-TYPE
			OBJECTS	{ ifIndex, ifAdminStatus, ifOperStatus,	ifName }
			STATUS current
			DESCRIPTION
				"Resilient Packet Ring (RPR) West Span Trap - indicates
				West span went Up or Down.  RPR	runs over Gigabit
				Ethernet."
			::= { enetV2Traps 2 }


		-- 1.3.6.1.4.1.5504.5.1.3.0.3
		linkAggLink1Trap NOTIFICATION-TYPE
			STATUS current
			DESCRIPTION
				"Link Aggregation Link1	Trap - indicates
				Link 1 went Up or Down.	 "
			::= { enetV2Traps 3 }


		-- 1.3.6.1.4.1.5504.5.1.3.0.4
		linkAggLink2Trap NOTIFICATION-TYPE
			STATUS current
			DESCRIPTION
				"Link Aggregation Link2	Trap - indicates
				Link 2 went Up or Down.	"
			::= { enetV2Traps 4 }


		-- 1.3.6.1.4.1.5504.5.1.3.2
		rprSpanGroup NOTIFICATION-GROUP
			NOTIFICATIONS {	rprEastSpanTrap, rprWestSpanTrap }
			STATUS current
			DESCRIPTION
				"Grouping of RPR Span Notifications."
			::= { zhoneEnetTraps 2 }


		-- 1.3.6.1.4.1.5504.5.1.3.3
		linkAggLinkGroup NOTIFICATION-GROUP
			NOTIFICATIONS {	linkAggLink1Trap, linkAggLink2Trap }
			STATUS current
			DESCRIPTION
				"Grouping of Link Aggregation Link Notifications."
			::= { zhoneEnetTraps 3 }


		-- 1.3.6.1.4.1.5504.5.1.4
		zhoneLinkAggTable OBJECT-TYPE
			SYNTAX SEQUENCE	OF ZhoneLinkAggEntry
			MAX-ACCESS not-accessible
			STATUS current
			DESCRIPTION
				"Table of Identifiers specifying the partner system to which an	aggregation is connected."
			::= { zhoneEnet	4 }


		-- 1.3.6.1.4.1.5504.5.1.4.1
		zhoneLinkAggEntry OBJECT-TYPE
			SYNTAX ZhoneLinkAggEntry
			MAX-ACCESS not-accessible
			STATUS current
			DESCRIPTION
				"An entry in the table,	containing information
					about a	single partner system aggregation."
			INDEX {	zhoneLinkAggIfIndex }
			::= { zhoneLinkAggTable	1 }


		ZhoneLinkAggEntry ::=
			SEQUENCE {
				zhoneLinkAggIfIndex
					Integer32,
				zhoneLinkAggPartnerSystem
					OCTET STRING,
				zhoneLinkAggPartnerSystemPriority
					Integer32,
				zhoneLinkAggPartnerGroupId
					Integer32
			 }

		-- 1.3.6.1.4.1.5504.5.1.4.1.1
		zhoneLinkAggIfIndex OBJECT-TYPE
			SYNTAX Integer32 (0..2147483647)
			MAX-ACCESS read-only
			STATUS current
			DESCRIPTION
				"This variable uniquely	identifies the link
				aggregation by which the profile described
				in this	entry is identified."
			::= { zhoneLinkAggEntry	1 }


		-- 1.3.6.1.4.1.5504.5.1.4.1.2
		zhoneLinkAggPartnerSystem OBJECT-TYPE
			SYNTAX OCTET STRING (SIZE (0..18))
			MAX-ACCESS read-only
			STATUS current
			DESCRIPTION
				"A six-byte identifier,	similar	to a MAC address,
				specifying the partner system, but stored as a
				string,	and specified in the pattern
				'nn:nn:nn:nn:nn:nn', where 'nn'	is a hex number
				specifying a byte of the pattern."
			::= { zhoneLinkAggEntry	2 }


		-- 1.3.6.1.4.1.5504.5.1.4.1.3
		zhoneLinkAggPartnerSystemPriority OBJECT-TYPE
			SYNTAX Integer32
			MAX-ACCESS read-only
			STATUS current
			DESCRIPTION
				"An integer further specifying the partner system."
			::= { zhoneLinkAggEntry	3 }


		-- 1.3.6.1.4.1.5504.5.1.4.1.4
		zhoneLinkAggPartnerGroupId OBJECT-TYPE
			SYNTAX Integer32
			MAX-ACCESS read-only
			STATUS current
			DESCRIPTION
				"An integer identifier specifying the link group."
			::= { zhoneLinkAggEntry	4 }



	END

--
-- phyEnetMauMib.mib
--
