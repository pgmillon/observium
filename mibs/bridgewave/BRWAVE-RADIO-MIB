--
-- This SMIv2 module has been generated by smidump 0.4.1. Do not edit.
--

BRWAVE-RADIO-MIB DEFINITIONS ::= BEGIN

IMPORTS
    ifIndex
        FROM IF-MIB
    OBJECT-GROUP
        FROM SNMPv2-CONF
    Integer32, MODULE-IDENTITY, NOTIFICATION-TYPE, OBJECT-IDENTITY, 
    OBJECT-TYPE, Unsigned32, enterprises
        FROM SNMPv2-SMI
    DisplayString
        FROM SNMPv2-TC;

brwaveRadioMibModule MODULE-IDENTITY
    LAST-UPDATED "200607061100Z"
    ORGANIZATION 
        "BridgeWave Communications"
    CONTACT-INFO 
        "
         Postal: BridgeWave Communications
            		3350 Thomas Road
         				Santa Clara, CA 95054
         				USA
            Tel:    +1 408 567 6900
            Fax:    +1 408 567 0775
            Web:    www.bridgewave.com
            "
    DESCRIPTION 
        "Radio MIB module."
    REVISION    "200607061100Z"
    DESCRIPTION 
        "Combined ROOT/RADIO mib in one module."
    REVISION    "200505261130Z"
    DESCRIPTION 
        "Radio MIB module created."
    ::= { brwaveMibs 3 }


bridgeWave OBJECT-IDENTITY
    STATUS      current
    DESCRIPTION 
        "BridgeWave enterprise OID."
    ::= { enterprises 6080 }

brwaveReg OBJECT-IDENTITY
    STATUS      current
    DESCRIPTION 
        "Sub-tree for BridgeWave objects registration."
    ::= { bridgeWave 1 }

brwaveMibs OBJECT-IDENTITY
    STATUS      current
    DESCRIPTION 
        "Sub-tree to register values assigned to MIB modules
         with the MODULES-IDENTITY construct."
    ::= { brwaveReg 1 }

brwaveModules OBJECT-IDENTITY
    STATUS      current
    DESCRIPTION 
        "Sub-tree to register unique values assigned to
         identify all BridgeWave hardware and software
         components of ethernet radio products."
    ::= { brwaveReg 2 }

brwaveRadioFE60 OBJECT-IDENTITY
    STATUS      current
    DESCRIPTION 
        "Registered System OID for FE60 radio."
    ::= { brwaveModules 1 }

brwaveRadioGE60 OBJECT-IDENTITY
    STATUS      current
    DESCRIPTION 
        "Registered System OID for GE60 radio."
    ::= { brwaveModules 2 }

brwaveRadioAR60 OBJECT-IDENTITY
    STATUS      current
    DESCRIPTION 
        "Registered system OID for AdaptiveRate(AR60) radio."
    ::= { brwaveModules 3 }

brwaveCommon OBJECT-IDENTITY
    STATUS      current
    DESCRIPTION 
        "Sub-tree for BridgeWave objects common across products."
    ::= { bridgeWave 2 }

brwaveRadioSn OBJECT-TYPE
    SYNTAX      DisplayString
    MAX-ACCESS  read-only
    STATUS      current
    DESCRIPTION 
        "Radio serial number."
    ::= { brwaveCommon 1 }

brwaveUnitModel OBJECT-TYPE
    SYNTAX      DisplayString
    MAX-ACCESS  read-only
    STATUS      current
    DESCRIPTION 
        "Unit's model."
    ::= { brwaveCommon 2 }

brwaveBbSn OBJECT-TYPE
    SYNTAX      DisplayString
    MAX-ACCESS  read-only
    STATUS      current
    DESCRIPTION 
        "Base Band hardware serial number"
    ::= { brwaveCommon 3 }

brwaveIfSn OBJECT-TYPE
    SYNTAX      DisplayString
    MAX-ACCESS  read-only
    STATUS      current
    DESCRIPTION 
        "IF hardware serial number"
    ::= { brwaveCommon 4 }

brwaveMmwSn OBJECT-TYPE
    SYNTAX      DisplayString
    MAX-ACCESS  read-only
    STATUS      current
    DESCRIPTION 
        "MMW Hardware serial number"
    ::= { brwaveCommon 5 }

brwaveTrapCount OBJECT-TYPE
    SYNTAX      Unsigned32
    MAX-ACCESS  read-only
    STATUS      current
    DESCRIPTION 
        "Number of traps generated by unit since start-up.
         Rolls back to zero once reached to maximum value."
    ::= { brwaveCommon 6 }

brwaveProducts OBJECT-IDENTITY
    STATUS      current
    DESCRIPTION 
        "Sub-tree for product specific objects & events"
    ::= { bridgeWave 3 }

brwaveRadio OBJECT-IDENTITY
    STATUS      current
    DESCRIPTION 
        "Ethernet Radio (FE60/GE60/AR60) obejcts."
    ::= { brwaveProducts 1 }

brwaveRadioFactorySetup OBJECT-IDENTITY
    STATUS      current
    DESCRIPTION 
        "Group of factory setup objects."
    ::= { brwaveRadio 2 }

brwaveRadioTxBand OBJECT-TYPE
    SYNTAX      INTEGER { low(1), high(2) }
    MAX-ACCESS  read-only
    STATUS      current
    DESCRIPTION 
        "Radio Link Transmit frequency."
    ::= { brwaveRadioFactorySetup 1 }

brwaveRadioFactoryRate OBJECT-TYPE
    SYNTAX      INTEGER { adaptRate(1), mbps1000(2), mbps100(3) }
    MAX-ACCESS  read-only
    STATUS      current
    DESCRIPTION 
        "Factory configured radio link rate."
    ::= { brwaveRadioFactorySetup 3 }

brwaveRadioClearStats OBJECT-TYPE
    SYNTAX      Integer32
    MAX-ACCESS  read-write
    STATUS      current
    DESCRIPTION 
        "Clear Statistics, Set value of 1 to clear.
         Returns always 0 when read."
    ::= { brwaveRadioFactorySetup 4 }

brwaveRadioStatus OBJECT-IDENTITY
    STATUS      current
    DESCRIPTION 
        "Group of radio status objects."
    ::= { brwaveRadio 3 }

brwaveRadioInVoltage OBJECT-TYPE
    SYNTAX      Integer32
    MAX-ACCESS  read-only
    STATUS      current
    DESCRIPTION 
        "Input voltage. The reading of the unit's input voltage
         level in Volts x100."
    ::= { brwaveRadioStatus 1 }

brwaveRadioUnitTemperature OBJECT-TYPE
    SYNTAX      Integer32
    MAX-ACCESS  read-only
    STATUS      current
    DESCRIPTION 
        "Unit Temperature. The reading of the temperature sensor
         in degrees C x 100."
    ::= { brwaveRadioStatus 2 }

brwaveRadioTxTemperature OBJECT-TYPE
    SYNTAX      Integer32
    MAX-ACCESS  read-only
    STATUS      current
    DESCRIPTION 
        "Radio Transmiter Temperature. The reading of the radio
         temperature sensor in degrees C x 100."
    ::= { brwaveRadioStatus 3 }

brwaveRadioRSL OBJECT-TYPE
    SYNTAX      Integer32
    MAX-ACCESS  read-only
    STATUS      current
    DESCRIPTION 
        "Received Signal Level. The signal level of the received
         radio frequency in dBm x 100"
    ::= { brwaveRadioStatus 4 }

brwaveRadioRSLVoltage OBJECT-TYPE
    SYNTAX      DisplayString
    MAX-ACCESS  read-only
    STATUS      current
    DESCRIPTION 
        "Received Signal Level measured as Voltage."
    ::= { brwaveRadioStatus 5 }

brwaveRadioAbsRSL OBJECT-TYPE
    SYNTAX      Integer32
    MAX-ACCESS  read-only
    STATUS      current
    DESCRIPTION 
        "Received Signal Level. The signal level of the received
         radio frequency in dBm x 100"
    ::= { brwaveRadioStatus 6 }

brwaveRadioRSLVoltageInt OBJECT-TYPE
    SYNTAX      Integer32
    MAX-ACCESS  read-only
    STATUS      current
    DESCRIPTION 
        "Received Signal Level measured as Voltage."
    ::= { brwaveRadioStatus 7 }

brwaveCopperUtilization OBJECT-TYPE
    SYNTAX      Integer32
    MAX-ACCESS  read-only
    STATUS      current
    DESCRIPTION 
        "Link utilization calculated every polling interval."
    ::= { brwaveRadioStatus 8 }

brwaveFiberUtilization OBJECT-TYPE
    SYNTAX      Integer32
    MAX-ACCESS  read-only
    STATUS      current
    DESCRIPTION 
        "Link utilization calculated every polling interval."
    ::= { brwaveRadioStatus 9 }

brwaveRadioUtilization OBJECT-TYPE
    SYNTAX      Integer32
    MAX-ACCESS  read-only
    STATUS      current
    DESCRIPTION 
        "Link utilization calculated every polling interval."
    ::= { brwaveRadioStatus 10 }

brwaveRadioFecError OBJECT-TYPE
    SYNTAX      INTEGER { noError(0), preFec(1), postFec(2) }
    MAX-ACCESS  read-only
    STATUS      current
    DESCRIPTION 
        "Post and Pre FEC error calculated every polling interval
         0 - No Error, 1-Pre FEC Error, 2-Post FEC Error"
    ::= { brwaveRadioStatus 11 }

brwaveRadioPreFecFlag OBJECT-TYPE
    SYNTAX      Integer32
    MAX-ACCESS  read-only
    STATUS      current
    DESCRIPTION 
        "Pre FEC error flag every polling interval"
    ::= { brwaveRadioStatus 12 }

brwaveRadioPostFecFlag OBJECT-TYPE
    SYNTAX      Integer32
    MAX-ACCESS  read-only
    STATUS      current
    DESCRIPTION 
        "Post FEC error Flag every polling interval"
    ::= { brwaveRadioStatus 13 }

brwaveRadioLinkRate OBJECT-TYPE
    SYNTAX      Integer32
    MAX-ACCESS  read-only
    STATUS      current
    DESCRIPTION 
        "Radio Link Rate in Mbps."
    ::= { brwaveRadioStatus 14 }

brwaveRadioEvents OBJECT IDENTIFIER
    ::= { brwaveRadio 9 }

brwaveRadioEventsV2 OBJECT IDENTIFIER
    ::= { brwaveRadioEvents 0 }

brwaveRadioTrapObjs OBJECT IDENTIFIER
    ::= { brwaveRadioEvents 1 }

managerIP OBJECT-TYPE
    SYNTAX      OCTET STRING (SIZE(0..32))
    MAX-ACCESS  accessible-for-notify
    STATUS      current
    DESCRIPTION 
        "IP address of NMS station accessing the unit."
    ::= { brwaveRadioTrapObjs 1 }

userName OBJECT-TYPE
    SYNTAX      OCTET STRING (SIZE(0..32))
    MAX-ACCESS  accessible-for-notify
    STATUS      current
    DESCRIPTION 
        "User accessing the unit."
    ::= { brwaveRadioTrapObjs 2 }

brwaveConformance OBJECT IDENTIFIER
    ::= { brwaveRadio 10 }

brwaveRadioGroups OBJECT IDENTIFIER
    ::= { brwaveConformance 1 }

brwaveCompliances OBJECT IDENTIFIER
    ::= { brwaveConformance 2 }

brwaveErrorsOverThreshold NOTIFICATION-TYPE
    OBJECTS     { ifIndex, brwaveRadioUnitTemperature, 
                  brwaveRadioTxTemperature, brwaveRadioRSL }
    STATUS      current
    DESCRIPTION 
        "Link has error rate over threshold."
    ::= { brwaveRadioEventsV2 1 }

brwaveErrorsUnderThreshold NOTIFICATION-TYPE
    OBJECTS     { ifIndex, brwaveRadioUnitTemperature, 
                  brwaveRadioTxTemperature, brwaveRadioRSL }
    STATUS      current
    DESCRIPTION 
        "Link error rate changed from over to under threshold ."
    ::= { brwaveRadioEventsV2 2 }

brwaveUnitTemperatureAbnormal NOTIFICATION-TYPE
    OBJECTS     { brwaveRadioUnitTemperature }
    STATUS      current
    DESCRIPTION 
        "Radio unit temperature not in normal operating range.
         Normal range is: -20 to +75 degree Centigrade."
    ::= { brwaveRadioEventsV2 3 }

brwaveUnitTemperatureNormal NOTIFICATION-TYPE
    OBJECTS     { brwaveRadioUnitTemperature }
    STATUS      current
    DESCRIPTION 
        "Unit temperature restores from abnormal to normal range."
    ::= { brwaveRadioEventsV2 4 }

brwaveTxTemperatureAbnormal NOTIFICATION-TYPE
    OBJECTS     { brwaveRadioTxTemperature }
    STATUS      current
    DESCRIPTION 
        "Transmitter temperature is not in normal operating range.
         Normal range is: -20 to +75 degree Centigrade."
    ::= { brwaveRadioEventsV2 5 }

brwaveTxTemperatureNormal NOTIFICATION-TYPE
    OBJECTS     { brwaveRadioTxTemperature }
    STATUS      current
    DESCRIPTION 
        "Transmitter temperature is restored to normal range."
    ::= { brwaveRadioEventsV2 6 }

brwaveInputVoltageAbnormal NOTIFICATION-TYPE
    OBJECTS     { brwaveRadioInVoltage }
    STATUS      current
    DESCRIPTION 
        "Unit's input voltage is not in normal range.
         Normal input voltage > 16 Volts."
    ::= { brwaveRadioEventsV2 7 }

brwaveInputVoltageNormal NOTIFICATION-TYPE
    OBJECTS     { brwaveRadioInVoltage }
    STATUS      current
    DESCRIPTION 
        "Unit's input voltage is restored to normal range."
    ::= { brwaveRadioEventsV2 8 }

brwaveRslNormal NOTIFICATION-TYPE
    OBJECTS     { brwaveRadioRSL }
    STATUS      current
    DESCRIPTION 
        "Received Signal Level is normal. Normal signal level
         RSL > -55.00 dBm (Gigabit) and RSL > -59.00 dBm (Fast Ethernet)."
    ::= { brwaveRadioEventsV2 10 }

brwaveRslMinor NOTIFICATION-TYPE
    OBJECTS     { brwaveRadioRSL }
    STATUS      current
    DESCRIPTION 
        "Received Signal Leve droped to the level of minor event.
         RSL from -55.00 to -59.00 dBm (GE Radio)
         RSL from -59.00 to -65.00 dBm (FE radio)."
    ::= { brwaveRadioEventsV2 11 }

brwaveRslMajor NOTIFICATION-TYPE
    OBJECTS     { brwaveRadioRSL }
    STATUS      current
    DESCRIPTION 
        "RSL droppped to the level of major event.
         RSL < -59.00 dBm (GE Radio) or RSL < -65 dBm (FE radio)."
    ::= { brwaveRadioEventsV2 13 }

brwaveConfigChange NOTIFICATION-TYPE
    STATUS      current
    DESCRIPTION 
        "Configuration changes are performed by WEB client."
    ::= { brwaveRadioEventsV2 26 }

brwaveLoginSuccessfull NOTIFICATION-TYPE
    STATUS      current
    DESCRIPTION 
        "NMS Loged in successfully."
    ::= { brwaveRadioEventsV2 27 }

brwaveGeToFeSwitch NOTIFICATION-TYPE
    OBJECTS     { brwaveRadioRSL }
    STATUS      current
    DESCRIPTION 
        "Tx Rate switched from GE to FE."
    ::= { brwaveRadioEventsV2 28 }

brwaveFeToGeSwitch NOTIFICATION-TYPE
    OBJECTS     { brwaveRadioRSL }
    STATUS      current
    DESCRIPTION 
        "Tx Rate switched from FE to GE."
    ::= { brwaveRadioEventsV2 29 }

brwaveCommonGroup OBJECT-GROUP
    OBJECTS     { brwaveRadioSn, brwaveUnitModel, brwaveTrapCount }
    STATUS      current
    DESCRIPTION 
        "Collection of common objects."
    ::= { brwaveRadioGroups 1 }

brwaveFactoryGroup OBJECT-GROUP
    OBJECTS     { brwaveRadioTxBand }
    STATUS      current
    DESCRIPTION 
        "Collection of factory setup objects."
    ::= { brwaveRadioGroups 2 }

brwaveStatusGroup OBJECT-GROUP
    OBJECTS     { brwaveRadioInVoltage, brwaveRadioUnitTemperature, 
                  brwaveRadioTxTemperature, brwaveRadioRSL, 
                  brwaveRadioRSLVoltage }
    STATUS      current
    DESCRIPTION 
        "Collection of status objects."
    ::= { brwaveRadioGroups 3 }

END -- end of module BRWAVE-RADIO-MIB.
