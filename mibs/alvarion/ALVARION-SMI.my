-- ****************************************************************************
--  ALVARION-SMI definitions
--
--  Copyright (c) 2007, Alvarion Ltd.
--  All Rights Reserved.
--
--  Alvarion enterprise Structure of Management Information.
--
-- ****************************************************************************


ALVARION-SMI DEFINITIONS ::= BEGIN

IMPORTS
    MODULE-IDENTITY, OBJECT-IDENTITY,
    enterprises
        FROM SNMPv2-SMI
;

alvarionWireless MODULE-IDENTITY
    LAST-UPDATED    "200710310000Z"
    ORGANIZATION    "Alvarion Ltd."
    CONTACT-INFO    "Alvarion Ltd.
                     Postal: 21a HaBarzel St.
                             P.O. Box 13139
                             Tel-Aviv 69710
                             Israel
                     Phone:  +972 3 645 6262"
    DESCRIPTION     "Structure of Management Information for Alvarion
                     enterprise MIBs."

    ::= { enterprises 12394 1 10 }    -- assigned by IANA


alvarionProducts OBJECT-IDENTITY
    STATUS      current
    DESCRIPTION "Root OID from which sysObjectID values are assigned. Actual
                 values are defined in ALVARION-PRODUCTS-MIB."
    ::= { alvarionWireless 1 }

alvarionExperiment OBJECT-IDENTITY
    STATUS      current
    DESCRIPTION "Main subtree for experimental mib development."
    ::= { alvarionWireless 3 }

alvarionModules OBJECT-IDENTITY
    STATUS      current
    DESCRIPTION "Root OID from which alvarion MODULE-IDENTITY values may be
                 assigned."
    ::= { alvarionWireless 4 }

alvarionMgmtV2 OBJECT-IDENTITY
    STATUS      current
    DESCRIPTION "Main subtree for mib development."
    ::= { alvarionWireless 5 }

variation OBJECT-IDENTITY
    STATUS      current
    DESCRIPTION "Main subtree for variation MIBs development."
    ::= { alvarionWireless 7 }

END
