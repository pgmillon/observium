-- ****************************************************************************
--  ALVARION-CLIENT-TRACKING-MIB definitions
--
--  Copyright (c) 2007, Alvarion Ltd.
--  All Rights Reserved.
--
--  Alvarion Client Tracking MIB file.
--
-- ****************************************************************************


ALVARION-CLIENT-TRACKING-MIB DEFINITIONS ::= BEGIN

IMPORTS
    MODULE-IDENTITY, OBJECT-TYPE, NOTIFICATION-TYPE
        FROM    SNMPv2-SMI
    DisplayString
        FROM    SNMPv2-TC
    MODULE-COMPLIANCE, OBJECT-GROUP, NOTIFICATION-GROUP
        FROM    SNMPv2-CONF
    alvarionMgmtV2
        FROM    ALVARION-SMI
    AlvarionNotificationEnable
        FROM    ALVARION-TC
;


alvarionClientTrackingMIB MODULE-IDENTITY
    LAST-UPDATED    "200710310000Z"
    ORGANIZATION    "Alvarion Ltd."
    CONTACT-INFO    "Alvarion Ltd.
                     Postal: 21a HaBarzel St.
                             P.O. Box 13139
                             Tel-Aviv 69710
                             Israel
                     Phone:  +972 3 645 6262"
    DESCRIPTION     "Alvarion Client Tracking module."

    ::= { alvarionMgmtV2 19 }


-- alvarionClientTrackingMIBObjects definition
alvarionClientTrackingMIBObjects OBJECT IDENTIFIER ::= { alvarionClientTrackingMIB 1 }

-- Firmware Distribution groups
clientTrackingConfig OBJECT IDENTIFIER ::=  { alvarionClientTrackingMIBObjects 1 }
clientTrackingInfo OBJECT IDENTIFIER ::=  { alvarionClientTrackingMIBObjects 2 }


-- The clientTrackingConfig group controls the process parameters

clientTrackingSuccessfulAssociationNotificationEnabled OBJECT-TYPE
    SYNTAX      AlvarionNotificationEnable
    MAX-ACCESS  read-write
    STATUS      current
    DESCRIPTION "Specifies if clientTrackingSuccessfulAssociation notifications
                 are generated."
    DEFVAL      { disable }
    ::= { clientTrackingConfig 1 }

clientTrackingAssociationFailureNotificationEnabled OBJECT-TYPE
    SYNTAX      AlvarionNotificationEnable
    MAX-ACCESS  read-write
    STATUS      current
    DESCRIPTION "Specifies if clientTrackingAssociationFailure notifications
                 are generated."
    DEFVAL      { disable }
    ::= { clientTrackingConfig 2 }

clientTrackingSuccessfulReAssociationNotificationEnabled OBJECT-TYPE
    SYNTAX      AlvarionNotificationEnable
    MAX-ACCESS  read-write
    STATUS      current
    DESCRIPTION "Specifies if clientTrackingSuccessfulReAssociation
                 notifications are generated."
    DEFVAL      { disable }
    ::= { clientTrackingConfig 3 }

clientTrackingReAssociationFailureNotificationEnabled OBJECT-TYPE
    SYNTAX      AlvarionNotificationEnable
    MAX-ACCESS  read-write
    STATUS      current
    DESCRIPTION "Specifies if clientTrackingReAssociationFailure notifications
                 are generated."
    DEFVAL      { disable }
    ::= { clientTrackingConfig 4 }

clientTrackingSuccessfulAuthenticationNotificationEnabled OBJECT-TYPE
    SYNTAX      AlvarionNotificationEnable
    MAX-ACCESS  read-write
    STATUS      current
    DESCRIPTION "Specifies if clientTrackingSuccessfulAuthentication
                 notifications are generated."
    DEFVAL      { disable }
    ::= { clientTrackingConfig 5 }

clientTrackingAuthenticationFailureNotificationEnabled OBJECT-TYPE
    SYNTAX      AlvarionNotificationEnable
    MAX-ACCESS  read-write
    STATUS      current
    DESCRIPTION "Specifies if clientTrackingAuthenticationFailure
                 notifications are generated."
    DEFVAL      { disable }
    ::= { clientTrackingConfig 6 }

clientTrackingSuccessfulDisAssociationNotificationEnabled OBJECT-TYPE
    SYNTAX      AlvarionNotificationEnable
    MAX-ACCESS  read-write
    STATUS      current
    DESCRIPTION "Specifies if clientTrackingSuccessfulDisAssociation notifications
                 are generated."
    DEFVAL      { disable }
    ::= { clientTrackingConfig 7 }

clientTrackingDisAssociationFailureNotificationEnabled OBJECT-TYPE
    SYNTAX      AlvarionNotificationEnable
    MAX-ACCESS  read-write
    STATUS      current
    DESCRIPTION "Specifies if clientTrackingDisAssociationFailure notifications
                 are generated."
    DEFVAL      { disable }
    ::= { clientTrackingConfig 8 }

clientTrackingSuccessfulDeAuthenticationNotificationEnabled OBJECT-TYPE
    SYNTAX      AlvarionNotificationEnable
    MAX-ACCESS  read-write
    STATUS      current
    DESCRIPTION "Specifies if clientTrackingSuccessfulDeAuthentication
                 notifications are generated."
    DEFVAL      { disable }
    ::= { clientTrackingConfig 9 }

clientTrackingDeAuthenticationFailureNotificationEnabled OBJECT-TYPE
    SYNTAX      AlvarionNotificationEnable
    MAX-ACCESS  read-write
    STATUS      current
    DESCRIPTION "Specifies if clientTrackingDeAuthenticationFailure
                 notifications are generated."
    DEFVAL      { disable }
    ::= { clientTrackingConfig 10 }


-- The clientTrackingInfo group contains information and statuses about
-- the client tracking feature.

clientTrackingEventInformation OBJECT-TYPE
    SYNTAX      DisplayString
    MAX-ACCESS  accessible-for-notify
    STATUS      current
    DESCRIPTION "Gives a detailed description of an event in the system."
    ::= { clientTrackingInfo 1 }


-- Client tracking notifications
alvarionClientTrackingMIBNotificationPrefix OBJECT IDENTIFIER ::= { alvarionClientTrackingMIB 2 }
alvarionClientTrackingMIBNotifications OBJECT IDENTIFIER ::= { alvarionClientTrackingMIBNotificationPrefix 0 }

clientTrackingSuccessfulAssociation NOTIFICATION-TYPE
    OBJECTS     {
                    clientTrackingEventInformation
                }
    STATUS      current
    DESCRIPTION "Sent when a user is successfully associated with the AP."
    ::= { alvarionClientTrackingMIBNotifications 1 }

clientTrackingAssociationFailure NOTIFICATION-TYPE
    OBJECTS     {
                    clientTrackingEventInformation
                }
    STATUS      current
    DESCRIPTION "Sent when a user has failed to associate with the AP."
    ::= { alvarionClientTrackingMIBNotifications 2 }

clientTrackingSuccessfulReAssociation NOTIFICATION-TYPE
    OBJECTS     {
                    clientTrackingEventInformation
                }
    STATUS      current
    DESCRIPTION "Sent when a user is successfully reassociated with the AP."
    ::= { alvarionClientTrackingMIBNotifications 3 }

clientTrackingReAssociationFailure NOTIFICATION-TYPE
    OBJECTS     {
                    clientTrackingEventInformation
                }
    STATUS      current
    DESCRIPTION "Sent when a user has failed to reassociate with the AP."
    ::= { alvarionClientTrackingMIBNotifications 4 }

clientTrackingSuccessfulAuthentication NOTIFICATION-TYPE
    OBJECTS     {
                    clientTrackingEventInformation
                }
    STATUS      current
    DESCRIPTION "Sent when a user is successfully authenticated."
    ::= { alvarionClientTrackingMIBNotifications 5 }

clientTrackingAuthenticationFailure NOTIFICATION-TYPE
    OBJECTS     {
                    clientTrackingEventInformation
                }
    STATUS      current
    DESCRIPTION "Sent when a user has failed to authenticate."
    ::= { alvarionClientTrackingMIBNotifications 6 }

clientTrackingSuccessfulDisAssociation NOTIFICATION-TYPE
    OBJECTS     {
                    clientTrackingEventInformation
                }
    STATUS      current
    DESCRIPTION "Sent when a user is successfully disassociated from the AP."
    ::= { alvarionClientTrackingMIBNotifications 7 }

clientTrackingDisAssociationFailure NOTIFICATION-TYPE
    OBJECTS     {
                    clientTrackingEventInformation
                }
    STATUS      current
    DESCRIPTION "Sent when a user has failed to disassociate from the AP."
    ::= { alvarionClientTrackingMIBNotifications 8 }

clientTrackingSuccessfulDeAuthentication NOTIFICATION-TYPE
    OBJECTS     {
                    clientTrackingEventInformation
                }
    STATUS      current
    DESCRIPTION "Sent when a user is successfully deauthenticated."
    ::= { alvarionClientTrackingMIBNotifications 9 }

clientTrackingDeAuthenticationFailure NOTIFICATION-TYPE
    OBJECTS     {
                    clientTrackingEventInformation
                }
    STATUS      current
    DESCRIPTION "Sent when a user has failed to deauthenticate."
    ::= { alvarionClientTrackingMIBNotifications 10 }


-- conformance information
alvarionClientTrackingMIBConformance OBJECT IDENTIFIER ::= { alvarionClientTrackingMIB 3 }
alvarionClientTrackingMIBCompliances OBJECT IDENTIFIER ::= { alvarionClientTrackingMIBConformance 1 }
alvarionClientTrackingMIBGroups      OBJECT IDENTIFIER ::= { alvarionClientTrackingMIBConformance 2 }

-- compliance statements
alvarionClientTrackingMIBCompliance MODULE-COMPLIANCE
    STATUS      current
    DESCRIPTION "The compliance statement for entities which implement
                 the Alvarion Tools MIB."
    MODULE      MANDATORY-GROUPS
                {
                    alvarionClientTrackingConfigMIBGroup,
                    alvarionClientTrackingInfoMIBGroup,
                    alvarionClientTrackingNotificationGroup
                }
    ::= { alvarionClientTrackingMIBCompliances 1 }

-- units of conformance
alvarionClientTrackingConfigMIBGroup OBJECT-GROUP
    OBJECTS     {
                    clientTrackingSuccessfulAssociationNotificationEnabled,
                    clientTrackingAssociationFailureNotificationEnabled,
                    clientTrackingSuccessfulReAssociationNotificationEnabled,
                    clientTrackingReAssociationFailureNotificationEnabled,
                    clientTrackingSuccessfulAuthenticationNotificationEnabled,
                    clientTrackingAuthenticationFailureNotificationEnabled,
                    clientTrackingSuccessfulDisAssociationNotificationEnabled,
                    clientTrackingDisAssociationFailureNotificationEnabled,
                    clientTrackingSuccessfulDeAuthenticationNotificationEnabled,
                    clientTrackingDeAuthenticationFailureNotificationEnabled
                }
    STATUS      current
    DESCRIPTION "A collection of objects providing control over the client
                 tracking MIB capability."
    ::= { alvarionClientTrackingMIBGroups 1 }

alvarionClientTrackingInfoMIBGroup OBJECT-GROUP
    OBJECTS     {
                    clientTrackingEventInformation
                }
    STATUS      current
    DESCRIPTION "A collection of objects providing information over the
                 client tracking MIB capability."
    ::= { alvarionClientTrackingMIBGroups 2 }

alvarionClientTrackingNotificationGroup NOTIFICATION-GROUP
    NOTIFICATIONS   {
                        clientTrackingSuccessfulAssociation,
                        clientTrackingAssociationFailure,
                        clientTrackingSuccessfulReAssociation,
                        clientTrackingReAssociationFailure,
                        clientTrackingSuccessfulAuthentication,
                        clientTrackingAuthenticationFailure,
                        clientTrackingSuccessfulDisAssociation,
                        clientTrackingDisAssociationFailure,
                        clientTrackingSuccessfulDeAuthentication,
                        clientTrackingDeAuthenticationFailure
                    }
    STATUS      current
    DESCRIPTION "A collection of supported notifications."
    ::= { alvarionClientTrackingMIBGroups 3 }

END
