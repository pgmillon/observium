-- ****************************************************************************
--  ALVARION-PRODUCTS-MIB definitions
--
--  Copyright (c) 2007, Alvarion Ltd.
--  All Rights Reserved.
--
--  Alvarion Product Identifiers.
--
-- ****************************************************************************


ALVARION-PRODUCTS-MIB DEFINITIONS ::= BEGIN

IMPORTS
    MODULE-IDENTITY
        FROM    SNMPv2-SMI
    alvarionProducts, alvarionModules
        FROM    ALVARION-SMI
;


alvarionProductsMIB MODULE-IDENTITY
    LAST-UPDATED    "200710310000Z"
    ORGANIZATION    "Alvarion Ltd."
    CONTACT-INFO    "Alvarion Ltd.
                     Postal: 21a HaBarzel St.
                             P.O. Box 13139
                             Tel-Aviv 69710
                             Israel
                     Phone:  +972 3 645 6262"
    DESCRIPTION     "Alvarion Product Identifiers."

    ::= { alvarionModules 2 }


-- Lists all the Alvarion product Identifiers.
-- Use the sysObjectID in order to determine what is the product you are using
alvarionWI2CTRL40       OBJECT IDENTIFIER ::= { alvarionProducts 25 }
alvarionWI2CTRL200      OBJECT IDENTIFIER ::= { alvarionProducts 27 }
alvarionWI2CTRL10       OBJECT IDENTIFIER ::= { alvarionProducts 35 }
alvarionWI2SR1          OBJECT IDENTIFIER ::= { alvarionProducts 36 }
alvarionWI2DR1          OBJECT IDENTIFIER ::= { alvarionProducts 37 }

END
