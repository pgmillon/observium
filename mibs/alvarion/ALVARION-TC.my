-- ****************************************************************************
--  ALVARION-TC definitions
--
--  Copyright (c) 2007, Alvarion Ltd.
--  All Rights Reserved.
--
--  Textual Conventions for Alvarion MIBs.
--
-- ****************************************************************************


ALVARION-TC DEFINITIONS ::= BEGIN

IMPORTS
    MODULE-IDENTITY,
    Integer32
        FROM    SNMPv2-SMI
    TEXTUAL-CONVENTION
        FROM    SNMPv2-TC
    alvarionModules
        FROM    ALVARION-SMI
;


alvarionTextualConventions MODULE-IDENTITY
    LAST-UPDATED    "200710310000Z"
    ORGANIZATION    "Alvarion Ltd."
    CONTACT-INFO    "Alvarion Ltd.
                     Postal: 21a HaBarzel St.
                             P.O. Box 13139
                             Tel-Aviv 69710
                             Israel
                     Phone:  +972 3 645 6262"
    DESCRIPTION     "This module defines the Textual Conventions used in
                    Alvarion enterprise MIBs."

    ::= { alvarionModules 1 }


-- Alvarion authentication mode textual convention
--      local   - the authentication is done locally from the device local
--                database information.
--      profile - an AAA profile is used in order to retrieve the
--                authentication parameters.
AlvarionAuthenticationMode ::= TEXTUAL-CONVENTION
    STATUS      current
    DESCRIPTION "Specifies the authentication mode to be used.

                  local: The authentication is done locally from the
                         device local database information.

                  profile: An AAA profile is used in order to retrieve
                           the authentication parameters."
    SYNTAX      INTEGER
                    {
                        local(1),
                        profile(2)
                    }

-- Alvarion public access users authentication mode textual convention
--      none    - users are not allowed to login.
--      local   - the authentication is done locally from the device local
--                database information.
--      profile - an AAA profile is used in order to retrieve the
--                authentication parameters.
--      localAndProfile - the authentication is done locally first. If it fails
--                        an AAA profile is used.
AlvarionUsersAuthenticationMode ::= TEXTUAL-CONVENTION
    STATUS      current
    DESCRIPTION "Specifies the authentication mode to be used.

                   none: Users are not allowed to login.

                   local: The authentication is done locally from the
                          device local database information.

                   profile: An AAA profile is used in order to retrieve
                            the authentication parameters.

                   localAndProfile: The authentication is done locally
                                    first. If it fails an AAA profile
                                    is used."
    SYNTAX      INTEGER
                    {
                        none(0),
                        local(1),
                        profile(2),
                        localAndProfile(3)
                    }

-- Alvarion public access users authentication type textual convention
--      mac          - users authenticated using their MAC addresses.
--      ieee802dot1x - users authenticated through 802.1x.
--      html         - users authenticated with html.
AlvarionUsersAuthenticationType ::= TEXTUAL-CONVENTION
    STATUS      current
    DESCRIPTION "Specifies the authentication type to be used.

                   mac: Users authenticated using their MAC addresses.

		       ieee802dot1x: Users authenticated through 802.1x.

		       html: Users authenticated with html."
    SYNTAX      INTEGER
                {
                    mac(1),
                    ieee802dot1x(2),
                    html(3)
                }

-- Alvarion Notification enable textual convention
--      enable  - enables the generation of the associated notification
--      disable - disables the generation of the associated notification
AlvarionNotificationEnable ::= TEXTUAL-CONVENTION
    STATUS      current
    DESCRIPTION "Specifies the generation of notification traps.
                 
                   enable: Enable the generation of the associated
                           notification.

                   disable: Disables the generation of the associated
                            notification"
    SYNTAX      INTEGER
                    {
                        enable(1),
                        disable(2)
                    }

-- Alvarion AAA Profile Index textual convention
--      A profile index refers to an entry in the AAA profile table.
AlvarionProfileIndex ::= TEXTUAL-CONVENTION
    STATUS      current
    DESCRIPTION "A profile index refers to an entry in the AAA profile table."
    SYNTAX      Integer32 (1..2147483647)

-- Alvarion AAA Profile Index textual convention
--      A profile index refers to an entry in the AAA profile table.
--      When the special value Zero is specified, no AAA server profile is
--      selected.
AlvarionProfileIndexOrZero ::= TEXTUAL-CONVENTION
    STATUS      current
    DESCRIPTION "A profile index refers to an entry in the AAA profile table.
                 When the special value Zero is specified, no AAA
                 server profile is selected."
    SYNTAX      Integer32 (0..2147483647)

-- Alvarion AAA Server Index textual convention
--      A server index refers to an entry in the AAA server table.
AlvarionServerIndex ::= TEXTUAL-CONVENTION
    STATUS      current
    DESCRIPTION "A server index refers to an entry in the AAA server table."
    SYNTAX      Integer32 (1..2147483647)

-- Alvarion AAA Server Index textual convention
--      A server index refers to an entry in the AAA server table.
--      When the special value Zero is specified, no AAA server is selected.
AlvarionServerIndexOrZero ::= TEXTUAL-CONVENTION
    STATUS      current
    DESCRIPTION "A server index refers to an entry in the AAA server table.
                 When the special value Zero is specified, no AAA
                 server is selected."
    SYNTAX      Integer32 (0..2147483647)

-- Alvarion Service Set Identifier textual convention
--      A generic service set identifier (SSID) convention is defined here and
--      used throughout the Alvarion proprietary MIBs.
AlvarionSSID ::= TEXTUAL-CONVENTION
    STATUS      current
    DESCRIPTION "A generic service set identifier (SSID) convention is defined
                 here and used throughout the Alvarion proprietary MIBs. This
		 specific textual convention is used for inputing SSIDs."
    SYNTAX      OCTET STRING (SIZE (1..32))

-- Alvarion Service Set Identifier textual convention
--      A generic service set identifier (SSID) convention is defined here and
--      used throughout the Alvarion proprietary MIBs.
AlvarionSSIDOrNone ::= TEXTUAL-CONVENTION
    STATUS      current
    DESCRIPTION "A generic service set identifier (SSID) convention is defined
                 here and used throughout the Alvarion proprietary MIBs. This
		 specific textual convention is used when displaying SSIDs."
    SYNTAX      OCTET STRING (SIZE (0..32))

-- Alvarion Security textual convention
--      An enumeration of the different Wireless Security modes allowed in the
--      Alvarion products.
--                     'none'   - No wireless protection.
--                     'wep'    - WEP (static keys).
--                     'ieee802dot1x' - 802.1x no encryption.
--                     'ieee802dot1xWithWep' - 802.1x + WEP (dynamic keys).
--                     'wpa'    - 802.1x + TKIP + Key source AAA profile.
--                     'wpaPsk' - 802.1x + TKIP + Key Source Pre-Shared Key.
AlvarionSecurity ::= TEXTUAL-CONVENTION
    STATUS      current
    DESCRIPTION "An enumeration of the different Security modes allowed
                 in the Alvarion products.

                 NOTE: 'unknown'- Could not identify the protection mode.
                       'none'   - No wireless protection.
                       'wep'    - WEP (static keys).
                       'ieee802dot1x' - 802.1x no encryption.
                       'ieee802dot1xWithWep' - 802.1x + WEP (dynamic keys).
                       'wpa'    - 802.1x + TKIP + Key source AAA profile.
                       'wpaPsk' - 802.1x + TKIP + Key Source Pre-Shared Key."
    SYNTAX      INTEGER
                {
                    unknown(0),
                    none(1),
                    wep(2),
                    ieee802dot1x(3),
                    ieee802dot1xWithWep(4),
                    wpa(5),
                    wpaPsk(6)
                }

-- Alvarion Priority Queue textual convention
--      An enumeration of the different queues supported in the QOS
--      and Bandwidth control feature of the Alvarion products.
--                     'low' - Low priority queue
--                     'normal' - Normal priority queue
--                     'high' - High priority queue
--                     'veryHigh' - Very High priority queue
AlvarionPriorityQueue ::= TEXTUAL-CONVENTION
    STATUS      current
    DESCRIPTION "An enumeration of the different queues supported in the
                 QOS and Bandwidth control feature of the Alvarion products."
    SYNTAX      INTEGER 
                {
                    low(1),
                    normal(2),
                    high(3),
                    veryHigh(4)
                }

-- Alvarion Data Rate textual convention
--      An enumeration of the different data rates supported on a per VAP basis.
--                     'lowestAvailable' - 
AlvarionDataRate ::= TEXTUAL-CONVENTION
    STATUS      current
    DESCRIPTION "An enumeration of the different data rates supported on a per
                 VAP basis."
    SYNTAX      INTEGER
                {
                    rateLowestAvailable(1),
                    rate1Meg(2),
                    rate2Meg(3),
                    rate5dot5Meg(4),
                    rate6Meg(5),
                    rate9Meg(6),
                    rate11Meg(7),
                    rate12Meg(8),
                    rate18Meg(9),
                    rate24Meg(10),
                    rate36Meg(11),
                    rate48Meg(12),
                    rate54Meg(13),
                    rateHighestAvailable(14)
                }

-- Alvarion Radio Type textual convention
--      An enumeration of the different radio types used in
--      the Alvarion products.
AlvarionRadioType ::= TEXTUAL-CONVENTION
    STATUS      current
    DESCRIPTION "An enumeration of the different radio types used in
                 the Alvarion products."
    SYNTAX      INTEGER 
                {
                    cm6(1),
                    cm9(2),
                    sunfish(3),
                    wi2(4)
                }

END
