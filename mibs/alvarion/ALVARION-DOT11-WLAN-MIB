-- Title:      ALVARION  Private MIB
--             This Private MIB supports BreezeAccess_VL, BreezeACCESS_4900 and BreezeNET-B product lines.
--
--
-- Version:    6.6.2
-- Date:       Wednesday June 8 2011
-- Comments:   ALVARION agents also support the following Public MIBs:

-- This MIB supports BreezeACCESS VL products (AU and SU), 
-- BreezeACCESS 4900 (AU and SU) and 
-- BreezeNET-B products (BU and RB). 
  
-- Some MIB compilers require that the following lines 
-- for proper compilation

--#include "rfc1155.smi"
--#include "rfc1212.smi"

 
-- mgmt           OBJECT IDENTIFIER ::= { iso org(3) dod(6) internet(1)  mgmt(2) }
-- mib            OBJECT IDENTIFIER ::= { mgmt 1  }
-- directory      OBJECT IDENTIFIER ::= { internet 1  }
-- experimental   OBJECT IDENTIFIER ::= { internet 3  }
-- private        OBJECT IDENTIFIER ::= { internet 4  }
-- enterprises    OBJECT IDENTIFIER ::= { private 1  }

-- End of lines which might be needed to other MIB browsers 
-- for proper compilation


ALVARION-DOT11-WLAN-MIB DEFINITIONS ::= BEGIN


  IMPORTS
       MODULE-IDENTITY, NOTIFICATION-TYPE, enterprises, IpAddress,Counter32,Integer32,Unsigned32,OBJECT-TYPE
               FROM SNMPv2-SMI;

alvarion        	OBJECT IDENTIFIER ::= { enterprises 12394 }
products		    OBJECT IDENTIFIER ::= { alvarion 1 }

breezeAccessVLMib	MODULE-IDENTITY
		LAST-UPDATED	"1009231130Z"
		ORGANIZATION	"Alvarion Ltd."
		CONTACT-INFO	"Alvarion Customer Service
					     Postal: Alvarion Ltd.
					     Barzel 21
					     Tel Aviv 69710 
					     ISRAEL
		                 E-mail: CS_Coordinator@alvarion.com"
		DESCRIPTION		
		      "BreezeAccess VL, BreezeACCESS 4900, BreezeNET-B and BreezeACCESS-Security"
		REVISION 	     "1009231130Z"
		
		DESCRIPTION		
		      "Version 6.6"
		::=  {  products 1 }

MacAddress ::= OCTET STRING (SIZE(6))
DisplayString ::= OCTET STRING 

alvarionOID     OBJECT IDENTIFIER ::= { alvarion      4 }
brzAccessVLOID  OBJECT IDENTIFIER ::= { alvarionOID   1 }


brzAccessVLAU     OBJECT IDENTIFIER ::= { brzAccessVLOID 1 }
brzAccessVLSU     OBJECT IDENTIFIER ::= { brzAccessVLOID 2 }

brzAccessVLAU-BS    OBJECT IDENTIFIER ::= { brzAccessVLOID 4 }
brzAccessVLAU-SA    OBJECT IDENTIFIER ::= { brzAccessVLOID 5 }

brzAccessVLAUS-BS   OBJECT IDENTIFIER ::= { brzAccessVLOID 6 }
brzAccessVLAUS-SA   OBJECT IDENTIFIER ::= { brzAccessVLOID 7 }
brzAccessAU-EZ		OBJECT IDENTIFIER ::= { brzAccessVLOID 8 }

brzAccessVLSU-6-1D   OBJECT IDENTIFIER ::= { brzAccessVLOID 11 }
brzAccessVLSU-6-BD   OBJECT IDENTIFIER ::= { brzAccessVLOID 12 }
brzAccessVLSU-24-BD  OBJECT IDENTIFIER ::= { brzAccessVLOID 13 }
brzAccessVLSU-BD     OBJECT IDENTIFIER ::= { brzAccessVLOID 14 }
brzAccessVLSU-54-BD  OBJECT IDENTIFIER ::= { brzAccessVLOID 15 }

brzAccessVLSU-3-1D  OBJECT IDENTIFIER ::= { brzAccessVLOID 16 }
brzAccessVLSU-3-4D  OBJECT IDENTIFIER ::= { brzAccessVLOID 17 }
brzAccessVLSU-I		OBJECT IDENTIFIER ::= { brzAccessVLOID 18 }
brzAccessVLSU-EZ	OBJECT IDENTIFIER ::= { brzAccessVLOID 19 }
brzAccessVLSU-V		OBJECT IDENTIFIER ::= { brzAccessVLOID 20 }

brzNetB-BU-B14     OBJECT IDENTIFIER ::= { brzAccessVLOID 21 }
brzNetB-BU-B28     OBJECT IDENTIFIER ::= { brzAccessVLOID 22 }
brzNetB-BU-B100    OBJECT IDENTIFIER ::= { brzAccessVLOID 23 }
brzNetB-BU-B10	   OBJECT IDENTIFIER ::= { brzAccessVLOID 24 }

brzNetB-RB-B14     OBJECT IDENTIFIER ::= { brzAccessVLOID 31 }
brzNetB-RB-B28     OBJECT IDENTIFIER ::= { brzAccessVLOID 32 }
brzNetB-RB-B100    OBJECT IDENTIFIER ::= { brzAccessVLOID 33 }
brzNetB-RB-B10	   OBJECT IDENTIFIER ::= { brzAccessVLOID 34 }

brzAccess4900-AU-BS OBJECT IDENTIFIER ::= { brzAccessVLOID 41 }
brzAccess4900-AU-SA OBJECT IDENTIFIER ::= { brzAccessVLOID 42 }
brzAccess4900-SU-BD OBJECT IDENTIFIER ::= { brzAccessVLOID 51 }

brzAccessVLSU-8-BD OBJECT IDENTIFIER ::= { brzAccessVLOID 61 }
brzAccessVLSU-1-BD  OBJECT IDENTIFIER ::= { brzAccessVLOID 62 }

brzAccessVLSU-3-L  OBJECT IDENTIFIER ::= { brzAccessVLOID 63 }
brzAccessVLSU-6-L  OBJECT IDENTIFIER ::= { brzAccessVLOID 64 }
brzAccessVLSU-12-L  OBJECT IDENTIFIER ::= { brzAccessVLOID 65 }

brzAccessVL-AU OBJECT IDENTIFIER ::= { brzAccessVLOID 70 }
brzAccessVL-SU OBJECT IDENTIFIER ::= { brzAccessVLOID 75 }

brzAccessVLProducts		OBJECT IDENTIFIER ::= {	brzAccessVLOID 3 }

-- ****************************************************************************************
-- ****************************************************************************************
-- General System Info
-- ===================
brzaccVLSysInfo       OBJECT IDENTIFIER ::= {breezeAccessVLMib 1}


    brzaccVLUnitHwVersion OBJECT-TYPE
            SYNTAX DisplayString (SIZE(0..32))
            MAX-ACCESS read-only
            STATUS current
            DESCRIPTION  
            "Applicable to all units.  
             Hardware platform version."
            ::= { brzaccVLSysInfo 1 }

    brzaccVLRunningSoftwareVersion OBJECT-TYPE
            SYNTAX DisplayString (SIZE(0..32))
            MAX-ACCESS read-only
            STATUS current
            DESCRIPTION  
            "Applicable to all units.  
             Running software version."
            ::= { brzaccVLSysInfo 2 }

    brzaccVLRunningFrom OBJECT-TYPE
            SYNTAX INTEGER { mainVersion(1) , shadowVersion(2)}
            MAX-ACCESS read-only
            STATUS current
            DESCRIPTION  
            "Applicable to all units.  
             The memory (main or shadow) from which the current version is 
             running from." 
            ::= { brzaccVLSysInfo 3 }

    brzaccVLMainVersionNumber OBJECT-TYPE
            SYNTAX DisplayString (SIZE(0..32))
            MAX-ACCESS read-only
            STATUS current
            DESCRIPTION  
            "Applicable to all units.  
             Main software version number."
            ::= { brzaccVLSysInfo 4 }

    brzaccVLMainVersionFileName OBJECT-TYPE
            SYNTAX DisplayString (SIZE(0..32))
            MAX-ACCESS read-only
            STATUS current
            DESCRIPTION  
            "Applicable to all units.  
             Main software version file name."
            ::= { brzaccVLSysInfo 5 }


    brzaccVLShadowVersionNumber OBJECT-TYPE
            SYNTAX DisplayString (SIZE(0..32))
            MAX-ACCESS read-only
            STATUS current
            DESCRIPTION  
            "Applicable to all units.  
             Shadow software version number."
            ::= { brzaccVLSysInfo 6 }

    brzaccVLShadowVersionFileName OBJECT-TYPE
            SYNTAX DisplayString (SIZE(0..32))
            MAX-ACCESS read-only
            STATUS current
            DESCRIPTION  
            "Applicable to all units.  
             Shadow software version file name."
            ::= { brzaccVLSysInfo 7 }

    brzaccVLUnitMacAddress OBJECT-TYPE
            SYNTAX  MacAddress
            MAX-ACCESS  read-only    
            STATUS  current
            DESCRIPTION
            "Applicable to all units.  
             Unit hardware MAC address."
            ::= { brzaccVLSysInfo 8 }

    brzaccVLUnitType OBJECT-TYPE
            SYNTAX INTEGER {auBS (1), auSA(2) , su-6-1D(3),su-6-BD(4),su-24-BD(5),
                            bu-B14(6),bu-B28(7),rb-B14(8),rb-B28(9),su-BD(10),su-54-BD (11),
                            su-3-1D(12),su-3-4D(13),ausBS(14),ausSA(15),
                            auBS4900(16),auSA4900(17),su4900(18), bu-B100(19), rb-B100(20), su-I(21), 
                            au-EZ(22),    su-EZ(23),    su-V(24),   bu-B10(25),  rb-B10(26),  su-8-BD(27), su-1-BD(28),
                            su-3-L(29),  su-6-L(30),  su-12-L(31), au(32), su(33)  }
            MAX-ACCESS read-only
            STATUS current
            DESCRIPTION  
            "Applicable to all units.  
             auBS     (1) : AU-BS (modular access unit). 
             auSA     (2) : AU-SA (stand-alone access unit).
             su-6-1D  (3) : SU-6-1D (subscriber unit supporting 6 Mbps)
                            Starting with 5.0 this is deprecated.
                            When a SU-6-1D is upgraded to 5.0, its type will be changed to SU-6-BD.
             su-6-BD  (4) : SU-6-BD (subscriber unit supporting 6 Mbps).
             su-24-BD (5) : SU-24-BD (subscriber unit supporting 24 Mbps).
			 bu-B14   (6) : BU-B14 (BreezeNET Base Unit supporting 14 Mbps).
			 bu-B28   (7) : BU-B28 (BreezeNET Base Unit supporting 28 Mbps).
			 rb-B14   (8) : RB-B14 (BreezeNET Remote Bridge supporting 14 Mbps).
			 rb-B28   (9) : RB-B28 (BreezeNET Remote Bridge supporting 28 Mbps).
			 su-BD   (10) : SU-BD (subscriber unit).
			 su-54-BD(11) : SU-54-BD (subscriber unit supporting 54 Mbps).
             su-3-1D (12) : SU-3-1D (subscriber unit supporting 3 Mbps).
                            Starting with 5.0 this is deprecated.
                            When a SU-3-1D is upgraded to 5.0, its type will be changed to SU-3-BD.
             su-3-4D (13) : SU-3-4D (subscriber unit supporting 3 Mbps).
                            Starting with 5.0 SW version this unit will work in BD mode
             ausBS   (14) : AUS-BS (modular access unit supporting maxim 25 
                            (via licensing) subscribers and allowing association 
                            only with SU-3 or SU-6).
             ausSA   (15) : AUS-SA (stand-alone access unit supporting maxim 25 
                            (via licensing) subscribers and allowing association 
                            only with SU-3 or SU-6 ).
             auBS4900(16) : AU-BS-4900 (BreezeAccess 4900 modular access unit)
             auSA4900(17) : AU-SA-4900 (BreezeAccess 4900 stand alone access unit)
             suBD4900(18) : SU-BD-4900 (BreezeAccess 4900 subscriber unit)
             bu-B100 (19) : BU-B100 (BreezeNET Base Unit unlimited throughput)
             rb-B100 (20) : BU-B100 (BreezeNET Remote Bridge unlimited throughput) 
             su-I    (21) : SU-I
             au-EZ   (22) : AU-EZ
             su-EZ   (23) : SU-EZ 
             su-V	(24)  : SU-V (subscriber unit supporting 12 Mbps downlink and 8 Mbps uplink ).
             bu-B10(25)	  :	BU-B10 (BreezeNET Base Unit supporting 5 Mbps).
             rb-B10  (26) : RB-B10 (BreezeNET Base Unit supporting 5 Mbps).
             su-8-BD (27) : SU-8-BD (subscriber unit supporting 8 Mbps).
             su-1-BD (28) : SU-1-BD (subscriber unit supporting 1 Mbps).
             su-3-L (29) : SU-3-L (subscriber unit supporting 3 Mbps).
             su-6-L (30) : SU-6-L (subscriber unit supporting 6 Mbps).
             su-12-L (31) : SU-12-L (subscriber unit supporting 12 Mbps).
             au      (32) : AU (security access unit).
             su      (33) : SU (security subscriber unit)."
             ::= { brzaccVLSysInfo 9 }

    brzaccVLAssociatedAU OBJECT-TYPE
            SYNTAX  MacAddress
            MAX-ACCESS read-only
            STATUS current
            DESCRIPTION  
            "Applicable to SU/RB only.  
             Associated AU/BU MAC address."
            ::= { brzaccVLSysInfo 10 }

    brzaccVLNumOfAssociationsSinceLastReset OBJECT-TYPE
            SYNTAX  INTEGER
            MAX-ACCESS read-only
            STATUS current
            DESCRIPTION  
            "Applicable to all units.  
             The number of associations since last reset, including 
             duplicate associations (re-associations)."
            ::= { brzaccVLSysInfo 11 }

    brzaccVLCurrentNumOfAssociations OBJECT-TYPE
            SYNTAX  INTEGER	
            MAX-ACCESS read-only
            STATUS current
            DESCRIPTION  
            "Applicable to AU only.  
             Not applicable to BreezeNET-B products.
             The number of SUs currently associated with the AU.
             BreezeNET-B products return 65535."
            ::= { brzaccVLSysInfo 13 }

    brzaccVLUnitBootVersion OBJECT-TYPE
            SYNTAX DisplayString (SIZE(0..32))
            MAX-ACCESS read-only
            STATUS current
            DESCRIPTION  
            "Applicable to all units.  
             Boot version."
            ::= { brzaccVLSysInfo 14 }

    brzaccVLRadioBand OBJECT-TYPE
            SYNTAX INTEGER {band-5-8GHz (1), band-5-4GHz (2) , band-4-9GHz (3),band-5-2GHz (4),band-2-4GHz (5),band-5-3GHz (6),band-4-9GHzJapan (7),band-900MHz(8)}
            MAX-ACCESS read-only
            STATUS current
            DESCRIPTION  
            "Applicable to all units.  
             The unit's radio band."
            ::= { brzaccVLSysInfo 15 }

    brzaccVLCurrentEthernetPortState  OBJECT-TYPE
            SYNTAX  INTEGER	{ halfDuplexAnd10Mbps  (1),
            				  fullDuplexAnd10Mbps  (2),
							  halfDuplexAnd100Mbps (3),
							  fullDuplexAnd100Mbps (4),
							  linkDown             (5) }

            MAX-ACCESS read-only
            STATUS current
            DESCRIPTION  
            "Applicable to all units.  
             The current Ethernet port state."
            ::= { brzaccVLSysInfo 16 }



    brzaccVLTimeSinceLastReset OBJECT-TYPE
            SYNTAX DisplayString (SIZE(0..32))
            MAX-ACCESS read-only
            STATUS current
            DESCRIPTION  
            "Applicable to all units.  
             The elapsed time since last reset."
            ::= { brzaccVLSysInfo 17 }

brzaccVLCountryDependentParameters   OBJECT IDENTIFIER ::= {brzaccVLSysInfo 18}
	
    brzaccVLCountryCode OBJECT-TYPE
            SYNTAX DisplayString (SIZE(0..32))
            MAX-ACCESS read-only
            STATUS current
            DESCRIPTION  
            "Applicable to all units.
             The country code and country name or country group name 
             that is supported by the unit."
            ::= { brzaccVLCountryDependentParameters 1 }

    brzaccVLCountryDependentParamsTable  OBJECT-TYPE
            SYNTAX SEQUENCE OF BrzaccVLCountryDependentParameterEntry
            MAX-ACCESS not-accessible
            STATUS current
            DESCRIPTION
            "Applicable to all units. A table of country dependent parameters."
            ::= {brzaccVLCountryDependentParameters 2}

    brzaccVLCountryDependentParameterEntry OBJECT-TYPE
            SYNTAX BrzaccVLCountryDependentParameterEntry
            MAX-ACCESS not-accessible
            STATUS current
            DESCRIPTION
            "Applicable to all units. 
             An entry in the Country Dependent Parameters table."  
             INDEX { brzaccVLCountryDependentParameterTableIdx }
            ::= { brzaccVLCountryDependentParamsTable 1 }

    BrzaccVLCountryDependentParameterEntry ::= SEQUENCE {
            brzaccVLCountryDependentParameterTableIdx     INTEGER,
            brzaccVLCountryDependentParameterFrequencies  DisplayString,
			brzaccVLAllowedBandwidth                      INTEGER,
			brzaccVLRegulationMaxTxPowerAtAntennaPort	  INTEGER,
			brzaccVLRegulationMaxEIRP					  INTEGER,
			brzaccVLMinModulationLevel                    INTEGER,
			brzaccVLMaxModulationLevel                    INTEGER,
			brzaccVLBurstModeSupport                      INTEGER,
			brzaccVLMaximumBurstDuration                  INTEGER,
			brzaccVLDfsSupport							  INTEGER,
			brzaccVLMinimumHwRevision                     INTEGER
            }
               
    brzaccVLCountryDependentParameterTableIdx  OBJECT-TYPE
            SYNTAX INTEGER  (1..5)
            MAX-ACCESS read-only
            STATUS current
            DESCRIPTION 
            "Applicable to all units. 
             The sub-band ID of the entry in the Country Dependent 
             Parameters table. Serves also as index for the table entry."
           ::= { brzaccVLCountryDependentParameterEntry 1 }

    brzaccVLCountryDependentParameterFrequencies   OBJECT-TYPE
            SYNTAX DisplayString  
            MAX-ACCESS read-only
            STATUS current
            DESCRIPTION 
            "Applicable to all units. 
             The frequencies included in the applicable sub-band entry."
           ::= { brzaccVLCountryDependentParameterEntry 2 }
	
    brzaccVLAllowedBandwidth   OBJECT-TYPE
            SYNTAX INTEGER  
            MAX-ACCESS read-only
            STATUS current
            DESCRIPTION 
            "Applicable to all units. 
             The bandwidth when using the applicable the sub-band."
           ::= { brzaccVLCountryDependentParameterEntry 3 }

    brzaccVLRegulationMaxTxPowerAtAntennaPort  OBJECT-TYPE
            SYNTAX INTEGER  
            MAX-ACCESS read-only
            STATUS current
            DESCRIPTION 
            "Applicable to all units. 
             The maximum allowed Tx power when using the applicable sub-band.
             A RegulationMaxTxPowerAtAntennaPort of 255, means no limit"
           ::= { brzaccVLCountryDependentParameterEntry 4 }
 
    brzaccVLRegulationMaxEIRP   OBJECT-TYPE
            SYNTAX INTEGER  
            MAX-ACCESS read-only
            STATUS current
            DESCRIPTION 
            "Applicable to all units.
             The maximum Tx EIRP 
             when using the applicable sub-band.
             A Regulation Max EIRP of 0, means no limit."
           ::= { brzaccVLCountryDependentParameterEntry 5 }


    brzaccVLMinModulationLevel  OBJECT-TYPE
            SYNTAX INTEGER {  level1 (1), 
                              level2 (2), 
                              level3 (3), 
                              level4 (4), 
                              level5 (5), 
                              level6 (6), 
                              level7 (7),
                              level8 (8)
                            } 
            MAX-ACCESS read-only
            STATUS current
            DESCRIPTION 
            "Applicable to all units. 
             The minimum supported modulation level."
           ::= { brzaccVLCountryDependentParameterEntry 6 }

    brzaccVLMaxModulationLevel  OBJECT-TYPE
            SYNTAX INTEGER {  level1 (1), 
                              level2 (2), 
                              level3 (3), 
                              level4 (4), 
                              level5 (5), 
                              level6 (6), 
                              level7 (7),
                              level8 (8)
                            } 
            MAX-ACCESS read-only
            STATUS current
            DESCRIPTION 
            "Applicable to all units. 
             The maximum supported modulation level."
           ::= { brzaccVLCountryDependentParameterEntry 7 }
	
    brzaccVLBurstModeSupport  OBJECT-TYPE
            SYNTAX INTEGER  {supported(1), notSupported(2)}
            MAX-ACCESS read-only
            STATUS current
            DESCRIPTION 
            "Applicable to all units. 
             The supported Burst Mode Option."
           ::= { brzaccVLCountryDependentParameterEntry 8}

    brzaccVLMaximumBurstDuration   OBJECT-TYPE
            SYNTAX INTEGER 
            MAX-ACCESS read-only
            STATUS current
            DESCRIPTION 
            "Applicable to all units. 
             Applicable only if Burst Mode Option is supported. 
             The maximum supported burst duration."
           ::= { brzaccVLCountryDependentParameterEntry 9}

	 
    brzaccVLDfsSupport  OBJECT-TYPE
            SYNTAX INTEGER  {supported(1), notSupported(2)}
            MAX-ACCESS read-only
            STATUS current
            DESCRIPTION 
            "Applicable to AU/BU only. 
             The supported Dfs Option."
           ::= { brzaccVLCountryDependentParameterEntry 10}
	
    brzaccVLMinimumHwRevision  OBJECT-TYPE
            SYNTAX INTEGER {hwRevisionA (1), hwRevisionB (2), 
                            hwRevisionC (3), hwRevisionD (4), 
                            hwRevisionE (5), hwRevisionF (6),
                            hwRevisionG (7), na (255)}
            MAX-ACCESS read-only
            STATUS current
            DESCRIPTION 
            "Applicable to all units. 
             The Minimum HW Revision needed to support the country code."
           ::= { brzaccVLCountryDependentParameterEntry 11}
 

    brzaccVLAuthenticationEncryptionSupport OBJECT-TYPE
            SYNTAX INTEGER  {supported(1), notSupported(2)}
            MAX-ACCESS read-only
            STATUS current
            DESCRIPTION  
            "Applicable to all units.
             The supported Authentication Encryption Option."
            ::= { brzaccVLCountryDependentParameters 3 }

    brzaccVLDataEncryptionSupport OBJECT-TYPE
            SYNTAX INTEGER  {supported(1), notSupported(2)}
            MAX-ACCESS read-only
            STATUS current
            DESCRIPTION  
            "Applicable to all units.
             The supported Data Encryption Option."
            ::= { brzaccVLCountryDependentParameters 4 }

    brzaccVLAESEncryptionSupport OBJECT-TYPE
            SYNTAX INTEGER  {supported(1), notSupported(2)}
            MAX-ACCESS read-only
            STATUS current
            DESCRIPTION  
            "Applicable to all units.
             The supported AES Encryption Option."
            ::= { brzaccVLCountryDependentParameters 5 }

    brzaccVLAntennaGainChange OBJECT-TYPE
            SYNTAX INTEGER {supported(1), notSupported(2)}
            MAX-ACCESS read-only
            STATUS current
            DESCRIPTION  
            "Applicable to all units.  
             Indicates whether the Antenna Gain parameter is changeable or fixed." 
            ::= { brzaccVLSysInfo 19 }

    brzaccVLAteTestResults OBJECT-TYPE
            SYNTAX INTEGER { none(0), pass(1), fail(2) }
            MAX-ACCESS read-only
            STATUS current
            DESCRIPTION  
            "Applicable to all units.  
            Results of ATE Test " 
            ::= { brzaccVLSysInfo 20 }
            
    brzaccVLSerialNumber OBJECT-TYPE
            SYNTAX DisplayString (SIZE(0..35))
            MAX-ACCESS read-only
            STATUS current
            DESCRIPTION  
            "Applicable to all units.  
            Serial Number of the unit" 
            ::= { brzaccVLSysInfo 21 }
            
    brzaccVLAUSSupportSU54 OBJECT-TYPE
            SYNTAX INTEGER { true(1), false(2), na(255) }
            MAX-ACCESS read-only
            STATUS current
            DESCRIPTION  
            "Applicable to AU only.
             If the AU is not AUS, it will return 255.
             If the AUS is in 900 MHz bandwidth, it will return 255
             Indicates if the AUS has license for association of SU-54." 
            ::= { brzaccVLSysInfo 22 }
            
    brzaccVLNumOfRejectionsSinceLastReset OBJECT-TYPE
            SYNTAX  INTEGER
            MAX-ACCESS read-only
            STATUS current
            DESCRIPTION  
            "Applicable to AU/BU only.
             The number of subscribers that were rejected because of wrong ESSID" 
            ::= { brzaccVLSysInfo 23 }
 
   brzaccVLAUSSupportSU8 OBJECT-TYPE
            SYNTAX INTEGER { true(1), false(2), na(255) }
            MAX-ACCESS read-only
            STATUS current
            DESCRIPTION  
            "Applicable to AU only.
             If the AU is not AUS, it will return 255.
             If the unit is AUS but not operating in 900 MHz, it will return 255.
             Indicates if the AUS has license for association of SU-8." 
            ::= { brzaccVLSysInfo 24 }
          

-- Unit Control
-- ============
brzaccVLUnitControl       OBJECT IDENTIFIER ::= {breezeAccessVLMib 2}

    brzaccVLResetUnit OBJECT-TYPE
            SYNTAX  INTEGER { cancel (1), resetSystemNow (2) }  
            MAX-ACCESS read-write
            STATUS current
            DESCRIPTION  
            "Applicable to all units.  
             Resets the unit and applies new parameter values."
            ::= { brzaccVLUnitControl 1 }


    brzaccVLSetDefaults OBJECT-TYPE
            SYNTAX  INTEGER {  noDefaultSettingRequested (0),
                               completeFactory  (1), 
                               partialFactory   (2), 
                               completeOperator (3), 
                               partialOperator  (4), 
                               cancelCurrentPendingRequest(5) }  
            MAX-ACCESS read-write
            STATUS current
            DESCRIPTION  
            "Applicable to all units.  
             Sets unit configuration to Defaults values after the 
             next reset.    
             noDefaultSettingRequested : Read-Only Option, no Default setting was Issued.
             completeFactory : All parameters revert to Factory 
                               Defaults values.
             partialFactory  : All parameters revert to Factory 
                               Defaults values, except the parameters 
                               required for maintaining wireless 
                               connectivity.    
             completeOperator: All parameters revert to Operator 
                               Defaults values. 
             partialOperator : All parameters revert to Operator 
                               Defaults values, except the parameters 
                               required for maintaining wireless 
                               connectivity.
             cancelCurrentPendingRequest : Default Setting request is cancelled."
            ::= { brzaccVLUnitControl 2 }

    brzaccVLUnitName OBJECT-TYPE
            SYNTAX DisplayString (SIZE(0..32))
            MAX-ACCESS read-write
            STATUS current
            DESCRIPTION  
            "Applicable to all units.  
             The unit name. 
             A string of up to 32 printable ASCII characters."
            ::= { brzaccVLUnitControl 3 }

    brzaccVLFlashMemoryControl OBJECT-TYPE
            SYNTAX  INTEGER { resetAndBootFromShadowVersion (1), 
                              useRunningVersionAfterReset (2),cancel(3) }  
            MAX-ACCESS read-write
            STATUS current
            DESCRIPTION  
            "Applicable to all units.  
             resetAndBootFromShadowVersion : Activates the backup 
                                             version.   
             useRunningVersionAfterReset   : The currently active 
                                             version will become the main 
                                             version and will be activated 
                                             after next reset."
            ::= { brzaccVLUnitControl 4 }


    brzaccVLTelnetLogoutTimer  OBJECT-TYPE
            SYNTAX  INTEGER   
            MAX-ACCESS read-write
            STATUS current
            DESCRIPTION  
            "Applicable to all units.  
             Time-out of management via Telnet program. 
             Automatic exit if the program is inactive for the 
             defined time.
             Range: 1 to 999 (minutes)."
            ::= { brzaccVLUnitControl 5 }

    brzaccVLSaveCurrentConfigurationAsOperatorDefaults OBJECT-TYPE
            SYNTAX  INTEGER { saveAsDefaults (1),cancel(2) }  
            MAX-ACCESS read-write
            STATUS current
            DESCRIPTION  
            "Applicable to all units.  
             Saves the current configuration as Operator Defaults.
             Cannot be executed after requesting set defaults 
             and the unit was not reset."
            ::= { brzaccVLUnitControl 6 }

    brzaccVLExitTelnet OBJECT-TYPE
            SYNTAX  INTEGER { cancelOperation (1), exit (2)}  
            MAX-ACCESS read-write
            STATUS current
            DESCRIPTION  
            "Applicable to all units.  
             Exit the management via Telnet program."
            ::= { brzaccVLUnitControl 7 }

brzaccVLUnitPasswords     OBJECT IDENTIFIER ::= {brzaccVLUnitControl 8}

    brzaccVLReadOnlyPassword OBJECT-TYPE
            SYNTAX DisplayString (SIZE(1..8))
            MAX-ACCESS read-write
            STATUS current
            DESCRIPTION  
            "Applicable to all units. 
             The User (read only) password.
             This is also the Read Community String.
             Up to 8 printable ASCII characters."
            ::= { brzaccVLUnitPasswords 1 }

    brzaccVLInstallerPassword OBJECT-TYPE
            SYNTAX DisplayString (SIZE(1..8))
            MAX-ACCESS read-write
            STATUS current
            DESCRIPTION  
            "Applicable to all units. 
             The Installer password.
             Up to 8 printable ASCII characters.
             Value read will allwais be ********* "
            ::= { brzaccVLUnitPasswords 2 }

    brzaccVLAdminPassword OBJECT-TYPE
            SYNTAX DisplayString (SIZE(1..8))
            MAX-ACCESS read-write
            STATUS current
            DESCRIPTION  
            "Applicable to all units. 
            The Administrator password. Value read will allwais be *********. 
            Up to 8 printable ASCII characters."
            ::= { brzaccVLUnitPasswords 3 }


    brzaccVLEthernetNegotiationMode  OBJECT-TYPE
            SYNTAX INTEGER { force10MbpsAndHalfDuplex   (1),
            				 force10MbpsAndFullDuplex   (2),
							 force100MbpsAndHalfDuplex  (3),
							 force100MbpsAndFullDuplex  (4),
							 autoNegotiationMode        (5) }
            MAX-ACCESS read-write
            STATUS current
            DESCRIPTION  
            "Applicable to all units.  
             The speed/duplex mode of the Ethernet port." 
            ::= { brzaccVLUnitControl 9 }

brzaccVLFTPParameters      OBJECT IDENTIFIER ::= {brzaccVLUnitControl 10}

brzaccVLFTPServerParams      OBJECT IDENTIFIER ::= {brzaccVLFTPParameters 1}

    brzaccVLFTPServerUserName OBJECT-TYPE
            SYNTAX  DisplayString (SIZE(0..18))  
            MAX-ACCESS read-write
            STATUS current
            DESCRIPTION  
            "Applicable to all units. 
             The user name to be used for access to the FTP server. 
             Accessible only with SNMP Write Community String 
             (administrator password)." 
            ::= { brzaccVLFTPServerParams 1 }

    brzaccVLFTPServerPassword OBJECT-TYPE
            SYNTAX  DisplayString (SIZE(0..18))  
            MAX-ACCESS read-write
            STATUS current
            DESCRIPTION  
            "Applicable to all units. 
             The password to be used for access to the FTP server. 
             Accessible only with SNMP Write Community String 
             (administrator password)." 
            ::= { brzaccVLFTPServerParams 2 }

    brzaccVLFTPClientIPAddress OBJECT-TYPE
            SYNTAX  IpAddress  
            MAX-ACCESS read-write
            STATUS current
            DESCRIPTION  
            "Applicable to all units.
             For SW version higher than 4.0 this is read-only. 
             The IP address of the FTP stack in the unit." 
            ::= { brzaccVLFTPServerParams 3 }  

    brzaccVLFTPServerIpAddress OBJECT-TYPE
            SYNTAX  IpAddress  
            MAX-ACCESS read-write
            STATUS current
            DESCRIPTION  
            "Applicable to all units.  
             The IP address of the FTP server." 
            ::= { brzaccVLFTPServerParams 4 }  

   brzaccVLFTPClientMask OBJECT-TYPE
            SYNTAX  IpAddress  
            MAX-ACCESS read-write
            STATUS current
            DESCRIPTION  
            "Applicable to all units. 
             Starting with 5.0 this parameter is not appplicable.  
             The Mask of the FTP stack in the unit." 
            ::= { brzaccVLFTPServerParams 5 }  


    brzaccVLFTPGatewayIpAddress OBJECT-TYPE
            SYNTAX  IpAddress  
            MAX-ACCESS read-write
            STATUS current
            DESCRIPTION  
            "Applicable to all units. 
             Starting with 5.0 this parameter is not appplicable. 
             The FTP Gateway address"
            ::= { brzaccVLFTPServerParams 6 }  


brzaccVLFTPSwDownload      OBJECT IDENTIFIER ::= {brzaccVLFTPParameters 2}

   brzaccVLFTPSwFileName  OBJECT-TYPE
            SYNTAX DisplayString (SIZE(1..20))
            MAX-ACCESS read-write
            STATUS current
            DESCRIPTION  
            "Applicable to all units.  
             The name of the SW file to be downloaded."
            ::= { brzaccVLFTPSwDownload 1 }

   brzaccVLFTPSwSourceDir  OBJECT-TYPE
            SYNTAX DisplayString (SIZE(0..80))
            MAX-ACCESS read-write
            STATUS current
            DESCRIPTION  
            "Applicable to all units.  
             The source directory of the required file in the FTP server.
             Up to 80 printable ASCII characters.
             Use dot (.) To clear field"
            ::= { brzaccVLFTPSwDownload 2 }

    brzaccVLFTPDownloadSwFile OBJECT-TYPE
            SYNTAX  INTEGER { downloadFile (1) , cancel (2)}  
            MAX-ACCESS read-write
            STATUS current
            DESCRIPTION  
            "Applicable to all units.  
             Execution  of the SW download operation" 
            ::= { brzaccVLFTPSwDownload 3 }

brzaccVLConfigurationFileLoading      OBJECT IDENTIFIER ::= {brzaccVLFTPParameters 3}

   brzaccVLConfigurationFileName  OBJECT-TYPE
            SYNTAX DisplayString (SIZE(1..20))
            MAX-ACCESS read-write
            STATUS current
            DESCRIPTION  
            "Applicable to all units.  
             The name of the configuration file to be downloaded/uploaded."
            ::= { brzaccVLConfigurationFileLoading 1 }

   brzaccVLOperatorDefaultsFileName  OBJECT-TYPE
            SYNTAX DisplayString (SIZE(1..20))
            MAX-ACCESS read-write
            STATUS current
            DESCRIPTION  
            "Applicable to all units.  
             The name of the Operator Defaults file to be downloaded/uploaded"
            ::= { brzaccVLConfigurationFileLoading 2 }

   brzaccVLFTPConfigurationFileSourceDir  OBJECT-TYPE
            SYNTAX DisplayString (SIZE(0..80))
            MAX-ACCESS read-write
            STATUS current
            DESCRIPTION  
            "Applicable to all units.  
             The source directory of the required file in the FTP server.
             Up to 80 printable ASCII characters.
             Use dot (.) To clear field"
            ::= { brzaccVLConfigurationFileLoading 3 }

    brzaccVLExecuteFTPConfigurationFileLoading OBJECT-TYPE
            SYNTAX  INTEGER {executeFTPGetConfigurationFile (1), executeFTPPutConfigurationFile (2),
							 executeFTPGetOperatorDefaults  (3) , executeFTPPutOperatorDefaults (4), cancel (5) }  
            MAX-ACCESS read-write
            STATUS current
            DESCRIPTION  
            "Applicable to all units.  
             Execution of the file download/upload operation." 
            ::= { brzaccVLConfigurationFileLoading 4 }



brzaccVLEventLogFileUploading   OBJECT IDENTIFIER ::= {brzaccVLFTPParameters 4}

   brzaccVLEventLogFileName  OBJECT-TYPE
            SYNTAX DisplayString (SIZE(1..20))
            MAX-ACCESS read-write
            STATUS current
            DESCRIPTION  
            "Applicable to all units.  
             The name of the Event Log file to be uploaded."
            ::= { brzaccVLEventLogFileUploading 1 }

   brzaccVLEventLogDestinationDir  OBJECT-TYPE
            SYNTAX DisplayString (SIZE(0..80))
            MAX-ACCESS read-write
            STATUS current
            DESCRIPTION  
            "Applicable to all units.  
             The destination directory of the event log file.
             Up to 80 printable ASCII characters.
             Use dot (.) To clear field."
            ::= { brzaccVLEventLogFileUploading 2 }

    brzaccVLUploadEventLogFile OBJECT-TYPE
            SYNTAX  INTEGER { uploadFile (1) , cancel (2)}  
            MAX-ACCESS read-write
            STATUS current
            DESCRIPTION  
            "Applicable to all units.  
             Execution  of the event log upload operation." 
            ::= { brzaccVLEventLogFileUploading 3 }

    brzaccVLLoadingStatus OBJECT-TYPE
            SYNTAX  INTEGER {inProcess (1), successful (2), failed (3)}  
            MAX-ACCESS read-only
            STATUS current
            DESCRIPTION  
            "Applicable to all units.  
             The status of the last loading operation."
            ::= { brzaccVLUnitControl 11 }

brzaccVLEventLogFileParams   OBJECT IDENTIFIER ::= {brzaccVLUnitControl 12}

   brzaccVLEventLogPolicy  OBJECT-TYPE
            SYNTAX INTEGER {message (1), warning (2), error (3),fatal(4), logNone(5)}
            MAX-ACCESS read-write
            STATUS current
            DESCRIPTION  
            "Applicable to all units.  
              The lowest level event to be registered in the event log."
            ::= { brzaccVLEventLogFileParams 1 }

   brzaccVLEraseEventLog  OBJECT-TYPE
            SYNTAX INTEGER { eraseEventLog (1),cancel(2) }
            MAX-ACCESS read-write
            STATUS current
            DESCRIPTION  
            "Applicable to all units.  
              Erase the event log."
            ::= { brzaccVLEventLogFileParams 2 }

    brzaccVLSystemLocation OBJECT-TYPE
            SYNTAX DisplayString (SIZE(0..34))
            MAX-ACCESS read-write
            STATUS current
            DESCRIPTION  
            "Applicable to all units.  
             The unit location."
            ::= { brzaccVLUnitControl 13 }

brzaccVLFeatureUpgrade   OBJECT IDENTIFIER ::= {brzaccVLUnitControl 14}
   
    brzaccVLFeatureUpgradeManually OBJECT-TYPE
            SYNTAX DisplayString (SIZE(32..64))
            MAX-ACCESS read-write
            STATUS current
            DESCRIPTION  
            "Applicable to all units.  
             Upgrade unit to support new feature. Enter your license number 
             (32 to 64 hex digits)."
            ::= { brzaccVLFeatureUpgrade 1 }

    brzaccVLChangeUnitType  OBJECT-TYPE
            SYNTAX INTEGER { bu(1), rb(2), cancel(3) }
            MAX-ACCESS read-write
            STATUS current
            DESCRIPTION  
            "Applicable RB/BU only.  
             Change the unit type between BU and RB."
            ::= { brzaccVLUnitControl 15 }

   brzaccVLApWorkingMode OBJECT-TYPE
        	SYNTAX  INTEGER  { ezMode(1), na(255) }
        	MAX-ACCESS read-only
        	STATUS current
        	DESCRIPTION 
        	"Applicable to AU-EZ only. 
        	Starting with 5.5 it is read-only.
         	Report unit running mode: 1 - EZ mode." 
			::= { brzaccVLUnitControl 16 }

brzaccVLLEDsettings   OBJECT IDENTIFIER ::= {brzaccVLUnitControl 17}

   brzaccVLLEDmode OBJECT-TYPE
        	SYNTAX  INTEGER  { normal(1), threshold(2) }
        	MAX-ACCESS read-write
        	STATUS current
        	DESCRIPTION 
        	"Applicable to all units with SW version 6.0 and higher, except AU. 
        	Sets the operating mode of the unit LEDS" 
			::= { brzaccVLLEDsettings 1 }
			
-- LED-THRESHOLD-TABLE
	
    brzaccVLThresholdTable OBJECT-TYPE
            SYNTAX SEQUENCE OF BrzaccVLThresholdTableSettings
            MAX-ACCESS not-accessible
            STATUS current
            DESCRIPTION
            "Applicable to all units with SW version 6.0 and higher, except AU. 
             A table with the settings for Threshold mode" 
            ::= { brzaccVLLEDsettings 2 }

    brzaccVLThresholdTableEntry  OBJECT-TYPE
            SYNTAX BrzaccVLThresholdTableSettings
            MAX-ACCESS not-accessible
            STATUS current
            DESCRIPTION
            "Applicable to all units with SW version 6.0 and higher, except AU. 
             An entry in the ThresholdTable." 
            INDEX { brzaccVLThresholdLEDnum }
            ::= { brzaccVLThresholdTable 1 }
                                
    BrzaccVLThresholdTableSettings ::= SEQUENCE { brzaccVLThresholdLEDnum INTEGER,
                                                  brzaccVLThresholdLEDtype INTEGER,
                                                  brzaccVLThresholdLEDmode INTEGER,
                                                  brzaccVLThresholdLEDtarget INTEGER 
                                                }

    brzaccVLThresholdLEDnum OBJECT-TYPE
            SYNTAX INTEGER ( 1..8 )
            MAX-ACCESS read-only
            STATUS current
            DESCRIPTION  
            "Applicable to all units with SW version 6.0 and higher, except AU. 
            The LED position and index." 
            ::= { brzaccVLThresholdTableEntry 1 }
            
     brzaccVLThresholdLEDtype OBJECT-TYPE
            SYNTAX INTEGER { typeDisabled (1), typeRSSI (2), typeCRC (3), typeSNR (4), typeAverageModulation (5) }
            MAX-ACCESS read-write
            STATUS current
            DESCRIPTION  
            "Applicable to all units with SW version 6.0 and higher, except AU. 
            The type of measurement of the LED" 
            ::= { brzaccVLThresholdTableEntry 2 }
            
	brzaccVLThresholdLEDmode OBJECT-TYPE
            SYNTAX INTEGER { equalOrLower (1), equalOrHigher (2), equal (3) }
            MAX-ACCESS read-write
            STATUS current
            DESCRIPTION  
            "Applicable to all units with SW version 6.0 and higher, except AU. 
             The condition to turn the LED on."
            ::= { brzaccVLThresholdTableEntry 3 }
            
	brzaccVLThresholdLEDtarget OBJECT-TYPE
            SYNTAX INTEGER ( -108..100 )
            MAX-ACCESS read-write
            STATUS current
            DESCRIPTION  
            "Applicable to all units with SW version 6.0 and higher, except AU. 
            The target value, depending on LED type,
            from brzaccVLThresholdLEDtype above."
            ::= { brzaccVLThresholdTableEntry 4 }
            
            
-- end of LED-THRESHOLD-TABLE


-- Network Management Params
-- =========================
   brzaccVLNwMngParameters   OBJECT IDENTIFIER ::= {breezeAccessVLMib 3}

    brzaccVLAccessToNwMng OBJECT-TYPE
           SYNTAX   INTEGER { fromWirelessOnly  (1), 
                              fromEthernetOnly (2), 
                              fromBothWirelessAndEthernet  (3), 
                              na (255) } 
            MAX-ACCESS read-write
            STATUS current
            DESCRIPTION 
            "Applicable to all units.  
             The port to be used for remote management."
            ::= { brzaccVLNwMngParameters 1 }


    brzaccVLNwMngFilter OBJECT-TYPE
             SYNTAX INTEGER { disable (1),
                              activateOnEthernetPort (2), 
                              activateOnWirelessPort  (3), 
                              activateOnBothWirelessAndEthernet  (4), 
                              na (255) } 
            MAX-ACCESS read-write
            STATUS current
            DESCRIPTION 
            "Applicable to all units.  
             Disables or enable on one of the ports, or on both 
             ports, IP address based filtering of management messages 
             (e.g. SNMP , Telnet , TFTP , DHCP)."
           ::= { brzaccVLNwMngParameters 2 }




    mngIpFilterTable OBJECT-TYPE
            SYNTAX SEQUENCE OF MngIpFilterEntry
            MAX-ACCESS not-accessible
            STATUS current
            DESCRIPTION
            "Starting with version 5.0, this is deprecated. Use newMngIpFilterTable instead.
			 Applicable to all units.  
             A Management IP Filter Table of up to 3 IP addresses 
             of devices that are authorized to access the unit 
             for management purposes." 
            ::= { brzaccVLNwMngParameters 3 }

    mngIpFilterEntry  OBJECT-TYPE
            SYNTAX MngIpFilterEntry
            MAX-ACCESS not-accessible
            STATUS current
            DESCRIPTION
            "Applicable to all units.  
             A Management IP Filter Table entry."
            INDEX { brzaccVLNwMngIpTableIdx }
            ::= { mngIpFilterTable 1 }

    MngIpFilterEntry ::= SEQUENCE { brzaccVLNwMngIpAddress   IpAddress,
                                    brzaccVLNwMngIpTableIdx  INTEGER }
   
    brzaccVLNwMngIpAddress   OBJECT-TYPE
            SYNTAX IpAddress  
            MAX-ACCESS read-write
            STATUS current
            DESCRIPTION 
            "Applicable to all units.  
             An IP address in the Management IP Filter Table."
          ::= { mngIpFilterEntry 1 }

    brzaccVLNwMngIpTableIdx   OBJECT-TYPE
            SYNTAX INTEGER (1..10) 
            MAX-ACCESS read-only
            STATUS current
            DESCRIPTION 
            "Applicable to all units.  
             A table index for an entry in the Management IP Filter 
             Table."
         ::= { mngIpFilterEntry 2 }


    brzaccVLDeleteOneNwIpAddr OBJECT-TYPE
            SYNTAX  INTEGER (0 | 1..10 | 255) 
            MAX-ACCESS read-write
            STATUS current
            DESCRIPTION 
            "Applicable to all units.  
             0 - cancel operation.
             1..10 - Deletes a single selected entry from the Management IP 
             Filter Table."
            ::= { brzaccVLNwMngParameters 4 }

    brzaccVLDeleteAllNwIpAddrs OBJECT-TYPE
            SYNTAX INTEGER { deleteAll (1), cancelOperation (2), na (255) } 
            MAX-ACCESS read-write
            STATUS current
            DESCRIPTION 
            "Applicable to all units.  
             Deletes all entries from the Management IP Filter Table."
            ::= { brzaccVLNwMngParameters 5 }

    brzaccVLAccessToNwTrap OBJECT-TYPE
            SYNTAX INTEGER { disable(1), enable(2) } 
            MAX-ACCESS read-write
            STATUS current
            DESCRIPTION 
            "Applicable to all units.  
             Enables or disables sending of traps."
            ::= { brzaccVLNwMngParameters 6 }

    mngTrapTable OBJECT-TYPE
            SYNTAX SEQUENCE OF MngTrapEntry
            MAX-ACCESS not-accessible
            STATUS current
            DESCRIPTION
            "Starting with version 5.0, this is deprecated. Use newMngTrapTable instead.
			 Applicable to all units.  
             A Management Trap Table of up to 10 IP addresses of 
             stations to send traps to." 
            ::= { brzaccVLNwMngParameters 7 }

    mngTrapEntry  OBJECT-TYPE
            SYNTAX MngTrapEntry
            MAX-ACCESS not-accessible
            STATUS current
            DESCRIPTION
            "Applicable to all units.  
             A Management Trap Table entry." 
            INDEX { brzaccVLNwTrapTableIdx }
            ::= { mngTrapTable 1 }
                                
    MngTrapEntry ::= SEQUENCE { brzaccVLNwMngTrapCommunity DisplayString,
                                brzaccVLNwMngTrapAddress   IpAddress,
                                brzaccVLNwTrapTableIdx     INTEGER }
                                
    brzaccVLNwMngTrapCommunity OBJECT-TYPE
            SYNTAX DisplayString (SIZE(0..14))
            MAX-ACCESS read-write
            STATUS current
            DESCRIPTION  
            "Applicable to all units.  
             The trap community associated with the applicable 
             entry in the Management Trap Table.
             Up to 14 printable case sensitive ASCII characters."
            ::= { mngTrapEntry 1 }

    brzaccVLNwMngTrapAddress   OBJECT-TYPE
            SYNTAX  IpAddress  
            MAX-ACCESS read-write
            STATUS current
            DESCRIPTION  
            "Applicable to all units.  
             An IP address in the Management Trap Table entry." 
        ::= { mngTrapEntry 2 }

    brzaccVLNwTrapTableIdx   OBJECT-TYPE
            SYNTAX  INTEGER (1..10) 
            MAX-ACCESS read-only
            STATUS current
            DESCRIPTION  
            "Applicable to all units.  
             Tables Index for an entry in the Management Trap Table."
        ::= { mngTrapEntry 3 }


    brzaccVLDeleteOneTrapAddr OBJECT-TYPE
            SYNTAX  INTEGER (0 | 1..10 | 255)
            MAX-ACCESS read-write
            STATUS current
            DESCRIPTION  
            "Applicable to all units.  
             0 - cancel operation.
             1..10 - Deletes a single selected entry from the Management 
             Trap Table."
            ::= { brzaccVLNwMngParameters 8 }


    brzaccVLDeleteAllTrapAddrs OBJECT-TYPE
            SYNTAX  INTEGER { deleteAll (1),cancelOperation (2),  na (255) } 
            MAX-ACCESS read-write
            STATUS current
            DESCRIPTION  
            "Applicable to all units.  
             Deletes all entries from the Management Trap Table."
            ::= { brzaccVLNwMngParameters 9 }

	brzaccVLMngIpRangesTable OBJECT-TYPE
            SYNTAX SEQUENCE OF BrzaccVLMngIpRangeEntry
            MAX-ACCESS not-accessible
            STATUS current
            DESCRIPTION
			"Starting with version 5.0, this is deprecated. Use brzaccVLNewMngIpRangesTable instead.
             Applicable to all units.  
             Table of Management IP Address Ranges" 
            ::= { brzaccVLNwMngParameters 10 }

    brzaccVLMngIpRangeEntry  OBJECT-TYPE
            SYNTAX BrzaccVLMngIpRangeEntry
            MAX-ACCESS not-accessible
            STATUS current
            DESCRIPTION
            "Applicable to all units.  
             A Management IP Address Ranges Table entry" 
            INDEX { brzaccVLMngIpRangeIdx }
            ::= { brzaccVLMngIpRangesTable 1 }
                                
    BrzaccVLMngIpRangeEntry ::= SEQUENCE { 
								brzaccVLMngIpRangeIdx		INTEGER,
								brzaccVLMngIpRangeFlag		INTEGER,					
                                brzaccVLMngIpRangeStart     IpAddress,
                                brzaccVLMngIpRangeEnd		IpAddress,
                                brzaccVLMngIpRangeMask		IpAddress
                                }
               
 
    brzaccVLMngIpRangeIdx OBJECT-TYPE
            SYNTAX  INTEGER (1..10)  
            MAX-ACCESS read-only
            STATUS current
            DESCRIPTION  
            "Applicable to all units.  
             Index of an entry in the Management IP Address Ranges Table"
            ::= { brzaccVLMngIpRangeEntry 1 }

    brzaccVLMngIpRangeFlag OBJECT-TYPE
            SYNTAX  INTEGER { rangeDefinedByStartEndAddr(1), rangeDefinedByStartAddrMask(2)}  
            MAX-ACCESS read-write
            STATUS current
            DESCRIPTION  
            "Applicable to all units.  
             Defines the method of defining the range:
             Using Start & End Address( rangeDefinedByStartEndAddr ),
             or using Start Address and Mask ( rangeDefinedByStartAddrSubNetMask )."
            ::= { brzaccVLMngIpRangeEntry 2 }

    
    brzaccVLMngIpRangeStart OBJECT-TYPE
            SYNTAX  IpAddress
            MAX-ACCESS read-write
            STATUS current
            DESCRIPTION  
            "Applicable to all units.  
             Start Address of the range"
            ::= { brzaccVLMngIpRangeEntry 3 }
    
    brzaccVLMngIpRangeEnd OBJECT-TYPE
            SYNTAX  IpAddress
            MAX-ACCESS read-write
            STATUS current
            DESCRIPTION  
            "Applicable to all units.  
             End Address of the range. 
             Used only if brzaccVLMngIpRangeFlag is  rangeDefinedByStartEndAddr"
            ::= { brzaccVLMngIpRangeEntry 4 }
            
	brzaccVLMngIpRangeMask OBJECT-TYPE
            SYNTAX  IpAddress
            MAX-ACCESS read-write
            STATUS current
            DESCRIPTION  
			"Applicable to all units.  
             End Address of the range. 
             Used only if brzaccVLMngIpRangeFlag is  rangeDefinedByStartAddrMask"
            ::= { brzaccVLMngIpRangeEntry 5 } 
            
	brzaccVLDeleteOneNwIpRange OBJECT-TYPE
            SYNTAX  INTEGER (0 | 1..10 | 255) 
            MAX-ACCESS read-write
            STATUS current
            DESCRIPTION 
            "Applicable to all units.  
             0 - cancel operation.
             1..10 - Deletes a single selected entry from the Management IP 
             Ranges Table."
            ::= { brzaccVLNwMngParameters 11 }
            
    
	brzaccVLDeleteAllNwIpRanges OBJECT-TYPE
            SYNTAX INTEGER { deleteAll (1), cancelOperation (2), na (255) } 
            MAX-ACCESS read-write
            STATUS current
            DESCRIPTION 
            "Applicable to all units.  
             Deletes all entries from the Management IP Ranges Table."
            ::= { brzaccVLNwMngParameters 12 }

	brzaccVLWi2IpAddress    OBJECT-TYPE
            SYNTAX  IpAddress
            MAX-ACCESS read-write
            STATUS current
            DESCRIPTION 
            "Applicable to SU/RB unit only.  
             The IP Address of the WIFI WIMAX unit"
            ::= { brzaccVLNwMngParameters 13 }

   brzaccVLNewNMngSystem      OBJECT IDENTIFIER ::= {brzaccVLNwMngParameters 14}                            
   brzaccVLErrorHandling      OBJECT IDENTIFIER ::= {brzaccVLNewNMngSystem 1}

   brzaccVLErrHandlingSetNMSId   OBJECT-TYPE
            SYNTAX  INTEGER
            MAX-ACCESS read-write
            STATUS current
            DESCRIPTION 
            "Applicable to all units.  
             The ID of the Network Management System that use Error Handling mechanism.
             Get request will return 0."
            ::= { brzaccVLErrorHandling 1 }
            
  
   	brzaccVLErrHandlingTable OBJECT-TYPE
            SYNTAX SEQUENCE OF BrzaccVLErrHandlingEntry
            MAX-ACCESS not-accessible
            STATUS current
            DESCRIPTION
            "" 
            ::= { brzaccVLErrorHandling 2 }

    brzaccVLErrHandlingEntry  OBJECT-TYPE
            SYNTAX BrzaccVLErrHandlingEntry
            MAX-ACCESS not-accessible
            STATUS current
            DESCRIPTION
            "" 
            INDEX { brzaccVLErrHandlingNMSId, brzaccVLErrHandlingRequestId }
            ::= { brzaccVLErrHandlingTable 1 }
                                
    BrzaccVLErrHandlingEntry ::= SEQUENCE { 
								brzaccVLErrHandlingNMSId		Unsigned32,
								brzaccVLErrHandlingRequestId	Unsigned32,					
								brzaccVLErrHandlingErrorCode	INTEGER,													
								brzaccVLErrHandlingParameter1	INTEGER,																							
								brzaccVLErrHandlingParameter2	INTEGER,
								brzaccVLErrHandlingParameter3	INTEGER,
								brzaccVLErrHandlingParameter4	INTEGER,
								brzaccVLErrHandlingParameter5	INTEGER								
                                }
               
 
    brzaccVLErrHandlingNMSId OBJECT-TYPE
            SYNTAX  Unsigned32(0..4294967295)
            MAX-ACCESS read-only
            STATUS current
            DESCRIPTION  
            ""
            ::= { brzaccVLErrHandlingEntry 1 }

    brzaccVLErrHandlingRequestId OBJECT-TYPE
            SYNTAX  Unsigned32(0..4294967295)
            MAX-ACCESS read-only
            STATUS current
            DESCRIPTION  
            ""
            ::= { brzaccVLErrHandlingEntry 2 }

    brzaccVLErrHandlingErrorCode OBJECT-TYPE
            SYNTAX  INTEGER
            MAX-ACCESS read-only
            STATUS current
            DESCRIPTION  
            ""
            ::= { brzaccVLErrHandlingEntry 3 }

    brzaccVLErrHandlingParameter1 OBJECT-TYPE
            SYNTAX  INTEGER
            MAX-ACCESS read-only
            STATUS current
            DESCRIPTION  
            ""
            ::= { brzaccVLErrHandlingEntry 4 }

    brzaccVLErrHandlingParameter2 OBJECT-TYPE
            SYNTAX  INTEGER
            MAX-ACCESS read-only
            STATUS current
            DESCRIPTION  
            ""
            ::= { brzaccVLErrHandlingEntry 5 }

    brzaccVLErrHandlingParameter3 OBJECT-TYPE
            SYNTAX  INTEGER
            MAX-ACCESS read-only
            STATUS current
            DESCRIPTION  
            ""
            ::= { brzaccVLErrHandlingEntry 6 }

    brzaccVLErrHandlingParameter4 OBJECT-TYPE
            SYNTAX  INTEGER
            MAX-ACCESS read-only
            STATUS current
            DESCRIPTION  
            ""
            ::= { brzaccVLErrHandlingEntry 7 }

    brzaccVLErrHandlingParameter5 OBJECT-TYPE
            SYNTAX  INTEGER
            MAX-ACCESS read-only
            STATUS current
            DESCRIPTION  
            ""
            ::= { brzaccVLErrHandlingEntry 8 }



-- begin NEW section


    newMngIpFilterTable OBJECT-TYPE
            SYNTAX SEQUENCE OF NewMngIpFilterEntry
            MAX-ACCESS not-accessible
            STATUS current
            DESCRIPTION
            "Applicable to all units.  
             A Management IP Filter Table of up to 10 IP addresses 
             of devices that are authorized to access the unit 
             for management purposes." 
            ::= { brzaccVLNwMngParameters 15 }

    newMngIpFilterEntry  OBJECT-TYPE
            SYNTAX NewMngIpFilterEntry
            MAX-ACCESS not-accessible
            STATUS current
            DESCRIPTION
            "Applicable to all units.  
             A Management IP Filter Table entry."
            INDEX { brzaccVLNewNwMngIpAddress }
            ::= { newMngIpFilterTable 1 }

    NewMngIpFilterEntry ::= SEQUENCE { brzaccVLNewNwMngIpAddress   IpAddress,
                                    brzaccVLNewNwMngIpAddressCommand  INTEGER }
   
    brzaccVLNewNwMngIpAddress   OBJECT-TYPE
            SYNTAX IpAddress  
            MAX-ACCESS read-only
            STATUS current
            DESCRIPTION 
            "Applicable to all units.  
             An IP address in the Management IP Filter Table."
          ::= { newMngIpFilterEntry 1 }

    brzaccVLNewNwMngIpAddressCommand   OBJECT-TYPE
            SYNTAX INTEGER { active(1), notInService(2), notReady(3), createAndGo(4), createAndWait(5), destroy(6) }
            MAX-ACCESS read-write
            STATUS current
            DESCRIPTION 
            "Applicable to all units.
			 Supports only active(1), createAndGo(4) and destroy(6).
             A command for an entry in the Management IP Filter 
             Table."
         ::= { newMngIpFilterEntry 2 }


-- end NEW section


-- begin NEW section


    newMngTrapTable OBJECT-TYPE
            SYNTAX SEQUENCE OF NewMngTrapEntry
            MAX-ACCESS not-accessible
            STATUS current
            DESCRIPTION
            "Applicable to all units.  
             A Management Trap Table of up to 10 IP addresses of 
             stations to send traps to." 
            ::= { brzaccVLNwMngParameters 16 }

    newMngTrapEntry  OBJECT-TYPE
            SYNTAX NewMngTrapEntry
            MAX-ACCESS not-accessible
            STATUS current
            DESCRIPTION
            "Applicable to all units.  
             A Management Trap Table entry." 
            INDEX { brzaccVLNewNwMngTrapAddress }
            ::= { newMngTrapTable 1 }
                                
    NewMngTrapEntry ::= SEQUENCE { brzaccVLNewNwMngTrapCommunity   DisplayString,
                                brzaccVLNewNwMngTrapAddress   IpAddress,
                                brzaccVLNewNwTrapCommand      INTEGER }
                                
    brzaccVLNewNwMngTrapCommunity OBJECT-TYPE
            SYNTAX DisplayString (SIZE(0..14))
            MAX-ACCESS read-write
            STATUS current
            DESCRIPTION  
            "Applicable to all units.  
             The trap community associated with the applicable 
             entry in the Management Trap Table.
             Up to 14 printable case sensitive ASCII characters."
            ::= { newMngTrapEntry 1 }

    brzaccVLNewNwMngTrapAddress   OBJECT-TYPE
            SYNTAX  IpAddress  
            MAX-ACCESS read-only
            STATUS current
            DESCRIPTION  
            "Applicable to all units.  
             An IP address in the Management Trap Table entry." 
        ::= { newMngTrapEntry 2 }

    brzaccVLNewNwTrapCommand   OBJECT-TYPE
            SYNTAX  INTEGER { active(1), notInService(2), notReady(3), createAndGo(4), createAndWait(5), destroy(6) }
            MAX-ACCESS read-write
            STATUS current
            DESCRIPTION  
            "Applicable to all units.
			 Supports only active(1), createAndGo(4) and destroy(6).
             A command for an entry in the Management Trap Table."
        ::= { newMngTrapEntry 3 }

    brzaccVLNewMngIpRangesTable OBJECT-TYPE
            SYNTAX SEQUENCE OF BrzaccVLNewMngIpRangeEntry
            MAX-ACCESS not-accessible
            STATUS current
            DESCRIPTION
            "Applicable to all units.  
             Table of Management IP Address Ranges" 
            ::= { brzaccVLNwMngParameters 17 }

    brzaccVLNewMngIpRangeEntry  OBJECT-TYPE
            SYNTAX BrzaccVLNewMngIpRangeEntry
            MAX-ACCESS not-accessible
            STATUS current
            DESCRIPTION
            "Applicable to all units.  
             A Management IP Address Ranges Table entry" 
            INDEX { brzaccVLNewMngIpRangeStart }
            ::= { brzaccVLNewMngIpRangesTable 1 }
                                
    BrzaccVLNewMngIpRangeEntry ::= SEQUENCE {
								brzaccVLNewMngIpRangeStart		IpAddress,
								brzaccVLNewMngIpRangeEnd		IpAddress,
								brzaccVLNewMngIpRangeMask		IpAddress,
								brzaccVLNewMngIpRangeFlag		INTEGER,
								brzaccVLNewMngIpRangeCommand		INTEGER
                                }
               
 
    brzaccVLNewMngIpRangeStart OBJECT-TYPE
            SYNTAX  IpAddress
            MAX-ACCESS read-only
            STATUS current
            DESCRIPTION  
            "Applicable to all units.  
             Start Address of the range"
            ::= { brzaccVLNewMngIpRangeEntry 1 }
    
    brzaccVLNewMngIpRangeEnd OBJECT-TYPE
            SYNTAX  IpAddress
            MAX-ACCESS read-write
            STATUS current
            DESCRIPTION  
            "Applicable to all units.  
             End Address of the range. 
             Used only if brzaccVLMngIpRangeFlag is  rangeDefinedByStartEndAddr"
            ::= { brzaccVLNewMngIpRangeEntry 2 }
            
	brzaccVLNewMngIpRangeMask OBJECT-TYPE
            SYNTAX  IpAddress
            MAX-ACCESS read-write
            STATUS current
            DESCRIPTION  
			"Applicable to all units.  
             End Address of the range. 
             Used only if brzaccVLMngIpRangeFlag is  rangeDefinedByStartAddrMask"
            ::= { brzaccVLNewMngIpRangeEntry 3 } 

    brzaccVLNewMngIpRangeFlag OBJECT-TYPE
            SYNTAX  INTEGER { rangeDefinedByStartEndAddr(1), rangeDefinedByStartAddrMask(2)}  
            MAX-ACCESS read-write
            STATUS current
            DESCRIPTION  
            "Applicable to all units.  
             Defines the method of defining the range:
             Using Start & End Address( rangeDefinedByStartEndAddr ),
             or using Start Address and Mask ( rangeDefinedByStartAddrSubNetMask )."
            ::= { brzaccVLNewMngIpRangeEntry 4 }

    brzaccVLNewMngIpRangeCommand OBJECT-TYPE
            SYNTAX  INTEGER { active(1), notInService(2), notReady(3), createAndGo(4), createAndWait(5), destroy(6) }
            MAX-ACCESS read-write
            STATUS current
            DESCRIPTION  
            "Applicable to all units.  
             Row Status in the New Management IP Address Ranges Table"
            ::= { brzaccVLNewMngIpRangeEntry 5 }

-- end NEW section



   brzaccVLTrapHistory        OBJECT IDENTIFIER ::= {brzaccVLNewNMngSystem 2}

   brzaccVLLastTrapSequenceNumber   OBJECT-TYPE
            SYNTAX  INTEGER
            MAX-ACCESS read-only
            STATUS current
            DESCRIPTION 
            "Applicable to AU/BU only.
            Sequence Number of Last generated Trap"
            ::= { brzaccVLTrapHistory 1 }
            
  
   	brzaccVLTrapHistoryTable OBJECT-TYPE
            SYNTAX SEQUENCE OF BrzaccVLTrapHistoryEntry
            MAX-ACCESS not-accessible
            STATUS current
            DESCRIPTION
            "Applicable to AU/BU only.
            This table contains the last 1024 traps generated by the unit." 
            ::= { brzaccVLTrapHistory 2 }

    brzaccVLTrapHistoryEntry  OBJECT-TYPE
            SYNTAX BrzaccVLTrapHistoryEntry
            MAX-ACCESS not-accessible
            STATUS current
            DESCRIPTION
            "Applicable to AU/BU only.
            An entry in Trap History Table." 
            INDEX { brzaccVLTrapHistorySequenceNumber}
            ::= { brzaccVLTrapHistoryTable 1 }
                                
    BrzaccVLTrapHistoryEntry ::= SEQUENCE { 
				brzaccVLTrapHistorySequenceNumber	INTEGER,
				brzaccVLTrapType					INTEGER,
				brzaccVLTrapMacAddrParam			MacAddress,
				brzaccVLTrapIntParam1				INTEGER,
				brzaccVLTrapIntParam2				INTEGER,
				brzaccVLTrapIntParam3				INTEGER,
				brzaccVLTrapStrParam				DisplayString
                                }
               
 
    brzaccVLTrapHistorySequenceNumber OBJECT-TYPE
            SYNTAX  INTEGER(0..2147483647)
            MAX-ACCESS read-only
            STATUS current
            DESCRIPTION  
            "Applicable to AU/BU only.
            Sequence number of the trap."
            ::= { brzaccVLTrapHistoryEntry 1 }
   
    brzaccVLTrapType OBJECT-TYPE
            SYNTAX  INTEGER
            MAX-ACCESS read-only
            STATUS current
            DESCRIPTION  
            "Applicable to AU/BU only.
            It contains the trap type."
            ::= { brzaccVLTrapHistoryEntry 2 }
            
    brzaccVLTrapMacAddrParam OBJECT-TYPE
            SYNTAX  MacAddress
            MAX-ACCESS read-only
            STATUS current
            DESCRIPTION  
            "Applicable to AU/BU only.
            It contains the MAC Address of the trap if the trap 
            type requires this field, otherwise it contains the NULL 
            MAC Address."
            ::= { brzaccVLTrapHistoryEntry 3 }

    brzaccVLTrapIntParam1 OBJECT-TYPE
            SYNTAX  INTEGER
            MAX-ACCESS read-only
            STATUS current
            DESCRIPTION  
            "Applicable to AU/BU only.
            It contains the first variable of integer type for the trap.
            If from the trap definition this variable is not applicable 
            it will be 0."
            ::= { brzaccVLTrapHistoryEntry 4 }

    brzaccVLTrapIntParam2 OBJECT-TYPE
            SYNTAX  INTEGER
            MAX-ACCESS read-only
            STATUS current
            DESCRIPTION  
            "Applicable to AU/BU only.
            It contains the second variable of integer type for the trap.
            If from the trap definition this variable is not applicable 
            it will be 0."
            ::= { brzaccVLTrapHistoryEntry 5 }

    brzaccVLTrapIntParam3 OBJECT-TYPE
            SYNTAX  INTEGER
            MAX-ACCESS read-only
            STATUS current
            DESCRIPTION  
            "Applicable to AU/BU only.
            It contains the third variable of integer type for the trap.
            If from the trap definition this variable is not applicable 
            it will be 0."
            ::= { brzaccVLTrapHistoryEntry 6 }

    brzaccVLTrapStrParam OBJECT-TYPE
            SYNTAX  DisplayString
            MAX-ACCESS read-only
            STATUS current
            DESCRIPTION  
            "Applicable to AU/BU only.
            It contains the string variable of the trap if this variable exists
            for that trap, otherwise it will contain the empty string."
            ::= { brzaccVLTrapHistoryEntry 7 }
            

-- IP Params:
-- ===========
brzaccVLIpParams      OBJECT IDENTIFIER ::= {breezeAccessVLMib 4}

    brzaccVLUnitIpAddress OBJECT-TYPE
            SYNTAX  IpAddress  
            MAX-ACCESS read-write
            STATUS current
            DESCRIPTION  
            "Applicable to all units.  
             IP address of the unit."
            ::= { brzaccVLIpParams 1 }

    brzaccVLSubNetMask OBJECT-TYPE
            SYNTAX  IpAddress  
            MAX-ACCESS read-write
            STATUS current
            DESCRIPTION  
            "Applicable to all units.  
             Subnet mask of the unit."
            ::= { brzaccVLIpParams 2 }

    brzaccVLDefaultGWAddress OBJECT-TYPE
            SYNTAX  IpAddress  
            MAX-ACCESS read-write
            STATUS current
            DESCRIPTION  
            "Applicable to all units.  
             Default gateway IP address of the unit."
            ::= { brzaccVLIpParams 3 }

    brzaccVLUseDhcp OBJECT-TYPE
            SYNTAX  INTEGER{ disable (1), 
                             dhcpOnly (2), 
                             automatic (3) }
            MAX-ACCESS  read-write    
            STATUS  current
            DESCRIPTION
            "Applicable to all units.  
             DHCP client mode of operation. 
             disabled : Use regular (manual) methods to configure IP 
                        parameters. 
             dHCP Only: Use DHCP server to configure IP parameters. 
             automatic: Use DHCP server to configure IP parameters. 
                        If a DHCP server is not available, use 
                        manually configured values."
            ::= { brzaccVLIpParams 4 }

    brzaccVLAccessToDHCP OBJECT-TYPE
            SYNTAX  INTEGER{ fromWirelessOnly    (1),
                             fromEthernetOnly (2),
                             fromBothWirelessAndEthernet (3) }
            MAX-ACCESS  read-write    
            STATUS  current
            DESCRIPTION
            "Applicable to all units.  
             The port to be used for communicating with a DHCP server."
            ::= { brzaccVLIpParams 5 }

    brzaccVLRunTimeIPaddr OBJECT-TYPE
            SYNTAX  IpAddress
            MAX-ACCESS  read-only
            STATUS  current
            DESCRIPTION
            "Applicable to all units.  
             The run-time IP address. If DHCP is used the Run Time 
             IP Address is the address given to the unit by the 
             server. Otherwise it is the manually configured address."
            ::= { brzaccVLIpParams 6 }

    brzaccVLRunTimeSubNetMask OBJECT-TYPE
            SYNTAX  IpAddress
            MAX-ACCESS  read-only
            STATUS  current
            DESCRIPTION
            "Applicable to all units.  
             The run-time Subnet Mask. If DHCP is used the Run Time 
             Subnet Mask is the mask given to the unit by the server. 
             Otherwise it is the manually configured mask."
            ::= { brzaccVLIpParams 7 }

    brzaccVLRunTimeDefaultIPGateway OBJECT-TYPE
            SYNTAX  IpAddress
            MAX-ACCESS  read-only
            STATUS  current
            DESCRIPTION
            "Applicable to all units.  
             The run-time Gateway IP address. If DHCP is used the 
             Run Time Gateway IP Address is the address given to the 
             unit by the server. Otherwise it is the manually 
             configured address."
            ::= { brzaccVLIpParams 8 }


-- Bridge Params
-- ==============
brzaccVLBridgeParameters      OBJECT IDENTIFIER ::= {breezeAccessVLMib 5}


brzaccVLVLANSupport       OBJECT IDENTIFIER ::= {brzaccVLBridgeParameters 1}

    brzaccVLVlanID OBJECT-TYPE
            SYNTAX  INTEGER 
            MAX-ACCESS read-write
            STATUS current
            DESCRIPTION  
            "Applicable to SU/RB only.
             VLAN ID for data frame tagging. 
             Applicable to Access Link only. 
             Range: 1 to 4094. 0 - not applicable."
            ::= { brzaccVLVLANSupport 1 }

    brzaccVLEthernetLinkType OBJECT-TYPE
            SYNTAX  INTEGER { accessLink          (1), 
                              trunkLink           (2), 
                              hybridLink          (3),
                              serviceProviderLink (4),
                              extAccessLink       (5),
                              extTrunkLink        (6) } 
            MAX-ACCESS read-write
            STATUS current
            DESCRIPTION  
            "Applicable to all units.  
             VLAN support mode (Link Type). 
             The Access Link, Extended Access Link and Extended Trunk Link 
             options are not available for AU/BU.
             Service Provider Link is not available for BU/RB."
            ::= { brzaccVLVLANSupport 2 }
 
    brzaccVLManagementVlanID OBJECT-TYPE
            SYNTAX  INTEGER 
            MAX-ACCESS read-write
            STATUS current
            DESCRIPTION  
            "Applicable to all units.  
             VLAN ID for management frame tagging.
             Range: 1 to 4094, 65535 for No VLAN tagging."
            ::= { brzaccVLVLANSupport 3 }

brzaccVLVLANForwarding        OBJECT IDENTIFIER ::= {brzaccVLVLANSupport 4}

     brzaccVLVlanForwardingSupport OBJECT-TYPE
            SYNTAX  INTEGER { disable (1) , enable (2), na(255) } 
            MAX-ACCESS read-write
            STATUS current
            DESCRIPTION  
            "Applicable to all units.  
             Enables or disables the VLAN forwarding feature. 
             (applicable in Trunk and Service Provider links only)."
            ::= { brzaccVLVLANForwarding 1 }

    brzaccVLVlanForwardingTable OBJECT-TYPE
            SYNTAX SEQUENCE OF BrzaccVLVlanForwardingEntry
            MAX-ACCESS not-accessible
            STATUS current
            DESCRIPTION
            "Starting with version 5.0, this is deprecated. Use brzaccVLNewVlanForwardingTable instead.
			 Applicable to all units.  
             A VLAN Forwarding Table of up to 20 VLAN IDs of devices 
             to which data frames are forwarded when VLAN Forwarding 
             is Enabled. (applicable in Trunk and Service Provider links only)."
            ::= { brzaccVLVLANForwarding 2 }

    brzaccVLVlanForwardingEntry  OBJECT-TYPE
            SYNTAX BrzaccVLVlanForwardingEntry
            MAX-ACCESS not-accessible
            STATUS current
            DESCRIPTION
            "Applicable to all units.  
             A VLAN Forwarding Table entry. (applicable in Trunk and Service Provider 
             links only)."
            INDEX { brzaccVLVlanForwardingTableIdx }
            ::= { brzaccVLVlanForwardingTable 1 }

    BrzaccVLVlanForwardingEntry ::= SEQUENCE {
            brzaccVLVlanForwardingTableIdx  INTEGER,
            brzaccVLVlanIdForwarding  INTEGER
            }

         
    brzaccVLVlanForwardingTableIdx   OBJECT-TYPE
            SYNTAX  INTEGER  (1..20)
            MAX-ACCESS read-only
            STATUS current
            DESCRIPTION  
            "Applicable to all units.  
             A read only table index for a VLAN entry in the VLAN 
             Forwarding Table."
        ::= { brzaccVLVlanForwardingEntry 1 }

    brzaccVLVlanIdForwarding   OBJECT-TYPE
            SYNTAX  INTEGER  
            MAX-ACCESS read-write
            STATUS current
            DESCRIPTION  
            "Applicable to all units.  
             The list of VLAN ID's in the VLAN ID Forwarding Table. 
             To Remove a VLAN ID - SET the corresponding entry to 0. 
             To Add a new VLAN ID SET an entry which is currently 0.
             Range : 0 to 4094"
        ::= { brzaccVLVlanForwardingEntry 2 }

    brzaccVLNewVlanForwardingTable OBJECT-TYPE
            SYNTAX SEQUENCE OF BrzaccVLNewVlanForwardingEntry
            MAX-ACCESS not-accessible
            STATUS current
            DESCRIPTION
            "Applicable to all units.  
             A VLAN Forwarding Table of up to 20 VLAN IDs of devices 
             to which data frames are forwarded when VLAN Forwarding 
             is Enabled. (applicable in Trunk and Service Provider links only)."
            ::= { brzaccVLVLANForwarding 3 }

    brzaccVLNewVlanForwardingEntry  OBJECT-TYPE
            SYNTAX BrzaccVLNewVlanForwardingEntry
            MAX-ACCESS not-accessible
            STATUS current
            DESCRIPTION
            "Applicable to all units.  
             A VLAN Forwarding Table entry. (applicable in Trunk and Service Provider 
             links only)."
            INDEX { brzaccVLNewVlanIdForwarding }
            ::= { brzaccVLNewVlanForwardingTable 1 }

    BrzaccVLNewVlanForwardingEntry ::= SEQUENCE {
            brzaccVLNewVlanIdForwarding  INTEGER,
            brzaccVLNewVlanForwardingCommand  INTEGER
            }


    brzaccVLNewVlanIdForwarding   OBJECT-TYPE
            SYNTAX  INTEGER  (1..4094)
            MAX-ACCESS read-only
            STATUS current
            DESCRIPTION  
            "Applicable to all units.
             The list of VLAN ID's in the VLAN ID Forwarding Table.
             Range : 1 to 4094"
        ::= { brzaccVLNewVlanForwardingEntry 1 }

    brzaccVLNewVlanForwardingCommand   OBJECT-TYPE
            SYNTAX  INTEGER  { active(1), notInService(2), notReady(3), createAndGo(4), createAndWait(5), destroy(6) }
            MAX-ACCESS read-write
            STATUS current
            DESCRIPTION  
            "Applicable to all units.  
             Row Status in the New VLAN Forwarding Table."
        ::= { brzaccVLNewVlanForwardingEntry 2 }

brzaccVLVlanRelaying    OBJECT IDENTIFIER ::= {brzaccVLVLANSupport 5}

    brzaccVLVlanRelayingSupport OBJECT-TYPE
            SYNTAX  INTEGER { disable (1) , enable (2), na(255) } 
            MAX-ACCESS read-write
            STATUS current
            DESCRIPTION  
            "Applicable to AU only. 
             Not applicable to BreezeNET-B products. 
             Enables or disables VLAN Relaying (applicable in 
             Trunk and Service Provider links only)."
            ::= { brzaccVLVlanRelaying 1 }

    brzaccVLVlanRelayingTable OBJECT-TYPE
            SYNTAX SEQUENCE OF BrzaccVLVlanRelayingEntry
            MAX-ACCESS not-accessible
            STATUS current
            DESCRIPTION
			"Starting with version 5.0, this is deprecated. Use brzaccVLNewVlanRelayingTable instead.
             Applicable to AU only. 
			 Not applicable to BreezeNET-B products.
             A VLAN Relaying Table of up to 20 VLAN IDs of devices 
             to which data frames are relayed when VLAN Relaying is 
             Enabled. (applicable in Trunk and Service Provider links only)."
            ::= { brzaccVLVlanRelaying 2 }

    brzaccVLVlanRelayingEntry  OBJECT-TYPE
            SYNTAX BrzaccVLVlanRelayingEntry
            MAX-ACCESS not-accessible
            STATUS current
            DESCRIPTION
            "Applicable to AU only.
             Not applicable to BreezeNET-B products. 
             A VLAN Relaying Table entry. (applicable in Trunk and Service 
             Provider links only)."
            INDEX { brzaccVLVlanRelayingTableIdx }
            ::= { brzaccVLVlanRelayingTable 1 }

    BrzaccVLVlanRelayingEntry ::= SEQUENCE {
            brzaccVLVlanRelayingTableIdx  INTEGER,
            brzaccVLVlanIdRelaying  INTEGER
            }
   
    brzaccVLVlanRelayingTableIdx   OBJECT-TYPE
            SYNTAX  INTEGER  (1..20)
            MAX-ACCESS read-only
            STATUS current
            DESCRIPTION  
            "Applicable to AU only. 
             Not applicable to BreezeNET-B products.
             A table index for a VLAN entry in the VLAN 
             Relaying Table."
        ::= { brzaccVLVlanRelayingEntry 1 }


    brzaccVLVlanIdRelaying   OBJECT-TYPE
            SYNTAX  INTEGER  
            MAX-ACCESS read-write
            STATUS current
            DESCRIPTION  
            "Applicable to AU only. 
             Not applicable to BreezeNET-B products.
             The list of VLAN ID's in the VLAN ID Relaying Table. 
             To Remove a VLAN ID - SET the corresponding entry to 0. 
             To Add a new VLAN ID SET an entry which is currently 0.
             Range: 0 to 4094 , 0 - remove entry."
        ::= { brzaccVLVlanRelayingEntry 2 }

    brzaccVLNewVlanRelayingTable OBJECT-TYPE
            SYNTAX SEQUENCE OF BrzaccVLNewVlanRelayingEntry
            MAX-ACCESS not-accessible
            STATUS current
            DESCRIPTION
            "Applicable to AU only. 
			 Not applicable to BreezeNET-B products.
             A VLAN Relaying Table of up to 20 VLAN IDs of devices 
             to which data frames are relayed when VLAN Relaying is 
             Enabled. (applicable in Trunk and Service Provider links only)."
            ::= { brzaccVLVlanRelaying 3 }

    brzaccVLNewVlanRelayingEntry  OBJECT-TYPE
            SYNTAX BrzaccVLNewVlanRelayingEntry
            MAX-ACCESS not-accessible
            STATUS current
            DESCRIPTION
            "Applicable to AU only.
             Not applicable to BreezeNET-B products. 
             A VLAN Relaying Table entry. (applicable in Trunk and Service 
             Provider links only)."
            INDEX { brzaccVLNewVlanIdRelaying }
            ::= { brzaccVLNewVlanRelayingTable 1 }

    BrzaccVLNewVlanRelayingEntry ::= SEQUENCE {
            brzaccVLNewVlanIdRelaying  INTEGER,
            brzaccVLNewVlanRelayingTableCommand  INTEGER
            }

    brzaccVLNewVlanIdRelaying   OBJECT-TYPE
            SYNTAX  INTEGER (1..4094)
            MAX-ACCESS read-only
            STATUS current
            DESCRIPTION  
            "Applicable to AU only. 
             Not applicable to BreezeNET-B products.
             The list of VLAN ID's in the VLAN ID Relaying Table. 
             Range: 1 to 4094."
        ::= { brzaccVLNewVlanRelayingEntry 1 }

    brzaccVLNewVlanRelayingTableCommand   OBJECT-TYPE
            SYNTAX  INTEGER  { active(1), notInService(2), notReady(3), createAndGo(4), createAndWait(5), destroy(6) }
            MAX-ACCESS read-write
            STATUS current
            DESCRIPTION  
            "Applicable to AU only. 
             Not applicable to BreezeNET-B products.
			 Supports only active(1), createAndGo(4) and destroy(6).
             A command to create or destroy a VLAN entry in the VLAN 
             Relaying Table."
        ::= { brzaccVLNewVlanRelayingEntry 2 }

brzaccVLVLANTrafficPriority       OBJECT IDENTIFIER ::= {brzaccVLVLANSupport 6}

    brzaccVLVlanDataPriority OBJECT-TYPE
            SYNTAX  INTEGER  { na(255) }
            MAX-ACCESS read-write
            STATUS current
            DESCRIPTION  
            "Applicable to SU/RB only. 
             Priority tagging for data frames. Applicable to Access 
             Link only.
             Range: 0 to 7."
            ::= { brzaccVLVLANTrafficPriority 1 }
  
    brzaccVLVlanManagementPriority OBJECT-TYPE
            SYNTAX  INTEGER  ( 0..7 )
            MAX-ACCESS read-write
            STATUS current
            DESCRIPTION  
            "Applicable to all units.  
             Priority tagging for management frames.
             Range: 0 to 7."
            ::= { brzaccVLVLANTrafficPriority 2 }

 
    brzaccVLVlanPriorityThreshold OBJECT-TYPE
            SYNTAX  INTEGER  { na(255) }
            MAX-ACCESS read-write
            STATUS current
            DESCRIPTION  
            "Applicable to all units. Not applicable to units with SW 
             version 3.1 or higher. 
             Priority threshold for tagged frames received from 
             Ethernet port. Applicable to Hybrid Link and Trunk Link 
             only.
             Valid values: 0-7."
            ::= { brzaccVLVLANTrafficPriority 3 }

brzaccVLVLANQinQ	OBJECT IDENTIFIER ::= {brzaccVLVLANSupport 7}

	brzaccVLQinQEthertype   OBJECT-TYPE
            SYNTAX	INTEGER  (33024 .. 36864|37120|37376)
            MAX-ACCESS read-write
            STATUS current
            DESCRIPTION  
            "Applicable to AU and SU. Not applicable to BreezeNET-B units. 
            The Ethernet type of the Service Provider Tag.
            The range is  0x8100(33024) - 0x9000(36864), 0x9100(37120), 0x9200(37376)."
        ::= { brzaccVLVLANQinQ 1 }
        
	brzaccVLQinQProviderVlanID   OBJECT-TYPE
            SYNTAX	INTEGER (1..4094)
            MAX-ACCESS read-write
            STATUS current
            DESCRIPTION  
            "Applicable to SU only.
            VLAN ID of the Service Provider Tag."
        ::= { brzaccVLVLANQinQ 2 }

-- VLAN Extended Access Link

    brzaccVLVlanExtendedAccessRulesTable     OBJECT-TYPE
            SYNTAX SEQUENCE OF BrzaccVLVlanExtendedAccessRulesEntry
            MAX-ACCESS not-accessible
            STATUS current
            DESCRIPTION
            "Starting with version 6.0.
             Available for SU/RB units only.
             An 8-VLAN Rule Table for Extended Access Link." 
            ::= { brzaccVLVLANSupport 8 }

    brzaccVLVlanExtendedAccessRulesEntry     OBJECT-TYPE
            SYNTAX  BrzaccVLVlanExtendedAccessRulesEntry
            MAX-ACCESS not-accessible
            STATUS current
            DESCRIPTION
            "Starting with version 6.0.
             Available for SU/RB units only.
             An entry in VLAN Rule Table for Extended Access Link." 
            INDEX { brzaccVLVlanExtendedAccessRulesTableIdx }
            ::= { brzaccVLVlanExtendedAccessRulesTable 1 }

    BrzaccVLVlanExtendedAccessRulesEntry ::= SEQUENCE {
               brzaccVLVlanExtendedAccessRulesTableIdx             INTEGER,
               brzaccVLVlanExtendedAccessRuleId                    INTEGER,
               brzaccVLVlanExtendedAccessRuleVlanId                INTEGER,
               brzaccVLVlanExtendedAccessRulePriority              INTEGER,
               brzaccVLVlanExtendedAccessRuleMulticastAllowed      INTEGER,
               brzaccVLVlanExtendedAccessRuleOpType                INTEGER,
               brzaccVLVlanExtendedAccessRuleOperands              DisplayString
            }

    brzaccVLVlanExtendedAccessRulesTableIdx   OBJECT-TYPE
            SYNTAX  INTEGER  (1..8)
            MAX-ACCESS read-only
            STATUS current
            DESCRIPTION  
            "Starting with version 6.0.
             Available for SU/RB units only.
             A table index for a VLAN Rule entry/rule in the 
             VLAN Rule Table for Extended Access Link."
        ::= { brzaccVLVlanExtendedAccessRulesEntry 1 }

    brzaccVLVlanExtendedAccessRuleId   OBJECT-TYPE
            SYNTAX  INTEGER {
                noRule                (1), 
                sourceMacAddress      (2),
                destinationMacAddress (3),
                sourceIpAddress       (4),
                destinationIpAddress  (5),
                sourceUdpPort         (6),
                destinationUdpPort    (7),
                sourceTcpPort         (8),
                destinationTcpPort    (9),
                ipProtocol           (10),
                default              (11)   }
            MAX-ACCESS read-write
            STATUS current
            DESCRIPTION  
            "Starting with version 6.0.
             Available for SU/RB units only.
             Identifies the VLAN Rule type of an entry/rule,
             in VLAN Rule Table for Extended Access Link."
    ::= { brzaccVLVlanExtendedAccessRulesEntry 2 }

    brzaccVLVlanExtendedAccessRuleVlanId   OBJECT-TYPE
            SYNTAX  INTEGER  (0..4094)
            MAX-ACCESS read-write
            STATUS current
            DESCRIPTION  
            "Starting with version 6.0.
             Available for SU/RB units only.
             Identifies the data VLAN ID of an entry/rule,
             in VLAN Rule Table for Extended Access Link.
             Range: 1-4094. Value zero is returned if
             no rule defined for this entry."
    ::= { brzaccVLVlanExtendedAccessRulesEntry 3 }

    brzaccVLVlanExtendedAccessRulePriority   OBJECT-TYPE
            SYNTAX  INTEGER  ( 0..7 | 255 )
            MAX-ACCESS read-write
            STATUS current
            DESCRIPTION  
            "Starting with version 6.0.
             Applicable to SU/RB units only. 
             Identifies the Priority tagging for data frames, for an entry/rule,
             in VLAN Rule Table for Extended Access Link.
             Range: 0-7. Value 255 is returned if
             no rule defined for this entry."
    ::= { brzaccVLVlanExtendedAccessRulesEntry 4 }

    brzaccVLVlanExtendedAccessRuleMulticastAllowed    OBJECT-TYPE
            SYNTAX  INTEGER  { allowed(1), notAllowed(2), na(255) }
            MAX-ACCESS read-write
            STATUS current
            DESCRIPTION  
            "Starting with version 6.0.
             Available for SU/RB units only.
             Determine if Multicast frames are tagged and sent on wireless LAN.
             Option for an entry/rule, in VLAN Rule Table for Extended Access Link.
             Value 255 is returned if no rule defined for this entry."
    ::= { brzaccVLVlanExtendedAccessRulesEntry 5 }

    brzaccVLVlanExtendedAccessRuleOpType   OBJECT-TYPE
            SYNTAX  INTEGER  {
                value          (1),
                range          (2),
                mask           (3),
                enumeration    (4),
                na           (255)   }
            MAX-ACCESS read-write
            STATUS current
            DESCRIPTION  
            "Starting with version 6.0.
             Available for SU/RB units only.
             Identifies the VLAN Operand type of an entry/rule,
             in VLAN Rule Table for Extended Access Link.
             Range: 1-4. Value 255 is returned if
             no rule or default rule defined for this entry.
             Accepted combinations are:
                 sourceMacAddress, destinationMacAddress    - value, range, mask;
                 sourceIpAddress, destinationIpAddress      - value, range, mask;
                 sourceUdpPort, destinationUdpPort          - value, range, enumeration;
                 sourceTcpPort, destinationTcpPort          - value, range, enumeration;
                 ipProtocol                                 - value, enumeration "
    ::= { brzaccVLVlanExtendedAccessRulesEntry 6 }

    brzaccVLVlanExtendedAccessRuleOperands   OBJECT-TYPE
            SYNTAX DisplayString (SIZE(0..63))
            MAX-ACCESS read-write
            STATUS current
            DESCRIPTION  
            "Starting with version 6.0.
             Available for SU/RB units only.
             The VLAN Operand list of an entry/rule,
             in VLAN Rule Table for Extended Access Link.
             Operand list may be one of the following:
                v1-v2    : range (v1 - v2), v1 and v2 included (not applicable for IP protocols);
                v,m      : value and mask (for MAC and IP only);
                v0       : single value;
                v1,v2,v3 : max 8-value enumeration (for Ports and IP protocols only). 
             An operand may be:
                xxxxxxxxxxxx    : 12-char hexadecimal representation of a MAC address; 
                ddd.ddd.ddd.ddd : max 15-char decimal representation of an IP address; 
                ddddd           : max 5-char decimal representation of a Port; 
                ddd             : max 3-char decimal representation of an IP Protocol. 
             Up to 63 printable ASCII characters."
    ::= { brzaccVLVlanExtendedAccessRulesEntry 7 }

-- end VLAN Extended Access Link

    brzaccVLVlanExtendedTrunkVlanID   OBJECT-TYPE
            SYNTAX  INTEGER (1..4094)
            MAX-ACCESS read-write
            STATUS current
            DESCRIPTION  
            "Starting with version 6.0.
             Available for SU/RB units only.
            Native VLAN ID value, for Extended Trunk Link."
            ::= { brzaccVLVLANSupport 9 }


    brzaccVLBridgeAgingTime OBJECT-TYPE
            SYNTAX  INTEGER  
            MAX-ACCESS read-write
            STATUS current
            DESCRIPTION  
            "Applicable to all units.  
             Bridge aging time for devices on both the Ethernet and 
             wireless link sides. 
             Range: 20 to 2000 seconds."
            ::= { brzaccVLBridgeParameters 2 }

    brzaccVLBroadcastRelaying OBJECT-TYPE
            SYNTAX  INTEGER  {	disable (1),
								broadcastMulticastEnable (2),
								broadcastEnable (3),
								multicastEnable (4),
								na (255) }
            MAX-ACCESS read-write
            STATUS current
            DESCRIPTION  
            "Applicable to AU only. 
             Not applicable to BreezeNET-B products.
             Enables/disables the relaying of broadcast messages to 
             the wireless link."
            ::= { brzaccVLBridgeParameters 4 }

    brzaccVLUnicastRelaying OBJECT-TYPE
            SYNTAX  INTEGER  { disable(1), enable(2), na (255) }
            MAX-ACCESS read-write
            STATUS current
            DESCRIPTION  
            "Applicable to AU only. 
             Not applicable to BreezeNET-B products.
             Enables/disables the relaying of unicast messages to 
             the wireless link."
            ::= { brzaccVLBridgeParameters 5 }

    brzaccVLEthBroadcastFiltering OBJECT-TYPE
            SYNTAX  INTEGER { disable (1), 
                              onEthernetOnly (2), 
                              onWirelessOnly  (3),
                              onBothWirelessAndEthernet (4), 
                              na (255) } 
            MAX-ACCESS read-write
            STATUS current
            DESCRIPTION  
            "Applicable to SU/RB only. 
             Enables/disables the filtering of Ethernet (layer2) 
             broadcasts.    
             disable             : No filtering.    
             onEthernetOnly      : Filters broadcasts received on the Ethernet port only.    
             onWirelessOnly      : Filters broadcasts received on the Wlan port only.    
             onBothWirelessAndEth: Filters broadcasts received on both ports."
            ::= { brzaccVLBridgeParameters 6 }                                                                        

brzaccVLEthBroadcastingParameters     OBJECT IDENTIFIER ::= {brzaccVLBridgeParameters 7}

    brzaccVLDHCPBroadcastOverrideFilter OBJECT-TYPE
            SYNTAX  INTEGER { disable (1), enable (2), na (255) } 
            MAX-ACCESS read-write
            STATUS current
            DESCRIPTION  
            "Applicable to SU/RB only. 
             Enables or disables the broadcasting of DHCP messages, 
             overriding the general *brzaccVLEthBroadcastFiltering Ethernet 
             broadcast filtering option." 
            ::= { brzaccVLEthBroadcastingParameters 1 }

    brzaccVLPPPoEBroadcastOverrideFilter OBJECT-TYPE
            SYNTAX  INTEGER { disable (1), enable (2), na (255) } 
            MAX-ACCESS read-write
            STATUS current
            DESCRIPTION  
            "Applicable to SU/RB only. 
             Enables or disables the broadcasting of PPPoE messages, 
             overriding the general *brzaccVLEthBroadcastFiltering Ethernet 
             broadcast filtering option."
            ::= { brzaccVLEthBroadcastingParameters 2 }

    brzaccVLARPBroadcastOverrideFilter OBJECT-TYPE
            SYNTAX  INTEGER { disable (1), enable (2), na (255) } 
            MAX-ACCESS read-write
            STATUS current
            DESCRIPTION  
            "Applicable to SU/RB only. 
             Enables or disables the broadcasting of ARP messages, 
             overriding the general *brzaccVLEthBroadcastFiltering Ethernet 
             broadcast filtering option."
            ::= { brzaccVLEthBroadcastingParameters 3 }
            
    brzaccVLEthBroadcastMulticastLimiterOption OBJECT-TYPE
            SYNTAX  INTEGER { disable (1),
							  limitOnlyBroadcasts(2),
							  limitMulticastsExceptBroadcasts(3),
							  limitAllMulticasts(4) } 
            MAX-ACCESS read-write
            STATUS current
            DESCRIPTION  
            "Applicable to all units.
            Enable/disable the limiter for multicast and broadcast packets." 
            ::= { brzaccVLEthBroadcastingParameters 4 }
       
   brzaccVLEthBroadcastMulticastLimiterThreshold OBJECT-TYPE
            SYNTAX  INTEGER
            MAX-ACCESS read-write
            STATUS current
            DESCRIPTION  
            "Applicable to all units.
            The limit on the number of multicast and broadcast packets when the 
            Ethernet Broadcast/Multicast Limiter Option is enabled.
            Range: 0 to 204800" 
            ::= { brzaccVLEthBroadcastingParameters 5 }
            
   brzaccVLEthBroadcastMulticastLimiterSendTrapInterval OBJECT-TYPE
            SYNTAX  INTEGER
            MAX-ACCESS read-write
            STATUS current
            DESCRIPTION  
            "Applicable to all units.
            The minimum time between two successive traps that are sent indicating the 
            number of packets that were dropped by the Ethernet Broadcast/Multicast 
            Limiter since the last trap was sent.
            Range: 1 to 60 minutes" 
            ::= { brzaccVLEthBroadcastingParameters 6 }

brzaccVLToSPriorityParameters     OBJECT IDENTIFIER ::= {brzaccVLBridgeParameters 8}

    brzaccVLToSPrecedenceThreshold OBJECT-TYPE
            SYNTAX  INTEGER  
            MAX-ACCESS read-write
            STATUS current
            DESCRIPTION  
            "Applicable to all units. Not applicable to units with SW version 3.1 or higher.
             Priority threshold (based on the ToS) for frames received 
             from the Ethernet port.
             Range: 0 to 7."
            ::= { brzaccVLToSPriorityParameters 1 }

    brzaccVLRoamingOption OBJECT-TYPE
            SYNTAX  INTEGER  { disable (1), enable (2), na(255) }
            MAX-ACCESS read-write      
            STATUS current       
            DESCRIPTION  
            "Applicable to SU/RB only.
             Disable/enable the roaming feature. When enabled, the SU/RB will start 
             scanning for an AU/BU after about one second of not receiving beacons or data 
             from current AU/BU. Once it found a new AU/BU, it will also send through 
             the wireless network a roaming SNAP on behalf of its clients informing 
             other devices in the network of their new location. When disabled, it 
             will wait for about seven seconds before starting scanning, and it will not 
             send a roaming SNAP."
            ::= { brzaccVLBridgeParameters 9 }

brzaccVLMacAddressDenyList  OBJECT IDENTIFIER ::= {brzaccVLBridgeParameters 10}

    brzaccVLMacAddressDenyListTable OBJECT-TYPE
            SYNTAX SEQUENCE OF BrzaccVLMacAddressDenyListEntry
            MAX-ACCESS not-accessible
            STATUS current
            DESCRIPTION
            "Starting with version 5.0, this is deprecated. Use brzaccVLNewMacAddressDenyListTable instead.
			 Applicable to AU only. 
			 Not applicable to BreezeNET-B units.                                   
             A list of up to 100 MAC Addresses of SUs.
             If brzaccVLMacAddressDenyListAction is set to denyList, 
             these are SUs that are not allowed to transfer data 
             to the AU. 
             If brzaccVLMacAddressDenyListAction is set to allowList, 
             only these SUs are allowed to transfer data to the AU."
            ::= { brzaccVLMacAddressDenyList 1 }

    brzaccVLMacAddressDenyListEntry  OBJECT-TYPE
            SYNTAX BrzaccVLMacAddressDenyListEntry
            MAX-ACCESS not-accessible
            STATUS current
            DESCRIPTION
            "Applicable to AU only.
			 Not applicable to BreezeNET-B units.                                   
             An entry in the Mac Address Deny List Table."
            INDEX { brzaccVLMacAddressDenyListTableIdx }
            ::= { brzaccVLMacAddressDenyListTable 1 }

    BrzaccVLMacAddressDenyListEntry ::= SEQUENCE {
            brzaccVLMacAddressDenyListTableIdx  INTEGER,
            brzaccVLMacAddressDenyListId  MacAddress
            }
        
    brzaccVLMacAddressDenyListTableIdx   OBJECT-TYPE
            SYNTAX  INTEGER (1..100) 
            MAX-ACCESS read-only
            STATUS current
            DESCRIPTION  
            "Applicable to AU only. 
			 Not applicable to BreezeNET-B units.                                   
             A read only table index for a MAC Address entry 
             in the Mac Address Deny List Table. Range: 1 to 100."
        ::= { brzaccVLMacAddressDenyListEntry 1 }

    brzaccVLMacAddressDenyListId   OBJECT-TYPE
            SYNTAX  MacAddress  
            MAX-ACCESS read-write
            STATUS current
            DESCRIPTION  
            "Applicable to AU only.
			 Not applicable to BreezeNET-B units.                                   
             The list of MAC Addresses in the Mac Address Deny
             List Table. 
             To Remove a MAC Address - SET the corresponding entry 
             to 0. 
             To Add a new MAC Address - SET an entry which is 
             currently 0."
        ::= { brzaccVLMacAddressDenyListEntry 2 }

    brzaccVLMacAddressDenyListAdd OBJECT-TYPE
            SYNTAX MacAddress
            MAX-ACCESS read-write
            STATUS current
            DESCRIPTION  
            "Applicable to AU only. 
			 Not applicable to BreezeNET-B units.                                   
             Add a MAC address to the MAC Address Deny List Table"
            ::= { brzaccVLMacAddressDenyList 2 }

    brzaccVLMacAddressDenyListRemove OBJECT-TYPE
            SYNTAX MacAddress
            MAX-ACCESS read-write
            STATUS current
            DESCRIPTION  
            "Applicable to AU only. 
			 Not applicable to BreezeNET-B units.                                   
             Delete a MAC address from the MAC Address Deny List Table"
            ::= { brzaccVLMacAddressDenyList 3 }

    brzaccVLNumberOfMacAddressesInDenyList OBJECT-TYPE
            SYNTAX INTEGER { na(255) }
            MAX-ACCESS read-only
            STATUS current
            DESCRIPTION  
            "Applicable to AU only. 
			 Not applicable to BreezeNET-B units.                                   
             Number of MAC addresses in the MAC Address Deny List Table."
            ::= { brzaccVLMacAddressDenyList 4 }

brzaccVLMacAddressDenyListAction OBJECT-TYPE
            SYNTAX  INTEGER  { denyList(1), allowedList(2), na(255) }
            MAX-ACCESS read-write      
            STATUS current       
            DESCRIPTION  
            "Applicable to AU only.        
            Define the action to be used by the Mac Address Deny List.
            allowedList(2) means that the list becomes Allow list."
            ::= { brzaccVLMacAddressDenyList 5 }


-- ===========================
-- New Allow/Deny List (begin)
-- ===========================

brzaccVLNewMacAddressDenyListTable OBJECT-TYPE
            SYNTAX SEQUENCE OF BrzaccVLNewMacAddressDenyListEntry
            MAX-ACCESS not-accessible
            STATUS current
            DESCRIPTION
            "Applicable to AU only. 
			 Not applicable to BreezeNET-B units.                                   
             A list of up to 100 MAC Addresses of SUs.
             If brzaccVLMacAddressDenyListAction is set to denyList, 
             these are SUs that are not allowed to transfer data 
             to the AU. 
             If brzaccVLMacAddressDenyListAction is set to allowList, 
             only these SUs are allowed to transfer data to the AU."
            ::= { brzaccVLMacAddressDenyList 6 }

    brzaccVLNewMacAddressDenyListEntry  OBJECT-TYPE
            SYNTAX BrzaccVLNewMacAddressDenyListEntry
            MAX-ACCESS not-accessible
            STATUS current
            DESCRIPTION
            "Applicable to AU only.
			 Not applicable to BreezeNET-B units.                                   
             An entry in the Mac Address Deny List Table."
            INDEX { brzaccVLNewMacAddressDenyListId }
            ::= { brzaccVLNewMacAddressDenyListTable 1 }

    BrzaccVLNewMacAddressDenyListEntry ::= SEQUENCE {
            brzaccVLNewMacAddressDenyListId  MacAddress,
            brzaccVLNewMacAddressDenyListCommand INTEGER
            }
        
    brzaccVLNewMacAddressDenyListId   OBJECT-TYPE
            SYNTAX  MacAddress  
            MAX-ACCESS read-only
            STATUS current
            DESCRIPTION  
            "Applicable to AU only.
			 Not applicable to BreezeNET-B units.                                   
             The list of MAC Addresses in the Mac Address Deny List Table."
        ::= { brzaccVLNewMacAddressDenyListEntry 1 }

	brzaccVLNewMacAddressDenyListCommand   OBJECT-TYPE
			SYNTAX  INTEGER { active(1), notInService(2), notReady(3), createAndGo(4), createAndWait(5), destroy(6) }
			MAX-ACCESS read-write
			STATUS current
			DESCRIPTION  
			"Applicable to AU only.
			Not applicable to BreezeNET-B units.
			Supports only active(1), createAndGo(4) and destroy(6).
			Used for add or destroy entry."
			::= { brzaccVLNewMacAddressDenyListEntry 2 }

-- =========================
-- New Allow/Deny List (end)
-- =========================

brzAccVLPortsControl  OBJECT IDENTIFIER ::= {brzaccVLBridgeParameters 11}

    brzaccVLEthernetPortControl OBJECT-TYPE
            SYNTAX  INTEGER   { disable(1), enable(2), na(255) }  
            MAX-ACCESS read-write
            STATUS current
            DESCRIPTION  
            "Applicable to SU/RB only.
             Enable/disable the Ethernet port. When disabled, only 
             data frames are blocked. Management frames are accepted."
            ::= { brzAccVLPortsControl 1 }

brzaccVLSendBroadcastsMulticastsAsUnicasts OBJECT-TYPE
        SYNTAX INTEGER { disable(1), enable(2) }
        MAX-ACCESS read-write
        STATUS current
        DESCRIPTION 
        "Applicable to BU only.
        When enabled the Multicast/Broadcast packets are sent by BU
        as Unicast packets to RB.
        When disabled the Multicast/Broadcast packets are sent by BU
        as Broadcast packets to RB"
::= { brzaccVLBridgeParameters 12 }

-- Air Interface Params
-- =====================
brzaccVLAirInterface      OBJECT IDENTIFIER ::= {breezeAccessVLMib 6}

brzaccVLESSIDParameters      OBJECT IDENTIFIER ::= {brzaccVLAirInterface 1}

    brzaccVLESSID OBJECT-TYPE
            SYNTAX DisplayString (SIZE(0..31))
            MAX-ACCESS read-write
            STATUS current
            DESCRIPTION  
            "Applicable to all units. 
             The Extended Service Set ID (ESSID) used to prevent 
             the merging of collocated systems.
             The ESSID is accessible only with the write community 
             string (administrator password).
             Up to 31 printable case sensitive ASCII characters." 
            ::= { brzaccVLESSIDParameters 1 }


    brzaccVLOperatorESSIDOption  OBJECT-TYPE
            SYNTAX INTEGER {disable (1) , enable (2), na (255) }
            MAX-ACCESS read-write
            STATUS current
            DESCRIPTION  
            "Applicable to AU/BU only. 
             Enabling/disabling the use of the Operator ESSID."
            ::= { brzaccVLESSIDParameters 2 }


    brzaccVLOperatorESSID OBJECT-TYPE
            SYNTAX DisplayString (SIZE(0..31))
            MAX-ACCESS read-write
            STATUS current
            DESCRIPTION  
            "Applicable to AU/BU only.
             A secondary ESSID to support easy installation of SUs as well as
             the use of the Best AU/BU feature.
             Accessible only with SNMP Write Community 
             Up to 31 printable case sensitive ASCII characters." 
            ::= { brzaccVLESSIDParameters 3}

	brzaccVLRunTimeESSID OBJECT-TYPE
		    SYNTAX DisplayString (SIZE(31))
		    MAX-ACCESS read-only
		    STATUS current
		    DESCRIPTION  
		    "Applicable to SU/RB only. 
		     The ESSID of the associated AU/BU.
		     Accessible only with SNMP Write Community.
		     Up to 31 printable ASCII characters, case sensitive."
		    ::= { brzaccVLESSIDParameters 4 }


brzaccVLHiddenESSIDParameters      OBJECT IDENTIFIER ::= {brzaccVLESSIDParameters 5}
 
	brzaccVLAUHiddenESSIDOption  OBJECT-TYPE
            SYNTAX INTEGER { enable(1) , disable(2), na(255) }
            MAX-ACCESS read-write
            STATUS current
            DESCRIPTION  
            "Applicable to AU/BU only. 
             Enabling/disabling the use of the Hidden ESSID."
            ::= { brzaccVLHiddenESSIDParameters 1 }
 
	brzaccVLSUHiddenESSIDSupport  OBJECT-TYPE
            SYNTAX INTEGER { enable(1) , disable(2), na(255) }
            MAX-ACCESS read-write
            STATUS current
            DESCRIPTION  
            "Applicable to SU/RB only. 
             Enabling/Disabling the option for an SU/RB to associate 
             with an AU/BU that is using Hidden ESSID"
            ::= { brzaccVLHiddenESSIDParameters 2 }
 
	brzaccVLSUHiddenESSIDTimeout  OBJECT-TYPE
            SYNTAX INTEGER (1..60)
            MAX-ACCESS read-write
            STATUS current
            DESCRIPTION  
            "Applicable to SU/RB only. 
            If an AU/BU rejects the subscribers because of worng ESSID
            the SU/RB will try again to associate with this AU/BU
            only after this period of time.
            The time is given in minutes"
            ::= { brzaccVLHiddenESSIDParameters 3 }


    brzaccVLMaximumCellRadius  OBJECT-TYPE
            SYNTAX  INTEGER  
            MAX-ACCESS read-write      
            STATUS current       
            DESCRIPTION  
            "Applicable to all units.  
             For AU/BU: read-write. In units with SW version 2.0 and up -
             applicable only when the Cell Distance Mode is set to Manual. 
             The highest distance from the AU/BU of any SU/RB served by it. 
             Affects the maximum time the units wait for a response message 
             and the slot size by taking into account the round trip propagation delay. 
             For SU/RB: read-only. The distance is learned from the AU/BU. 
             Range: For units below version 2.0 the range is 0 - 50000 Meters. 
             Otherwise - the range is 0 to 54 Kilometers.
             0 means no compensation (minimum slot size, maximal delay timeout)."
            ::= { brzaccVLAirInterface 2 }

    brzaccVLAIFS  OBJECT-TYPE
            SYNTAX  INTEGER ( 1..50 )
            MAX-ACCESS read-write      
            STATUS current       
            DESCRIPTION  
            "Applicable to AU and SU. Not applicable to BreezeNET-B products.
             Not applicable if Wireless Link Prioritization is enabled.
             Arbitration Inter-Frame Spacing (AIFS) value, in slots. 
             This is the number of time slots that define the DIFS. (DIFS=SIFS+AIFS). 
             A value of 1 should be used only in point-to-point applications to 
             allow one unit to have advantage over the other unit."
            ::= { brzaccVLAirInterface 3 }


	brzaccVLWirelessTrapThreshold OBJECT-TYPE
	    SYNTAX INTEGER     
	    MAX-ACCESS read-write
	    STATUS current
	    DESCRIPTION
	    "Applicable to AU/BU only.
	     A wireless link quality threshold, expressed in % of retransmissions,
	     for sending the brzaccVLAUWirelessQualityTRAP.   
	     This trap indicate whether the quality has gone below or 
	     above the specified threshold.
	     The Threshold Range: 1 to 100 (%  retransmissions)."
	     ::= {  brzaccVLAirInterface 4 }



    brzaccVLTransmitPowerTable OBJECT-TYPE
            SYNTAX SEQUENCE OF BrzaccVLTransmitPowerEntry
            MAX-ACCESS not-accessible
            STATUS current
            DESCRIPTION
            "Applicable to all units.
             A table of transmit power parameters. " 
            ::= { brzaccVLAirInterface 5}

    brzaccVLTransmitPowerEntry  OBJECT-TYPE
            SYNTAX BrzaccVLTransmitPowerEntry
            MAX-ACCESS not-accessible
            STATUS current
            DESCRIPTION
            "Applicable to all units. 
             An entry in the Transmit Power Table." 
            INDEX { brzaccVLTransmitPowerIdx }
            ::= { brzaccVLTransmitPowerTable 1 }
                                
    BrzaccVLTransmitPowerEntry ::= SEQUENCE {   brzaccVLTransmitPowerIdx          INTEGER,
                                				brzaccVLApplicableModulationLevel INTEGER,
                                				brzaccVLMaximumTxPowerRange       DisplayString,
                                				brzaccVLTxPower     	          DisplayString,
												brzaccVLCurrentTxPower		      DisplayString
                                			  }

    brzaccVLTransmitPowerIdx OBJECT-TYPE
            SYNTAX INTEGER	(1..4)
            MAX-ACCESS read-only
            STATUS current
            DESCRIPTION  
            "Applicable to all units.
             An index of an entry in the Transmit Power Table." 
            ::= { brzaccVLTransmitPowerEntry 1 }
								

    brzaccVLApplicableModulationLevel       OBJECT-TYPE
            SYNTAX INTEGER {level1to5 (1), level6  (2), level7  (3),level8  (4)}
            MAX-ACCESS read-only
            STATUS current
            DESCRIPTION  
            "Applicable to all units.
             The applicable modulation level for an entry in the Transmit Power Table.
              Level 8 is not applicable to units with HW revision A." 
            ::= { brzaccVLTransmitPowerEntry 2 }

    brzaccVLMaximumTxPowerRange  OBJECT-TYPE
            SYNTAX DisplayString
            MAX-ACCESS read-only
            STATUS current
            DESCRIPTION  
            "Applicable to all units.
             The allowed range for the brzaccVLTxPower parameter at the 
             applicable modulation level . Range: -10 to the maximum allowed 
             power level at the applicable modulation level , in dBm." 
            ::= { brzaccVLTransmitPowerEntry 3 }


    brzaccVLTxPower OBJECT-TYPE
            SYNTAX DisplayString
            MAX-ACCESS read-write
            STATUS current
            DESCRIPTION  
            "Applicable to all units.
             Read-only for units with SW version 4.0 and higher.
			 In AU/BU: The transmit power in dBm defined for the applicable rate.
			 In SU/RB: If ATPC is disabled, this is the transmit power in dBm 
			 defined for the applicable rate.
			 If ATPC is enabled, it serves as the initial transmit power in dBm 
			 for the ATPC algorithm. 
			 In SU/RB: The range is -10 dBm to the power value defined by 
			           brzaccVLMaximumTxPower for the applicable modulation level.
			 In AU/BU: The range is -10 dBm to the power value defined by 
			           brzaccVLMaximumTxPowerRange for the applicable modulation level."
            ::= { brzaccVLTransmitPowerEntry 4 }



    brzaccVLCurrentTxPower OBJECT-TYPE
            SYNTAX DisplayString
            MAX-ACCESS read-only
            STATUS current
            DESCRIPTION 
            "Applicable to SU/RB.
             The actual transmit power in dBm for the applicable rate.
             Range: -17 to the maximum value defined by brzaccVLMaximumTxPowerRange 
             for the applicable modulation level."
            ::= { brzaccVLTransmitPowerEntry 5 }

-- NewTransmitPowerTable

brzaccVLNewTransmitPowerTable OBJECT-TYPE
            SYNTAX SEQUENCE OF BrzaccVLNewTransmitPowerEntry
            MAX-ACCESS not-accessible
            STATUS current
            DESCRIPTION
            "Applicable to all units with SW version 5.1 and higher
             A table of transmit power parameters. " 
            ::= { brzaccVLAirInterface 27 }

    brzaccVLNewTransmitPowerEntry  OBJECT-TYPE
            SYNTAX BrzaccVLNewTransmitPowerEntry
            MAX-ACCESS not-accessible
            STATUS current
            DESCRIPTION
            "Applicable to all units with SW version 5.1 and higher 
             An entry in the Transmit Power Table." 
            INDEX { brzaccVLNewModulationLevelIdx }
            ::= { brzaccVLNewTransmitPowerTable 1 }
                                
    BrzaccVLNewTransmitPowerEntry ::= SEQUENCE {    brzaccVLNewModulationLevelIdx           INTEGER,
                                                    brzaccVLNewMaximumTxPowerRange          DisplayString,
                                                    brzaccVLNewTxPower                      DisplayString,
                                                    brzaccVLNewCurrentTxPower               DisplayString
                                                }

    brzaccVLNewModulationLevelIdx OBJECT-TYPE
            SYNTAX INTEGER  (1..8)
            MAX-ACCESS read-only
            STATUS current
            DESCRIPTION  
            "Applicable to all units with SW version 5.1 and higher.
             An index ( and modulation level ) of an entry in the NewTransmitPowerTable." 
            ::= { brzaccVLNewTransmitPowerEntry 1 }


    brzaccVLNewMaximumTxPowerRange  OBJECT-TYPE
            SYNTAX DisplayString
            MAX-ACCESS read-only
            STATUS current
            DESCRIPTION  
            "Applicable to all units with SW version 5.1 and higher.
             The allowed range for the brzaccVLNewTxPower parameter at the 
             applicable modulation level . Range: -10 to the maximum allowed 
             power level at the applicable modulation level , in dBm." 
            ::= { brzaccVLNewTransmitPowerEntry 2 }


    brzaccVLNewTxPower OBJECT-TYPE
            SYNTAX DisplayString
            MAX-ACCESS read-write
            STATUS current
            DESCRIPTION  
            "Applicable to all units with SW version 5.1 and higher.            
             In AU/BU: The transmit power in dBm defined for the applicable rate.
             In SU/RB: If ATPC is disabled, this is the transmit power in dBm 
             defined for the applicable rate.
             If ATPC is enabled, it serves as the initial transmit power in dBm 
             for the ATPC algorithm. 
             In SU/RB: The range is -10 dBm to the power value defined by 
                       brzaccVLNewMaximumTxPower for the applicable modulation level.
             In AU/BU: The range is -10 dBm to the power value defined by 
                       brzaccVLNewMaximumTxPowerRange for the applicable modulation level."
            ::= { brzaccVLNewTransmitPowerEntry 3 }



    brzaccVLNewCurrentTxPower OBJECT-TYPE
            SYNTAX DisplayString
            MAX-ACCESS read-only
            STATUS current
            DESCRIPTION 
            "Applicable to SU/RB with SW version 5.1 and higher.
             The actual transmit power in dBm for the applicable rate.
             Range: -17 to the maximum value defined by brzaccVLNewMaximumTxPowerRange 
             for the applicable modulation level."
            ::= { brzaccVLNewTransmitPowerEntry 4 }
            
-- end of NewTransmitPowerTable

    brzaccVLMaximumTransmitPowerTable OBJECT-TYPE
            SYNTAX SEQUENCE OF BrzaccVLMaximumTransmitPowerEntry
            MAX-ACCESS not-accessible
            STATUS current
            DESCRIPTION
            "Applicable to SU/RB only.
             A table of maximum transmit power parameters. " 
            ::= { brzaccVLAirInterface 6}

    brzaccVLMaximumTransmitPowerEntry  OBJECT-TYPE
            SYNTAX BrzaccVLMaximumTransmitPowerEntry
            MAX-ACCESS not-accessible
            STATUS current
            DESCRIPTION
            "Applicable to SU/RB only. 
             An entry in the Maximum Transmit Power Table." 
            INDEX { brzaccVLMaximumTransmitPowerIdx }
            ::= { brzaccVLMaximumTransmitPowerTable 1 }
                                
    BrzaccVLMaximumTransmitPowerEntry ::= SEQUENCE {   brzaccVLMaximumTransmitPowerIdx        INTEGER,
                                				       brzaccVLMaxTxApplicableModulationLevel INTEGER,
                                				       brzaccVLDefinedMaximumTxPowerRange     DisplayString,
                                				       brzaccVLMaxTxPower     	              DisplayString
                                			  }

    brzaccVLMaximumTransmitPowerIdx OBJECT-TYPE
            SYNTAX INTEGER	(1..4)
            MAX-ACCESS read-only
            STATUS current
            DESCRIPTION  
            "Applicable to SU/RB only.
             An index of an entry in the Maximum Transmit Power Table." 
            ::= { brzaccVLMaximumTransmitPowerEntry 1 }
								

    brzaccVLMaxTxApplicableModulationLevel       OBJECT-TYPE
            SYNTAX INTEGER {level1to5 (1), level6  (2), level7  (3),level8  (4)}
            MAX-ACCESS read-only
            STATUS current
            DESCRIPTION  
            "Applicable to SU/RB only.
             The applicable modulation level for an entry in the Maximum 
              Transmit Power Table.
              Level 8 is not applicable to units with HW revision A." 
            ::= { brzaccVLMaximumTransmitPowerEntry 2 }

    brzaccVLDefinedMaximumTxPowerRange  OBJECT-TYPE
            SYNTAX DisplayString
            MAX-ACCESS read-only
            STATUS current
            DESCRIPTION  
            "Applicable to SU/RB only.
             The allowed range for the brzaccVLMaxTxPower parameter at the 
             applicable modulation level .
             Range: -10 to the maximum allowed power level at the applicable 
             modulation level , in dBm." 
            ::= { brzaccVLMaximumTransmitPowerEntry 3 }


    brzaccVLMaxTxPower OBJECT-TYPE
            SYNTAX DisplayString
            MAX-ACCESS read-write
            STATUS current
            DESCRIPTION  
            "Applicable to SU/RB only.
            Read-only for units with SW version 4.0 and higher.
			The maximum value that can be configured for the brzaccVLTxPower 
			parameter. This is also the maximum power level that can be reached 
			by the ATPC algorithm.
			The range is -10 dBm to the maximum value defined by 
			brzaccVLDefinedMaximumTxPowerRange for the applicable modulation level."
            ::= { brzaccVLMaximumTransmitPowerEntry 4 }


-- NewMaximumTransmitPowerTable

brzaccVLNewMaximumTransmitPowerTable OBJECT-TYPE
            SYNTAX SEQUENCE OF BrzaccVLNewMaximumTransmitPowerEntry
            MAX-ACCESS not-accessible
            STATUS current
            DESCRIPTION
            "Applicable to SU/RB only.
             A table of maximum transmit power parameters. " 
            ::= { brzaccVLAirInterface 28 }

    brzaccVLNewMaximumTransmitPowerEntry  OBJECT-TYPE
            SYNTAX BrzaccVLNewMaximumTransmitPowerEntry
            MAX-ACCESS not-accessible
            STATUS current
            DESCRIPTION
            "Applicable to SU/RB only. 
             An entry in the Maximum Transmit Power Table." 
            INDEX { brzaccVLNewMaxModulationLevelIdx }
            ::= { brzaccVLNewMaximumTransmitPowerTable 1 }
                                
    BrzaccVLNewMaximumTransmitPowerEntry ::= SEQUENCE { brzaccVLNewMaxModulationLevelIdx          INTEGER,
                                                        brzaccVLNewDefinedMaximumTxPowerRange     DisplayString,
                                                        brzaccVLNewMaxTxPower                     DisplayString
                                                      }

    brzaccVLNewMaxModulationLevelIdx OBJECT-TYPE
            SYNTAX INTEGER  (1..8)
            MAX-ACCESS read-only
            STATUS current
            DESCRIPTION  
            "Applicable to SU/RB only.
             The applicable modulation level for an entry in the NEW Maximum Transmit Power Table.
             This OID also represent an index of an entry in the NEW Maximum Transmit Power Table." 
            ::= { brzaccVLNewMaximumTransmitPowerEntry 1 }


   brzaccVLNewDefinedMaximumTxPowerRange  OBJECT-TYPE
            SYNTAX DisplayString
            MAX-ACCESS read-only
            STATUS current
            DESCRIPTION  
            "Applicable to SU/RB only.
             The allowed range for the brzaccVLNewMaxTxPower parameter at the 
             applicable modulation level .
             Range: -10 to the maximum allowed power level at the applicable 
             modulation level , in dBm." 
            ::= { brzaccVLNewMaximumTransmitPowerEntry 2 }


    brzaccVLNewMaxTxPower OBJECT-TYPE
            SYNTAX DisplayString
            MAX-ACCESS read-write
            STATUS current
            DESCRIPTION  
            "Applicable to SU/RB only.
            Read-only for units with SW version 4.0 and higher.
            The maximum value that can be configured for the brzaccVLNewTxPower 
            parameter. This is also the maximum power level that can be reached 
            by the ATPC algorithm.
            The range is -10 dBm to the maximum value defined by 
            brzaccVLNewDefinedMaximumTxPowerRange for the applicable modulation level."
            ::= { brzaccVLNewMaximumTransmitPowerEntry 3 }

-- end of NewMaximumTransmitPowerTable

    brzaccVLMaxNumOfAssociations OBJECT-TYPE
            SYNTAX  INTEGER  
            MAX-ACCESS read-write      
            STATUS current       
            DESCRIPTION  
            "Applicable to AU only. 
             Not applicable to BreezeNET-B products.
             Sets the upper limit for the number of SUs 
             that can be associated with the AU.
             Range: For regular AUs (AU-BS, AU-SA, AU) 
             the range is from 0 to 512 if encryption is disabled
             the range id form 0 to 124 if encryption is enabled
             For AUS-BS and AUS-SA with SW version 4.0 and higher 
             the range is between 0 to 8 or 25 (via licensing).
             For AUS-BS and AUS-SA with SW version below 4.0 the range 
             is between 0 to 5.  
             BreezeNET-B products return 65535."
            ::= { brzaccVLAirInterface 10 }


brzaccVLBestAu   OBJECT IDENTIFIER ::= {brzaccVLAirInterface 11}

    brzaccVLBestAuSupport OBJECT-TYPE
            SYNTAX  INTEGER  { disable (1), enable (2), na (255) }
            MAX-ACCESS read-write      
            STATUS current       
            DESCRIPTION  
            "Applicable to SU/RB only. 
             Disable/enable the Best AU/BU selection mechanism."
            ::= { brzaccVLBestAu  1 }

    brzaccVLBestAuNoOfScanningAttempts OBJECT-TYPE
            SYNTAX  INTEGER
            MAX-ACCESS read-write      
            STATUS current       
            DESCRIPTION  
            "Applicable to SU/RB only. 
             The number of scanning attempts to collect information 
             for the Best AU/BU decision.
             Range: 1 to 255."
            ::= { brzaccVLBestAu  2 }

    brzaccVLPreferredAuMacAddress OBJECT-TYPE
            SYNTAX MacAddress 
            MAX-ACCESS read-write      
            STATUS current       
            DESCRIPTION  
            "Applicable to SU/RB only.
             The MAC address of the preferred AU/BU (overriding the 
             Best AU/BU selection process). 
             000000000000 means no preferred AU/BU."
            ::= { brzaccVLBestAu 3 }

    brzaccVLNeighborAuTable OBJECT-TYPE
            SYNTAX SEQUENCE OF BrzaccVLNeighborAuEntry
            MAX-ACCESS not-accessible
            STATUS current
            DESCRIPTION
            "Applicable to SU/RB only. 
             A table of data on neighboring AUs/BUs."
            ::= { brzaccVLBestAu 4}

    brzaccVLNeighborAuEntry  OBJECT-TYPE
            SYNTAX BrzaccVLNeighborAuEntry
            MAX-ACCESS not-accessible
            STATUS current
            DESCRIPTION
            "Applicable to SU/RB only. 
             An entry in the Neighbor AU/BU Table." 
            INDEX { brzaccVLNeighborAuIdx }
            ::= { brzaccVLNeighborAuTable 1 }
                                
    BrzaccVLNeighborAuEntry ::= SEQUENCE { brzaccVLNeighborAuIdx        INTEGER,
    							brzaccVLNeighborAuMacAdd                MacAddress,
                                brzaccVLNeighborAuESSID                 DisplayString,
                                brzaccVLNeighborAuSNR                   INTEGER,
                                brzaccVLNeighborAuAssocLoadStatus       INTEGER,
                                brzaccVLNeighborAuMark                  INTEGER,
	                            brzaccVLNeighborAuHwRevision	        INTEGER,
	                            brzaccVLNeighborAuCountryCode           INTEGER,
	                            brzaccVLNeighborAuSwVer			        DisplayString,
	                            brzaccVLNeighborAuAtpcOption	        INTEGER,
	                            brzaccVLNeighborAuAdapModOption	        INTEGER,
	                            brzaccVLNeighborAuBurstModeOption       INTEGER,
	                         	brzaccVLNeighborAuDfsOption	            INTEGER,
	                            brzaccVLNeighborAuConcatenationOption   INTEGER,
	                            brzaccVLNeighborAuLearnCountryCodeBySU  INTEGER,
	                            brzaccVLNeighborAuSecurityMode	        INTEGER,
	                            brzaccVLNeighborAuAuthOption	        INTEGER,
	                            brzaccVLNeighborAuDataEncyptOption      INTEGER,
	                            brzaccVLNeighborAuPerSuDistanceLearning INTEGER,
	                            brzaccVLNeighborAuRSSI				    INTEGER
                                }

    brzaccVLNeighborAuIdx OBJECT-TYPE
            SYNTAX INTEGER	(1..20)
            MAX-ACCESS read-only
            STATUS current
            DESCRIPTION  
            "Applicable to SU/RB only. 
             An index of an entry in the Neighbor AU/BU Table."
            ::= { brzaccVLNeighborAuEntry 1 }
								
    brzaccVLNeighborAuMacAdd OBJECT-TYPE
            SYNTAX MacAddress
            MAX-ACCESS read-only
            STATUS current
            DESCRIPTION  
            "Applicable to SU/RB only. 
             A MAC address of an AU/BU in the Neighbor AU/BU Table."
            ::= { brzaccVLNeighborAuEntry 2 }

    brzaccVLNeighborAuESSID OBJECT-TYPE
            SYNTAX DisplayString
            MAX-ACCESS read-only
            STATUS current
            DESCRIPTION  
            "Applicable to SU/RB only.  
             The ESSID of an AU/BU in the Neighbor AU/BU Table.
             Accessible only with SNMP Write Community."
            ::= { brzaccVLNeighborAuEntry 3 }

    brzaccVLNeighborAuSNR OBJECT-TYPE
            SYNTAX INTEGER { na (255) }
            MAX-ACCESS read-only
            STATUS current
            DESCRIPTION  
            "Applicable to SU/RB only. 
             The received signal quality (SNR) in dB of an AU/BU 
             in the Neighbor AU/BU Table. If the returned value is 255
             this means that the indication is not available."
            ::= { brzaccVLNeighborAuEntry 4 }

    brzaccVLNeighborAuAssocLoadStatus OBJECT-TYPE
            SYNTAX INTEGER {  full (1),notFull (2), na (255) }
            MAX-ACCESS read-only
            STATUS current
            DESCRIPTION  
            "Applicable to SU/RB only. 
             Neighbor AU/BU association load status in the Neighbor 
             AU/BU Table."
            ::= { brzaccVLNeighborAuEntry 5 }
    
    brzaccVLNeighborAuMark OBJECT-TYPE
            SYNTAX INTEGER
            MAX-ACCESS read-only
            STATUS current
            DESCRIPTION  
            "Applicable to SU/RB only.
             Neighbor AU/BU mark in the Neighbor AU/BU Table."
            ::= { brzaccVLNeighborAuEntry 6 }

    brzaccVLNeighborAuHwRevision OBJECT-TYPE
            SYNTAX INTEGER {hwRevisionA (1), hwRevisionB (2), hwRevisionC (3),
                            hwRevisionD(4), hwRevisionE(5), hwRevisionF(6), hwRevisionG(7), na(255)}
            MAX-ACCESS read-only
            STATUS current
            DESCRIPTION  
            "Applicable to SU/RB only.
             Neighbor AU/BU HW revision in the Neighbor AU/BU Table."
            ::= { brzaccVLNeighborAuEntry 7 }

    brzaccVLNeighborAuCountryCode OBJECT-TYPE
            SYNTAX INTEGER 	
            MAX-ACCESS read-only
            STATUS current
            DESCRIPTION  
            "Applicable to SU/RB only.
             Neighbor AU/BU supported country code in the Neighbor 
             AU/BU Table."
            ::= { brzaccVLNeighborAuEntry 8 }

    brzaccVLNeighborAuSwVer OBJECT-TYPE
            SYNTAX DisplayString 
            MAX-ACCESS read-only
            STATUS current
            DESCRIPTION  
            "Applicable to SU/RB only.
             Neighbor AU/BU SW version in the Neighbor 
             AU/BU Table."
            ::= { brzaccVLNeighborAuEntry 9 }

    brzaccVLNeighborAuAtpcOption OBJECT-TYPE
            SYNTAX INTEGER { disable (1), enable (2), na (255)}
            MAX-ACCESS read-only
            STATUS current
            DESCRIPTION  
            "Applicable to SU/RB only.
             Neighbor AU/BU ATPC option configuration in the Neighbor 
             AU/BU Table."
            ::= { brzaccVLNeighborAuEntry 10 }

    brzaccVLNeighborAuAdapModOption OBJECT-TYPE
            SYNTAX INTEGER { disable (1), enable (2), na (255)}
            MAX-ACCESS read-only
            STATUS current
            DESCRIPTION  
            "Applicable to SU/RB only.
             Neighbor AU/BU adaptive modulation option configuration 
             in the Neighbor AU/BU Table."
            ::= { brzaccVLNeighborAuEntry 11 }

    brzaccVLNeighborAuBurstModeOption OBJECT-TYPE
            SYNTAX INTEGER { disable (1), enable (2), na (255)}
            MAX-ACCESS read-only
            STATUS current
            DESCRIPTION  
            "Applicable to SU/RB only.
             Neighbor AU/BU burst mode option configuration 
             in the Neighbor AU/BU Table."
            ::= { brzaccVLNeighborAuEntry 12 }

    brzaccVLNeighborAuDfsOption OBJECT-TYPE
            SYNTAX INTEGER { disable (1), enable (2), na(255)}
            MAX-ACCESS read-only
            STATUS current
            DESCRIPTION  
            "Applicable to SU/RB only.
             Neighbor AU/BU DFS option configuration 
             in the Neighbor AU/BU Table."
            ::= { brzaccVLNeighborAuEntry 14 }

    brzaccVLNeighborAuConcatenationOption OBJECT-TYPE
            SYNTAX INTEGER { disable (1), enable (2), na (255)}
            MAX-ACCESS read-only
            STATUS current
            DESCRIPTION  
            "Applicable to SU/RB only.
             Neighbor AU/BU concatenation option configuration 
             in the Neighbor AU/BU Table."
            ::= { brzaccVLNeighborAuEntry 15 }

    brzaccVLNeighborAuLearnCountryCodeBySU OBJECT-TYPE
            SYNTAX INTEGER { disable (1), enable (2), na (255)}
            MAX-ACCESS read-only
            STATUS current
            DESCRIPTION  
            "Applicable to SU only.
             Starting with 4.0 is not applicable for BA4900 and BreezeNET B products.
             Neighbor AU Learn Country Code by SU configuration 
             in the Neighbor AU Table."
            ::= { brzaccVLNeighborAuEntry 17 }

   brzaccVLNeighborAuSecurityMode     OBJECT-TYPE
            SYNTAX INTEGER  {wep(1), aesOCB(2), fips197(3), na (255)}
            MAX-ACCESS read-only
            STATUS current
            DESCRIPTION  
            "Applicable to SU/RB only.
             Neighbor AU/BU security mode configuration 
             in the Neighbor AU/BU Table."
            ::= { brzaccVLNeighborAuEntry 18 }

   brzaccVLNeighborAuAuthOption     OBJECT-TYPE
            SYNTAX INTEGER  {openSystem (1), sharedKey (2), na (255)}
            MAX-ACCESS read-only
            STATUS current
            DESCRIPTION  
            "Applicable to SU/RB only.
             Neighbor AU/BU authentication option configuration 
             in the Neighbor AU/BU Table."
            ::= { brzaccVLNeighborAuEntry 19 }

   brzaccVLNeighborAuDataEncyptOption     OBJECT-TYPE
            SYNTAX INTEGER  {disable (1), enable (2), na (255)}
            MAX-ACCESS read-only
            STATUS current
            DESCRIPTION  
            "Applicable to SU/RB only.
             Neighbor AU/BU data encryption option configuration 
             in the Neighbor AU/BU Table."
            ::= { brzaccVLNeighborAuEntry 20 }

  brzaccVLNeighborAuPerSuDistanceLearning		OBJECT-TYPE
            SYNTAX INTEGER  {disable (1), enable (2), na (255)}
            MAX-ACCESS read-only
            STATUS current
            DESCRIPTION  
            "Applicable to SU only.
             Neighbor AU per SU distance learning option configuration 
             in the Neighbor AU Table."
            ::= { brzaccVLNeighborAuEntry 21 }
            
  brzaccVLNeighborAuRSSI OBJECT-TYPE
            SYNTAX INTEGER { na (255) }
            MAX-ACCESS read-only
            STATUS current
            DESCRIPTION  
            "Applicable to SU/RB only. 
             The Recieved Signal Strength Indication of an AU/BU 
             in the Neighbor AU/BU Table. If the returned value 
             is 255 this means that the indication is not available.
             This value is given in dBm units."
            ::= { brzaccVLNeighborAuEntry 22 }


brzaccVLFrequencyDefinition	   OBJECT IDENTIFIER ::= {brzaccVLAirInterface 12}
   

    brzaccVLSubBandLowerFrequency OBJECT-TYPE
            SYNTAX INTEGER
            MAX-ACCESS read-write
            STATUS obsolete
            DESCRIPTION  
		    "Applicable to SU only. 
		     Not applicable to units with SW version 2.0 or higher. 
             The lowest frequency in the subset to be used for scanning.
             For 5.8GHz products the range is 5740 to 5830 MHz using 10MHz resolution.
             For 4.9GHz products the range is 4920 to 5080 MHz using 10MHz resolution.
             For HW Revision C and above this leaf is not relevant - shall return 0."
            ::= { brzaccVLFrequencyDefinition 1 }

    brzaccVLSubBandUpperFrequency OBJECT-TYPE
            SYNTAX INTEGER
            MAX-ACCESS read-write
            STATUS obsolete
            DESCRIPTION  
            "Applicable to SU only. 
             Not applicable to units with SW version 2.0 or higher. 
             The highest frequency in the subset to be used for scanning.
             For 5.8GHz products the range is 5740 to 5830 MHz using 10MHz resolution.
             For 4.9GHz products the range is 4920 to 5080 MHz using 10MHz resolution.
             For HW Revision C and above this leaf is not relevant - shall return 0."
            ::= { brzaccVLFrequencyDefinition 2 }

    brzaccVLScanningStep  OBJECT-TYPE
            SYNTAX INTEGER  { mhz-5(1), mhz-10(2) , mhz-20(3), khz-500(4), mhz-1(5), na(255) }
            MAX-ACCESS read-only
            STATUS current
            DESCRIPTION  
            "Applicable to all units - For flexible Sub-Bands only.		
             For units with version 2.0 and above this is a read-only parameter.
             The scanning step to be used for generating the frequency subset."
            ::= { brzaccVLFrequencyDefinition 3 }


    brzaccVLFrequencySubsetTable OBJECT-TYPE
            SYNTAX SEQUENCE OF BrzaccVLFrequencySubsetEntry
            MAX-ACCESS not-accessible
            STATUS current
            DESCRIPTION
            "Applicable to SU/RB and to AU/BU.
             Not applicable to SU/RB with SW version 4.0 and higher.
			 The Frequency Subset Table that includes all frequencies from 
			 the selected Sub-band."
            ::= { brzaccVLFrequencyDefinition 4 }

    brzaccVLFrequencySubsetEntry  OBJECT-TYPE
            SYNTAX BrzaccVLFrequencySubsetEntry
            MAX-ACCESS not-accessible
            STATUS current
            DESCRIPTION
            "Applicable to SU/RB and to AU/BU.
             Not applicable to SU/RB with SW version 4.0 and higher.
             An entry in the Frequency Subset Table. "  
             INDEX { brzaccVLFrequencySubsetTableIdx }
            ::= { brzaccVLFrequencySubsetTable 1 }

    BrzaccVLFrequencySubsetEntry ::= SEQUENCE {
            brzaccVLFrequencySubsetTableIdx       INTEGER,
            brzaccVLFrequencySubsetFrequency      INTEGER,
            brzaccVLFrequencySubsetActive         INTEGER,
            brzaccVLFrequencySubsetFrequencyNew   DisplayString
            }
               
    brzaccVLFrequencySubsetTableIdx   OBJECT-TYPE
            SYNTAX INTEGER  (1..40)
            MAX-ACCESS read-only
            STATUS current
            DESCRIPTION 
            "Applicable to SU/RB and to AU/BU.
             Not applicable to SU/RB with SW version 4.0 and higher.
			 An index of an entry in the Frequency subset Table."
           ::= { brzaccVLFrequencySubsetEntry 1 }


    brzaccVLFrequencySubsetFrequency   OBJECT-TYPE
            SYNTAX INTEGER  
            MAX-ACCESS read-only
            STATUS current
            DESCRIPTION 
            "Applicable to SU/RB and to AU/BU. 
             Not applicable to SU/RB with SW version 4.0 and higher.
             Applicable to all units with HW revision B and lower 
             (for units with HW revision C and higher replaced by 
             brzaccVLFrequencySubsetFrequencyNew to support a 
             resolution of 0.5 MHz).  
             The frequency in MHz of an entry in the Frequency Subset table."
           ::= { brzaccVLFrequencySubsetEntry 2 }

    brzaccVLFrequencySubsetActive   OBJECT-TYPE
            SYNTAX INTEGER  {active (1) , notActive (2)}
            MAX-ACCESS read-write
            STATUS current
            DESCRIPTION 
            "Applicable to SU/RB and to AU/BU.
             Not applicable to SU/RB with SW version 4.0 and higher.
			 The status of an entry in the Frequency subset Table.
			 The frequency of an active entry will be included in the 
			 final list of frequencies to be used for scanning."
           ::= { brzaccVLFrequencySubsetEntry 3 }

    brzaccVLFrequencySubsetFrequencyNew   OBJECT-TYPE
            SYNTAX DisplayString
            MAX-ACCESS read-only
            STATUS current
            DESCRIPTION 
            "Applicable to all units. 
             Not applicable to SU/RB with SW version 4.0 and higher.
             The frequency in MHz of an entry in the Frequency Subset table. 
             (Replaces brzaccVLFrequencySubsetFrequency to support a resolution 
             of 0.5 MHz for units with HW revision C and higher)."
           ::= { brzaccVLFrequencySubsetEntry 4 }

    brzaccVLSetSelectedFreqSubset  OBJECT-TYPE
            SYNTAX INTEGER	 {setSelectedFreqsSubset(1) ,cancel (2)}
            MAX-ACCESS read-write
            STATUS current
            DESCRIPTION  
            "Applicable to SU/RB and to AU/BU.
             Not applicable to SU/RB with SW version 4.0 and higher.
			 Apply the selected subset.
			 After the next reset the new subset will be used."
            ::= { brzaccVLFrequencyDefinition 5 }




    brzaccVLCurrentFrequencySubsetTable OBJECT-TYPE
            SYNTAX SEQUENCE OF BrzaccVLCurrentFrequencySubsetEntry
            MAX-ACCESS not-accessible
            STATUS current
            DESCRIPTION
            "Applicable to SU/RB and to AU/BU.
             Not applicable to SU/RB with SW version 4.0 and higher.
			 The Current Frequency Subset table. In SU/RB it includes all 
			 frequencies that are currently used for scanning.
			 In AU/BU it includes all frequencies that can be used by the 
			 DFS mechanism (if applicable)"
                ::= { brzaccVLFrequencyDefinition 6 }

    brzaccVLCurrentFrequencySubsetEntry  OBJECT-TYPE
            SYNTAX BrzaccVLCurrentFrequencySubsetEntry
            MAX-ACCESS not-accessible
            STATUS current
            DESCRIPTION
            "Applicable to SU/RB and to AU/BU.
             An entry in the Current Frequency Subset Table. "  
             INDEX { brzaccVLCurrentFrequencySubsetTableIdx }
            ::= { brzaccVLCurrentFrequencySubsetTable 1 }

    BrzaccVLCurrentFrequencySubsetEntry ::= SEQUENCE {
            brzaccVLCurrentFrequencySubsetTableIdx      INTEGER,
            brzaccVLCurrentFrequencySubsetFrequency     INTEGER,
            brzaccVLCurrentFrequencySubsetFrequencyNew  DisplayString
            }
               
    brzaccVLCurrentFrequencySubsetTableIdx   OBJECT-TYPE
            SYNTAX INTEGER  (1..40)
            MAX-ACCESS read-only
            STATUS current
            DESCRIPTION 
            "Applicable to SU/RB and to AU/BU.
			 An index of an entry in the Current Frequency subset Table.
			 Not applicable to SU/RB with SW version 4.0 and higher."
           ::= { brzaccVLCurrentFrequencySubsetEntry 1 }


    brzaccVLCurrentFrequencySubsetFrequency   OBJECT-TYPE
            SYNTAX INTEGER  
            MAX-ACCESS read-only
            STATUS current
            DESCRIPTION 
			"Applicable to all units. 
			 Not applicable to SU/RB with SW version 4.0 and higher.
			 Applicable to all units with HW revision B and lower 
			 (for units with HW revision C and higher replaced by 
			 brzaccVLCurrentFrequencySubsetFrequencyNew to support 
			 a resolution of 0.5 MHz). 
			 The frequency in MHz of an entry in the Current Frequency Subset table."
           ::= { brzaccVLCurrentFrequencySubsetEntry 2 }

    brzaccVLCurrentFrequencySubsetFrequencyNew   OBJECT-TYPE
            SYNTAX DisplayString  
            MAX-ACCESS read-only
            STATUS current
            DESCRIPTION 
            "Applicable to all units. Not applicable to SU/RB with SW version 4.0 and higher. 
             The frequency in MHz of an entry in the Current Frequency Subset table. 
             (Replaces brzaccVLCurrentFrequencySubsetFrequency to support a 
             resolution of 0.5 MHz for units with HW revision C and higher)."
            ::= { brzaccVLCurrentFrequencySubsetEntry 3 }
	
    brzaccVLCurrentAUOperatingFrequency  OBJECT-TYPE
            SYNTAX INTEGER	
            MAX-ACCESS read-only
            STATUS current
            DESCRIPTION  
		    "Applicable to AU/BU with HW revision B and lower 
		     (for units with HW revision C and higher replaced by 
		     brzaccVLCurrentUOperatingFrequencyNew to support a resolution 
		     of 0.5 MHz). 
		     The operating frequency in MHz. 
		     For 5.8GHz products with SW version below 2.0 the range is 
		     5740 to 5830 MHz using 10MHz resolution. 
		     For units with SW version 2.0 and up the range is as defined 
		     in the selected Sub Band."
            ::= { brzaccVLFrequencyDefinition 7 }

    brzaccVLAUDefinedFrequency  OBJECT-TYPE
            SYNTAX INTEGER	
            MAX-ACCESS read-write
            STATUS current
            DESCRIPTION  
            "Applicable to AU/BU with HW revision B and lower 
             (for units with HW revision C and higher replaced by 
             brzaccVLAUDefinedFrequencyNew to support a resolution of 0.5 MHz). 
             For 5.8GHz products with SW version below 2.0 this is the frequency 
             in MHz of the AU/BU after the next reset. 
             For units with SW version 2.0 and up this is the frequency in MHz 
             to use when the DFS Option is disabled. 
             For 5.8GHz products with SW version below 2.0 the range is 
             5740 to 5830 MHz using 10MHz resolution. 
             For units with SW version 2.0 and up the range is as defined 
             in the selected Sub Band."            
            ::= { brzaccVLFrequencyDefinition 8 }

    brzaccVLCurrentSUOperatingFrequency  OBJECT-TYPE
            SYNTAX DisplayString	
            MAX-ACCESS read-only
            STATUS current
            DESCRIPTION  
            "Applicable to SU/RB only.
			 The frequency used currently by the unit.
			 For 5.8GHz products with SW version below 2.0 the range is 
			 5740 to 5830 MHz using 10MHz resolution.
             For units with SW version 2.0 and up the range is as defined 
             in the selected Sub Band."
            ::= { brzaccVLFrequencyDefinition 9 }

brzaccVLSubBandSelect   OBJECT IDENTIFIER ::= {brzaccVLFrequencyDefinition 10}


    brzaccVLSelectSubBandIndex OBJECT-TYPE
            SYNTAX INTEGER	
            MAX-ACCESS read-write
            STATUS current
            DESCRIPTION
            "Applicable to all units with SW version below 4.0 
            For units with SW version 4.0 and up it is applicable 
            only for AU/BU. For SU/RB it defines only the sub-band 
            for the Spectrum Analyzer.
            The ID of the sub-band configured in the unit.
            Its range depends on unit's type and Country Code."  
            ::= { brzaccVLSubBandSelect 1 }



brzaccVLDFSParameters   OBJECT IDENTIFIER ::= {brzaccVLFrequencyDefinition 11}

    brzaccVLDFSOption  OBJECT-TYPE
            SYNTAX INTEGER	{ disable (1) , enable (2), na (255) } 
            MAX-ACCESS read-write
            STATUS current
            DESCRIPTION  
            "Applicable to AU/BU.
             Applicable to SU/RB with SW version 5.5.20 and higher. 
             Enabling/disabling the DFS Algorithm. 
             Not applicable if DFS Option is not supported by the current Sub Band."
            ::= { brzaccVLDFSParameters 1 }

    brzaccVLDFSChannelCheckTime  OBJECT-TYPE
            SYNTAX INTEGER	 
            MAX-ACCESS read-write
            STATUS current
            DESCRIPTION  
            "Applicable to AU/BU. 
             Applicable to SU/RB with SW version 5.5.20 and higher. Channel Availability Check time
             defines the time the unit checks the channel for presence of 
             radar signals and does not transmit after power up or association 
             or after moving to a new channel due to detecting radar in the used 
             channel. Range: 1 to 3600 (seconds)."
            ::= { brzaccVLDFSParameters 3 }


    brzaccVLDFSChannelAvoidancePeriod  OBJECT-TYPE
            SYNTAX INTEGER	 
            MAX-ACCESS read-write
            STATUS current
            DESCRIPTION  
            "Applicable to AU/BU. 
             Applicable to SU/RB with SW version 5.5.20 and higher. 
             Defines the time after detecting radar signals in a channel of 
             avoiding using the channel or adjacent channels in 
             accordance with the bandwidth. Range: 1 to 60 (minutes)."
            ::= { brzaccVLDFSParameters 4 }


    brzaccVLDFSSuWaitingOption  OBJECT-TYPE
            SYNTAX INTEGER	{ disable (1) , enable (2), na(255) }	 
            MAX-ACCESS read-write
            STATUS current
            DESCRIPTION  
            "Applicable to AU/BU only. 
            Defines whether the associated SUs should wait for this AU/BU 
            after it stopped transmitting due to radar detection, before 
            they starts scanning for other AUs/BUs."
            ::= { brzaccVLDFSParameters 5 }


    brzaccVLDFSClearRadarDetectedChannelsAfterReset OBJECT-TYPE
            SYNTAX  INTEGER { cancel (1), clearRadarChannels (2), na(255) }  
            MAX-ACCESS read-write
            STATUS current
            DESCRIPTION  
            "Applicable to all units with SW version 5.5.20 and higher. 
             Clear Radar Detected and Adjacent to Radar channels after unit reset.
             Returns the unit to operate in default frequency."
            ::= { brzaccVLDFSParameters 6 }

	brzaccVLDFSRadarDetectionChannelsTable OBJECT-TYPE	  
			SYNTAX SEQUENCE OF BrzaccVLDFSRadarDetectionChannelsEntry
			MAX-ACCESS not-accessible
			STATUS current
			DESCRIPTION
            "Applicable to AU/BU only. 
             Applicable only when DFS option is on.
             Displays the current channels defined in the sub-band and their radar 
             detection status."
			::= { brzaccVLDFSParameters 7 }

	brzaccVLDFSRadarDetectionChannelsEntry OBJECT-TYPE	
			SYNTAX BrzaccVLDFSRadarDetectionChannelsEntry
			MAX-ACCESS not-accessible
			STATUS current
	        DESCRIPTION
	        "Applicable to AU/BU only. 
	         An entry in the brzaccVLDFSRadarDetectionChannelsTable."
			INDEX { brzaccVLDFSChannelIdx }
			::= { brzaccVLDFSRadarDetectionChannelsTable 1 }
								
	BrzaccVLDFSRadarDetectionChannelsEntry ::= SEQUENCE { 
	        brzaccVLDFSChannelIdx	                    INTEGER, 
			brzaccVLDFSChannelFrequency                 INTEGER,	 
			brzaccVLDFSChannelRadarStatus               INTEGER,
			brzaccVLDFSChannelFrequencyNew              DisplayString }

	brzaccVLDFSChannelIdx   OBJECT-TYPE			 
			SYNTAX INTEGER  (1..40)
			MAX-ACCESS read-only
			STATUS current
			DESCRIPTION	 
            "Applicable to AU/BU only. Read-only. 
             The index of the entry in the 
             brzaccVLDFSRadarDetectionChannelsTable."
	    ::= { brzaccVLDFSRadarDetectionChannelsEntry 1 }
		   							
	brzaccVLDFSChannelFrequency   OBJECT-TYPE			 
			SYNTAX INTEGER  
			MAX-ACCESS read-only
			STATUS current
			DESCRIPTION	 
			"Applicable to AU/BU with HW revision B and lower 
			 (for units with HW revision C and higher replaced by 
			 brzaccVLDFSChannelFrequency New to support a resolution 
			 of 0.5 MHz). 
			 The frequency in MHz of a channel in the DFS Radar 
			 Detection Channels Table."
	    ::= { brzaccVLDFSRadarDetectionChannelsEntry 2 }

    brzaccVLDFSChannelRadarStatus   OBJECT-TYPE			 
			SYNTAX INTEGER  { radarFree       (1),
			                  adjacentToRadar (2),
			                  radarDetected   (3) }
			MAX-ACCESS read-only
			STATUS current
			DESCRIPTION	 
            "Applicable to AU/BU only.  
             The radar detection status of a channel in 
             brzaccVLDFSRadarDetectionChannelTable."
	    ::= { brzaccVLDFSRadarDetectionChannelsEntry 3 }

	brzaccVLDFSChannelFrequencyNew   OBJECT-TYPE			 
			SYNTAX DisplayString  
			MAX-ACCESS read-only
			STATUS current
			DESCRIPTION	 
			"Applicable to AU/BU. The frequency of a channel in the 
			 DFS Radar Detection Channels Table. 
			 (Replaces brzaccVLDFSChannelFrequency to support a 
			 resolution of 0.5 MHz for units with HW revision C and higher)."
	    ::= { brzaccVLDFSRadarDetectionChannelsEntry 4 }

    brzaccVLDFSMinimumPulsesToDetect  OBJECT-TYPE
            SYNTAX INTEGER	 
            MAX-ACCESS read-write
            STATUS current
            DESCRIPTION  
            "Applicable to AU/BU. 
             Applicable to SU/RB with SW version 5.5.20 and higher. 
             Defines the minimum number of pulses to detect a radar. 
             Range: 1 - 100."
            ::= { brzaccVLDFSParameters 8 }

	
brzaccVLDFSChannelReuseParameters OBJECT IDENTIFIER ::= {brzaccVLDFSParameters 9}

    brzaccVLDFSChannelReuseOption  OBJECT-TYPE
            SYNTAX INTEGER	{ disable (1) , enable (2), na (255) } 
            MAX-ACCESS read-write
            STATUS current
            DESCRIPTION  
            "Applicable to AU/BU only.
             Enabling/disabling the DFS Channel Reuse Algorithm. 
             Not applicable if DFS Option is not supported by the current Sub Band."
            ::= { brzaccVLDFSChannelReuseParameters 1 }

    brzaccVLDFSRadarActivityAssessmentPeriod  OBJECT-TYPE
            SYNTAX INTEGER	 
            MAX-ACCESS read-write
            STATUS current
            DESCRIPTION  
            "Applicable to AU/BU only. 
             Range: 1 to 12 (Houres)."
            ::= { brzaccVLDFSChannelReuseParameters 2 }

    brzaccVLDFSMaximumNumberOfDetectionsInAssessmentPeriod  OBJECT-TYPE
            SYNTAX INTEGER	 
            MAX-ACCESS read-write
            STATUS current
            DESCRIPTION  
            "Applicable to AU/BU only. 
             Range: 1 to 10 (Times)."
            ::= { brzaccVLDFSChannelReuseParameters 3 }

    brzaccVLDFSDetectionAlgorithm  OBJECT-TYPE
            SYNTAX INTEGER	{ etsi(1), fcc(2), na(255) }
            MAX-ACCESS read-write
            STATUS current
            DESCRIPTION  
            "Applicable to AU/BU. 
             Applicable to SU/RB with SW version 5.5.20 and higher. 
             Defines the DFS Detection Algorithm."
            ::= { brzaccVLDFSParameters 10 }

    brzaccVLDFSRemoteRadarEventReports OBJECT-TYPE
            SYNTAX INTEGER	 
            MAX-ACCESS read-write
            STATUS current
            DESCRIPTION  
            "Applicable to AU only with SW version 5.5.20 and higher. 
             Defines the number of SU radar reports for the AU to leave channel . 
             Range: 0 - 512."
            ::= { brzaccVLDFSParameters 11 }
          
     brzaccVLDFSRemoteRadarEventMonitoringPeriod OBJECT-TYPE
            SYNTAX INTEGER	 
            MAX-ACCESS read-write
            STATUS current
            DESCRIPTION  
            "Applicable to AU only with SW version 5.5.20 and higher. 
             Defines the interval in minutes of accumulated SU Radar Reports for the AU to leave channel. 
             Range: 1 - 30."
            ::= { brzaccVLDFSParameters 12 }

	brzaccVLEnhancedETSIRadarDetection OBJECT-TYPE
            SYNTAX INTEGER { off(1), on(2) }
            MAX-ACCESS read-write
            STATUS current
            DESCRIPTION  
            "Applicable to AU/BU units with software version 5.5.27.1 and higher."
            ::= { brzaccVLDFSParameters 13 }

   brzaccVLCountryCodeLearningBySU OBJECT-TYPE
            SYNTAX  INTEGER  { disable(1), enable(2), na(255) }
            MAX-ACCESS read-write      
            STATUS current       
            DESCRIPTION  
            "Applicable to AU only. 
             Starting with 4.0 it is not applicable for BA4900 and BreezeNET B.
             Defines whether the SUs learn the country code of the AU."
            ::= { brzaccVLFrequencyDefinition 12 }

    brzaccVLCurrentAUOperatingFrequencyNew  OBJECT-TYPE
            SYNTAX DisplayString	
            MAX-ACCESS read-only
            STATUS current
            DESCRIPTION  
            "Applicable to AU/BU. The operating frequency in MHz. 
             (Replaces brzaccVLCurrentAUOperatingFrequency to support 
             a resolution of 0.5 MHz for units with HW revision C and higher). 
             For 5.8GHz products with SW version below 2.0 the range is 
             5740 to 5830 MHz using 10MHz resolution. 
             For units with SW version 2.0 and up the range is as defined 
             in the selected Sub Band."
            ::= { brzaccVLFrequencyDefinition 13 }

    brzaccVLAUDefinedFrequencyNew  OBJECT-TYPE
            SYNTAX DisplayString	
            MAX-ACCESS read-write
            STATUS current
            DESCRIPTION  
            "Applicable to AU/BU. 
             For 5.8GHz products with SW version below 2.0 this is the 
             frequency in MHz of the AU/BU after the next reset. 
             For units with SW version 2.0 and up this is the 
             frequency in MHz to use when the DFS Option is disabled. 
             (Replaces brzaccVLAUDefinedFrequency to support a resolution 
             of 0.5 MHz for units with HW revision C and higher). 
             For 5.8GHz products with SW version below 2.0 the range 
             is 5740 to 5830 MHz using 10MHz resolution. 
             For units with SW version 2.0 and up the range is as 
             defined in the selected Sub Band."
            ::= { brzaccVLFrequencyDefinition 14 }


-- AUTOMATIC SUB BAND SELECT BEGIN

	brzaccVLAutoSubBandSelect	OBJECT IDENTIFIER ::= { brzaccVLFrequencyDefinition 15 }
	
	brzaccVLAutoSubBandSelectedFreqSubset  OBJECT-TYPE
            SYNTAX INTEGER	 { setAllSelectedFreqsSubset(1), cancel (2) }
            MAX-ACCESS read-write
            STATUS current
            DESCRIPTION  
            "Applicable to SU/RB with SW version 4.0 and higher.        
			 Apply the selected subset. After the next reset the new 
			 subset will be used for scanning."
            ::= { brzaccVLAutoSubBandSelect 1 }
            
	brzaccVLAutoSubBandFrequencySubsetTable OBJECT-TYPE
            SYNTAX SEQUENCE OF BrzaccVLAutoSubBandFrequencySubsetEntry
            MAX-ACCESS not-accessible
            STATUS current
            DESCRIPTION
            "Applicable to SU/RB with SW version 4.0 and higher. 
            The Frequency Subset Table that includes all available 
            sub-bands and all the frequencies in these sub-bands."
            ::= { brzaccVLAutoSubBandSelect 2 }

    brzaccVLAutoSubBandFrequencySubsetEntry  OBJECT-TYPE
            SYNTAX BrzaccVLAutoSubBandFrequencySubsetEntry
            MAX-ACCESS not-accessible
            STATUS current
            DESCRIPTION
            "Applicable to SU/RB with SW version 4.0 and higher.
             An entry in the Frequency Subset Table. "  
             INDEX { brzaccVLAutoSubBandFrequencySubsetBandIdx, brzaccVLAutoSubBandFrequencySubsetFrequencyIdx }
            ::= { brzaccVLAutoSubBandFrequencySubsetTable 1 }

    BrzaccVLAutoSubBandFrequencySubsetEntry ::= SEQUENCE {
            brzaccVLAutoSubBandFrequencySubsetBandIdx		INTEGER,
            brzaccVLAutoSubBandFrequencySubsetFrequencyIdx  INTEGER,
            brzaccVLAutoSubBandFrequencySubsetActive        INTEGER,
            brzaccVLAutoSubBandFrequencySubsetFrequency     DisplayString,
            brzaccVLAutoSubBandFrequencySubsetBandwidth		INTEGER,
            brzaccVLAutoSubBandFrequencySubsetDFSStatus		INTEGER
            }
               
    brzaccVLAutoSubBandFrequencySubsetBandIdx   OBJECT-TYPE
            SYNTAX INTEGER  (1..5)
            MAX-ACCESS read-only
            STATUS current
            DESCRIPTION 
            "Applicable to SU/RB with SW version 4.0 and higher.
			 The index of the applicable Sub Band. 
			 This is the Sub Band ID of the relevant entry in 
			 the Country Dependent Parameters table.
			 Serves also as an index of the entry in the 
			 Frequency subset Table."
           ::= { brzaccVLAutoSubBandFrequencySubsetEntry 1 }
           
	brzaccVLAutoSubBandFrequencySubsetFrequencyIdx   OBJECT-TYPE
            SYNTAX INTEGER  (1..40)
            MAX-ACCESS read-only
            STATUS current
            DESCRIPTION 
            "Applicable to SU/RB with SW version 4.0 and higher.
			 The index of the applicable frequency in the 
			 applicable Sub Band.  
			 Serves also as an index of the entry in the 
			 Frequency subset Table."
           ::= { brzaccVLAutoSubBandFrequencySubsetEntry 2 }


    brzaccVLAutoSubBandFrequencySubsetActive   OBJECT-TYPE
            SYNTAX INTEGER  {active (1) , notActive (2)}
            MAX-ACCESS read-write
            STATUS current
            DESCRIPTION 
            "Applicable to SU/RB with SW version 4.0 and higher.
			 The status of an entry in the Auto Sub Band Frequency subset Table.
			 The frequency of an active entry will be included in the 
			 final list of frequencies to be used for scanning."
           ::= { brzaccVLAutoSubBandFrequencySubsetEntry 3 }

    brzaccVLAutoSubBandFrequencySubsetFrequency   OBJECT-TYPE
            SYNTAX DisplayString
            MAX-ACCESS read-only
            STATUS current
            DESCRIPTION 
            "Applicable to SU/RB with SW version 4.0 and higher. 
             The frequency in MHz of the entry in the Auto Sub Band Frequency Subset table."
           ::= { brzaccVLAutoSubBandFrequencySubsetEntry 4 }

	brzaccVLAutoSubBandFrequencySubsetBandwidth OBJECT-TYPE
            SYNTAX INTEGER
            MAX-ACCESS read-only
            STATUS current
            DESCRIPTION 
            "Applicable to SU/RB with SW version 4.0 and higher. 
             The bandwidth in MHz of the entry in the Auto Sub Band Frequency Subset table."
           ::= { brzaccVLAutoSubBandFrequencySubsetEntry 5 }
           
    brzaccVLAutoSubBandFrequencySubsetDFSStatus OBJECT-TYPE
            SYNTAX INTEGER  { radarFree       (1),
			                  adjacentToRadar (2),
			                  radarDetected   (3) }
            MAX-ACCESS read-only
            STATUS current
            DESCRIPTION 
            "Applicable to SU/RB with SW version 4.0 and higher. 
             The channel status of the entry in the Auto Sub Band Frequency Subset table."
           ::= { brzaccVLAutoSubBandFrequencySubsetEntry 6 }
           
           
           


-- AUTOMATIC SUB BAND SELECT END


brzaccVLATPC   OBJECT IDENTIFIER ::= {brzaccVLAirInterface 13}

    brzaccVLAtpcOption  OBJECT-TYPE
            SYNTAX INTEGER	{ disable (1) , enable (2) , na (255) } 
            MAX-ACCESS read-write
            STATUS current
            DESCRIPTION  
            "Applicable all units.
             Enabling/disabling the ATPC Algorithm."
            ::= { brzaccVLATPC 1 }

    brzaccVLDeltaFromMinSNRLevel  OBJECT-TYPE
            SYNTAX INTEGER	 
            MAX-ACCESS read-write
            STATUS current
            DESCRIPTION  
            "Applicable AU/BU only.
			 The Minimum SNR Level plus the value of this parameter define the 
			 maximum desired level of the average SNR at the AU/BU. 
			 If the ATPC Option is enabled,	than if the received SNR is above 
			 the maximum desired level, the AU/BU will transmit Power-Down 
			 messages to the applicable SU/RB.
             Range: 4 to 20 (dB)."
            ::= { brzaccVLATPC 2 }

    brzaccVLMinimumSNRLevel  OBJECT-TYPE
            SYNTAX INTEGER	 
            MAX-ACCESS read-write
            STATUS current
            DESCRIPTION  
            "Applicable AU/BU only.
             Defines the minimum desired level of the average SNR at the AU/BU.
             Below this level, if *AtpcOption is enabled, the AU/BU will transmit
             ATPC Power-Up messages to the applicable SU/RB.
             The *MinimumSNRLevel cannot be higher  than *MaximumSNRLevel.
             Range: 4 to 60 (dB)."
            ::= { brzaccVLATPC 3 }


    brzaccVLMinimumIntervalBetweenATPCMessages  OBJECT-TYPE
            SYNTAX INTEGER	 
            MAX-ACCESS read-write
            STATUS current
            DESCRIPTION  
            "Applicable AU/BU only.
			 The minimum interval between two consecutive AU/BU to SU/RB messages.
             Range: 1 to 3600 (Sec)."
            ::= { brzaccVLATPC 4 }



    brzaccVLPowerLevelSteps  OBJECT-TYPE
            SYNTAX INTEGER	 
            MAX-ACCESS read-write
            STATUS current
            DESCRIPTION  
            "Applicable AU/BU only.
			 The step in dB that the SU/RB will use when receiving an ATPC 
			 Power-Up/Power-Down message.
             Range: 1 to 20  (dB)."
            ::= { brzaccVLATPC 6 }


    brzaccVLAtpcOptionEZ  OBJECT-TYPE
            SYNTAX INTEGER	{ disable (1) , enable (2) , na (255) } 
            MAX-ACCESS read-write
            STATUS current
            DESCRIPTION  
            "Applicable AU only.
             Enabling/disabling the ATPC Algorithm for EZ."
            ::= { brzaccVLATPC 7 }


brzaccVLCellDistanceParameters   OBJECT IDENTIFIER ::= {brzaccVLAirInterface 15}

    brzaccVLCellDistanceMode  OBJECT-TYPE
            SYNTAX INTEGER	{ automatic (1) , manual (2), na (255) } 
            MAX-ACCESS read-write
            STATUS current
            DESCRIPTION  
            "Applicable AU/BU only. 
             The selected mode of deciding on Cell Distance."
            ::= { brzaccVLCellDistanceParameters 1 }

  brzaccVLFairnessFactor  OBJECT-TYPE
            SYNTAX INTEGER
            MAX-ACCESS read-write
            STATUS current
            DESCRIPTION  
            "Applicable AU/BU only.
             Not applicable to BreezeNET-B products for SW version below 4.0.
             The percentage of the maximum distance that is taken into 
             account in the time slot calculation. Range: 0 to 100 
             (Percent). A value of 0 means the minimal slot size 
             (9 microseconds).
             BreezeNET-B products with SW version below 4.0 return na.
             The na value is 255."
            ::= { brzaccVLCellDistanceParameters 2 }

    brzaccVLMeasuredCellDistance  OBJECT-TYPE
            SYNTAX INTEGER {below-2-Km(1)}
            MAX-ACCESS read-only
            STATUS current
            DESCRIPTION  
            "Applicable AU/BU only.
			 The Maximum Cell Distance as calculated by the AU/BU.
             Range: 0 to 54 (Kilometers)."
            ::= { brzaccVLCellDistanceParameters 3 }

    brzaccVLUnitWithMaxDistance  OBJECT-TYPE
            SYNTAX MacAddress	 
            MAX-ACCESS read-only
            STATUS current
            DESCRIPTION  
            "Applicable AU only.
			 Not applicable to BreezeNET-B units.
			 The MAC address of the unit with the maximum distance
			 from the AU."
            ::= { brzaccVLCellDistanceParameters 4 }

	brzaccVLPerSuDistanceLearning	OBJECT-TYPE
            SYNTAX INTEGER	{ disable (1) , enable (2), na(255) } 
            MAX-ACCESS read-write
            STATUS current
            DESCRIPTION  
            "Aplicable to AU only. Applicable only if Cell Distance Mode is 
			set to Automatic. When disabled, all SUs in the cell will use 
			for the ACK Timeout the computed distance of the farthest SU. 
			When enabled, each SU will use its own computed distance"
            ::= { brzaccVLCellDistanceParameters 5 }

   brzaccVLScanningMode OBJECT-TYPE
            SYNTAX  INTEGER  { passive (1), active (2)}
            MAX-ACCESS read-write      
            STATUS current       
            DESCRIPTION  
            "Applicable to SU/RB only. 
             The scanning mode. In cells where the DFS Option is enabled 
             Scanning Mode is forced to Passive."
            ::= { brzaccVLAirInterface 16 }

   brzaccVLAntennaGain OBJECT-TYPE
            SYNTAX  DisplayString
            MAX-ACCESS read-write      
            STATUS current       
            DESCRIPTION  
            "Applicable to all units. Read-write in units where 
             brzaccVLAntennaGainChange  is supported. 
             Read-only in units where brzaccVLAntennaGainChange is not supported. 
             The net gain (including cable attenuation for detached antennas) of 
             the antenna. 
             Range: 0  - to Maximum EIRP defined by country code + 10 (dBi). 
             A value of -2 (this value is configurable only in factory) 
             means don't care.
             A value of -1 (this value is configurable only in factory) 
             means that the unit will not transmit until the actual value 
             is configured."
            ::= { brzaccVLAirInterface 17 }

brzaccVLSpectrumAnalysisParameters       OBJECT IDENTIFIER ::= {brzaccVLAirInterface 18}

    brzaccVLSpectrumAnalysisChannelScanPeriod OBJECT-TYPE
            SYNTAX  INTEGER  
            MAX-ACCESS read-write
            STATUS current
            DESCRIPTION 
            "Applicable to all units. 
             The period of staying on each channel for information gathering 
             when performing Spectrum analysis. 
             Range: 2-30 seconds."
            ::= { brzaccVLSpectrumAnalysisParameters 1 }

    brzaccVLSpectrumAnalysisScanCycles OBJECT-TYPE
            SYNTAX  INTEGER  
            MAX-ACCESS read-write
            STATUS current
            DESCRIPTION 
            "Applicable to all units.  
             The number of scanning cycles when performing Spectrum Analysis. 
             Range: 1-100."
            ::= { brzaccVLSpectrumAnalysisParameters 2 }

    brzaccVLAutomaticChannelSelection OBJECT-TYPE
            SYNTAX  INTEGER  { disable (1), enable (2), na (255)}
            MAX-ACCESS read-write
            STATUS current
            DESCRIPTION 
            "Applicable to AU/BU only.  
             Defines weather the AU/BU shall choose the most noise free channel
             upon startup after spectrum analysis."
            ::= { brzaccVLSpectrumAnalysisParameters 3 }

    brzaccVLSpectrumAnalysisActivation OBJECT-TYPE
            SYNTAX  INTEGER  { cancelOperation (1), activateNow (2)}
            MAX-ACCESS read-write
            STATUS current
            DESCRIPTION 
            "Applicable to all units.  
             Activates spectrum analysis, the unit is automatically reset upon 
             activation."
            ::= { brzaccVLSpectrumAnalysisParameters 4 }

    brzaccVLSpectrumAnalysisStatus OBJECT-TYPE
            SYNTAX  INTEGER  { inactive (1), currentlyActive (2), currentlyBlocked(3) }
            MAX-ACCESS read-only
            STATUS current
            DESCRIPTION 
            "Applicable to all units.  
             Defines whether the unit is currently performing 
             a Spectrum Analysis process.
             Value currentlyBlocked means unit current status prohibits 
             Spectrum Analysis activation."
            ::= { brzaccVLSpectrumAnalysisParameters 5 }

    brzaccVLResetSpectrumCounters OBJECT-TYPE
            SYNTAX  INTEGER  { cancelOperation (1), resetCounters (2)}
            MAX-ACCESS read-write
            STATUS current
            DESCRIPTION 
            "Applicable to all units.  
             Resets the spectrum analysis counters."
            ::= { brzaccVLSpectrumAnalysisParameters 6 }

    brzaccVLSpectrumAnalysisInformationTable OBJECT-TYPE
            SYNTAX SEQUENCE OF BrzaccVLSpectrumAnalysisInformationEntry
            MAX-ACCESS not-accessible
            STATUS current
            DESCRIPTION
            "Applicable to all units.  
             The spectrum analysis information table."
            ::= { brzaccVLSpectrumAnalysisParameters 7 }

    brzaccVLSpectrumAnalysisInformationEntry  OBJECT-TYPE
            SYNTAX BrzaccVLSpectrumAnalysisInformationEntry
            MAX-ACCESS not-accessible
            STATUS current
            DESCRIPTION
            "Applicable to all units.  
             The spectrum analysis information table entry."
            INDEX { brzaccVLSpectrumAnalysisInformationTableIdx }
            ::= { brzaccVLSpectrumAnalysisInformationTable 1 }

    BrzaccVLSpectrumAnalysisInformationEntry ::= SEQUENCE {
            brzaccVLSpectrumAnalysisInformationTableIdx           INTEGER,
            brzaccVLSpectrumAnalysisInformationChannel            DisplayString,
            brzaccVLSpectrumAnalysisInformationSignalCount        INTEGER,
            brzaccVLSpectrumAnalysisInformationSignalSNR          INTEGER,
            brzaccVLSpectrumAnalysisInformationSignalWidth        INTEGER,
            brzaccVLSpectrumAnalysisInformationOFDMFrames         INTEGER,
            brzaccVLSpectrumAnalysisInformationOFDMAvgSnr		  INTEGER,
            brzaccVLSpectrumAnalysisInformationAvgNoiseFloor	  INTEGER,
            brzaccVLSpectrumAnalysisInformationMaxNoiseFloor	  INTEGER,
            brzaccVLSpectrumAnalysisInformationSignalMaxSNR		  INTEGER,
            brzaccVLSpectrumAnalysisInformationOFDMMaxSNR		  INTEGER
            }

         
    brzaccVLSpectrumAnalysisInformationTableIdx   OBJECT-TYPE
            SYNTAX INTEGER (1..60)
            MAX-ACCESS read-only
            STATUS current
            DESCRIPTION  
            "Applicable to all units.  
             A read only table index for a Spectrum Analysis Information entry in the  
             Spectrum Analysis Information Table."
        ::= { brzaccVLSpectrumAnalysisInformationEntry 1 }

    brzaccVLSpectrumAnalysisInformationChannel   OBJECT-TYPE
            SYNTAX DisplayString 
            MAX-ACCESS read-only
            STATUS current
            DESCRIPTION  
            "Applicable to all units.  
             The channels in the Spectrum Analysis Information Table.
             If the unit is currently under spectrum analysis the channels would 
             be those on which the analysis is currently performed.
             If the unit is in normal mode the channels would be the those on 
             which the last analysis was performed."
        ::= { brzaccVLSpectrumAnalysisInformationEntry 2 }

    brzaccVLSpectrumAnalysisInformationSignalCount    OBJECT-TYPE
            SYNTAX INTEGER 
            MAX-ACCESS read-only
            STATUS current
            DESCRIPTION  
            "Applicable to all units.
             The number of signals (excluding OFDM frames) detected in the channel. 
             If the unit is currently under spectrum analysis the count would 
             be of the analysis that is currently performed. 
             If the unit is in normal mode the count would be of the last 
             analysis performed."
        ::= { brzaccVLSpectrumAnalysisInformationEntry 3 }

    brzaccVLSpectrumAnalysisInformationSignalSNR   OBJECT-TYPE
            SYNTAX INTEGER 
            MAX-ACCESS read-only
            STATUS current
            DESCRIPTION  
            "Applicable to all units.
			 The approximate SNR of the signals (excluding OFDM frames)
			 detected in the channel.
			 If the unit is currently under spectrum analysis the SNR would
			 be of the analysis that is currently performed.
			 If the unit is in normal mode the SNR would be of the last
			 analysis performed."
        ::= { brzaccVLSpectrumAnalysisInformationEntry 4 }

    brzaccVLSpectrumAnalysisInformationSignalWidth   OBJECT-TYPE
            SYNTAX INTEGER 
            MAX-ACCESS read-only
            STATUS current
            DESCRIPTION  
            "Applicable to all units. 
             The average width of the signals (excluding OFDM frames) 
             detected in the channel. 
             If the unit is currently under spectrum analysis the width would 
             be of the analysis that is currently performed. 
             If the unit is in normal mode the width would be of the last 
             analysis performed."
        ::= { brzaccVLSpectrumAnalysisInformationEntry 5 }

    brzaccVLSpectrumAnalysisInformationOFDMFrames   OBJECT-TYPE
            SYNTAX INTEGER 
            MAX-ACCESS read-only
            STATUS current
            DESCRIPTION  
            "Applicable to all units. 
             The number of OFDM frames detected in the channel. 
             If the unit is currently under spectrum analysis the count would 
             be of the analysis that is currently performed. 
             If the unit is in normal mode the count would be of the last 
             analysis performed."
        ::= { brzaccVLSpectrumAnalysisInformationEntry 6 }

    brzaccVLSpectrumAnalysisInformationOFDMAvgSnr   OBJECT-TYPE
            SYNTAX INTEGER 
            MAX-ACCESS read-only
            STATUS current
            DESCRIPTION  
            "Applicable to all units. 
             The average SNR of the OFDM frames detected in the channel. 
             If the unit is currently under spectrum analysis the average SNR would 
             be of the analysis that is currently performed. 
             If the unit is in normal mode the average SNR would be of the last 
             analysis performed."
        ::= { brzaccVLSpectrumAnalysisInformationEntry 7 }
        
    brzaccVLSpectrumAnalysisInformationAvgNoiseFloor   OBJECT-TYPE
            SYNTAX INTEGER 
            MAX-ACCESS read-only
            STATUS current
            DESCRIPTION  
            "Applicable to all units. 
             The average Noise Floor detected in the channel. 
             If the unit is currently under spectrum analysis the average 
             Noise Floor would be of the analysis that is currently performed. 
             If the unit is in normal mode the average Noise Floor would be 
             of the last analysis performed."
        ::= { brzaccVLSpectrumAnalysisInformationEntry 8 }
        
     brzaccVLSpectrumAnalysisInformationMaxNoiseFloor   OBJECT-TYPE
            SYNTAX INTEGER 
            MAX-ACCESS read-only
            STATUS current
            DESCRIPTION  
            "Applicable to all units. 
             The maximum Noise Floor detected in the channel. 
             If the unit is currently under spectrum analysis the maximum 
             Noise Floor would be of the analysis that is currently performed. 
             If the unit is in normal mode the maximum Noise Floor would be 
             of the last analysis performed."
        ::= { brzaccVLSpectrumAnalysisInformationEntry 9 }
     
     brzaccVLSpectrumAnalysisInformationSignalMaxSNR   OBJECT-TYPE
            SYNTAX INTEGER 
            MAX-ACCESS read-only
            STATUS current
            DESCRIPTION  
            "Applicable to all units. 
             The maximum SNR of the signals (excluding OFDM frames)
             detected in the channel. 
             If the unit is currently under spectrum analysis the maximum SNR would 
             be of the analysis that is currently performed. 
             If the unit is in normal mode the maximum SNR would be of the last 
             analysis performed."
        ::= { brzaccVLSpectrumAnalysisInformationEntry 10 }
        
    brzaccVLSpectrumAnalysisInformationOFDMMaxSNR   OBJECT-TYPE
            SYNTAX INTEGER 
            MAX-ACCESS read-only
            STATUS current
            DESCRIPTION  
            "Applicable to all units. 
             The maximum SNR of the OFDM frames detected in the channel. 
             If the unit is currently under spectrum analysis the maximum SNR would 
             be of the analysis that is currently performed. 
             If the unit is in normal mode the maximum SNR would be of the last 
             analysis performed."
        ::= { brzaccVLSpectrumAnalysisInformationEntry 11 }
       
    brzaccVLMaxNumOfAssociationsLimit OBJECT-TYPE
            SYNTAX  INTEGER  
            MAX-ACCESS read-only      
            STATUS current       
            DESCRIPTION  
            "Applicable to AU only. 
             Not applicable to BreezeNET-B products. 
             Shows the limit for the number of SUs that can be associated 
             with the AU. 
             For AU-BS, AU-SA, AU if Data Encryption is enabled, the upper 
             limit is 124, otherwise it is 512. 
             For AUS-BS, AUS-SA with SW version 4.0 and higher the upper limit 
             is 8 or 25 (via licensing).
             For AUS-BS, AUS-SA with SW version below 4.0 the upper limit is 5.
             BreezeNET-B products return 65535."
            ::= { brzaccVLAirInterface 19 }

brzaccVLDisassociate   OBJECT IDENTIFIER ::= {brzaccVLAirInterface 20}

    brzaccVLDisassociateAllSUs OBJECT-TYPE
            SYNTAX  INTEGER  { cancelOperation (1), disassociateAllSUs(2)}
            MAX-ACCESS read-write
            STATUS current
            DESCRIPTION 
            "Applicable to AU only.  
             The AU shall disassociate all its associated units."
            ::= { brzaccVLDisassociate 1 }

    brzaccVLDisassociateSuByMacAddress OBJECT-TYPE
            SYNTAX  MacAddress 
            MAX-ACCESS read-write
            STATUS current
            DESCRIPTION 
            "Applicable to AU only.  
             The AU shall disassociate the SU with the configured MAC address."
            ::= { brzaccVLDisassociate 2 }

    brzaccVLTxControl OBJECT-TYPE
            SYNTAX  INTEGER  { on (1), off(2), ethernetStatusControl(3)}
            MAX-ACCESS read-write
            STATUS current
            DESCRIPTION 
            "Applicable to AU/BU only.  
             Tx Control of the AU/BU.
             Starting with version 4.0 it is run-time.
             For SW version below 4.0 the unit reset itself.
             If set to ethernetStatusControl, the unit will not transmit 
             if the Ethernet link is down.
             This parameter can be configured only via the ethernet port."
            ::= { brzaccVLAirInterface 21 }

    brzaccVLLostBeaconsWatchdogThreshold OBJECT-TYPE
            SYNTAX  INTEGER  ( 0 | 100..1000 )
            MAX-ACCESS read-write
            STATUS current
            DESCRIPTION 
            "Applicable to AU/BU only.  
            The number of unsuccessful consecutive transmissions beacons 
            before Internal refresh is performed. 
			0 means that the lost beacons watchdog is not 
			used and internal refresh is not performed."
			::= { brzaccVLAirInterface 22}     

    brzaccVLTransmitPower       OBJECT-TYPE
            SYNTAX INTEGER
            MAX-ACCESS read-write
            STATUS current
            DESCRIPTION  
            "Applicable to all units with SW version 4.0 and higher.
             The uniform transmit power for all modulation levels. For a specific
             modulation level the effective transmit power (brzaccVLTxPower) is 
             the minimum between the uniform transmit power and the maximum 
             transmit power for that modulation level." 
            ::= { brzaccVLAirInterface 23 }
    
    brzaccVLMaximumTxPower       OBJECT-TYPE
            SYNTAX INTEGER
            MAX-ACCESS read-write
            STATUS current
            DESCRIPTION  
            "Applicable to only SU/RB with SW version 4.0 and higher.
            The Maximum Transmit Power for all modulation levels.
            The Maximum Transmit Power for a specific modulation level is the 
            minimum between this parameter and the hardware limitation for 
            that modulation level" 
            ::= { brzaccVLAirInterface 24 }        
            
   brzaccVLCountryCodeParameters   OBJECT IDENTIFIER ::= {brzaccVLAirInterface 25}            
   
   brzaccVLCountryCodeReApply OBJECT-TYPE
	     	SYNTAX	INTEGER { reapply(1),cancel(2), na(255) }  
		    MAX-ACCESS read-write
	     	STATUS current
		    DESCRIPTION	 
            "Applicable to all units.
             Re-apply country code parameters."
			::= { brzaccVLCountryCodeParameters 1 }

    brzaccVLCountryCodeTable OBJECT-TYPE
            SYNTAX SEQUENCE OF BrzaccVLCountryCodeEntry
            MAX-ACCESS not-accessible
            STATUS current
            DESCRIPTION
            "Applicable to all units. "
            ::= {brzaccVLCountryCodeParameters 2}
            
    brzaccVLCountryCodeEntry OBJECT-TYPE
            SYNTAX BrzaccVLCountryCodeEntry
            MAX-ACCESS not-accessible
            STATUS current
            DESCRIPTION
            "Applicable to all units."  
             INDEX {  brzaccVLCCNumber }
            ::= { brzaccVLCountryCodeTable 1 }
             
    BrzaccVLCountryCodeEntry ::= SEQUENCE {
				brzaccVLCCNumber							INTEGER,
				brzaccVLCCName								DisplayString,
				brzaccVLCCAuthenticationEncryptionSupport	INTEGER,
				brzaccVLCCDataEncryptionSupport				INTEGER, 
				brzaccVLCCAESEncryptionSupport				INTEGER  
            }
    	
   brzaccVLCCNumber  OBJECT-TYPE
            SYNTAX INTEGER(0..2147483647)
            MAX-ACCESS read-only
            STATUS current
            DESCRIPTION 
            "Applicable to all units." 
           ::= { brzaccVLCountryCodeEntry 1 }
           
    brzaccVLCCName OBJECT-TYPE
            SYNTAX DisplayString (SIZE(0..32))
            MAX-ACCESS read-only
            STATUS current
            DESCRIPTION  
            "Applicable to all units."
            ::= { brzaccVLCountryCodeEntry 2 }

    brzaccVLCCAuthenticationEncryptionSupport OBJECT-TYPE
            SYNTAX INTEGER  {supported(1), notSupported(2)}
            MAX-ACCESS read-only
            STATUS current
            DESCRIPTION  
            "Applicable to all units."
            ::= { brzaccVLCountryCodeEntry 3 }

    brzaccVLCCDataEncryptionSupport OBJECT-TYPE
            SYNTAX INTEGER  {supported(1), notSupported(2)}
            MAX-ACCESS read-only
            STATUS current
            DESCRIPTION  
            "Applicable to all units."
            ::= { brzaccVLCountryCodeEntry 4 }

    brzaccVLCCAESEncryptionSupport OBJECT-TYPE
            SYNTAX INTEGER  {supported(1), notSupported(2)}
            MAX-ACCESS read-only
            STATUS current
            DESCRIPTION  
            "Applicable to all units."
            ::= { brzaccVLCountryCodeEntry 5 }

    brzaccVLCCParamsTable  OBJECT-TYPE
            SYNTAX SEQUENCE OF BrzaccVLCCParamsEntry
            MAX-ACCESS not-accessible
            STATUS current
            DESCRIPTION
            "Applicable to all units. A table of country dependent parameters."
            ::= {brzaccVLCountryCodeParameters 3}

    brzaccVLCCParamsEntry OBJECT-TYPE
            SYNTAX BrzaccVLCCParamsEntry
            MAX-ACCESS not-accessible
            STATUS current
            DESCRIPTION
            "Applicable to all units. "
             INDEX { brzaccVLCCNumberIdx, brzaccVLCCParamsIndex }
            ::= { brzaccVLCCParamsTable 1 }

    BrzaccVLCCParamsEntry ::= SEQUENCE {
		    brzaccVLCCNumberIdx								INTEGER,
            brzaccVLCCParamsIndex							INTEGER,
            brzaccVLCCParamsFrequencies						DisplayString,
			brzaccVLCCAllowedBandwidth                      INTEGER,
			brzaccVLCCRegulationMaxTxPowerAtAntennaPort		INTEGER,
			brzaccVLCCRegulationMaxEIRP						INTEGER,
			brzaccVLCCMinModulationLevel                    INTEGER,
			brzaccVLCCMaxModulationLevel                    INTEGER,
			brzaccVLCCBurstModeSupport                      INTEGER,
			brzaccVLCCMaximumBurstDuration                  INTEGER,
			brzaccVLCCDfsSupport							INTEGER,
			brzaccVLCCMinimumHwRevision                     INTEGER
            }
    
    brzaccVLCCNumberIdx  OBJECT-TYPE
            SYNTAX INTEGER(0..2147483647) 
            MAX-ACCESS read-only
            STATUS current
            DESCRIPTION 
            "Applicable to all units. "
           ::= { brzaccVLCCParamsEntry 1 }
                 
    brzaccVLCCParamsIndex  OBJECT-TYPE
            SYNTAX INTEGER  (1..5)
            MAX-ACCESS read-only
            STATUS current
            DESCRIPTION 
            "Applicable to all units. "
           ::= { brzaccVLCCParamsEntry 2 }

    brzaccVLCCParamsFrequencies   OBJECT-TYPE
            SYNTAX DisplayString  
            MAX-ACCESS read-only
            STATUS current
            DESCRIPTION 
            "Applicable to all units. 
             The frequencies included in the applicable sub-band entry."
           ::= { brzaccVLCCParamsEntry 3 }
	
    brzaccVLCCAllowedBandwidth   OBJECT-TYPE
            SYNTAX INTEGER  
            MAX-ACCESS read-only
            STATUS current
            DESCRIPTION 
            "Applicable to all units. 
             The bandwidth when using the applicable the sub-band."
           ::= { brzaccVLCCParamsEntry 4 }

    brzaccVLCCRegulationMaxTxPowerAtAntennaPort  OBJECT-TYPE
            SYNTAX INTEGER  
            MAX-ACCESS read-only
            STATUS current
            DESCRIPTION 
            "Applicable to all units. 
             The maximum allowed Tx power when using the applicable sub-band.
             A RegulationMaxTxPowerAtAntennaPort of 255, means no limit"
           ::= { brzaccVLCCParamsEntry 5 }
 
    brzaccVLCCRegulationMaxEIRP   OBJECT-TYPE
            SYNTAX INTEGER  
            MAX-ACCESS read-only
            STATUS current
            DESCRIPTION 
            "Applicable to all units.
             The maximum Tx EIRP 
             when using the applicable sub-band.
             A Regulation Max EIRP of 0, means no limit."
           ::= { brzaccVLCCParamsEntry 6 }


    brzaccVLCCMinModulationLevel  OBJECT-TYPE
            SYNTAX INTEGER {  level1 (1), 
                              level2 (2), 
                              level3 (3), 
                              level4 (4), 
                              level5 (5), 
                              level6 (6), 
                              level7 (7),
                              level8 (8)
                            } 
            MAX-ACCESS read-only
            STATUS current
            DESCRIPTION 
            "Applicable to all units. 
             The minimum supported modulation level."
           ::= { brzaccVLCCParamsEntry 7 }

    brzaccVLCCMaxModulationLevel  OBJECT-TYPE
            SYNTAX INTEGER {  level1 (1), 
                              level2 (2), 
                              level3 (3), 
                              level4 (4), 
                              level5 (5), 
                              level6 (6), 
                              level7 (7),
                              level8 (8)
                            } 
            MAX-ACCESS read-only
            STATUS current
            DESCRIPTION 
            "Applicable to all units. 
             The maximum supported modulation level."
           ::= { brzaccVLCCParamsEntry 8 }
	
    brzaccVLCCBurstModeSupport  OBJECT-TYPE
            SYNTAX INTEGER  {supported(1), notSupported(2)}
            MAX-ACCESS read-only
            STATUS current
            DESCRIPTION 
            "Applicable to all units. 
             The supported Burst Mode Option."
           ::= { brzaccVLCCParamsEntry 9}

    brzaccVLCCMaximumBurstDuration   OBJECT-TYPE
            SYNTAX INTEGER 
            MAX-ACCESS read-only
            STATUS current
            DESCRIPTION 
            "Applicable to all units. 
             Applicable only if Burst Mode Option is supported. 
             The maximum supported burst duration."
           ::= { brzaccVLCCParamsEntry 10}

	 
    brzaccVLCCDfsSupport  OBJECT-TYPE
            SYNTAX INTEGER  {supported(1), notSupported(2)}
            MAX-ACCESS read-only
            STATUS current
            DESCRIPTION 
            "Applicable to AU/BU only. 
             The supported Dfs Option."
           ::= { brzaccVLCCParamsEntry 11}
	
    brzaccVLCCMinimumHwRevision  OBJECT-TYPE
            SYNTAX INTEGER {hwRevisionA (1), hwRevisionB (2), 
                            hwRevisionC (3), hwRevisionD (4), 
                            hwRevisionE (5), hwRevisionF (6),
                            hwRevisionG (7), na (255)}
            MAX-ACCESS read-only
            STATUS current
            DESCRIPTION 
            "Applicable to all units. 
             The Minimum HW Revision needed to support the country code."
           ::= { brzaccVLCCParamsEntry 12}
 
         
   brzaccVLCountryCodeSelect OBJECT-TYPE
	     	SYNTAX	INTEGER 
		    MAX-ACCESS read-write
	     	STATUS current
		    DESCRIPTION	 
            "Applicable to all units.
             Configure the Country Code
             WARNING: It is the responsibility of the wireless system operator 
             to verify that use of the selected Country Code does not result in
             violation of the relevant local radio regulations! 
             For more details refer to the Selecting Country Code document"
			::= { brzaccVLCountryCodeParameters 4 }
   
   
   brzaccVLNoiseImmunityParameters   OBJECT IDENTIFIER ::= {brzaccVLAirInterface 26}    

   brzaccVLNoiseImmunityAlgorithm OBJECT-TYPE
	     	SYNTAX	INTEGER { manual(1), automatic(2), na(255) }
		    MAX-ACCESS read-write
	     	STATUS current
		    DESCRIPTION	 
            "Applicable to all units except for units with HW revision B and lower.
            automatic(2) is not applicable for units with HW revision F or G.
             Noise Immunity Algorithm"
			::= { brzaccVLNoiseImmunityParameters 1 }
   
   brzaccVLNoiseImmunityLevel OBJECT-TYPE
	     	SYNTAX	INTEGER ( 0..4 | 255 )
		    MAX-ACCESS read-write
	     	STATUS current
		    DESCRIPTION	 
            "Applicable to all units except for units with HW revision B and lower.
             Noise Immunity Level. (255) : Not Available"
			::= { brzaccVLNoiseImmunityParameters 2 }

   brzaccVLSpuriousImmunityLevel OBJECT-TYPE
	     	SYNTAX	INTEGER ( 0..7 | 255 )
		    MAX-ACCESS read-write
	     	STATUS current
		    DESCRIPTION	 
            "Applicable to all units except for units with HW revision B and lower.
             (255) : Not Available"
			::= { brzaccVLNoiseImmunityParameters 3 }


   brzaccVLOFDMWeakSignal OBJECT-TYPE
	     	SYNTAX	INTEGER { enable(1), disable(2), na(255) }
		    MAX-ACCESS read-write
	     	STATUS current
		    DESCRIPTION	 
            "Applicable to all units except for units with HW revision B and lower.
             "
			::= { brzaccVLNoiseImmunityParameters 4 }
   
   brzaccVLPulseDetectionSensitivity OBJECT-TYPE
	     	SYNTAX	INTEGER { low(1), high(2) }
		    MAX-ACCESS read-write
	     	STATUS current
		    DESCRIPTION	 
            "Applicable to all units.
             "
			::= { brzaccVLNoiseImmunityParameters 5 }

   brzaccVLNoiseFloorCalculationParameters   OBJECT IDENTIFIER ::= {brzaccVLAirInterface 29}
   
   brzaccVLNoiseFloorCalculationMode OBJECT-TYPE
            SYNTAX  INTEGER { automatic(1), forced(2), minimumlevel(3) }
            MAX-ACCESS read-write
            STATUS current
            DESCRIPTION  
            "Applicable to all units."
            ::= { brzaccVLNoiseFloorCalculationParameters 1 }
            
   brzaccVLNoiseFloorForcedValue OBJECT-TYPE
            SYNTAX  INTEGER
            MAX-ACCESS read-write
            STATUS current
            DESCRIPTION  
            "Applicable to all units.
            Range: -107 to -55"
            ::= { brzaccVLNoiseFloorCalculationParameters 2 }

	brzaccVLNoiseFloorCalibrationParameters OBJECT IDENTIFIER ::= {brzaccVLAirInterface 30}

	brzaccVLNoiseFloorRunCalibration OBJECT-TYPE
		SYNTAX INTEGER { run(1), cancel(2), na(255) }
		MAX-ACCESS read-write
		STATUS current
		DESCRIPTION 
		"Not applicable to 900 MHz units. 
		Start calibration process for Noise Floor Indication.
		The unit will rest itself, will perform calibration 
		and after that will reset again.
		The status of last calibration run can be read from
		brzaccVLNoiseFloorIndicationLastCalibrationResult.
		Get operation will return cancel(2); on 900 MHz units it will return na(255)."
		::= { brzaccVLNoiseFloorCalibrationParameters 1 } 

	brzaccVLNoiseFloorFieldCalibrationStatus OBJECT-TYPE
		SYNTAX INTEGER { inactive (1), currentlyActive (2)}
		MAX-ACCESS read-only
		STATUS current
		DESCRIPTION 
		"Applicable to all units.
		Defines weather the unit is currently under performing 
		a noise floor indication calibration."
		::= { brzaccVLNoiseFloorCalibrationParameters 2 }

	brzaccVLNoiseFloorLastFieldCalibrationResult OBJECT-TYPE
		SYNTAX INTEGER { passed(1), failed(2), none(3) }
		MAX-ACCESS read-only
		STATUS current
		DESCRIPTION 
		"Applicable to all units.
		Return the status of last calibration of 
		Noise Floor Indication that was performed."
		::= { brzaccVLNoiseFloorCalibrationParameters 3 }
	 
	brzaccVLNoiseFloorBandwidthUsedForLastFieldCalibration OBJECT-TYPE
		SYNTAX INTEGER { none(0), bandwidth-5MHz(5), bandwidth-10MHz(10), bandwidth-20MHz(20), bandwidth-40MHz(40) }
		MAX-ACCESS read-only
		STATUS current
		DESCRIPTION 
		"Applicable to all units.
		Return the bandwidth used for last successful calibration
		of Noise Floor Indication."
		::= { brzaccVLNoiseFloorCalibrationParameters 4 }

	brzaccVLNoiseFloorAvailableCalibrationOptions OBJECT-TYPE
		SYNTAX INTEGER { notCalibrated(1), factoryOnly(2), fieldOnly(3), factoryAndField(4) }
		MAX-ACCESS read-only
		STATUS current
		DESCRIPTION 
		"Applicable to all units.
		Indicates what types of Noise Floor Indication calibration
		are available:
		notCalibrated: means that the unit is not calibrated
		factoryOnly: means that the unit was calibrated in factory
		fieldOnly: means that the unit was calibrated in field using
		brzaccVLNoiseFloorIndicationRunCalibration command
		factoryAndField: means that unit was calibrated in factory and also
		in field"
		::= { brzaccVLNoiseFloorCalibrationParameters 5 }

	brzaccVLNoiseFloorUseCalibration OBJECT-TYPE
		SYNTAX INTEGER { none(1), fieldCalibration(2), factoryCalibration(3) }
		MAX-ACCESS read-write
		STATUS current
		DESCRIPTION 
		"Not applicable to 900 MHz units. 
		Select if the Noise Floor reported by the unit is using the
		calibration of Noise Floor Indication.
		The value that can be choose are according with 
		brzaccVLNoiseFloorIndicationCalibrationAvailability."
		::= { brzaccVLNoiseFloorCalibrationParameters 6 }

-- InterferenceMitigationParameters

brzaccVLInterferenceMitigationParameters      OBJECT IDENTIFIER ::= {brzaccVLAirInterface 31}

    brzaccVLInterferenceMitigationChannelScanPeriod  OBJECT-TYPE
            SYNTAX  INTEGER  
            MAX-ACCESS read-write
            STATUS current
            DESCRIPTION 
            "Applicable to 900 MHz units, 2.4 GHz units and BNB10. 
             The period of time, in seconds, to stay on each channel to gather information, 
             when performing Interference Mitigation or Spectrum Analysis. 
             Range: 2-30 seconds."
            ::= { brzaccVLInterferenceMitigationParameters 1 }
            
    brzaccVLBeaconPeriod  OBJECT-TYPE
            SYNTAX  INTEGER  
            MAX-ACCESS read-write
            STATUS current
            DESCRIPTION 
            "Applicable only to AU VL.
            Range: 16-160 miliseconds."
            ::= { brzaccVLAirInterface 32 }
           
    brzaccVLMaxBeaconsLost  OBJECT-TYPE
            SYNTAX  INTEGER  
            MAX-ACCESS read-write
            STATUS current
            DESCRIPTION 
            "Applicable only to AU VL.
            Range: 3-64."
            ::= { brzaccVLAirInterface 33 }                

    brzaccVLInterferenceMitigationAutomaticScanPeriod  OBJECT-TYPE
            SYNTAX  INTEGER
            MAX-ACCESS read-write
            STATUS current
            DESCRIPTION 
            "Applicable to 900 MHz units, 2.4 GHz units and BNB10. 
             The period of time, in minutes, to execute automatic channel scanning,
             when performing Interference Mitigation.
             Range: 0 or 10-10080 minutes.
             A value of 0 means periodicity disabled,
             Interference Mitigation being performed only one time."
            ::= { brzaccVLInterferenceMitigationParameters 2 }

    brzaccVLInterferenceMitigationScanType    OBJECT-TYPE
            SYNTAX INTEGER  { clearChannelAndAutomaticNoiseFloorSelection (1), automaticNoiseFloorSelectionOnly (2), 
              clearChannelSelectionOnly (3), statisticsOnly(4) } 
            MAX-ACCESS read-write
            STATUS current
            DESCRIPTION  
            "Applicable to 900 MHz units, 2.4 GHz units and BNB10.
             The selected method for scanning, 
             when performing Interference Mitigation."
            ::= { brzaccVLInterferenceMitigationParameters 3 }

    brzaccVLInterferenceMitigationScanMode    OBJECT-TYPE
            SYNTAX INTEGER  { optimizePerformanceForMinimumDesiredDistance (1), optimizeDistanceForMinimumDesiredPerformance (2) } 
            MAX-ACCESS read-write
            STATUS current
            DESCRIPTION  
            "Applicable to 900 MHz units, 2.4 GHz units and BNB10. 
             The selected Optimization Criteria to choose the best result, 
             when performing Interference Mitigation: 
             1 = best throughput, 2 = best distance."
            ::= { brzaccVLInterferenceMitigationParameters 4 }

    brzaccVLInterferenceMitigationDistance    OBJECT-TYPE
            SYNTAX  INTEGER
            MAX-ACCESS read-write
            STATUS current
            DESCRIPTION 
            "Applicable to 900 MHz units, 2.4 GHz units and BNB10. 
             The desired value of Maximum Distance, utilized if
             Optimization Criteria is set to best distance,
             when performing Interference Mitigation. 
             Range: 100 - 54000 meters."
            ::= { brzaccVLInterferenceMitigationParameters 5 }

    brzaccVLInterferenceMitigationThroughput    OBJECT-TYPE
            SYNTAX  INTEGER
            MAX-ACCESS read-write
            STATUS current
            DESCRIPTION 
            "Applicable to 900 MHz units, 2.4 GHz units and BNB10. 
             The desired value of Throughput, utilized if
             Optimization Criteria is set to best throughput,
             when performing Interference Mitigation. 
             Range: 500-10000 Kbps."
            ::= { brzaccVLInterferenceMitigationParameters 6 }

-- 7 reserved for frequency subset

    brzaccVLInterferenceMitigationActivation    OBJECT-TYPE
            SYNTAX  INTEGER  { cancelOperation (1), activateNow (2), notAvailable (3) }
            MAX-ACCESS read-write
            STATUS current
            DESCRIPTION 
            "Applicable to 900 MHz units, 2.4 GHz units and BNB10.
             Activates Interference Mitigation, the unit is automatically reset upon 
             activation."
            ::= { brzaccVLInterferenceMitigationParameters 8 }

    brzaccVLInterferenceMitigationStatus    OBJECT-TYPE
            SYNTAX  INTEGER  { inactive (1), currentlyActive (2), currentlyBlocked(3) }
            MAX-ACCESS read-only
            STATUS current
            DESCRIPTION 
            "Applicable to 900 MHz units, 2.4 GHz units and BNB10.
             Defines whether the unit is currently performing 
             an Interference Mitigation process.
             Value currentlyBlocked means unit current status prohibits 
             Interference Mitigation activation."
            ::= { brzaccVLInterferenceMitigationParameters 9 }

    brzaccVLInterferenceMitigationDeleteStatisticsFile    OBJECT-TYPE
            SYNTAX  INTEGER  { cancelOperation (1), delete (2) }
            MAX-ACCESS read-write
            STATUS current
            DESCRIPTION 
            "Applicable to 900 MHz units, 2.4 GHz units and BNB10.
             Deletes the Interference Mitigation statistics file."
            ::= { brzaccVLInterferenceMitigationParameters 10 }
            
    brzaccVLInterferenceMitigationModel    OBJECT-TYPE
            SYNTAX  INTEGER  { typeLOS (1), typenLOS (2), typeNoLOS (3) }
            MAX-ACCESS read-write
            STATUS current
            DESCRIPTION 
            "Applicable to 900 MHz units, 2.4 GHz units and BNB10.
             Specifies the Installation Model used by the cell."
            ::= { brzaccVLInterferenceMitigationParameters 11 }            

    brzaccVLInterferenceMitigationScanTime    OBJECT-TYPE
            SYNTAX  INTEGER
            MAX-ACCESS read-only
            STATUS current
            DESCRIPTION 
            "Applicable to 900 MHz units, 2.4 GHz units and BNB10.
             Displays the estimated value of the scan time."
            ::= { brzaccVLInterferenceMitigationParameters 12 }

    brzaccVLInterferenceMitigationAUheight    OBJECT-TYPE
            SYNTAX INTEGER
            MAX-ACCESS read-write
            STATUS current
            DESCRIPTION  
            "Applicable to 900 MHz units, 2.4 GHz units and BNB10.
            The Base Station height used in determining
            the best noise floor in the Interference
            Mitigation algorithm. Range: 0 - 300 meters."
            ::= { brzaccVLInterferenceMitigationParameters 13 }
            
    brzaccVLInterferenceMitigationAntennaGain    OBJECT-TYPE
            SYNTAX INTEGER
            MAX-ACCESS read-write
            STATUS current
            DESCRIPTION  
            "Applicable to 900 MHz units, 2.4 GHz units and BNB10.
            The Antenna Gain of the pair unit (AU/SU),
            expressed in dBi. Range: 10 - 17 dBi."
            ::= { brzaccVLInterferenceMitigationParameters 14 }
            
    brzaccVLInterferenceMitigationMaxModulation    OBJECT-TYPE
            SYNTAX INTEGER
            MAX-ACCESS read-write
            STATUS current
            DESCRIPTION  
            "Applicable to 900 MHz units, 2.4 GHz units and BNB10.
            The maximum modulation of the pair untit.
            Range: 1 - 8."
            ::= { brzaccVLInterferenceMitigationParameters 15 }
            
            
    brzaccVLInterferenceMitigationKeepLink    OBJECT-TYPE
            SYNTAX  INTEGER  { disabled (1), enabled (2) }
            MAX-ACCESS read-write
            STATUS current
            DESCRIPTION 
            "Applicable to 900 MHz AU units, 2.4 GHz AU units and BNB10.
             Activates the KeepLink procedure in order to not
             lose SUs near the border of the cell"
            ::= { brzaccVLInterferenceMitigationParameters 16 }

            
	-- INTERFERENCE-MITIGATION-OUTPUT-TABLE
	
    brzaccVLInterferenceMitigationOutputTable OBJECT-TYPE
            SYNTAX SEQUENCE OF BrzaccVLInterferenceMitigationOutput
            MAX-ACCESS not-accessible
            STATUS current
            DESCRIPTION
            "Applicable to 900 MHz units, 2.4 GHz units and BNB10.
             A table of Clear Channel Selection or Automatic Noise Floor Selection results. " 
            ::= { brzaccVLInterferenceMitigationParameters 17 }

    brzaccVLInterferenceMitigationOutputEntry  OBJECT-TYPE
            SYNTAX BrzaccVLInterferenceMitigationOutput
            MAX-ACCESS not-accessible
            STATUS current
            DESCRIPTION
            "Applicable to 900 MHz units, 2.4 GHz units and BNB10.
             An entry in the InterferenceMitigationOutputTable." 
            INDEX { brzaccVLInterferenceMitigationOutputFrequency }
            ::= { brzaccVLInterferenceMitigationOutputTable 1 }
                                
    BrzaccVLInterferenceMitigationOutput ::= SEQUENCE { brzaccVLInterferenceMitigationOutputFrequency INTEGER,
                                                        brzaccVLInterferenceMitigationOutputScanningType INTEGER,
                                                        brzaccVLInterferenceMitigationOutputInstallationModel INTEGER,
                                                        brzaccVLInterferenceMitigationOutputNoiseFloor INTEGER,
                                                        brzaccVLInterferenceMitigationOutputDistance INTEGER,
                                                        brzaccVLInterferenceMitigationOutputPerformance INTEGER 
                                                      }

    brzaccVLInterferenceMitigationOutputFrequency OBJECT-TYPE
            SYNTAX INTEGER ( 905..925 )
            MAX-ACCESS read-only
            STATUS current
            DESCRIPTION  
            "Applicable to 900 MHz units, 2.4 GHz units and BNB10.
            The channel frequency" 
            ::= { brzaccVLInterferenceMitigationOutputEntry 1 }
            
	brzaccVLInterferenceMitigationOutputScanningType OBJECT-TYPE
            SYNTAX INTEGER { typeCCSandANFS (1), typeANFS (2), typeCCS(3), typeStatistics(4) }
            MAX-ACCESS read-only
            STATUS current
            DESCRIPTION  
            "Applicable to 900 MHz units, 2.4 GHz units and BNB10.
            Type of scan that was run" 
            ::= { brzaccVLInterferenceMitigationOutputEntry 2 }
            
     brzaccVLInterferenceMitigationOutputInstallationModel OBJECT-TYPE
            SYNTAX INTEGER { typeLOS (1), typeNearLOS (2), typeNoLOS (3) }
            MAX-ACCESS read-only
            STATUS current
            DESCRIPTION  
             "Applicable to 900 MHz units, 2.4 GHz units and BNB10.
             Specifies the Installation Model used by the cell."
            ::= { brzaccVLInterferenceMitigationOutputEntry 3 }
            
	brzaccVLInterferenceMitigationOutputNoiseFloor OBJECT-TYPE
            SYNTAX INTEGER ( -102..-55 )
            MAX-ACCESS read-only
            STATUS current
            DESCRIPTION  
            "Applicable to 900 MHz units, 2.4 GHz units and BNB10.
            Noise floor calculated for current frequency" 
            ::= { brzaccVLInterferenceMitigationOutputEntry 4 }
            
     brzaccVLInterferenceMitigationOutputDistance OBJECT-TYPE
            SYNTAX INTEGER
            MAX-ACCESS read-only
            STATUS current
            DESCRIPTION  
            "Applicable to 900 MHz units, 2.4 GHz units and BNB10.
            Estimated cell radius" 
            ::= { brzaccVLInterferenceMitigationOutputEntry 5 }
            
	brzaccVLInterferenceMitigationOutputPerformance OBJECT-TYPE
            SYNTAX INTEGER
            MAX-ACCESS read-only
            STATUS current
            DESCRIPTION  
            "Applicable to 900 MHz units, 2.4 GHz units and BNB10.
            Estimated cell performance" 
            ::= { brzaccVLInterferenceMitigationOutputEntry 6 }
            
	-- end of INTERFERENCE-MITIGATION-OUTPUT-TABLE
            
-- end of InterferenceMitigationParameters


-- Service Params
-- ==============
   brzaccVLServiceParameters       OBJECT IDENTIFIER ::= {breezeAccessVLMib 7}

--    brzaccVLMirCirOption OBJECT-TYPE
--    SYNTAX  INTEGER {disable (1),
--                     enable (2), 
--                     na (255)} 
--        MAX-ACCESS read-write
--        STATUS current
--        DESCRIPTION 
--        "Applicable to AU and SU. Read-only in SU. 
--         The setting in the AU enables/disables the MIR/CIR support 
--         feature for all SUs served by the AU."
--    ::= { brzaccVLServiceParameters 1 }

    brzaccVLMirDownlink OBJECT-TYPE
        SYNTAX  INTEGER  
        MAX-ACCESS read-write
        STATUS current
        DESCRIPTION 
        "Applicable to SU/RB only. 
         The Maximum Information Rate (MIR) from AU/BU to SU/RB.
         MIR must be above brzaccVLCirDownlink value.
         Range for set: 128 to 2,048 (Kbps) for SU-3 with SW version below 4.0,
						128 to 3,072 (Kbps) for SU-3 with SW version 4.0 and higher,				
                        128 to 3,968 (Kbps) for SU-6 with SW version less than 4.0,
                        128 to 6,016 (Kbps) for SU-6 with SW version greater than 4.0,
         	            128 to 14,976 (Kbps) for SU-24, 
         	            128 to 53,888 (Kbps) for SU-BD and SU-54,
                        128 to 13,440 (Kbps) for SU-8,
         	            128 to 6,912  (Kbps) for RB-14, 
         	            128 to 22,016 (Kbps) for RB-28,
                        128 to 107,904 (Kbps) for RB-100,
                        128 to 6,016 (Kbps) for SU-I,
         	            128 to 12,032 (Kbps) for SU-V,
         	            128 to 4,992  (Kbps) for RB-10, 
         	            128 to 1,024 (Kbps) for SU-1-BD 
         The actual value (Get) will be the entered value rounded to the nearest 
         multiple of 128 (N*128)." 
    ::= { brzaccVLServiceParameters 2 }
   
    brzaccVLMirUplink OBJECT-TYPE
        SYNTAX INTEGER  
        MAX-ACCESS read-write
        STATUS current
        DESCRIPTION 
        "Applicable to SU/RB only. 
         The Maximum Information Rate (MIR) from SU/RB to AU/BU.
         MIR must be above brzaccVLCirUplink value.
         Range for set: 128 to 2,048 (Kbps) for SU-3,
                        128 to 3,968  (Kbps) for SU-6 with SW version less than 4.0,
                        128 to 4,096  (Kbps) for SU-6 with SW version greater than 4.0,
         	            128 to 14,976 (Kbps) for SU-24, 
         	            128 to 53,888 (Kbps) for SU-BD and SU-54,
                        128 to 13,440 (Kbps) for SU-8,
         	            128 to 6,912  (Kbps) for RB-14, 
         	            128 to 22,016 (Kbps) for RB-28, 
                        128 to 107,904 (Kbps) for RB-100,
                        128 to 4,096 (Kbps) for SU-I,
         	            128 to 8,064 (Kbps) for SU-V,
                        128 to 4,992 (Kbps) for RB-10, 
                        128 to 896 (Kbps) for SU-1-BD 
		 The actual value (Get) will be the entered value rounded to the nearest 
		 multiple of 128 (N*128)." 
    ::= { brzaccVLServiceParameters 3 }

   
    brzaccVLCirDownlink OBJECT-TYPE
        SYNTAX INTEGER  
        MAX-ACCESS read-write
        STATUS current
        DESCRIPTION 
        "Applicable to SU only. 
         Not applicable to BreezeNET-B products. 
         The Committed Information Rate (CIR) from AU to SU.
         CIR must be below brzaccVLMirDownlink value.
         Range for Set: 
         0 to 2,048 (Kbps) for SU-3 with SW version below 4.0,
		 0 to 3,072 (Kbps) for SU-3 with SW version 4.0 and higher,				
         0 to 3,968 (Kbps) for SU-6 with SW version less than 4.0,
         0 to 6,016 (Kbps) for SU-6 with SW version greater than 4.0,
         0 to 14,976 (Kbps) for SU-24, 
         0 to 45,056 (Kbps) for SU-BD and SU-54,
         0 to 11,264 (Kbps) for SU-8,
         0 to 6,016 (Kbps) for SU-I,
         0 to 12,032 (Kbps) for SU-V,
		 0 to 4,992 (Kbps) for RB-10,
		 0 to 1,024 (Kbps) for SU-1-BD 
         The actual value (Get) will be the entered value rounded to the 
         nearest multiple of 128 (N*128).
		 BreezeNET-B products will return 65535."
    ::= { brzaccVLServiceParameters 4 }

   
    brzaccVLCirUplink OBJECT-TYPE	  
         SYNTAX INTEGER  
         MAX-ACCESS read-write
         STATUS current
         DESCRIPTION  
         "Applicable to SU only. 
          Not applicable to BreezeNET-B products. 
          The Committed Information Rate (CIR) from SU to AU.
          CIR must be below brzaccVLMirUplink value.
          Range for Set: 
          0 to 2,048 (Kbps) for SU-3,
          0 to 3,968  (Kbps) for SU-6 with SW version less than 4.0,
          0 to 4,096  (Kbps) for SU-6 with SW version greater than 4.0,
          0 to 14,976 (Kbps) for SU-24, 
          0 to 45,056 (Kbps) for SU-BD and SU-54,
          0 to 11,264 (Kbps) for SU-8,
          0 to 2,048 (Kbps) for SU-I,
          0 to 8,064 (Kbps) for SU-V,
		  0 to 4,992 (Kbps) for RB-10,
		  0 to 896 (Kbps) for SU-1-BD 
          The actual value (Get) will be the entered value rounded to the nearest 
          multiple of 128 (N*128).
          BreezeNET-B products will return 65535."
    ::= { brzaccVLServiceParameters 5 }


    brzaccVLMaxDelay OBJECT-TYPE
        SYNTAX INTEGER  
        MAX-ACCESS read-write
        STATUS current
        DESCRIPTION 
        "Applicable to SU only. 
         Not applicable to BreezeNET-B products.
         The maximal time packets may be delayed by the 
         CIR\MIR mechanism. Above the configured maximal period 
         the packets are discarded.
         Range: 300 to 10000 milliseconds.
         BreezeNET-B products return 65535."
    ::= { brzaccVLServiceParameters 6 }

    brzaccVLMaxBurstDuration OBJECT-TYPE
        SYNTAX INTEGER  
        MAX-ACCESS read-write
        STATUS current
        DESCRIPTION 
        "Applicable to all units. 
         The maximum time during which inactivity bonus time 
         can be accumulated for future burst transmissions.
         Range: 0 to 2000 milliseconds."
    ::= { brzaccVLServiceParameters 7 }

    brzaccVLGracefulDegradationLimit OBJECT-TYPE
        SYNTAX INTEGER  
        MAX-ACCESS read-write
        STATUS current
        DESCRIPTION 
        "Applicable to AU only. 
         Not applicable to BreezeNET-B products.
         The maximum limit for activating the graceful 
         degradation algorithm.
         Range: 0 to 70% rate of the CIR.
         BreezeNET-B products return 255."
    ::= { brzaccVLServiceParameters 8 }

    brzaccVLMirOnlyOption OBJECT-TYPE
        SYNTAX  INTEGER {disable (1), enable (2), na (255)} 
        MAX-ACCESS read-write
        STATUS current
        DESCRIPTION 
        "Applicable to AU only. 
         Not applicable to BreezeNET-B products. 
         When brzaccMirOnly is enabled, it overrides the CIR/MIR 
         algorithm for determining actual information rate and 
         forces the algorithm to operate with MIR parameter 
         settings only. When enabled, the Graceful Degradation 
         algorithm is disabled."
    ::= { brzaccVLServiceParameters 9 }


brzaccVLTrafficPrioritization OBJECT IDENTIFIER ::= {brzaccVLServiceParameters 10}

brzaccVLTrafficPriVLAN OBJECT IDENTIFIER ::= {brzaccVLTrafficPrioritization 1}

brzaccVLVLANPriorityThreshold OBJECT-TYPE
        SYNTAX  INTEGER (1..7)
        MAX-ACCESS read-write
        STATUS current
        DESCRIPTION 
        "Applicable to all units. 
        If the VLAN Priority's value of the frame is less than or equal to this
        threshold the frame will get LOW priority, otherwise the frame will get 
        HIGH priority.
        Untagged frames will get LOW priority"
    ::= { brzaccVLTrafficPriVLAN 1 }


brzaccVLTrafficPriIPToS OBJECT IDENTIFIER ::= {brzaccVLTrafficPrioritization 2}

brzaccVLToSPrioritizationOption OBJECT-TYPE
        SYNTAX  INTEGER {disable(1), ipPrecedence(2), dSCP(3) } 
        MAX-ACCESS read-write
        STATUS current
        DESCRIPTION 
		"Applicable to all units. Disable/Enable IP ToS prioritization and 
		choose the interpretation of the IP ToS field from IP header.
		ipPrecedence(2): The IP ToS field is defined by RFC791. In this 
                         case the prioritization will be done using the 
                         Precedence sub-field of IP ToS. This sub-field 
                         has 3 bits, so it can be between 0 and 7.
		dSCP(3):         The IP ToS field is defined by RFC2474. In this
                         case the prioritization will be done using the 
                         DSCP sub-field. The size of the sub-field is 6 bits, 
                         so the range is 0 to 63."
    ::= { brzaccVLTrafficPriIPToS 1 }

brzaccVLIPPrecedenceThreshold OBJECT-TYPE
        SYNTAX  INTEGER (0..7)
        MAX-ACCESS read-write
        STATUS current
        DESCRIPTION 
		"Applicable to all units. The threshold of Precedence sub-field of IP ToS 
		field from IP Header (RFC791) to be used when the ToS Prioritization 
		Option is set to IP Precedence.
		If the Precedence sub-field of a frame is less than or equal to this 
		threshold the frame will have LOW priority, otherwise it will get HIGH 
		priority."
    ::= { brzaccVLTrafficPriIPToS 2 }

brzaccVLIPDSCPThreshold OBJECT-TYPE
        SYNTAX  INTEGER (0..63)
        MAX-ACCESS read-write
        STATUS current
        DESCRIPTION 
		"Applicable to all units. The threshold of DSCP sub-field of IP ToS 
		field from IP Header (RFC2474) to be used when ToS Prioritization 
		Option is set to DSCP.
		If the DSCP sub-field of a frame is less than or equal to this 
		threshold the frame will have LOW priority, otherwise it will get 
		HIGH priority."
    ::= { brzaccVLTrafficPriIPToS 3 }
 
        
brzaccVLTrafficPriUdpTcpPortRange OBJECT IDENTIFIER ::= {brzaccVLTrafficPrioritization 3}

brzaccVLUdpTcpPortRangePrioritizationOption OBJECT-TYPE
        SYNTAX  INTEGER {disable(1), udpOnly(2), tcpOnly(3), udpANDtcp(4) } 
        MAX-ACCESS read-write
        STATUS current
        DESCRIPTION 
        "Applicable to all units. Disable/Enable Prioritization using UDP and/or
        TCP Port Ranges. 
		udpOnly(2)  : prioritization will be done only for UDP packets
		tcpOnly(3)  : prioritization will be done only for TCP packets
		udpANDtcp(4): prioritization will be done for UDP and TCP packets"
    ::= { brzaccVLTrafficPriUdpTcpPortRange 1 }

brzaccVLUdpPortRangeConfig OBJECT IDENTIFIER ::= {brzaccVLTrafficPriUdpTcpPortRange 2}

brzaccVLUdpPortPriRTPRTCP OBJECT-TYPE
        SYNTAX  INTEGER {rtpANDrtcp(1),rtpOnly(2) } 
        MAX-ACCESS read-write
        STATUS current
        DESCRIPTION 
        "Applicale to all units.
        RTP/RTCP ports prioritization option for UDP packets. 
        rtpANDrtcp(1): RTP and RTCP packets with destination port in the
                       defined port ranges will get HIGH priority
        rtpOnly(2):    only RTP packets (packets with even destination port) 
                       with destination port in the defined port ranges will get  
                       HIGH priority."
    ::= { brzaccVLUdpPortRangeConfig 1 }

brzaccVLUdpPortRangeNum OBJECT-TYPE
        SYNTAX  INTEGER 
        MAX-ACCESS read-only
        STATUS current
        DESCRIPTION 
        "Applicable to all units. The number of entries in the UDP Port Range Table"
    ::= { brzaccVLUdpPortRangeConfig 2 }
    
brzaccVLUdpPortRangeTable OBJECT-TYPE
        SYNTAX SEQUENCE OF BrzaccVLUdpPortRangeEntry
        MAX-ACCESS not-accessible
        STATUS current
        DESCRIPTION
		"Applicable to all units. A table of UDP port ranges use for prioritization. 
		The user can define up to 64 ranges.
        An entry is empty if start is 65535 and end is 0"
        ::= { brzaccVLUdpPortRangeConfig 3 }

brzaccVLUdpPortRangeEntry  OBJECT-TYPE
        SYNTAX BrzaccVLUdpPortRangeEntry
        MAX-ACCESS not-accessible
        STATUS current
        DESCRIPTION
        "Applicable to all units. A UDP Port Ranges Table entry." 
        INDEX { brzaccVLUdpPortRangeIdx }
        ::= { brzaccVLUdpPortRangeTable 1 }

BrzaccVLUdpPortRangeEntry ::= SEQUENCE {
        brzaccVLUdpPortRangeStart INTEGER,
        brzaccVLUdpPortRangeEnd INTEGER,
        brzaccVLUdpPortRangeIdx INTEGER
        }
            
brzaccVLUdpPortRangeStart OBJECT-TYPE
        SYNTAX INTEGER(0..65535)  
        MAX-ACCESS read-only
        STATUS current
        DESCRIPTION 
        "Applicable to all units. Start port of an UDP Port Range"
        ::= { brzaccVLUdpPortRangeEntry 1 }

brzaccVLUdpPortRangeEnd OBJECT-TYPE
        SYNTAX INTEGER(0..65535)  
        MAX-ACCESS read-only
        STATUS current
        DESCRIPTION 
        "Applicable to all units. End port of an UDP Port Range"
        ::= { brzaccVLUdpPortRangeEntry 2 }
           
brzaccVLUdpPortRangeIdx OBJECT-TYPE
        SYNTAX INTEGER(1..64)  
        MAX-ACCESS read-only
        STATUS current
        DESCRIPTION 
        "Applicable to all units. UDP Port Range Entry's index "
        ::= { brzaccVLUdpPortRangeEntry 3 }


brzaccVLUdpPortRangeAdd OBJECT-TYPE
        SYNTAX DisplayString (SIZE(0..250)) 
        MAX-ACCESS read-write
        STATUS current
        DESCRIPTION 
        "Applicable to all units. Add port range(s) to UDP Port Ranges Table. 
        Get operation will return the empty string. 
		A range is defined <start>-<end> or <start> where <start> is the Start 
		Port of the range and <end> is the End Port. If only <start> is 
		specified the range is <start>-<start>.
        The value of  <start> and <end> are between 0..65535.
        The user can add several ranges using a comma to separate between ranges. 
        Example: 10-256,99,987-900"
    ::= { brzaccVLUdpPortRangeConfig 4 }
    
brzaccVLUdpPortRangeDelete OBJECT-TYPE
        SYNTAX DisplayString (SIZE(0..250)) 
        MAX-ACCESS read-write
        STATUS current
        DESCRIPTION 
        "Applicable to all units. Delete port range(s) from UDP Port Ranges Table. 
        Get operation will return the empty string.
        A range is defined <start>-<end> or <start> where <start> is the Start 
        Port of the range and <end> is the End Port. If only <start> is 
        specified the range is <start>-<start>.
        The value of  <start> and <end> are between 0..65535.
        The user can delete several ranges using a comma to separate between 
        ranges.
        Example: 10-256,99,987-900"
    ::= { brzaccVLUdpPortRangeConfig 5 }

brzaccVLUdpPortRangeDeleteAll OBJECT-TYPE
        SYNTAX INTEGER { deleteAll(1), cancelOperation(2) }
        MAX-ACCESS read-write
        STATUS current
        DESCRIPTION 
		"Applicable to all units. Delete all entries form UDP Port Ranges Table. 
		Get operation will return 1"
    ::= { brzaccVLUdpPortRangeConfig 6 }



brzaccVLTcpPortRangeConfig OBJECT IDENTIFIER ::= {brzaccVLTrafficPriUdpTcpPortRange 3}

brzaccVLTcpPortPriRTPRTCP OBJECT-TYPE
        SYNTAX  INTEGER {rtpANDrtcp(1),rtpOnly(2) } 
        MAX-ACCESS read-write
        STATUS current
        DESCRIPTION 
        "Applicable to all units. RTP/RTCP ports prioritization option for TCP packets. 
        rtpANDrtcp(1): RTP and RTCP packets with destination port in the
                       defined port ranges will get HIGH priority
        rtpOnly(2):    only RTP packets (packets with even destination port) 
                       with destination port in the defined port ranges will get  
                       HIGH priority."
    ::= { brzaccVLTcpPortRangeConfig 1 }

brzaccVLTcpPortRangeNum OBJECT-TYPE
        SYNTAX  INTEGER 
        MAX-ACCESS read-only
        STATUS current
        DESCRIPTION 
        "Applicable to all units. The number of entries in the TCP Port Range Table"
    ::= { brzaccVLTcpPortRangeConfig 2 }
    
brzaccVLTcpPortRangeTable OBJECT-TYPE
        SYNTAX SEQUENCE OF BrzaccVLTcpPortRangeEntry
        MAX-ACCESS not-accessible
        STATUS current
        DESCRIPTION
        "Table of TCP Port Ranges use for prioritization.
        The user can define up to 64 ranges.
        An entry is empty if start is 65535 and end is 0"
        ::= { brzaccVLTcpPortRangeConfig 3 }

brzaccVLTcpPortRangeEntry  OBJECT-TYPE
        SYNTAX BrzaccVLTcpPortRangeEntry
        MAX-ACCESS not-accessible
        STATUS current
        DESCRIPTION
        "Applicable to all units. A TCP Port Ranges Table entry." 
        INDEX { brzaccVLTcpPortRangeIdx }
        ::= { brzaccVLTcpPortRangeTable 1 }

BrzaccVLTcpPortRangeEntry ::= SEQUENCE {
        brzaccVLTcpPortRangeStart INTEGER,
        brzaccVLTcpPortRangeEnd INTEGER,
        brzaccVLTcpPortRangeIdx INTEGER
        }
            
brzaccVLTcpPortRangeStart OBJECT-TYPE
        SYNTAX INTEGER(0..65535)  
        MAX-ACCESS read-only
        STATUS current
        DESCRIPTION 
        "Applicable to all units. Start port of a TCP Port Range"
        ::= { brzaccVLTcpPortRangeEntry 1 }

brzaccVLTcpPortRangeEnd OBJECT-TYPE
        SYNTAX INTEGER(0..65535)  
        MAX-ACCESS read-only
        STATUS current
        DESCRIPTION 
        "Applicable to all units. End port of a TCP Port Range"
        ::= { brzaccVLTcpPortRangeEntry 2 }
           
brzaccVLTcpPortRangeIdx OBJECT-TYPE
        SYNTAX INTEGER(1..64)  
        MAX-ACCESS read-only
        STATUS current
        DESCRIPTION 
        "Applicable to all units. TCP Port Range Entry's index"
        ::= { brzaccVLTcpPortRangeEntry 3 }


brzaccVLTcpPortRangeAdd OBJECT-TYPE
        SYNTAX DisplayString (SIZE(0..250)) 
        MAX-ACCESS read-write
        STATUS current
        DESCRIPTION 
        "Applicable to all units. Add port range(s) to TCP Port Ranges Table. 
        Get operation will return the empty string. 
		A range is defined <start>-<end> or <start> where <start> is the Start 
		Port of the range and <end> is the End Port. If only <start> is specified 
		the range is <start>-<start>.
        The value of  <start> and <end> are between 0..65535.
        The user can add several ranges using comma to separate between ranges.
        Example: 10-256,99,987-900"
    ::= { brzaccVLTcpPortRangeConfig 4 }
    
brzaccVLTcpPortRangeDelete OBJECT-TYPE
        SYNTAX DisplayString (SIZE(0..250)) 
        MAX-ACCESS read-write
        STATUS current
        DESCRIPTION 
		"Applicable to all units. Delete port range(s) from TCP Port Ranges Table. 
		Get operation will return the empty string.
        A range is defined <start>-<end> or <start> where <start> is the Start 
        Port of the range and <end> is the End Port. If only <start> is specified 
        the range is <start>-<start>.
        The value of  <start> and <end> are between 0..65535.
        The user can delete several ranges using comma to separate between ranges.
        Example: 10-256,99,987-900"
    ::= { brzaccVLTcpPortRangeConfig 5 }

brzaccVLTcpPortRangeDeleteAll OBJECT-TYPE
        SYNTAX INTEGER { deleteAll(1), cancelOperation(2) }
        MAX-ACCESS read-write
        STATUS current
        DESCRIPTION 
        "Applicable to all units. Delete all entries form TCP Port Ranges Table
        Get operation will return 1"
    ::= { brzaccVLTcpPortRangeConfig 6 }

brzaccVLWirelessLinkPrioritization OBJECT IDENTIFIER ::= {brzaccVLTrafficPrioritization 4}

brzaccVLWirelessLinkPrioritizationOption OBJECT-TYPE
            SYNTAX  INTEGER  { disable(1), enable(2), na(255) }
            MAX-ACCESS read-write      
            STATUS current       
            DESCRIPTION  
            "Applicable only to AU with a license for the Wireless Link Prioritization feature and to BU-100. 
             Enable/disable the traffic prioritization over the 
             Wireless Link"
            ::= { brzaccVLWirelessLinkPrioritization  1}

brzaccVLlowPriorityAIFS OBJECT-TYPE
            SYNTAX  INTEGER  (3..50)
            MAX-ACCESS read-write      
            STATUS current       
            DESCRIPTION  
            "Applicable only to AU with a license for the Wireless Link Prioritization feature and to BU-100. 
            Applicable only if the Wireless Link Prioritization Option is enabled.
            Define the AIFS (Arbitration Inter-frame Space) that will be used   
            for transmitting Low Priority Traffic"
            ::= { brzaccVLWirelessLinkPrioritization  2}

brzaccVLHWRetriesHighPriority OBJECT-TYPE
            SYNTAX  INTEGER (0..14)
            MAX-ACCESS read-write      
            STATUS current       
            DESCRIPTION  
            "Applicable only to AU with a license for the Wireless Link Prioritization feature and to BU-100.
            Applicable only if the Wireless Link Prioritization Option is enabled. 
            Defines the Maximum number of HW Retries for a unicast data packet 
            that has High Priority"
            ::= { brzaccVLWirelessLinkPrioritization  3}
            
brzaccVLHWRetriesLowPriority OBJECT-TYPE
            SYNTAX  INTEGER (0..14)
            MAX-ACCESS read-write      
            STATUS current       
            DESCRIPTION  
            "Applicable only to AU with a license for the Wireless Link Prioritization feature and to BU-100.
            Applicable only if the Wireless Link Prioritization Option is enabled. 
            Defines the Maximum number of HW Retries for a unicast data packet 
            that has Low Priority"
            ::= { brzaccVLWirelessLinkPrioritization 4}
            
brzaccVLAUBurstDurationHighPriority OBJECT-TYPE
            SYNTAX  INTEGER  (0..40)
            MAX-ACCESS read-write      
            STATUS current       
            DESCRIPTION  
            "Applicable only to AU with a license for the Wireless Link Prioritization feature and to BU-100. 
            Applicable only if the Wireless Link Prioritization Option is enabled.
             Defines the Maximum duration of burst that can be done by AU with 
             High Priority packets.
             The time is given in 250 microseconds units"
            ::= { brzaccVLWirelessLinkPrioritization  5}
            
brzaccVLAUBurstDurationLowPriority OBJECT-TYPE
            SYNTAX  INTEGER  (0..40)
            MAX-ACCESS read-write      
            STATUS current       
            DESCRIPTION  
            "Applicable only to AU with a license for the Wireless Link Prioritization feature and to BU-100. 
            Applicable only if the Wireless Link Prioritization Option is enabled.
             Defines the Maximum duration of burst that can be done by AU 
             with Low Priority packets.
             The time is given in 250 microseconds units"
            ::= { brzaccVLWirelessLinkPrioritization  6}
            
brzaccVLSUBurstDurationHighPriority OBJECT-TYPE
            SYNTAX  INTEGER (0..40)
            MAX-ACCESS read-write      
            STATUS current       
            DESCRIPTION  
            "Applicable only to AU with a license for the Wireless Link Prioritization feature and to BU-100. 
            Applicable only if the Wireless Link Prioritization Option is enabled.
            Defines the Maximum duration of burst that can be done by SU/RB 
            with High Priority packets.
            The parameter is configurable in AU and the SUs/RB will learn it 
            form AU/BU.
            The time is given in 250 microseconds units"
            ::= { brzaccVLWirelessLinkPrioritization  7}

brzaccVLSUBurstDurationLowPriority OBJECT-TYPE
            SYNTAX  INTEGER (0..40)
            MAX-ACCESS read-write      
            STATUS current       
            DESCRIPTION  
            "Applicable only to AU with a license for the Wireless Link Prioritization feature and to BU-100. 
            Applicable only if the Wireless Link Prioritization Option is enabled.
            Defines the Maximum duration of burst that can be done by SU/RB 
            with High Priority packets.
            The parameter is configurable in AU/BU and the SUs/RB will learn it 
            from AU/BU.
            The time is given in 250 microseconds units"
            ::= { brzaccVLWirelessLinkPrioritization  8}


brzaccVLTrafficPriIpRange  OBJECT IDENTIFIER ::= {brzaccVLTrafficPrioritization 5}

brzaccVLTrafficPriIpRangeOption  OBJECT-TYPE
        SYNTAX  INTEGER {disable(1), ipSource(2), ipDestination(3), ipSourceOrDestination(4) } 
        MAX-ACCESS  read-write
        STATUS  current
        DESCRIPTION 
        "Applicable to all units.
        disable(1):       Disable IP Range Prioritization.
        ipSource(2):      Prioritization of the IP protocol packets with
                          IP source address in range defined by following two OIDs.
        ipDestination(3): Prioritization of the IP protocol packets with
                          IP destination address in range defined by following two OIDs.
        ipSourceOrDestination(4): Prioritization of the IP protocol packets with
                          IP source address or  IP destination address
                          in range defined by following two OIDs."
    ::= { brzaccVLTrafficPriIpRange 1 }

brzaccVLTrafficPriIpRangeIpAddress  OBJECT-TYPE
        SYNTAX  IpAddress  
        MAX-ACCESS read-write
        STATUS current
        DESCRIPTION 
        "Applicable to all units.
        Defines the IP Address for the IP Range Prioritization.
        IP protocol packets with IP source address in range defined by Address and Mask
        will get High Priority."
    ::= { brzaccVLTrafficPriIpRange 2 }

brzaccVLTrafficPriIpRangeIpMask  OBJECT-TYPE
        SYNTAX  IpAddress  
        MAX-ACCESS read-write
        STATUS current
        DESCRIPTION 
        "Applicable to all units.
        Defines the IP Mask for the IP Range Prioritization.
        IP protocol packets with IP source address in range defined by Address and Mask
        will get High Priority."
    ::= { brzaccVLTrafficPriIpRange 3 }


--DRAP BEGIN

brzaccVLDrap OBJECT IDENTIFIER ::= { brzaccVLServiceParameters 11 }

brzaccVLDrapSupport OBJECT-TYPE
		SYNTAX INTEGER {disable(1), enable(2), na(255)}
		MAX-ACCESS read-write
		STATUS current
		DESCRIPTION
		"Applicable to AU. Not applicable to BreezeNET B products
		Disable/Enable the DRAP feature" 
		::= { brzaccVLDrap 1 }

brzaccVLDrapUdpPort OBJECT-TYPE
		SYNTAX INTEGER (8000..8200)
		MAX-ACCESS read-write
		STATUS current
		DESCRIPTION
		"Applicable to AU when DRAP support is enabled. 
		Not applicable to BreezeNET B products. 
		The UDP port used for the DRAP server"
		::= { brzaccVLDrap 2 }

brzaccVLDrapMaxNumberOfVoiceCalls OBJECT-TYPE
		SYNTAX INTEGER (0..255)
		MAX-ACCESS read-write
		STATUS current
		DESCRIPTION
		"Applicable to AU when DRAP support is enabled. 
		Not applicable to BreezeNET B products. 
		The maximum number of voice calls that can be supported by the AU"
		::= { brzaccVLDrap 3 }

brzaccVLDrapTTL OBJECT-TYPE
		SYNTAX INTEGER (1..255)
		MAX-ACCESS read-write
		STATUS current
		DESCRIPTION
		"Applicable to AU when DRAP support is enabled. 
		Not applicable to BreezeNET B products. 
		The maximum time between two allocation requests"
		::= { brzaccVLDrap 4 }

brzaccVLDrapNoOfActiveVoiceCalls OBJECT-TYPE
        SYNTAX INTEGER
        MAX-ACCESS read-only
        STATUS current
        DESCRIPTION 
		"Applicable to AU when DRAP support is enabled. 
		Not applicable to BreezeNET B products. 
		The current total number of  active voice calls."
        ::= { brzaccVLDrap 5 }


--DRAP END

brzaccVLLowPriorityTrafficMinimumPercent OBJECT-TYPE
		SYNTAX INTEGER (0..100)
		MAX-ACCESS read-write
		STATUS current
		DESCRIPTION 
		"The minimum percent of the traffic rate that is allocated to the low priority traffic"
		::= { brzaccVLServiceParameters 12 }
				

brzaccVLSUEZMirDownlink OBJECT-TYPE
        SYNTAX  INTEGER  
        MAX-ACCESS read-write
        STATUS current
        DESCRIPTION 
        "Applicable to AU only. 
         The Maximum Information Rate (MIR) from AU to SU-EZ.
         Range for set: 128 to 12,032 (Kbps).
         The actual value (Get) will be the entered value rounded to the nearest 
         multiple of 128 (N*128).
         This parameter is not runtime. The SU-EZ must be re-associated
         in order to re-apply this parameter." 
    ::= { brzaccVLServiceParameters 13 }
   
brzaccVLMIRThresholdPercent OBJECT-TYPE
        SYNTAX  INTEGER (0..100)  
        MAX-ACCESS read-write
        STATUS current
        DESCRIPTION 
        "Applicable to AU only. 
		MIR Threshold Percent" 
    ::= { brzaccVLServiceParameters 14 }


-- Proportional IR Parameters

brzaccVLProportionalIRParameters   OBJECT IDENTIFIER ::= { brzaccVLServiceParameters 15 }

brzaccVLProportionalIRFactor OBJECT-TYPE
            SYNTAX INTEGER  (0..100)
            MAX-ACCESS read-write
            STATUS current
            DESCRIPTION 
            "Applicable to SU only.
            Proportional IR Factor (percentage).
            The weight used for computing the used MIR/CIR values." 
         ::= {brzaccVLProportionalIRParameters  1}

brzaccVLProportionalIRUpdatePeriod OBJECT-TYPE
            SYNTAX INTEGER  (1..30)
            MAX-ACCESS read-write
            STATUS current
            DESCRIPTION 
            "Applicable to SU only.
            The period of time (in minutes) for periodical computation of used MIR/CIR values."
         ::= {brzaccVLProportionalIRParameters  2}

brzaccVLProportionalIRThresholdPercentage OBJECT-TYPE
            SYNTAX INTEGER  (0..100)
            MAX-ACCESS read-write
            STATUS current
            DESCRIPTION 
            "Applicable to SU only.
            When the difference between two consecutive calculations of used MIR/CIR value
            is bigger than this percentage from value, the new computed MIR/CIR values
            will be considered." 
         ::= {brzaccVLProportionalIRParameters  3}

brzaccVLProportionalIRThresholdRate OBJECT-TYPE
            SYNTAX INTEGER  (1..8)
            MAX-ACCESS read-write
            STATUS current
            DESCRIPTION 
            "Applicable to SU only.
            The new computed MIR/CIR values will be considered only when the rate,
            on uplink or downlink respectively, is lower than the rate corresponding
            to this threshold rate." 
         ::= {brzaccVLProportionalIRParameters  4}


-- User Filtering Params
-- =====================
   brzaccVLUserFilterParams   OBJECT IDENTIFIER ::= {breezeAccessVLMib 8}

    brzaccVLUserFilterOption OBJECT-TYPE
            SYNTAX INTEGER { disable (1), 
                             ipOnly (2), 
                             userDefinedAddrOnly (3), 
                             pPPoEOnly (4), 
                             na (255) } 
            MAX-ACCESS read-write
            STATUS current
            DESCRIPTION 
            "Applicable to SU, RB and AU. 
             Not applicable to AU on 900 MHz. 
             Defines user-filtering options.
             disable: No filtering.
             iPOnly: Only IP protocol frames pass. 
             userDefinedAddrOnly: Only ip frames to/from user defined IP 
                                  addresses pass.
             pPPoE Only: Only PPPoE frames pass. This option is not applicable for AU"
             ::= { brzaccVLUserFilterParams 1 }

    brzaccVLIpFilterTable OBJECT-TYPE
            SYNTAX SEQUENCE OF BrzaccVLIpFilterEntry
            MAX-ACCESS not-accessible
            STATUS current
            DESCRIPTION
            "Starting with version 5.0, this is deprecated. 
            Use brzaccVLNewIpFilterTable instead.
			Applicable to SU, RB and AU. 
             Not applicable to AU on 900 MHz. 
             An IP Filter Table of up to 8 user defined addresses, 
             or address groups, to be used if the selected User 
             Filtering option is userDefinedAddrOnly." 
            ::= { brzaccVLUserFilterParams 2 }

    brzaccVLIpFilterEntry  OBJECT-TYPE
            SYNTAX BrzaccVLIpFilterEntry
            MAX-ACCESS not-accessible
            STATUS current
            DESCRIPTION
            "Applicable to SU, RB and AU. 
             Not applicable to AU on 900 MHz.
             An IP Filter Table entry." 
            INDEX { brzaccVLIpFilterIdx }
            ::= { brzaccVLIpFilterTable 1 }

   BrzaccVLIpFilterEntry ::= SEQUENCE {
            brzaccVLIpID   IpAddress,
            brzaccVLMaskID IpAddress,
            brzaccVLIpFilterRange INTEGER,
            brzaccVLIpFilterIdx INTEGER
            }
               
    brzaccVLIpID   OBJECT-TYPE
            SYNTAX IpAddress  
            MAX-ACCESS read-write
            STATUS current
            DESCRIPTION 
            "Applicable to SU, RB and AU. 
             Not applicable to AU on 900 MHz.
             An IP address of an IP Filter Table entry."
           ::= { brzaccVLIpFilterEntry 1 }

    brzaccVLMaskID OBJECT-TYPE
            SYNTAX IpAddress  
            MAX-ACCESS read-write
            STATUS current
            DESCRIPTION 
            "Applicable to SU, RB and AU. 
             Not applicable to AU on 900 MHz.
             An IP Mask of an IP Filter Table entry. Either a mask 
             or a range, but not both can be used to define an 
             address group. If the range is other than 0, than the mask is 
             ignored and only the range value is used to define the address group."
           ::= { brzaccVLIpFilterEntry 2 }
   
    brzaccVLIpFilterRange OBJECT-TYPE
            SYNTAX INTEGER 
            MAX-ACCESS read-write
            STATUS current
            DESCRIPTION 
            "Applicable to SU, RB and AU. 
             Not applicable to AU on 900 MHz.
             An addresses range for the IP Filter Table entry. The 
             first address in the range is the IP address.
             0 means that the range is not used.  
             Either a mask or a range, but not both can be used to 
             define an address group.
			 If the range is other than 0, than the mask is ignored and 
			 only the range value is used to define the address group.
             Range: 0 to 255."
            ::= { brzaccVLIpFilterEntry 3 }

    brzaccVLIpFilterIdx   OBJECT-TYPE
            SYNTAX INTEGER  (1..8)
            MAX-ACCESS read-only
            STATUS current
            DESCRIPTION 
            "Applicable to SU, RB and AU. 
             Not applicable to AU on 900 MHz.
             A table index for the IP Filter Table entry." 
         ::= { brzaccVLIpFilterEntry 4 }

    brzaccVLDeleteOneUserFilter OBJECT-TYPE
            SYNTAX  INTEGER { deletefirstEntry  (1), deletesecondEntry (2), 
                              deletethirdEntry  (3), deletefourthEntry (4), 
                              deletefifthEntry  (5), deletesixthEntry (6), 
                              deleteseventhEntry(7), deleteeighthEntry (8), 
                              cancelOperation   (9), na (255) } 
 
            MAX-ACCESS read-write
            STATUS current
            DESCRIPTION 
            "Applicable to SU/RB and AU-EZ only.  
             Deletes a single selected entry from the IP Filter 
             Table."
            ::= { brzaccVLUserFilterParams 3 }

    brzaccVLDeleteAllUserFilters OBJECT-TYPE
            SYNTAX  INTEGER { deleteAll (1), cancelOperation (2),  
                              na (255) } 
            MAX-ACCESS read-write
            STATUS current
            DESCRIPTION 
            "Applicable to SU, RB and AU. 
             Not applicable to AU on 900 MHz.
             Deletes all entries from the IP Filter Table."
            ::= { brzaccVLUserFilterParams 4 }

    brzaccVLDHCPUnicastOverrideFilter OBJECT-TYPE
            SYNTAX  INTEGER { disable (1), enable (2), na (255) } 
            MAX-ACCESS read-write
            STATUS current
            DESCRIPTION  
            "Applicable to SU, RB and AU. 
             Not applicable to AU on 900 MHz.
             Enables or disables the unicast DHCP messages, 
             overriding the IP Filtering option." 
            ::= { brzaccVLUserFilterParams 5 }


    brzaccVLNewIpFilterTable OBJECT-TYPE
            SYNTAX SEQUENCE OF BrzaccVLNewIpFilterEntry
            MAX-ACCESS not-accessible
            STATUS current
            DESCRIPTION
            "Applicable to SU, RB and AU. 
             Not applicable to AU on 900 MHz.
             An IP Filter Table of up to 8 user defined addresses, 
             or address groups, to be used if the selected User 
             Filtering option is userDefinedAddrOnly." 
            ::= { brzaccVLUserFilterParams 6 }

    brzaccVLNewIpFilterEntry  OBJECT-TYPE
            SYNTAX BrzaccVLNewIpFilterEntry
            MAX-ACCESS not-accessible
            STATUS current
            DESCRIPTION
            "Applicable to SU, RB and AU. 
             Not applicable to AU on 900 MHz.
             An IP Filter Table entry." 
            INDEX { brzaccVLNewIpID }
            ::= { brzaccVLNewIpFilterTable 1 }

   BrzaccVLNewIpFilterEntry ::= SEQUENCE {
            brzaccVLNewIpID   IpAddress,
            brzaccVLNewMaskID IpAddress,
            brzaccVLNewIpFilterRange INTEGER,
            brzaccVLNewIpFilterCommand INTEGER
            }
               
    brzaccVLNewIpID   OBJECT-TYPE
            SYNTAX IpAddress  
            MAX-ACCESS read-only
            STATUS current
            DESCRIPTION 
            "Applicable to SU, RB and AU. 
             Not applicable to AU on 900 MHz.
             An IP address of an IP Filter Table entry."
           ::= { brzaccVLNewIpFilterEntry 1 }

    brzaccVLNewMaskID OBJECT-TYPE
            SYNTAX IpAddress  
            MAX-ACCESS read-write
            STATUS current
            DESCRIPTION 
            "Applicable to SU, RB and AU. 
             Not applicable to AU on 900 MHz.
             An IP Mask of an IP Filter Table entry. Either a mask 
             or a range, but not both can be used to define an 
             address group. If the range is other than 0, than the mask is 
             ignored and only the range value is used to define the address group."
           ::= { brzaccVLNewIpFilterEntry 2 }
   
    brzaccVLNewIpFilterRange OBJECT-TYPE
            SYNTAX INTEGER 
            MAX-ACCESS read-write
            STATUS current
            DESCRIPTION 
            "Applicable to SU, RB and AU. 
             Not applicable to AU on 900 MHz.
             An addresses range for the IP Filter Table entry. The 
             first address in the range is the IP address.
             0 means that the range is not used.  
             Either a mask or a range, but not both can be used to 
             define an address group.
			 If the range is other than 0, than the mask is ignored and 
			 only the range value is used to define the address group.
             Range: 0 to 255."
            ::= { brzaccVLNewIpFilterEntry 3 }

    brzaccVLNewIpFilterCommand   OBJECT-TYPE
            SYNTAX INTEGER  { active(1), notInService(2), notReady(3), createAndGo(4), createAndWait(5), destroy(6) }
            MAX-ACCESS read-write
            STATUS current
            DESCRIPTION 
            "Applicable to SU, RB and AU. 
             Not applicable to AU on 900 MHz.
             Supports only active(1), createAndGo(4) and destroy(6).
             A command for the IP Filter Table entry." 
         ::= { brzaccVLNewIpFilterEntry 4 }

    brzaccVLDHCPPPPoEOverrideFilter OBJECT-TYPE
            SYNTAX  INTEGER { disable (1), enable (2), na (255) } 
            MAX-ACCESS read-write
            STATUS current
            DESCRIPTION  
            "Applicable to SU, RB and AU. 
             Not applicable to AU on 900 MHz.
             Enables or disables the PPPoE messages, 
             overriding the IP Filtering option." 
            ::= { brzaccVLUserFilterParams 7 }
            	 
-- Security Params
-- ==================
brzaccVLSecurityParameters     OBJECT IDENTIFIER ::= {breezeAccessVLMib 9}

    brzaccVLAuthenticationAlgorithm OBJECT-TYPE
            SYNTAX  INTEGER  {openSystem(1) , sharedKey(2)}
            MAX-ACCESS read-write
            STATUS current
            DESCRIPTION  
            "Applicable to all units.
            Enables/disables the authentication encryption option.
            openSystem: Authentication messages are not encrypted.
            sharedKey : Authentication messages are encrypted "
            ::= { brzaccVLSecurityParameters 1 }

    brzaccVLSUDefaultKeyID OBJECT-TYPE
            SYNTAX  INTEGER  
            MAX-ACCESS read-write
            STATUS current
            DESCRIPTION  
            "Applicable to SU/RB only.
			 The key to be used for encryption of authentication messages 
			 and/or data.
             Range: 1 to 4. "
            ::= { brzaccVLSecurityParameters 2 }

    brzaccVLDataEncryptionOption OBJECT-TYPE
            SYNTAX  INTEGER  {disable(1) , enable(2)}
            MAX-ACCESS read-write
            STATUS current
            DESCRIPTION  
            "Applicable to all units.
             Enables/disables the data encryption option. "
            ::= { brzaccVLSecurityParameters 3 }

    brzaccVLAUDefaultMulticastKeyID OBJECT-TYPE
            SYNTAX  INTEGER  
            MAX-ACCESS read-write
            STATUS current
            DESCRIPTION  
            "Applicable to AU/BU only.
             The key to be used for encryption of multicasts and broadcasts."
            ::= { brzaccVLSecurityParameters 4 }

    brzaccVLSecurityMode OBJECT-TYPE
            SYNTAX  INTEGER   {wep(1) , aesOCB(2), fips197(3)}
            MAX-ACCESS read-write
            STATUS current
            DESCRIPTION  
            "Applicable to all units. The fips197 option is applicable only to units with a license to
             use FIPS 197 algorithm.
             The encryption algorithm to be used for authentication messages 
             and/or data encryption.
             The aesOCB option is not applicable for AU-EZ."
            ::= { brzaccVLSecurityParameters 5 }


    brzaccVLAuthenticationPromiscuousMode OBJECT-TYPE
            SYNTAX  INTEGER   {disable(1) , enable(2)}
            MAX-ACCESS read-write
            STATUS current
            DESCRIPTION  
            "Applicable to AU/BU only.
             Enables/disable the promiscuous mode allowing authentication of 
             and communication with all SUs/RB regardless of their security 
             parameters."
            ::= { brzaccVLSecurityParameters 6 }


    brzaccVLKey1 OBJECT-TYPE
            SYNTAX  DisplayString (SIZE(32))
            MAX-ACCESS read-write
            STATUS current
            DESCRIPTION  
            "Applicable to all units.
             Key number 1. Accessible only with SNMP Write Community String 
             (administrator password).
             Valid values: 32 hexadecimal digits."
            ::= { brzaccVLSecurityParameters 7 }

    brzaccVLKey2 OBJECT-TYPE
            SYNTAX  DisplayString (SIZE(32))
            MAX-ACCESS read-write
            STATUS current
            DESCRIPTION  
            "Applicable to all units.
             Key number 2. Accessible only with SNMP Write Community String 
             (administrator password).
             Valid values: 32 hexadecimal digits."
            ::= { brzaccVLSecurityParameters 8 }

    brzaccVLKey3 OBJECT-TYPE
            SYNTAX  DisplayString (SIZE(32))
            MAX-ACCESS read-write
            STATUS current
            DESCRIPTION  
            "Applicable to all units.
             Key number 3. Accessible only with SNMP Write Community String 
             (administrator password).
             Valid values: 32 hexadecimal digits."
            ::= { brzaccVLSecurityParameters 9 }

    brzaccVLKey4 OBJECT-TYPE
            SYNTAX  DisplayString (SIZE(32))
            MAX-ACCESS read-write
            STATUS current
            DESCRIPTION  
            "Applicable to all units.
             Key number 4. Accessible only with SNMP Write Community String 
             (administrator password).
             Valid values: 32 hexadecimal digits."
            ::= { brzaccVLSecurityParameters 10 }

    brzaccVLSecurityModeSupport OBJECT-TYPE
            SYNTAX  INTEGER (0..7)
            MAX-ACCESS read-only
            STATUS current
            DESCRIPTION  
            "Applicable to all units. Returns types of encryption that are supported.
            0 - no encryption
            1 - WEP
            2 - AES OCB
            3 - WEP and AES OCB
            4 - FIPS-197
            5 - FIPS-197 and WEP
            6 - FIPS-197 and AES OCB
            7 - FIPS-197, AES OCB and WEP"
            ::= { brzaccVLSecurityParameters 12 }

--brzaccVLSecurityPermission     OBJECT IDENTIFIER ::= {brzaccVLSecurityParameters 12}
--
--    brzaccVLDataEncryptionPermission   OBJECT-TYPE
--            SYNTAX INTEGER  {permitted(1), notPermitted(2)}
--            MAX-ACCESS read-only
--            STATUS current
--            DESCRIPTION 
--            "."
--           ::= { brzaccVLSecurityPermission 1 }
--
--    brzaccVLEncryptionByAESPermission   OBJECT-TYPE
--            SYNTAX INTEGER  {permitted(1), notPermitted(2)}
--            MAX-ACCESS read-only
--            STATUS current
--            DESCRIPTION 
--            "."
--           ::= { brzaccVLSecurityPermission 2 }
--
-- 
--    brzaccVLAuthenticationBySharedKeyAlgorithmPermission   OBJECT-TYPE
--            SYNTAX INTEGER  {permitted(1), notPermitted(2)}
--            MAX-ACCESS read-only
--            STATUS current
--            DESCRIPTION 
--            "."
--           ::= { brzaccVLSecurityPermission 3 }


-- Performance Params
-- ==================
brzaccVLPerformanceParams     OBJECT IDENTIFIER ::= {breezeAccessVLMib 10}

    brzaccVLRTSThreshold OBJECT-TYPE
            SYNTAX  INTEGER  
            MAX-ACCESS read-write
            STATUS current
            DESCRIPTION  
            "Applicable to SU and AU. 
             Not applicable to BreezeNET-B products. 
             The minimum frame size that requires an RTS/CTS handshake.            
             Range: For units bearing SW version 3.0 and above: 20 to 3400 bytes,
			 for previous SW versions 20 to 1600 bytes.
             BreezeNET-B products return 65535."
            ::= { brzaccVLPerformanceParams 1 }

    brzaccVLMinContentionWindow OBJECT-TYPE
            SYNTAX  INTEGER  
            MAX-ACCESS read-write
            STATUS current
            DESCRIPTION  
            "Applicable to SU and AU. 
             For units bearing SW version 4.0 and above applicable to 
             BreezeNET-B products, for previous SW versions not applicable 
             to BreezeNET-B products. 
             The initial value to be used by the contention window calculation 
             algorithm.
             Value must be 0 or power of 2 minus 1 (7,15,31...).
             Range: 0 to 1023, excluding 1 and 3.
             BreezeNET-B products with SW version below 4.0 return 65535."
            ::= { brzaccVLPerformanceParams 3 }

    brzaccVLMaxContentionWindow OBJECT-TYPE
            SYNTAX  INTEGER  
            MAX-ACCESS read-write
            STATUS current
            DESCRIPTION  
            "Applicable to SU and AU. 
             For units bearing SW version 4.0 and above applicable to 
             BreezeNET-B products, for previous SW versions not applicable 
             to BreezeNET-B products. 
             The maximum value to be used by the contention window calculation 
             algorithm.
             Value must be power of 2 minus 1 (7,15,31...)
             Range: 7 to 1023."
            ::= { brzaccVLPerformanceParams 4 }

    brzaccVLMaximumModulationLevel OBJECT-TYPE
            SYNTAX  INTEGER { level1 (1), 
                              level2 (2), 
                              level3 (3), 
                              level4 (4), 
                              level5 (5), 
                              level6 (6), 
                              level7 (7),
                              level8 (8)
                            } 
            MAX-ACCESS read-write
            STATUS current
            DESCRIPTION  
            "Applicable to all units.
             If the Adaptive Modulation algorithm is enabled, it sets the 
             Maximum Modulation Level to be used.
             If The Modulation algorithm is disabled, it sets the Fixed 
             Modulation Level to be used.
			 The range is 1 to 8. 8 is not applicable for units with HW revision A." 
            ::= { brzaccVLPerformanceParams 5 }

    brzaccVLMulticastModulationLevel OBJECT-TYPE
            SYNTAX  INTEGER { level1 (1), 
                              level2 (2), 
                              level3 (3), 
                              level4 (4), 
                              level5 (5), 
                              level6 (6), 
                              level7 (7),
                              level8 (8) 
                            } 
 
            MAX-ACCESS read-write
            STATUS current
            DESCRIPTION  
            "Applicable to AU/BU only.
             The modulation level for multicast and broadcast data frames.
			 The range is 1 to 8.
			 8 is not applicable for units with HW revision A." 
            ::= { brzaccVLPerformanceParams 6 }

    brzaccVLAvgSNRMemoryFactor  OBJECT-TYPE
            SYNTAX DisplayString	 
            MAX-ACCESS read-write
            STATUS current
            DESCRIPTION  
            "Applicable to all units.
			 The weight of history in average SNR calculation.
			 The higher is the value, the higher is the weight of history.
             Range: -1 (Disregard History) to 32."
            ::= { brzaccVLPerformanceParams 7 }

    brzaccVLHardwareRetries OBJECT-TYPE
            SYNTAX  INTEGER  
            MAX-ACCESS read-write
            STATUS current
            DESCRIPTION  
            "Applicable to all units.
             Not applicable if Wireless Link Prioritization is enabled.
             The maximum number of trials to transmit an unacknowledged 
             frame in each Hardware Retrial phase.
             Range : 1 to 14." 
            ::= { brzaccVLPerformanceParams 8 }


brzaccVLAdaptiveModulationParams     OBJECT IDENTIFIER ::= {brzaccVLPerformanceParams 9}

    brzaccVLAdaptiveModulationAlgorithmOption OBJECT-TYPE
            SYNTAX  INTEGER  {   disable (1) , enable (2), na (255) }
            MAX-ACCESS read-write      
            STATUS current       
            DESCRIPTION  
            "Applicable to all units. 
             Enables/disables the adaptive modulation level decision mechanism."
            ::= { brzaccVLAdaptiveModulationParams  1 }


    brzaccVLSoftwareRetrySupport OBJECT-TYPE
            SYNTAX  INTEGER  {   disable (1) , enable (2), na (255) }
            MAX-ACCESS read-write      
            STATUS current       
            DESCRIPTION  
            "Applicable to all units. 
             Read-only for units with version 2.0. 
             Not applicable for units with SW version 3.0 and higher. 
             The status of the Software Retry mechanism. 
             Enabled when the Adaptive Modulation algorithm is enabled and 
             the Burst Mode Option is disabled. Otherwise it is disabled." 
            ::= { brzaccVLAdaptiveModulationParams  2 }


    brzaccVLNumOfSoftwareRetries OBJECT-TYPE
            SYNTAX  INTEGER { na (255) }
            MAX-ACCESS read-write 
            STATUS current
            DESCRIPTION  
            "Applicable to all units. 
             Read-only for units with version 2.0. 
             Not applicable for units with SW version 3.0 and higher. 
             The maximum number of times to use the Software Retry mechanism 
             when it is enabled."
            ::= { brzaccVLAdaptiveModulationParams 3 }



    brzaccVLMinIntervalBetweenAdaptiveModulationAlgorithmMessages  OBJECT-TYPE
            SYNTAX INTEGER	 
            MAX-ACCESS read-write
            STATUS current
            DESCRIPTION  
            "Applicable all units.
			 The minimum interval between two consecutive AU/BU to SU/RB messages.
             Range: 1 to 3600 (Sec)."
            ::= { brzaccVLAdaptiveModulationParams 4 }

    brzaccVLAdaptiveModulationDecisionThresholds OBJECT-TYPE
            SYNTAX  INTEGER  { normal (1) , high (2), na (255) }
            MAX-ACCESS read-write      
            STATUS current       
            DESCRIPTION  
            "Applicable to all units. 
             Defines the setting of thresholds for the rate decision algorithm. 
             high (2) should typically be used when the SNR is lower than 13dB."
            ::= { brzaccVLAdaptiveModulationParams  5 }
 
	brzaccVLAdaptiveModulationHistorySize OBJECT-TYPE
            SYNTAX  INTEGER (15..25)
            MAX-ACCESS read-write      
            STATUS current       
            DESCRIPTION  
            "Applicable to all units with HW version C or higher. 
             This value is used to compute the transmission time.
             Not used in version 6.0 and higher."
            ::= { brzaccVLAdaptiveModulationParams 7 }
            
	brzaccVLAdaptiveModulationPacketThresholdToTestUpRate OBJECT-TYPE
            SYNTAX  INTEGER (10..10000)
            MAX-ACCESS read-write      
            STATUS current       
            DESCRIPTION  
            "Applicable to all units with HW version C or higher. 
             When the number of transmitted frames exceeds this number
             the upper modulations will be tested."
            ::= { brzaccVLAdaptiveModulationParams 8 }
            
	brzaccVLAdaptiveModulationPacketNoOnUpperRate OBJECT-TYPE
            SYNTAX  INTEGER (1..3)
            MAX-ACCESS read-write      
            STATUS current       
            DESCRIPTION  
            "Applicable to all units with HW version C or higher. 
             The number of frames used on upper modulations."
            ::= { brzaccVLAdaptiveModulationParams 9 }
                       
	brzaccVLAdaptiveModulationAlgorithm OBJECT-TYPE
            SYNTAX INTEGER  { adaptiveModulation(1), statisticsBasedRateControl(2), na(255) }
            MAX-ACCESS read-write      
            STATUS current       
            DESCRIPTION  
            "Applicable to all units with HW version C or higher. 
             Defines the adaptive modulation algorithm used by the unit."
            ::= { brzaccVLAdaptiveModulationParams 10 }
            
	brzaccVLAdaptiveModulationRetriesOnLowerModulations OBJECT-TYPE
            SYNTAX INTEGER  { disable(1), enable(2) }
            MAX-ACCESS read-write      
            STATUS current       
            DESCRIPTION  
            "Applicable to all units with HW version C or higher. 
             It allows retransmissions at lower modulation levels."
            ::= { brzaccVLAdaptiveModulationParams 11 }
            
	brzaccVLAdaptiveModulationRTSDurationMode OBJECT-TYPE
            SYNTAX INTEGER  { shortRTSDuration(1), longRTSDuration(2) }
            MAX-ACCESS read-write      
            STATUS current       
            DESCRIPTION  
            "Applicable to all units with HW version C or higher. 
            It defines the mode to calculate the value for RTS duration field."
            ::= { brzaccVLAdaptiveModulationParams 12 }
            
            

brzaccVLBurstMode     OBJECT IDENTIFIER ::= {brzaccVLPerformanceParams 10}

    brzaccVLBurstModeOption OBJECT-TYPE
            SYNTAX  INTEGER  {   disable (1) , enable (2), blocked(3), na (255) }
            MAX-ACCESS read-write      
            STATUS current       
            DESCRIPTION  
            "Applicable to all units.
             Applicable only if Burst Mode Option is supported by country 
             specific parameters of the Sub Band.  
             Not applicable if Wireless Link Prioritization is enabled.
             Enables/disable burst mode operation.
             In SU/RB with HW Revision B or lower blocked(3) value is returned
             when Security Mode is Wep , Data Encryption Option
			 is Enabled and Burst option is Enabled.
			 In AU/BU with HW Revision B or lower blocked(3) value is returned
			 when Dfs Option is Enabled and Burst mode is enabled."
            ::= { brzaccVLBurstMode  1 }

    brzaccVLBurstInterval OBJECT-TYPE
            SYNTAX  INTEGER
            MAX-ACCESS read-write      
            STATUS current       
            DESCRIPTION  
            "Applicable to all units.
             Not applicable if Wireless Link Prioritization is enabled.
             Burst mode interval in milliseconds.
             Range: 1 to the maximum value as defined in the country 
             specific parameters of the Sub Band (milliseconds)."
            ::= { brzaccVLBurstMode  2 }

brzaccVLConcatenationParameters     OBJECT IDENTIFIER ::= {brzaccVLPerformanceParams 11}
  
   brzaccVLConcatenationOption OBJECT-TYPE
            SYNTAX  INTEGER  { disable (1), enable (2), na (255)}
            MAX-ACCESS read-write      
            STATUS current       
            DESCRIPTION  
            "Applicable to all units. 
             Defines the Concatenation option."
            ::= { brzaccVLConcatenationParameters 1 }

  brzaccVLConcatenationMaximumNumberOfFrames OBJECT-TYPE
            SYNTAX  INTEGER (2..8)
            MAX-ACCESS read-write      
            STATUS current       
            DESCRIPTION  
            "Applicable to all units with SW version 3.X . 
             Not applicable for version 4.0 and higher.
             Defines the maximum numbers of frames that can be concatenated.
             Range:2 to 8 (frames)."
            ::= { brzaccVLConcatenationParameters 2 }
 
   brzaccVLConcatenationMaxFrameSize OBJECT-TYPE
            SYNTAX  INTEGER
            MAX-ACCESS read-write      
            STATUS current       
            DESCRIPTION  
            "Applicable to all units. 
			 Defines the maximum size of a concatenated frame.
			 Range:
			 256 to 2200 (bytes) for BreezeNET-B products BU/RB14 BU/RB28, 
			 or for AU/SU with HW revision A or B.
			 256 to 4032 (bytes) for AU/SU with HW Revision 
			 C or higher, BreezeNET-B products BU/RB100
			 and BreezeNET-B products BU/RB10."
            ::= { brzaccVLConcatenationParameters 3 }

                        
	brzaccVLControlModulationLevel OBJECT-TYPE
		SYNTAX INTEGER { basicRate(1), modulationLevel1(2) } 
		MAX-ACCESS read-write
		STATUS current
		DESCRIPTION  
		"Applicable to all units wits software version 6.0 and higher.
		The modulation level for control frames.
		basicRates(1) means the all control frames will be sent at basic rate and
		modulationLevel1(2) means the all control frames will be sent at modulation level 1" 
		::= { brzaccVLPerformanceParams 13 }

	brzaccVLEthernetFrameSize OBJECT-TYPE
           SYNTAX INTEGER { size1600(1), size2000(2) }
           MAX-ACCESS read-write
           STATUS current
            DESCRIPTION 
           "Applicable only for BNB-10 products.
			The maximum frame size used on Ethernet port."
            ::= { brzaccVLPerformanceParams 14 }

	brzaccVLRunningEthernetFrameSize OBJECT-TYPE
           SYNTAX INTEGER
           MAX-ACCESS read-only
           STATUS current
            DESCRIPTION 
           "Applicable only for BNB-10 products.
			The frame size used on Ethernet port."
            ::= { brzaccVLPerformanceParams 15 }

                  
                        
-- Site Survey Params
-- ==================
brzaccVLSiteSurvey        OBJECT IDENTIFIER ::= {breezeAccessVLMib 11}

    brzaccVLAverageReceiveSNR  OBJECT-TYPE
            SYNTAX INTEGER
            MAX-ACCESS read-only
            STATUS current
            DESCRIPTION 
            "Applicable to SU/RB only. 
             The average Signal to Noise Ratio of received frames."
            ::= { brzaccVLSiteSurvey 1 }

-- Traffic Counters
-- ================
brzaccVLTrafficStatistics	    OBJECT IDENTIFIER ::= {brzaccVLSiteSurvey 2}


    brzaccVLResetTrafficCounters OBJECT-TYPE
	     	SYNTAX	INTEGER { reset (1),cancel(2) }  
		    MAX-ACCESS read-write
	     	STATUS current
		    DESCRIPTION	 
            "Applicable to all units.
             Resets the traffic counters."
			::= { brzaccVLTrafficStatistics 1 }

brzaccVLEthCounters	         OBJECT IDENTIFIER ::= {brzaccVLTrafficStatistics 2}
brzaccVLWirelessLinkCounters OBJECT IDENTIFIER ::= {brzaccVLTrafficStatistics 3}
brzaccVLWirelessLinkEvents	 OBJECT IDENTIFIER ::= {brzaccVLTrafficStatistics 4}

brzaccVLPerModulationLevelCounters	     OBJECT IDENTIFIER ::= {brzaccVLTrafficStatistics 5}


	brzaccVLResetPerModulationLevelCounters OBJECT-TYPE
	     	SYNTAX	INTEGER { resetCounters(1) , cancel (2) } 
		    MAX-ACCESS read-write
	     	STATUS current
		    DESCRIPTION	 
            "Applicable to all units.
             Resets the per-Modulation Level counters ." 
			::= { brzaccVLPerModulationLevelCounters 1 }



    brzaccVLSUPerModulationLevelCountersTable OBJECT-TYPE
            SYNTAX SEQUENCE OF BrzaccVLSUPerModulationLevelCountersEntry
            MAX-ACCESS not-accessible
            STATUS current
            DESCRIPTION
            "Applicable to SU/RB. 
             Per Rate Counters table." 
            ::= { brzaccVLPerModulationLevelCounters 2 }

    brzaccVLSUPerModulationLevelCountersEntry  OBJECT-TYPE
            SYNTAX BrzaccVLSUPerModulationLevelCountersEntry
            MAX-ACCESS not-accessible
            STATUS current
            DESCRIPTION
            "Applicable to SU/RB. 
             An entry in the Per modulation  Counters table." 
            INDEX { brzaccVLSUPerModulationLevelCountersTableIdx }
            ::= { brzaccVLSUPerModulationLevelCountersTable 1 }

    BrzaccVLSUPerModulationLevelCountersEntry ::= SEQUENCE {
            brzaccVLSUPerModulationLevelCountersTableIdx       INTEGER,
            brzaccVLSUPerModulationLevelCountersApplicableModLevel INTEGER,
            brzaccVLSUPerModulationLevelCountersTxSuccess      Counter32,
            brzaccVLSUPerModulationLevelCountersTxFailed   Counter32
            }

         
    brzaccVLSUPerModulationLevelCountersTableIdx   OBJECT-TYPE
            SYNTAX  INTEGER  (1..8)
            MAX-ACCESS read-only
            STATUS current
            DESCRIPTION  
            "Applicable to SU/RB.
             An index of an entry in the Per modulation level Counters table." 
        ::= { brzaccVLSUPerModulationLevelCountersEntry 1 }

    brzaccVLSUPerModulationLevelCountersApplicableModLevel   OBJECT-TYPE
            SYNTAX  INTEGER    { 
            					 modLevel-1  (1), 
							     modLevel-2  (2), 
							     modLevel-3  (3), 
							     modLevel-4  (4), 
							     modLevel-5  (5), 
							     modLevel-6  (6), 
							     modLevel-7  (7), 
							     modLevel-8  (8) 
							   } 
            MAX-ACCESS read-only
            STATUS current
            DESCRIPTION  
            "Applicable to SU/RB.
             The applicable modulation level of the entry in the Per 
             modulation level Counters table.
             Modulation Level 8 is not applicable for units with HW revision A." 
        ::= { brzaccVLSUPerModulationLevelCountersEntry 2 }


    brzaccVLSUPerModulationLevelCountersTxSuccess      OBJECT-TYPE
            SYNTAX  Counter32  
            MAX-ACCESS read-only
            STATUS current
            DESCRIPTION  
            "Applicable to SU/RB.
             The total number of successfully transmitted unicasts at the 
             applicable modulation level." 
        ::= { brzaccVLSUPerModulationLevelCountersEntry 3 }


    brzaccVLSUPerModulationLevelCountersTxFailed   OBJECT-TYPE
            SYNTAX  Counter32  
            MAX-ACCESS read-only
            STATUS current
            DESCRIPTION  
            "Applicable to SU/RB.
             The total number of dropped frames at the applicable 
             Modulation Level." 
        ::= { brzaccVLSUPerModulationLevelCountersEntry 4 }


   brzaccVLAverageModulationLevel	 OBJECT-TYPE
	        SYNTAX INTEGER 
	        MAX-ACCESS read-only
	        STATUS current
	        DESCRIPTION	
	        "Applicable to SU/RB. 
	         The average modulation level for successful transmission 
	         (rounded to nearest integer) since last reset of the 
	         Per Modulation Level counters. 
	         Range: 1 to 8."  
	        ::= { brzaccVLPerModulationLevelCounters 3 }

    brzaccVLTotalRxFramesViaEthernet OBJECT-TYPE
      		SYNTAX  Counter32
		    MAX-ACCESS read-only
	     	STATUS current
		    DESCRIPTION	 
            "Applicable to all units. 
             Total number of frames received via the Ethernet port."
			::= { brzaccVLEthCounters 1 }

    brzaccVLTxWirelessToEthernet OBJECT-TYPE
      		SYNTAX  Counter32
		    MAX-ACCESS read-only
	     	STATUS current
		    DESCRIPTION	 
            "Applicable to all units. 
             Total number of frames transmitted to the Ethernet port."
			::= { brzaccVLEthCounters 2 }

brzaccVLTxFramesToWireless	 OBJECT IDENTIFIER ::= {brzaccVLWirelessLinkCounters 1}

    brzaccVLAUBeaconsToWireless OBJECT-TYPE
      		SYNTAX  Counter32
		    MAX-ACCESS read-only
	     	STATUS current
		    DESCRIPTION	 
            "Applicable to AU/BU only.
             The number of beacons transmitted to the wireless media."
			::= { brzaccVLTxFramesToWireless 1 }

--    brzaccVLOtherMngFramesToWireless OBJECT-TYPE
--      		SYNTAX  Counter32
--		    MAX-ACCESS read-only
--	     	STATUS current
--		    DESCRIPTION	 
--            "Applicable to AU and SU.
--             The number of management frames transmitted to the wireless media.
--             In AU, this count does not include Beacons."
--			::= { brzaccVLTxFramesToWireless 2 }

    brzaccVLDataAndOtherMngFramesToWireless OBJECT-TYPE
      		SYNTAX  Counter32
		    MAX-ACCESS read-only
	     	STATUS current
		    DESCRIPTION	 
            "Applicable to AU/BU only.
             The number of data and management frames transmitted to the 
             wireless media. The count includes one count for each data 
             frame transmitted successfully (excluding retransmissions)."
			::= { brzaccVLTxFramesToWireless 3 }

    brzaccVLTotalTxFramesToWireless OBJECT-TYPE
      		SYNTAX  Counter32
		    MAX-ACCESS read-only
	     	STATUS current
		    DESCRIPTION	 
            "Applicable to all units. 
             The number of frames transmitted to the wireless media.
             The count includes one count for each data frame
             that was transmitted successfully (excluding retransmissions),
             and also the number of transmitted control and management frames, 
             including beacons."
			::= { brzaccVLTxFramesToWireless 4 }
   
    brzaccVLTotalTransmittedUnicasts OBJECT-TYPE
      		SYNTAX  Counter32
		    MAX-ACCESS read-only
	     	STATUS current
		    DESCRIPTION	 
            "Applicable to AU/BU only.	 
             The total number of unicast frames successfully transmitted 
             to the wireless media, excluding retransmissions."
			::= { brzaccVLTxFramesToWireless 5 }

    brzaccVLTotalTransmittedConcatenatedFramesDouble OBJECT-TYPE
      		SYNTAX  Counter32
		    MAX-ACCESS read-only
	     	STATUS current
		    DESCRIPTION	 
            "Applicable to all products.	 
             The total number of double concatenated frames successfully transmitted 
             to the wireless media, excluding retransmissions."
			::= { brzaccVLTxFramesToWireless 6 }

    brzaccVLTotalTransmittedConcatenatedFramesSingle OBJECT-TYPE
      		SYNTAX  Counter32
		    MAX-ACCESS read-only
	     	STATUS current
		    DESCRIPTION	 
            "Applicable to all products.	 
             The total number of double concatenated frames successfully transmitted 
             to the wireless media, excluding retransmissions."
			::= { brzaccVLTxFramesToWireless 7 }

    brzaccVLTotalTransmittedConcatenatedFramesMore OBJECT-TYPE
      		SYNTAX  Counter32
		    MAX-ACCESS read-only
	     	STATUS current
		    DESCRIPTION	 
            "Applicable to all products.	 
             The total number of concatenated frames with more then two frames successfully 
             transmitted to the wireless media, excluding retransmissions."
			::= { brzaccVLTxFramesToWireless 8 }
			
    brzaccVLTotalRxFramesFromWireless OBJECT-TYPE
      		SYNTAX  Counter32
		    MAX-ACCESS read-only
	     	STATUS current
		    DESCRIPTION	 
            "Applicable to all units. 
             The total number of frames that were received
             from the wireless media.
             The count includes data and control and management
             frames, including beacons received from the AU/BU.
             The count does not include frames that were discarded
             internally, bad frames and duplicate frames."
			::= { brzaccVLWirelessLinkCounters 2 }

    brzaccVLTotalRetransmittedFrames OBJECT-TYPE
      		SYNTAX  Counter32
		    MAX-ACCESS read-only
	     	STATUS current
		    DESCRIPTION	 
            "Applicable to all units. 
             The total number of retransmissions of data frames 
             (counts all unsuccessful transmissions/retransmissions)."
			::= { brzaccVLWirelessLinkCounters 3 }

    brzaccVLFramesDropped OBJECT-TYPE
      		SYNTAX  Counter32
		    MAX-ACCESS read-only
	     	STATUS current
		    DESCRIPTION	 
            "Applicable to all units. 
             The number of dropped frames.
             The frames that were retransmitted to the extent
             of the maximum allowed number of retransmissions
             without being acknowledged.."
			::= { brzaccVLWirelessLinkCounters 4 }


brzaccVLDataFramesSubmittedToBridge	 OBJECT IDENTIFIER ::= {brzaccVLWirelessLinkCounters 5}

	brzaccVLFramesSubmittedViaHighQueue OBJECT-TYPE
      		SYNTAX  Counter32
		    MAX-ACCESS read-only
	     	STATUS current
		    DESCRIPTION	 
            "Applicable to all units. 
             Frames submitted to the internal bridge via the High priority queue. 
             for transmission to the wireless media."
			::= { brzaccVLDataFramesSubmittedToBridge 1 }

	brzaccVLFramesSubmittedViaMidQueue OBJECT-TYPE
      		SYNTAX  Counter32
		    MAX-ACCESS read-only
	     	STATUS current
		    DESCRIPTION	 
            "Applicable to all units. 
             Frames submitted to the internal bridge via the Mid priority queue 
             for transmission to the wireless media."
			::= { brzaccVLDataFramesSubmittedToBridge 2 }

	brzaccVLFramesSubmittedViaLowQueue OBJECT-TYPE
      		SYNTAX  Counter32
		    MAX-ACCESS read-only
	     	STATUS current
		    DESCRIPTION	 
            "Applicable to all units. 
             Frames submitted to the internal bridge via the Low priority queue 
             for transmission to the wireless media."
			::= { brzaccVLDataFramesSubmittedToBridge 3 }

	brzaccVLTotalNoOfDataFramesSubmitted OBJECT-TYPE
      		SYNTAX  Counter32
		    MAX-ACCESS read-only
	     	STATUS current
		    DESCRIPTION	 
            "Applicable to all units. 
             The total number of data frames submitted to the internal bridge 
             for transmission to the wireless media."
			::= { brzaccVLDataFramesSubmittedToBridge 4 }


    brzaccVLTotalRecievedDataFrames OBJECT-TYPE
      		SYNTAX  Counter32
		    MAX-ACCESS read-only
	     	STATUS current
		    DESCRIPTION	 
            "Applicable to all units. 
             The total number of data frames received from the
             wireless media, including duplicate frames."
			::= { brzaccVLWirelessLinkCounters 6 }

    brzaccVLRecievedBadFrames OBJECT-TYPE
      		SYNTAX  Counter32
		    MAX-ACCESS read-only
	     	STATUS current
		    DESCRIPTION	 
            "Applicable to all units. 
             The number of frames received from the wireless
             media with errors (CRC errors)."
			::= { brzaccVLWirelessLinkCounters 7 }

    brzaccVLNoOfDuplicateFramesDiscarded OBJECT-TYPE
      		SYNTAX  Counter32
		    MAX-ACCESS read-only
	     	STATUS current
		    DESCRIPTION	 
            "Applicable to all units. 
             The number of frames discarded due to receiving multiple copies."
			::= { brzaccVLWirelessLinkCounters 8 }

    brzaccVLNoOfInternallyDiscardedMirCir OBJECT-TYPE
      		SYNTAX  Counter32
		    MAX-ACCESS read-only
	     	STATUS current
		    DESCRIPTION	 
            "Applicable to all units. 
            The number of data frames received from the Ethernet port that were 
            discarded by the MIR/CIR mechanism either to avoid exceeding the 
            maximum allowed information rate, or when the wireless link conditions 
            do not enable reaching the allowed rate."
			::= { brzaccVLWirelessLinkCounters 9 }

    brzaccVLTotalRxConcatenatedFramesDouble OBJECT-TYPE
      		SYNTAX  Counter32
		    MAX-ACCESS read-only
	     	STATUS current
		    DESCRIPTION	 
            "Applicable to all units.
            The total number of double concatenated frames received 
            from the wireless media, including duplicate frames."
			::= { brzaccVLWirelessLinkCounters 10 }

    brzaccVLTotalRxConcatenatedFramesSingle OBJECT-TYPE
      		SYNTAX  Counter32
		    MAX-ACCESS read-only
	     	STATUS current
		    DESCRIPTION	 
            "Applicable to all units. 
             The total number of data fast frames single concatenated 
             frames received from the wireless media, including duplicate frames."
			::= { brzaccVLWirelessLinkCounters 11 }

    brzaccVLTotalRxConcatenatedFramesMore OBJECT-TYPE
      		SYNTAX  Counter32
		    MAX-ACCESS read-only
	     	STATUS current
		    DESCRIPTION	 
            "Applicable to all units. 
             The total number of data fast frames concatenated with more then two 
             frames received from the wireless media, including duplicate frames."
			::= { brzaccVLWirelessLinkCounters 12 }
					
    brzaccVLTXRetransmissionPercentage OBJECT-TYPE
      		SYNTAX  Counter32
		    MAX-ACCESS read-only
	     	STATUS current
		    DESCRIPTION	 
            "Applicable to all units. 
             Indicates the percentage of frames that have been retransmitted."
			::= { brzaccVLWirelessLinkCounters 13 }
			
    brzaccVLRXCRCPercentage OBJECT-TYPE
      		SYNTAX  Counter32
		    MAX-ACCESS read-only
	     	STATUS current
		    DESCRIPTION	 
            "Applicable to all units. 
             Indicates the percentage of received frames with CRC error."
			::= { brzaccVLWirelessLinkCounters 14 }
					
--	brzaccVLInternallyGeneratedFramesSubmittedToBridge OBJECT-TYPE
--      		SYNTAX  Counter32
--		    MAX-ACCESS read-only
--	     	STATUS current
--		    DESCRIPTION	 
--            "Applicable to SU and AU. Read-only.
--             The number of internally generated frames(wireless management and control frames)
--             submitted to the bridge for transmission to the wireless media."
--			::= { brzaccVLWirelessLinkCounters 10 }


brzaccVLTxEvents	 OBJECT IDENTIFIER ::= {brzaccVLWirelessLinkEvents 1}

    brzaccVLDroppedFrameEvents OBJECT-TYPE
      		SYNTAX  Counter32
		    MAX-ACCESS read-only
	     	STATUS current
		    DESCRIPTION	 
            "Applicable to all units. 
			 The number of frames that were dropped because they were retransmitted
			 to the maximum allowed number of retransmissions without being 
			 acknowledged."
			::= { brzaccVLTxEvents 1 }

    brzaccVLFramesDelayedDueToSwRetry OBJECT-TYPE
      		SYNTAX  Counter32
		    MAX-ACCESS read-only
	     	STATUS current
		    DESCRIPTION	 
            "Applicable to all units. 
             Not applicable for units with SW Version 3.0 and higher.
             The number of frames that were delayed because the SW retry 
             algorithm was activated on a previous frame designated for the 
             same recipient."
			::= { brzaccVLTxEvents 2 }

    brzaccVLUnderrunEvents OBJECT-TYPE
      		SYNTAX  Counter32
		    MAX-ACCESS read-only
	     	STATUS current
		    DESCRIPTION	 
            "Applicable to all units. 
             The number of frames whose transmission was aborted because the rate
             of submitting frames for transmission exceeded the available 
             transmission capability."
			::= { brzaccVLTxEvents 3 }

    brzaccVLOthersTxEvents  OBJECT-TYPE
      		SYNTAX  Counter32
		    MAX-ACCESS read-only
	     	STATUS current
		    DESCRIPTION	 
            "Applicable to all units. 
             The number of Tx events due to problems other than those of 
             the other Tx Events counters."
			::= { brzaccVLTxEvents 4 }

    brzaccVLTotalTxEvents OBJECT-TYPE
      		SYNTAX  Counter32
		    MAX-ACCESS read-only
	     	STATUS current
		    DESCRIPTION	 
            "Applicable to all units. 
             The total number of Tx special events."
			::= { brzaccVLTxEvents 5 }

brzaccVLRxEvents	 OBJECT IDENTIFIER ::= {brzaccVLWirelessLinkEvents 2}

    brzaccVLPhyErrors OBJECT-TYPE
      		SYNTAX  Counter32
		    MAX-ACCESS read-only
	     	STATUS current
		    DESCRIPTION	 
            "Applicable to all units, only when DFS is enabled. 
             The number of unidentified signals."
			::= { brzaccVLRxEvents 1 }

    brzaccVLCRCErrors OBJECT-TYPE
      		SYNTAX  Counter32
		    MAX-ACCESS read-only
	     	STATUS current
		    DESCRIPTION	 
            "Applicable to all units. 
             The number of frames received from the wireless media containing 
             CRC errors."
			::= { brzaccVLRxEvents 2 }

    brzaccVLOverrunEvents OBJECT-TYPE
      		SYNTAX  Counter32
		    MAX-ACCESS read-only
	     	STATUS current
		    DESCRIPTION	 
            "Applicable to all units. 
             The number of frames that were discarded because the receive 
             rate exceeded the processing capability or the capacity of the 
             Ethernet port."
			::= { brzaccVLRxEvents 3 }

    brzaccVLRxDecryptEvents OBJECT-TYPE
      		SYNTAX  Counter32
		    MAX-ACCESS read-only
	     	STATUS current
		    DESCRIPTION	 
            "Applicable to all units. 
             The number of frames that were not received properly due to a 
             problem in the data decryption mechanism."
			::= { brzaccVLRxEvents 4 }

    brzaccVLTotalRxEvents OBJECT-TYPE
      		SYNTAX  Counter32
		    MAX-ACCESS read-only
	     	STATUS current
		    DESCRIPTION	 
            "Applicable to all units. 
             The total number of Rx special events."
			::= { brzaccVLRxEvents 5 }


-- Associations Database
-- 
brzaccVLMacAddressDatabase   OBJECT IDENTIFIER ::= {brzaccVLSiteSurvey 5}

brzaccVLAUMacAddressDatabase   OBJECT IDENTIFIER ::= {brzaccVLMacAddressDatabase 1}

brzaccVLAUAdbResetAllModulationLevelCounters OBJECT-TYPE
	  SYNTAX  INTEGER { reset (1), cancel (2) }  
      MAX-ACCESS  read-write    
      STATUS  current
      DESCRIPTION
      "Applicable to AU/BU only. 
	   To reset all the counters for all SUs/RB in the MAC Address Database."
      ::= { brzaccVLAUMacAddressDatabase 1 }

brzaccVLAUAdbTable OBJECT-TYPE
	  SYNTAX SEQUENCE OF BrzaccVLAUAdbEntry
	  MAX-ACCESS not-accessible
	  STATUS current
	  DESCRIPTION
      "Applicable to AU/BU only. 
       AU/BU MAC Address Database table."
	  ::= { brzaccVLAUMacAddressDatabase 2 }

brzaccVLAUAdbEntry  OBJECT-TYPE
	  SYNTAX BrzaccVLAUAdbEntry
	  MAX-ACCESS not-accessible
	  STATUS current
      DESCRIPTION
      "Applicable to AU/BU only. 
       An entry in the AU/BU MAC Address Database table."
	  INDEX { brzaccVLAdbIndex }
	  ::= { brzaccVLAUAdbTable 1 }

			   
BrzaccVLAUAdbEntry ::= SEQUENCE {
 	  brzaccVLAdbIndex			    INTEGER,
 	  brzaccVLAdbMacAddress		    MacAddress,
	  brzaccVLAdbStatus			    INTEGER,
	  brzaccVLAdbSwVersion			DisplayString,
	  brzaccVLAdbSNR                INTEGER,
 	  brzaccVLAdbMaxModulationLevel INTEGER,
	  brzaccVLAdbTxFramesTotal	    Counter32,
	  brzaccVLAdbDroppedFramesTotal	Counter32,
	  brzaccVLAdbTxSuccessModLevel1	Counter32,
	  brzaccVLAdbTxSuccessModLevel2	Counter32,
	  brzaccVLAdbTxSuccessModLevel3	Counter32,
	  brzaccVLAdbTxSuccessModLevel4	Counter32,
	  brzaccVLAdbTxSuccessModLevel5	Counter32,
	  brzaccVLAdbTxSuccessModLevel6	Counter32,
	  brzaccVLAdbTxSuccessModLevel7	Counter32,
	  brzaccVLAdbTxSuccessModLevel8	Counter32,
	  brzaccVLAdbTxFailedModLevel1	Counter32,
	  brzaccVLAdbTxFailedModLevel2	Counter32,
	  brzaccVLAdbTxFailedModLevel3	Counter32,
	  brzaccVLAdbTxFailedModLevel4	Counter32,
	  brzaccVLAdbTxFailedModLevel5	Counter32,
	  brzaccVLAdbTxFailedModLevel6	Counter32,
	  brzaccVLAdbTxFailedModLevel7	Counter32,
	  brzaccVLAdbTxFailedModLevel8	Counter32,
   	  brzaccVLAdbCirTx              INTEGER,
      brzaccVLAdbMirTx              INTEGER,
      brzaccVLAdbCirRx              INTEGER,
      brzaccVLAdbMirRx              INTEGER,
      brzaccVLAdbCirMaxDelay        INTEGER,
	  brzaccVLAdbDistance			INTEGER,
	  brzaccVLAdbHwRevision			INTEGER,
	  brzaccVLAdbCpldVer			DisplayString,
	  brzaccVLAdbCountryCode    	INTEGER,
	  brzaccVLAdbBootVer			DisplayString,
	  brzaccVLAdbAtpcOption			INTEGER,
	  brzaccVLAdbAdapModOption		INTEGER,
	  brzaccVLAdbBurstModeOption	INTEGER,
	  brzaccVLAdbConcatenationOption	INTEGER,
	  brzaccVLAdbSecurityMode		INTEGER,
	  brzaccVLAdbAuthOption			INTEGER,
	  brzaccVLAdbDataEncyptOption	INTEGER,
	  brzaccVLAdbAge                INTEGER,
	  brzaccVLAdbUnitName           DisplayString,
	  brzaccVLAdbRSSI				INTEGER,
	  brzaccVLAdbIpAddress			IpAddress
	  }

brzaccVLAdbIndex OBJECT-TYPE
	  SYNTAX INTEGER  (1..512)
	  MAX-ACCESS read-only
	  STATUS current
	  DESCRIPTION	
      "Applicable to AU/BU only. 
	   The index of an entry in the AU/BU MAC Address Database table."
	  ::= { brzaccVLAUAdbEntry 1 }

brzaccVLAdbMacAddress  OBJECT-TYPE
	  SYNTAX MacAddress  
	  MAX-ACCESS read-only
	  STATUS current
	  DESCRIPTION
      "Applicable to AU/BU only. 
	   The MAC Address of an SU/RB entry in the MAC Address Database 
	   table."
	  ::= { brzaccVLAUAdbEntry 2 }

brzaccVLAdbStatus	 OBJECT-TYPE
	  SYNTAX INTEGER { associated       (1), 
	                   authenticated    (2),
	                   notAuthenticated (3) }
	  MAX-ACCESS read-only
	  STATUS current
	  DESCRIPTION	
      "Applicable to AU/BU only. 
	   The status of the relevant SU/RB."
	  ::= { brzaccVLAUAdbEntry 3 }

brzaccVLAdbSwVersion OBJECT-TYPE
	  SYNTAX DisplayString  
	  MAX-ACCESS read-only
	  STATUS current
	  DESCRIPTION	
      "Applicable to AU/BU only. 
	   The SW version of the relevant SU/RB.
	   Not available for SU-EZ."
	  ::= { brzaccVLAUAdbEntry 4 }

brzaccVLAdbSNR	OBJECT-TYPE
	  SYNTAX INTEGER  
	  MAX-ACCESS read-only
	  STATUS current
	  DESCRIPTION	
      "Applicable to AU/BU only. 
	   The average Signal to Noise Ratio in dB of frames received by 
	   the AU/BU from the relevant SU/RB."
	  ::= { brzaccVLAUAdbEntry 5 }

brzaccVLAdbMaxModulationLevel  OBJECT-TYPE
	  SYNTAX INTEGER  { modLevel-1 (1), 
	                    modLevel-2 (2), 
                        modLevel-3 (3), 
                        modLevel-4 (4), 
                        modLevel-5 (5), 
                        modLevel-6 (6), 
                        modLevel-7 (7), 
                        modLevel-8 (8),
                        na ( 255 ) 
                      }  
	  MAX-ACCESS read-only
	  STATUS current
	  DESCRIPTION	
      "Applicable to AU/BU only. 
	   The value configured in the relevant SU/RB for the Maximum Modulation 
	   Level parameter.
	   Modulation Level 8 is not applicable for units with HW revision A.
	   It is not applicable for SU-EZ and it returns na."
	  ::= { brzaccVLAUAdbEntry 6 }

brzaccVLAdbTxFramesTotal	OBJECT-TYPE
	  SYNTAX Counter32 
	  MAX-ACCESS read-only
	  STATUS current
	  DESCRIPTION	
      "Applicable to AU/BU only. 
	   Counts the total number of unicast  frames (excluding retransmissions) 
	   that were successfully transmitted to the SU/RB over the wireless link."
	  ::= { brzaccVLAUAdbEntry 7 }

brzaccVLAdbDroppedFramesTotal  OBJECT-TYPE
	  SYNTAX Counter32 
	  MAX-ACCESS read-only
	  STATUS current
	  DESCRIPTION	
      "Applicable to AU/BU only. 
	   Counts the total number of frames intended to the SU/RB that 
	   were dropped because they were retransmitted to the extent 
	   of the maximum allowed number of retransmissions without 
	   being acknowledged."
	  ::= { brzaccVLAUAdbEntry 8 }

brzaccVLAdbTxSuccessModLevel1	OBJECT-TYPE
	  SYNTAX Counter32 
	  MAX-ACCESS read-only
	  STATUS current
	  DESCRIPTION	
      "Applicable to AU/BU only. 
	   Counts the total number of unicast frames (excluding retransmissions) 
	   that were successfully transmitted to the SU/RB over the wireless link 
	   using modulation level 1."
	  ::= { brzaccVLAUAdbEntry 9 }

brzaccVLAdbTxSuccessModLevel2	OBJECT-TYPE
	  SYNTAX Counter32 
	  MAX-ACCESS read-only
	  STATUS current
	  DESCRIPTION	
      "Applicable to AU/BU only. 
	   Counts the total number of unicast frames (excluding retransmissions) 
	   that were successfully transmitted to the SU/RB over the wireless link 
	   using modulation level 2."
	  ::= { brzaccVLAUAdbEntry 10 }

brzaccVLAdbTxSuccessModLevel3	OBJECT-TYPE
	  SYNTAX Counter32 
	  MAX-ACCESS read-only
	  STATUS current
	  DESCRIPTION	
      "Applicable to AU/BU only. 
	   Counts the total number of unicast frames (excluding retransmissions) 
	   that were successfully transmitted to the SU/BU over the wireless link 
	   using modulation level 3."
	  ::= { brzaccVLAUAdbEntry 11 }

brzaccVLAdbTxSuccessModLevel4	OBJECT-TYPE
	  SYNTAX Counter32 
	  MAX-ACCESS read-only
	  STATUS current
	  DESCRIPTION	
      "Applicable to AU/BU only. 
	   Counts the total number of unicast frames (excluding retransmissions) 
	   that were successfully transmitted to the SU/RB over the wireless link 
	   using modulation level 4."
	  ::= { brzaccVLAUAdbEntry 12 }

brzaccVLAdbTxSuccessModLevel5	OBJECT-TYPE
	  SYNTAX Counter32 
	  MAX-ACCESS read-only
	  STATUS current
	  DESCRIPTION	
      "Applicable to AU/BU only. 
	   Counts the total number of unicast frames (excluding retransmissions) 
	   that were successfully transmitted to the SU/RB over the wireless link 
	   using modulation level 5."
	  ::= { brzaccVLAUAdbEntry 13 }

brzaccVLAdbTxSuccessModLevel6	OBJECT-TYPE
	  SYNTAX Counter32 
	  MAX-ACCESS read-only
	  STATUS current
	  DESCRIPTION	
      "Applicable to AU/BU only. 
	   Counts the total number of unicast frames (excluding retransmissions) 
	   that were successfully transmitted to the SU/BU over the wireless link 
	   using modulation level 6."
	  ::= { brzaccVLAUAdbEntry 14 }

brzaccVLAdbTxSuccessModLevel7	OBJECT-TYPE
	  SYNTAX Counter32 
	  MAX-ACCESS read-only
	  STATUS current
	  DESCRIPTION	
      "Applicable to AU/BU only. 
	   Counts the total number of unicast frames (excluding retransmissions) 
	   that were successfully transmitted to the SU/RB over the wireless link 
	   using modulation level 7."
	  ::= { brzaccVLAUAdbEntry 15 }

brzaccVLAdbTxSuccessModLevel8	OBJECT-TYPE
	  SYNTAX Counter32 
	  MAX-ACCESS read-only
	  STATUS current
	  DESCRIPTION	
      "Applicable to AU/BU only. 
	   Counts the total number of unicast frames (excluding retransmissions) 
	   that were successfully transmitted to the SU/RB over the wireless link 
	   using modulation level 8.
	   Not applicable for units with HW revision A."
	  ::= { brzaccVLAUAdbEntry 16 }

brzaccVLAdbTxFailedModLevel1	OBJECT-TYPE
	  SYNTAX Counter32 
	  MAX-ACCESS read-only
	  STATUS current
	  DESCRIPTION	
      "Applicable to AU/BU only. 
	   Counts the total number of failures to successfully
	   transmit unicast frames intended to the SU/RB using modulation level 1."
	  ::= { brzaccVLAUAdbEntry 17 }

brzaccVLAdbTxFailedModLevel2	OBJECT-TYPE
	  SYNTAX Counter32 
	  MAX-ACCESS read-only
	  STATUS current
	  DESCRIPTION	
      "Applicable to AU/BU only. 
	   Counts the total number of failures to successfully
	   transmit unicast frames intended to the SU/RB using modulation level 2."
	  ::= { brzaccVLAUAdbEntry 18 }

brzaccVLAdbTxFailedModLevel3	OBJECT-TYPE
	  SYNTAX Counter32 
	  MAX-ACCESS read-only
	  STATUS current
	  DESCRIPTION	
      "Applicable to AU/BU only. 
	   Counts the total number of failures to successfully
	   transmit unicast frames intended to the SU/RB using modulation level 3."
	  ::= { brzaccVLAUAdbEntry 19 }

brzaccVLAdbTxFailedModLevel4	OBJECT-TYPE
	  SYNTAX Counter32 
	  MAX-ACCESS read-only
	  STATUS current
	  DESCRIPTION	
      "Applicable to AU/BU only. 
	   Counts the total number of failures to successfully
	   transmit unicast frames intended to the SU/RB using modulation level 4."
	  ::= { brzaccVLAUAdbEntry 20 }

brzaccVLAdbTxFailedModLevel5	OBJECT-TYPE
	  SYNTAX Counter32 
	  MAX-ACCESS read-only
	  STATUS current
	  DESCRIPTION	
      "Applicable to AU/BU only. 
	   Counts the total number of failures to successfully
	   transmit unicast frames intended to the SU/RB using modulation level 5."
	  ::= { brzaccVLAUAdbEntry 21 }

brzaccVLAdbTxFailedModLevel6	OBJECT-TYPE
	  SYNTAX Counter32 
	  MAX-ACCESS read-only
	  STATUS current
	  DESCRIPTION	
      "Applicable to AU/BU only. 
	   Counts the total number of failures to successfully
	   transmit unicast frames intended to the SU/RB using modulation level 6."
	  ::= { brzaccVLAUAdbEntry 22 }

brzaccVLAdbTxFailedModLevel7	OBJECT-TYPE
	  SYNTAX Counter32 
	  MAX-ACCESS read-only
	  STATUS current
	  DESCRIPTION	
      "Applicable to AU/BU only. 
	   Counts the total number of failures to successfully
	   transmit unicast frames intended to the SU/RB using modulation level 7."
	  ::= { brzaccVLAUAdbEntry 23 }

brzaccVLAdbTxFailedModLevel8	OBJECT-TYPE
	  SYNTAX Counter32 
	  MAX-ACCESS read-only
	  STATUS current
	  DESCRIPTION	
      "Applicable to AU/BU only. 
	   Counts the total number of failures to successfully
	   transmit unicast frames intended to the SU/RB using modulation level 8.
	   Not applicable for units with HW revision A."
	  ::= { brzaccVLAUAdbEntry 24 }

brzaccVLAdbCirTx  OBJECT-TYPE
   SYNTAX INTEGER 
   MAX-ACCESS read-only
   STATUS current
   DESCRIPTION 
   "Applicable to AU Only. 
    Not applicable to BreezeNET-B products. 
    This parameter is not relevant for SU-EZ with SW 1.00.15
    and it is 0.
    The value configured in the relevant SU for the CIR: 
    SU to AU parameter."
   ::= { brzaccVLAUAdbEntry 25 }

brzaccVLAdbMirTx  OBJECT-TYPE
   SYNTAX INTEGER 
   MAX-ACCESS read-only
   STATUS current
   DESCRIPTION 
   "Applicable to AU/BU only. 
    The value configured in the relevant SU/RB for the MIR: 
    SU/RB to AU/BU parameter.
    For SU-EZ SW version 1.00.15, it represents the value 
    set in AU-EZ."
   ::= { brzaccVLAUAdbEntry 26 }
    
brzaccVLAdbCirRx  OBJECT-TYPE
   SYNTAX INTEGER 
   MAX-ACCESS read-only
   STATUS current
   DESCRIPTION 
   "Applicable to AU Only.
    Not applicable to BreezeNET-B products.
    This parameter is not relevant for SU-EZ with SW 
    version 1.00.15 and it is 0.    
    The value configured in the relevant SU for the CIR: 
    AU to SU parameter."
   ::= { brzaccVLAUAdbEntry 27 }

brzaccVLAdbMirRx  OBJECT-TYPE
   SYNTAX INTEGER 
   MAX-ACCESS read-only
   STATUS current
   DESCRIPTION 
   "Applicable to AU/BU only. 
    This parameter is not relevant for SU-EZ with SW 
    version 1.00.15 and it is 0.
    The value configured in the relevant SU/RB for the MIR: 
    AU/BU to SU/RB parameter."
   ::= { brzaccVLAUAdbEntry 28 }

brzaccVLAdbCirMaxDelay   OBJECT-TYPE
   SYNTAX INTEGER 
   MAX-ACCESS read-only
   STATUS current
   DESCRIPTION 
   "Applicable to AU Only. 
    Not applicable to BreezeNET-B products.
    The value configured in the relevant SU for the CIR Maximum 
    Delay parameter.
    It returns maximum value on 32 bits for SU-EZ with SW 
    version 1.00.15 and this means NA (Not Available)."
   ::= { brzaccVLAUAdbEntry 29 }

brzaccVLAdbDistance     OBJECT-TYPE
   SYNTAX INTEGER  {below-2-Km(1)}
   MAX-ACCESS read-only
   STATUS current
   DESCRIPTION 
   "Applicable to AU/BU Only.  
    The distance between the SU/RB and the AU/BU (In Kilometers).
    It is not applicable for SU-EZ and it returns 0."
   ::= { brzaccVLAUAdbEntry 30 }

brzaccVLAdbHwRevision     OBJECT-TYPE
   SYNTAX INTEGER  {hwRevisionA(1), hwRevisionB(2), hwRevisionC(3), 
                    hwRevisionD(4), hwRevisionE(5), hwRevisionF(6),
                    hwRevisionG(7), na(255)}
   MAX-ACCESS read-only
   STATUS current
   DESCRIPTION 
   "Applicable to AU/BU Only.  
    The SU/RB HW Revision.
    Not available for SU-EZ."
   ::= { brzaccVLAUAdbEntry 31 }

brzaccVLAdbCpldVer     OBJECT-TYPE
   SYNTAX DisplayString
   MAX-ACCESS read-only
   STATUS current
   DESCRIPTION 
   "Applicable to AU/BU Only.  
    The SU/RB CPLD Version.
    Not available for SU-EZ."
   ::= { brzaccVLAUAdbEntry 32 }

brzaccVLAdbCountryCode     OBJECT-TYPE
   SYNTAX INTEGER  
   MAX-ACCESS read-only
   STATUS current
   DESCRIPTION 
   "Applicable to AU/BU Only.  
    The SU/RB country code.
    9999 means unavailable country code."
   ::= { brzaccVLAUAdbEntry 33 }

brzaccVLAdbBootVer     OBJECT-TYPE
   SYNTAX DisplayString
   MAX-ACCESS read-only
   STATUS current
   DESCRIPTION 
   "Applicable to AU/BU Only.  
    The SU/RB Boot Version.
    Not available for SU-EZ."
   ::= { brzaccVLAUAdbEntry 34 }

brzaccVLAdbAtpcOption     OBJECT-TYPE
   SYNTAX INTEGER  {disable (1), enable (2), na (255)}
   MAX-ACCESS read-only
   STATUS current
   DESCRIPTION 
   "Applicable to AU/BU Only.  
    The SU/RB ATPC option configuration."
   ::= { brzaccVLAUAdbEntry 35 }

brzaccVLAdbAdapModOption     OBJECT-TYPE
   SYNTAX INTEGER  {disable (1), enable (2), na (255)}
   MAX-ACCESS read-only
   STATUS current
   DESCRIPTION 
   "Applicable to AU/BU Only.  
    The SU/RB adaptive modulation option configuration.
    It is not applicable for SU-EZ."
   ::= { brzaccVLAUAdbEntry 36 }

brzaccVLAdbBurstModeOption     OBJECT-TYPE
   SYNTAX INTEGER  {disable (1), enable (2), na (255)}
   MAX-ACCESS read-only
   STATUS current
   DESCRIPTION 
   "Applicable to AU/BU Only.  
    The SU/RB burst mode option configuration.
    It is not applicable for SU-EZ."
   ::= { brzaccVLAUAdbEntry 37 }

brzaccVLAdbConcatenationOption     OBJECT-TYPE
   SYNTAX INTEGER  {disable (1), enable (2), na(255)}
   MAX-ACCESS read-only
   STATUS current
   DESCRIPTION 
   "Applicable to AU/BU Only.  
    The SU/RB concatenation option configuration.
    It is not applicable for SU-EZ."
   ::= { brzaccVLAUAdbEntry 39 }

brzaccVLAdbSecurityMode     OBJECT-TYPE
   SYNTAX INTEGER  {wep(1), aes(2), fips197(3), na(255)}
   MAX-ACCESS read-only
   STATUS current
   DESCRIPTION 
   "Applicable to AU/BU Only.  
    The SU/RB security mode configuration.
    Not available for SU-EZ."
   ::= { brzaccVLAUAdbEntry 41 }

brzaccVLAdbAuthOption     OBJECT-TYPE
   SYNTAX INTEGER  {openSystem (1), sharedKey (2), na (255)}
   MAX-ACCESS read-only
   STATUS current
   DESCRIPTION 
   "Applicable to AU/BU Only.  
    The SU/RB authentication algorithm configuration.
    Not available for SU-EZ."
   ::= { brzaccVLAUAdbEntry 42 }

brzaccVLAdbDataEncyptOption     OBJECT-TYPE
   SYNTAX INTEGER  {disable (1), enable (2), na (255)}
   MAX-ACCESS read-only
   STATUS current
   DESCRIPTION 
   "Applicable to AU/BU Only.  
    The SU/RB data encryption option configuration.
    Not available for SU-EZ."
   ::= { brzaccVLAUAdbEntry 43 }

brzaccVLAdbAge	OBJECT-TYPE
	  SYNTAX INTEGER  
	  MAX-ACCESS read-only
	  STATUS current
	  DESCRIPTION	
      "Applicable to AU/BU only. 
	   The time since any packet was received from the relevant SU/RB."
	  ::= { brzaccVLAUAdbEntry 44 }
	  
brzaccVLAdbUnitName	OBJECT-TYPE
	  SYNTAX DisplayString 
	  MAX-ACCESS read-only
	  STATUS current
	  DESCRIPTION
      "Applicable to AU/BU only. 
	   The unit name of the relevant SU/RB.
	   Not available for SU-EZ."
	  ::= { brzaccVLAUAdbEntry 45 }
	  
brzaccVLAdbRSSI OBJECT-TYPE
	SYNTAX INTEGER  
	MAX-ACCESS read-only
	STATUS current
	DESCRIPTION 
	"Applicable to AU/BU only with SW version 5.1 and higher. 
	The average Received Signal Strength Indication of frames received by 
	the AU/BU from the relevant SU/RB.
	This value is given in dBm units."
	::= { brzaccVLAUAdbEntry 46 }

brzaccVLAdbIpAddress OBJECT-TYPE
	SYNTAX IpAddress
	MAX-ACCESS read-only
	STATUS current
	DESCRIPTION 
	"Applicable to AU/BU only with SW version 5.2.11 and higher. 
	The Running IP address of the relevant SU/RB.
	Not available for SU-EZ with SW version lower than 1.1.1"
	::= { brzaccVLAUAdbEntry 47 }


brzaccVLAUNewAdbTable OBJECT-TYPE
	  SYNTAX SEQUENCE OF BrzaccVLAUNewAdbEntry
	  MAX-ACCESS not-accessible
	  STATUS current
	  DESCRIPTION
      "Applicable to AU/BU only with SW version 5.0 and higher. 
       AU/BU MAC Address New Database table idexed by MAC Address"
	  ::= { brzaccVLAUMacAddressDatabase 3 }

brzaccVLAUNewAdbEntry  OBJECT-TYPE
	  SYNTAX BrzaccVLAUNewAdbEntry
	  MAX-ACCESS not-accessible
	  STATUS current
      DESCRIPTION
      "Applicable to AU/BU only with SW version 5.0 and higher. 
       An entry in the AU/BU MAC Address New Database table."
	  INDEX { brzaccVLNewAdbMacAddress }
	  ::= { brzaccVLAUNewAdbTable 1 }


BrzaccVLAUNewAdbEntry ::= SEQUENCE {
		brzaccVLNewAdbMacAddress				MacAddress,  
		brzaccVLNewAdbIPaddress					IpAddress,
		brzaccVLNewAdbUnitName					DisplayString,
		brzaccVLNewAdbUnitType					INTEGER,
		brzaccVLNewAdbSwVersion					DisplayString,
		brzaccVLNewAdbHwRevision				INTEGER,
		brzaccVLNewAdbCpldVer					DisplayString,
		brzaccVLNewAdbBootVer					DisplayString,
		brzaccVLNewAdbCountryCode    			INTEGER,
		brzaccVLNewAdbCirTx						INTEGER,
		brzaccVLNewAdbMirTx						INTEGER,
		brzaccVLNewAdbCirRx						INTEGER,
		brzaccVLNewAdbMirRx						INTEGER,
		brzaccVLNewAdbCirMaxDelay				INTEGER,
		brzaccVLNewAdbAtpcOption				INTEGER,
		brzaccVLNewAdbAdapModOption				INTEGER,
		brzaccVLNewAdbBurstModeOption			INTEGER,
		brzaccVLNewAdbConcatenationOption		INTEGER,
		brzaccVLNewAdbSecurityMode				INTEGER,
		brzaccVLNewAdbAuthOption				INTEGER,
		brzaccVLNewAdbDataEncyptOption			INTEGER,
		brzaccVLAdbWi2IPaddress					IpAddress,
		brzaccVLNewAdbStatus					INTEGER,
		brzaccVLNewAdbAge						INTEGER,
		brzaccVLNewAdbDistance					INTEGER,
		brzaccVLNewAdbSNR						INTEGER,
		brzaccVLNewAdbMaxModulationLevel		INTEGER,
		brzaccVLNewAdbTxFramesTotal				Counter32,
		brzaccVLNewAdbDroppedFramesTotal		Counter32,
		brzaccVLNewAdbTxSuccessModLevel1		Counter32,
		brzaccVLNewAdbTxSuccessModLevel2		Counter32,
		brzaccVLNewAdbTxSuccessModLevel3		Counter32,
		brzaccVLNewAdbTxSuccessModLevel4		Counter32,
		brzaccVLNewAdbTxSuccessModLevel5		Counter32,
		brzaccVLNewAdbTxSuccessModLevel6		Counter32,
		brzaccVLNewAdbTxSuccessModLevel7		Counter32,
		brzaccVLNewAdbTxSuccessModLevel8		Counter32,
		brzaccVLNewAdbTxFailedModLevel1			Counter32,
		brzaccVLNewAdbTxFailedModLevel2			Counter32,
		brzaccVLNewAdbTxFailedModLevel3			Counter32,
		brzaccVLNewAdbTxFailedModLevel4			Counter32,
		brzaccVLNewAdbTxFailedModLevel5			Counter32,
		brzaccVLNewAdbTxFailedModLevel6			Counter32,
		brzaccVLNewAdbTxFailedModLevel7			Counter32,
		brzaccVLNewAdbTxFailedModLevel8			Counter32,
		brzaccVLNewAdbMainSwVersion				DisplayString,
		brzaccVLNewAdbShadowSwVersion			DisplayString,
		brzaccVLNewAdbReadOnlyCommunity			DisplayString,
		brzaccVLNewAdbWriteCommunity			DisplayString,
		brzaccVLNewAdbAIFS						INTEGER,
		brzaccVLNewAdbMinimumCW					INTEGER,
		brzaccVLNewAdbMaximumCW					INTEGER,
		brzaccVLNewAdbESSID						DisplayString,
		brzaccVLNewAdbRSSI						INTEGER,
		brzaccVLNewAdbDfsOption					INTEGER
	 }

brzaccVLNewAdbMacAddress  OBJECT-TYPE
	  SYNTAX MacAddress  
	  MAX-ACCESS read-only
	  STATUS current
	  DESCRIPTION
      "Applicable to AU/BU only with SW version 5.0 and higher. 
	   The MAC Address of an SU/RB entry in the MAC Address Database 
	   table."
	  ::= { brzaccVLAUNewAdbEntry 1 }

brzaccVLNewAdbIPaddress	OBJECT-TYPE
	  SYNTAX IpAddress
	  MAX-ACCESS read-only
	  STATUS current
	  DESCRIPTION
      "Applicable to AU/BU only with SW version 5.0 and higher. 
	   The Running IP address of the relevant SU/RB.
	   Not available for SU-EZ with SW version lower than 1.1.1"
	  ::= { brzaccVLAUNewAdbEntry 2 }

brzaccVLNewAdbUnitName	OBJECT-TYPE
	  SYNTAX DisplayString 
	  MAX-ACCESS read-only
	  STATUS current
	  DESCRIPTION
      "Applicable to AU/BU only with SW version 5.0 and higher. 
	   The unit name of the relevant SU/RB.
	   Not available for SU-EZ."
	  ::= { brzaccVLAUNewAdbEntry 3 }

brzaccVLNewAdbUnitType	OBJECT-TYPE
	  SYNTAX INTEGER { su-6-1D(3),
	                   su-6-BD(4),
	                   su-24-BD(5),
                       rb-B14(8),
                       rb-B28(9), 
                       su-BD(10),
                       su-54-BD (11), 
                       su-3-1D(12),
                       su-3-4D(13),
                       su4900(18), 
                       rb-B100(20), 
                       su-I(21),
                       su-EZ(23),
                       su-V(24),
                       rb-B10(26),
                       su-8-BD(27),
                       su-1-BD(28),
                       su-3-L(29),
                       su-6-L(30),
                       su-12-L(31),
                       su(33),
					   na (255)
					 }
	  MAX-ACCESS read-only
	  STATUS current
	  DESCRIPTION
      "Applicable to AU/BU only with SW version 5.0 and higher. 
	   The type of the relevant SU/RB.
			 su-6-1D  (3) : SU-6-1D (subscriber unit supporting 6 Mbps)
                            Starting with 5.0 this is deprecated.
                            When a SU-6-1D is upgraded to 5.0, its type will be changed to SU-6-BD.
             su-6-BD  (4) : SU-6-BD (subscriber unit supporting 6 Mbps).
             su-24-BD (5) : SU-24-BD (subscriber unit supporting 24 Mbps).
			 rb-B14   (8) : RB-B14 (BreezeNET Remote Bridge supporting 14 Mbps).
			 rb-B28   (9) : RB-B28 (BreezeNET Remote Bridge supporting 28 Mbps).
			 su-BD   (10) : SU-BD (subscriber unit).
			 su-54-BD(11) : SU-54-BD (subscriber unit supporting 54 Mbps).
             su-3-1D (12) : SU-3-1D (subscriber unit supporting 3 Mbps).
                            Starting with 5.0 this is deprecated.
                            When a SU-3-1D is upgraded to 5.0, its type will be changed to SU-3-BD.
             su-3-4D (13) : SU-3-4D (subscriber unit supporting 3 Mbps).
                            Starting with 5.0 SW version this unit will work in BD mode
             suBD4900(18) : SU-BD-4900 (BreezeAccess 4900 subscriber unit)
             rb-B100 (20) : BU-B100 (BreezeNET Remote Bridge unlimited throughput) 
             su-I    (21) : SU-I
             su-EZ   (23) : SU-EZ
             su-8-BD (27) : SU-8-BD (subscriber unit supporting 8 Mbps).
             su-1-BD (28) : SU-1-BD (subscriber unit supporting 1 Mbps).
             su-3-L (29) : SU-3-L (subscriber unit supporting 3 Mbps).
             su-6-L (30) : SU-6-L (subscriber unit supporting 6 Mbps).
             su-12-L (31) : SU-12-L (subscriber unit supporting 12 Mbps).
             su      (33) : SU (security subscriber unit)
			 na     (255) : Not Available"
	  ::= { brzaccVLAUNewAdbEntry 4 }

brzaccVLNewAdbSwVersion OBJECT-TYPE
	  SYNTAX DisplayString  
	  MAX-ACCESS read-only
	  STATUS current
	  DESCRIPTION	
      "Applicable to AU/BU only with SW version 5.0 and higher. 
	   The SW version of the relevant SU/RB.
	   Not available for SU-EZ."
	  ::= { brzaccVLAUNewAdbEntry 5 }

brzaccVLNewAdbHwRevision     OBJECT-TYPE
   SYNTAX INTEGER  {hwRevisionA(1), hwRevisionB(2), hwRevisionC(3), 
                    hwRevisionD(4), hwRevisionE(5), hwRevisionF(6),
                    hwRevisionG(7), na(255)}
   MAX-ACCESS read-only
   STATUS current
   DESCRIPTION 
   "Applicable to AU/BU only with SW version 5.0 and higher.  
    The SU/RB HW Revision.
    Not available for SU-EZ."
   ::= { brzaccVLAUNewAdbEntry 6 }

brzaccVLNewAdbCpldVer     OBJECT-TYPE
   SYNTAX DisplayString
   MAX-ACCESS read-only
   STATUS current
   DESCRIPTION 
   "Applicable to AU/BU only with SW version 5.0 and higher.  
    The SU/RB CPLD Version.
    Not available for SU-EZ."
   ::= { brzaccVLAUNewAdbEntry 7 }

brzaccVLNewAdbBootVer     OBJECT-TYPE
   SYNTAX DisplayString
   MAX-ACCESS read-only
   STATUS current
   DESCRIPTION 
   "Applicable to AU/BU only with SW version 5.0 and higher.  
    The SU/RB Boot Version.
    Not available for SU-EZ."
   ::= { brzaccVLAUNewAdbEntry 8 }

brzaccVLNewAdbCountryCode     OBJECT-TYPE
   SYNTAX INTEGER  
   MAX-ACCESS read-only
   STATUS current
   DESCRIPTION 
   "Applicable to AU/BU only with SW version 5.0 and higher.  
    The SU/RB country code. 9999 means unavailable country code"
   ::= { brzaccVLAUNewAdbEntry 9 }

brzaccVLNewAdbCirTx  OBJECT-TYPE
   SYNTAX INTEGER 
   MAX-ACCESS read-only
   STATUS current
   DESCRIPTION 
   "Applicable to AU/BU only with SW version 5.0 and higher.   
    For BreezeNET-B products it is 0. 
    For SU_EZ with SW version 1.00.15 is not relevant and it is 0.
    The value configured in the relevant SU for the CIR: 
    SU to AU parameter."
   ::= { brzaccVLAUNewAdbEntry 10 }

brzaccVLNewAdbMirTx  OBJECT-TYPE
   SYNTAX INTEGER 
   MAX-ACCESS read-only
   STATUS current
   DESCRIPTION 
   "Applicable to AU/BU only with SW version 5.0 and higher. 
    The value configured in the relevant SU/RB for the MIR: 
    SU/RB to AU/BU parameter.
    For SU-EZ SW version 1.00.15, it represents the value 
    set in AU-EZ."
   ::= { brzaccVLAUNewAdbEntry 11 }

brzaccVLNewAdbCirRx  OBJECT-TYPE
   SYNTAX INTEGER 
   MAX-ACCESS read-only
   STATUS current
   DESCRIPTION 
   "Applicable to AU/BU only with SW version 5.0 and higher.   
    For BreezeNET-B products it is 0. 
    This parameter is not relevant for SU-EZ with version 1.00.15 
    and it is 0.
    The value configured in the relevant SU for the CIR: 
    AU to SU parameter."
   ::= { brzaccVLAUNewAdbEntry 12 }

brzaccVLNewAdbMirRx  OBJECT-TYPE
   SYNTAX INTEGER 
   MAX-ACCESS read-only
   STATUS current
   DESCRIPTION 
   "Applicable to AU/BU only with SW version 5.0 and higher. 
    This parameter is not relevant for SU-EZ with version 1.00.15 
    and it is 0.
    The value configured in the relevant SU/RB for the MIR: 
    AU/BU to SU/RB parameter."
   ::= { brzaccVLAUNewAdbEntry 13 }

brzaccVLNewAdbCirMaxDelay   OBJECT-TYPE
   SYNTAX INTEGER 
   MAX-ACCESS read-only
   STATUS current
   DESCRIPTION 
   "Applicable to AU/BU only with SW version 5.0 and higher. 
    For BreezeNET-B products and SU-EZ with SW version 1.00.15 
    it is not relevant.
    The value configured in the relevant SU/RB for the CIR Maximum 
    Delay parameter.
    It returns maximum value on 32 bits for SU-EZ with 1.00.15 
    and this means NA (Not Available)."
   ::= { brzaccVLAUNewAdbEntry 14 }

brzaccVLNewAdbAtpcOption     OBJECT-TYPE
   SYNTAX INTEGER  {disable (1), enable (2), na (255)}
   MAX-ACCESS read-only
   STATUS current
   DESCRIPTION 
   "Applicable to AU/BU only with SW version 5.0 and higher.  
    The SU/RB ATPC option configuration."
   ::= { brzaccVLAUNewAdbEntry 15 }

brzaccVLNewAdbAdapModOption     OBJECT-TYPE
   SYNTAX INTEGER  {disable (1), enable (2), na (255)}
   MAX-ACCESS read-only
   STATUS current
   DESCRIPTION 
   "Applicable to AU/BU only with SW version 5.0 and higher.  
    The SU/RB adaptive modulation option configuration. 
    It is not applicable for SU-EZ."
   ::= { brzaccVLAUNewAdbEntry 16 }

brzaccVLNewAdbBurstModeOption     OBJECT-TYPE
   SYNTAX INTEGER  {disable (1), enable (2), na (255)}
   MAX-ACCESS read-only
   STATUS current
   DESCRIPTION 
   "Applicable to AU/BU only with SW version 5.0 and higher.  
    The SU/RB burst mode option configuration.
    It is not applicable for SU-EZ."
   ::= { brzaccVLAUNewAdbEntry 17 }

brzaccVLNewAdbConcatenationOption     OBJECT-TYPE
   SYNTAX INTEGER  {disable (1), enable (2), na(255)}
   MAX-ACCESS read-only
   STATUS current
   DESCRIPTION 
   "Applicable to AU/BU only with SW version 5.0 and higher.  
    The SU/RB concatenation option configuration.
    It is not applicable for SU-EZ."
   ::= { brzaccVLAUNewAdbEntry 18 }

brzaccVLNewAdbSecurityMode     OBJECT-TYPE
   SYNTAX INTEGER  {wep(1), aes(2), fips197(3), na(255)}
   MAX-ACCESS read-only
   STATUS current
   DESCRIPTION 
   "Applicable to AU/BU only with SW version 5.0 and higher.  
    The SU/RB security mode configuration.
    Not available for SU-EZ."
   ::= { brzaccVLAUNewAdbEntry 19 }

brzaccVLNewAdbAuthOption     OBJECT-TYPE
   SYNTAX INTEGER  {openSystem (1), sharedKey (2), na (255)}
   MAX-ACCESS read-only
   STATUS current
   DESCRIPTION 
   "Applicable to AU/BU only with SW version 5.0 and higher.  
    The SU/RB authentication algorithm configuration.
    Not available for SU-EZ."
   ::= { brzaccVLAUNewAdbEntry 20 }

brzaccVLNewAdbDataEncyptOption     OBJECT-TYPE
   SYNTAX INTEGER  {disable (1), enable (2), na (255)}
   MAX-ACCESS read-only
   STATUS current
   DESCRIPTION 
   "Applicable to AU/BU only with SW version 5.0 and higher.  
    The SU/RB data encryption option configuration.
    Not available for SU-EZ."
   ::= { brzaccVLAUNewAdbEntry 21 }

brzaccVLAdbWi2IPaddress	OBJECT-TYPE
	  SYNTAX IpAddress
	  MAX-ACCESS read-only
	  STATUS current
	  DESCRIPTION
      "Applicable to AU/BU only with SW version 5.0 and higher. 
	   The IP address of the Wi2 Access Point.
	   Not available for SU-EZ."
	  ::= { brzaccVLAUNewAdbEntry 22 }

brzaccVLNewAdbStatus	 OBJECT-TYPE
	  SYNTAX INTEGER { associated       (1), 
	                   authenticated    (2),
	                   notAuthenticated (3) }
	  MAX-ACCESS read-only
	  STATUS current
	  DESCRIPTION	
      "Applicable to AU/BU only with SW version 5.0 and higher. 
	   The status of the relevant SU/RB."
	  ::= { brzaccVLAUNewAdbEntry 23 }

brzaccVLNewAdbAge	OBJECT-TYPE
	  SYNTAX INTEGER  
	  MAX-ACCESS read-only
	  STATUS current
	  DESCRIPTION	
      "Applicable to AU/BU only with SW version 5.0 and higher. 
	   The time since any packet was received from the relevant SU/RB."
	  ::= { brzaccVLAUNewAdbEntry 24 }

brzaccVLNewAdbDistance     OBJECT-TYPE
   SYNTAX INTEGER  {below-2-Km(1)}
   MAX-ACCESS read-only
   STATUS current
   DESCRIPTION 
   "Applicable to AU/BU only with SW version 5.0 and higher.  
    The distance between the SU/RB and the AU/BU (In Kilometers).
    It is not applicable for SU-EZ and it returns 0."
   ::= { brzaccVLAUNewAdbEntry 25 }

brzaccVLNewAdbSNR	OBJECT-TYPE
	  SYNTAX INTEGER  
	  MAX-ACCESS read-only
	  STATUS current
	  DESCRIPTION	
      "Applicable to AU/BU only with SW version 5.0 and higher. 
	   The average Signal to Noise Ratio in dB of frames received by 
	   the AU/BU from the relevant SU/RB."
	  ::= { brzaccVLAUNewAdbEntry 26 }

brzaccVLNewAdbMaxModulationLevel  OBJECT-TYPE
	  SYNTAX INTEGER  { modLevel-1 (1), 
	                    modLevel-2 (2), 
                        modLevel-3 (3), 
                        modLevel-4 (4), 
                        modLevel-5 (5), 
                        modLevel-6 (6), 
                        modLevel-7 (7), 
                        modLevel-8 (8),
                        na ( 255 ) 
                      }  
	  MAX-ACCESS read-only
	  STATUS current
	  DESCRIPTION	
      "Applicable to AU/BU only with SW version 5.0 and higher. 
	   The value configured in the relevant SU/RB for the Maximum Modulation 
	   Level parameter.
	   Modulation Level 8 is not applicable for units with HW revision A.
	   It is not applicable for SU-EZ and it returns na."
	  ::= { brzaccVLAUNewAdbEntry 27 }

brzaccVLNewAdbTxFramesTotal	OBJECT-TYPE
	  SYNTAX Counter32 
	  MAX-ACCESS read-only
	  STATUS current
	  DESCRIPTION	
      "Applicable to AU/BU only with SW version 5.0 and higher. 
	   Counts the total number of unicast  frames (excluding retransmissions) 
	   that were successfully transmitted to the SU/RB over the wireless link."
	  ::= { brzaccVLAUNewAdbEntry 28 }

brzaccVLNewAdbDroppedFramesTotal  OBJECT-TYPE
	  SYNTAX Counter32 
	  MAX-ACCESS read-only
	  STATUS current
	  DESCRIPTION	
      "Applicable to AU/BU only with SW version 5.0 and higher. 
	   Counts the total number of frames intended to the SU/RB that 
	   were dropped because they were retransmitted to the extent 
	   of the maximum allowed number of retransmissions without 
	   being acknowledged."
	  ::= { brzaccVLAUNewAdbEntry 29 }

brzaccVLNewAdbTxSuccessModLevel1	OBJECT-TYPE
	  SYNTAX Counter32 
	  MAX-ACCESS read-only
	  STATUS current
	  DESCRIPTION	
      "Applicable to AU/BU only with SW version 5.0 and higher. 
	   Counts the total number of unicast frames (excluding retransmissions) 
	   that were successfully transmitted to the SU/RB over the wireless link 
	   using modulation level 1."
	  ::= { brzaccVLAUNewAdbEntry 30 }

brzaccVLNewAdbTxSuccessModLevel2	OBJECT-TYPE
	  SYNTAX Counter32 
	  MAX-ACCESS read-only
	  STATUS current
	  DESCRIPTION	
      "Applicable to AU/BU only with SW version 5.0 and higher. 
	   Counts the total number of unicast frames (excluding retransmissions) 
	   that were successfully transmitted to the SU/RB over the wireless link 
	   using modulation level 2."
	  ::= { brzaccVLAUNewAdbEntry 31 }

brzaccVLNewAdbTxSuccessModLevel3	OBJECT-TYPE
	  SYNTAX Counter32 
	  MAX-ACCESS read-only
	  STATUS current
	  DESCRIPTION	
      "Applicable to AU/BU only with SW version 5.0 and higher. 
	   Counts the total number of unicast frames (excluding retransmissions) 
	   that were successfully transmitted to the SU/BU over the wireless link 
	   using modulation level 3."
	  ::= { brzaccVLAUNewAdbEntry 32 }

brzaccVLNewAdbTxSuccessModLevel4	OBJECT-TYPE
	  SYNTAX Counter32 
	  MAX-ACCESS read-only
	  STATUS current
	  DESCRIPTION	
      "Applicable to AU/BU only with SW version 5.0 and higher. 
	   Counts the total number of unicast frames (excluding retransmissions) 
	   that were successfully transmitted to the SU/RB over the wireless link 
	   using modulation level 4."
	  ::= { brzaccVLAUNewAdbEntry 33 }

brzaccVLNewAdbTxSuccessModLevel5	OBJECT-TYPE
	  SYNTAX Counter32 
	  MAX-ACCESS read-only
	  STATUS current
	  DESCRIPTION	
      "Applicable to AU/BU only with SW version 5.0 and higher. 
	   Counts the total number of unicast frames (excluding retransmissions) 
	   that were successfully transmitted to the SU/RB over the wireless link 
	   using modulation level 5."
	  ::= { brzaccVLAUNewAdbEntry 34 }

brzaccVLNewAdbTxSuccessModLevel6	OBJECT-TYPE
	  SYNTAX Counter32 
	  MAX-ACCESS read-only
	  STATUS current
	  DESCRIPTION	
      "Applicable to AU/BU only with SW version 5.0 and higher. 
	   Counts the total number of unicast frames (excluding retransmissions) 
	   that were successfully transmitted to the SU/BU over the wireless link 
	   using modulation level 6."
	  ::= { brzaccVLAUNewAdbEntry 35 }

brzaccVLNewAdbTxSuccessModLevel7	OBJECT-TYPE
	  SYNTAX Counter32 
	  MAX-ACCESS read-only
	  STATUS current
	  DESCRIPTION	
      "Applicable to AU/BU only with SW version 5.0 and higher. 
	   Counts the total number of unicast frames (excluding retransmissions) 
	   that were successfully transmitted to the SU/RB over the wireless link 
	   using modulation level 7."
	  ::= { brzaccVLAUNewAdbEntry 36 }

brzaccVLNewAdbTxSuccessModLevel8	OBJECT-TYPE
	  SYNTAX Counter32 
	  MAX-ACCESS read-only
	  STATUS current
	  DESCRIPTION	
      "Applicable to AU/BU only with SW version 5.0 and higher. 
	   Counts the total number of unicast frames (excluding retransmissions) 
	   that were successfully transmitted to the SU/RB over the wireless link 
	   using modulation level 8.
	   Not applicable for units with HW revision A."
	  ::= { brzaccVLAUNewAdbEntry 37 }

brzaccVLNewAdbTxFailedModLevel1	OBJECT-TYPE
	  SYNTAX Counter32 
	  MAX-ACCESS read-only
	  STATUS current
	  DESCRIPTION	
      "Applicable to AU/BU only with SW version 5.0 and higher. 
	   Counts the total number of failures to successfully
	   transmit unicast frames intended to the SU/RB using modulation level 1."
	  ::= { brzaccVLAUNewAdbEntry 38 }

brzaccVLNewAdbTxFailedModLevel2	OBJECT-TYPE
	  SYNTAX Counter32 
	  MAX-ACCESS read-only
	  STATUS current
	  DESCRIPTION	
      "Applicable to AU/BU only with SW version 5.0 and higher. 
	   Counts the total number of failures to successfully
	   transmit unicast frames intended to the SU/RB using modulation level 2."
	  ::= { brzaccVLAUNewAdbEntry 39 }

brzaccVLNewAdbTxFailedModLevel3	OBJECT-TYPE
	  SYNTAX Counter32 
	  MAX-ACCESS read-only
	  STATUS current
	  DESCRIPTION	
      "Applicable to AU/BU only with SW version 5.0 and higher. 
	   Counts the total number of failures to successfully
	   transmit unicast frames intended to the SU/RB using modulation level 3."
	  ::= { brzaccVLAUNewAdbEntry 40 }

brzaccVLNewAdbTxFailedModLevel4	OBJECT-TYPE
	  SYNTAX Counter32 
	  MAX-ACCESS read-only
	  STATUS current
	  DESCRIPTION	
      "Applicable to AU/BU only with SW version 5.0 and higher. 
	   Counts the total number of failures to successfully
	   transmit unicast frames intended to the SU/RB using modulation level 4."
	  ::= { brzaccVLAUNewAdbEntry 41 }

brzaccVLNewAdbTxFailedModLevel5	OBJECT-TYPE
	  SYNTAX Counter32 
	  MAX-ACCESS read-only
	  STATUS current
	  DESCRIPTION	
      "Applicable to AU/BU only with SW version 5.0 and higher. 
	   Counts the total number of failures to successfully
	   transmit unicast frames intended to the SU/RB using modulation level 5."
	  ::= { brzaccVLAUNewAdbEntry 42 }

brzaccVLNewAdbTxFailedModLevel6	OBJECT-TYPE
	  SYNTAX Counter32 
	  MAX-ACCESS read-only
	  STATUS current
	  DESCRIPTION	
      "Applicable to AU/BU only with SW version 5.0 and higher. 
	   Counts the total number of failures to successfully
	   transmit unicast frames intended to the SU/RB using modulation level 6."
	  ::= { brzaccVLAUNewAdbEntry 43 }

brzaccVLNewAdbTxFailedModLevel7	OBJECT-TYPE
	  SYNTAX Counter32 
	  MAX-ACCESS read-only
	  STATUS current
	  DESCRIPTION	
      "Applicable to AU/BU only with SW version 5.0 and higher. 
	   Counts the total number of failures to successfully
	   transmit unicast frames intended to the SU/RB using modulation level 7."
	  ::= { brzaccVLAUNewAdbEntry 44 }

brzaccVLNewAdbTxFailedModLevel8	OBJECT-TYPE
	  SYNTAX Counter32 
	  MAX-ACCESS read-only
	  STATUS current
	  DESCRIPTION	
      "Applicable to AU/BU only with SW version 5.0 and higher. 
	   Counts the total number of failures to successfully
	   transmit unicast frames intended to the SU/RB using modulation level 8.
	   Not applicable for units with HW revision A."
	  ::= { brzaccVLAUNewAdbEntry 45 }
	  
brzaccVLNewAdbMainSwVersion	OBJECT-TYPE
	  SYNTAX DisplayString (SIZE(0..35)) 
	  MAX-ACCESS read-only
	  STATUS current
	  DESCRIPTION	
      "Applicable to AU/BU only with SW version 5.0 and higher. 
	   Main Software Version of SU. Not available for SU-EZ."
	  ::= { brzaccVLAUNewAdbEntry 46 }
	  
brzaccVLNewAdbShadowSwVersion	OBJECT-TYPE
	  SYNTAX DisplayString (SIZE(0..35))
	  MAX-ACCESS read-only
	  STATUS current
	  DESCRIPTION	
      "Applicable to AU/BU only with SW version 5.0 and higher. 
	   Shadow Software Version of SU. Not available for SU-EZ."
	  ::= { brzaccVLAUNewAdbEntry 47 }
	  
brzaccVLNewAdbReadOnlyCommunity	OBJECT-TYPE
	  SYNTAX DisplayString (SIZE(1..8))
	  MAX-ACCESS read-only
	  STATUS current
	  DESCRIPTION	
      "Applicable to AU/BU only with SW version 5.0 and higher . 
	   SU/RB Read Only Community. Not available for SU-EZ."
	  ::= { brzaccVLAUNewAdbEntry 48 }
	  

brzaccVLNewAdbWriteCommunity	OBJECT-TYPE
	  SYNTAX DisplayString (SIZE(1..8))
	  MAX-ACCESS read-only
	  STATUS current
	  DESCRIPTION	
      "Applicable to AU/BU only with SW version 5.0 and higher. 
	   SU/RB Write Community
   	   The Community is accessible only with the Read-Write community 
       string (administrator password).
       If the Read-Only community of the AU/BU is used this field will 
       contain the SU/RB read-only community.
       Not available for SU-EZ with SW version lower than 1.1.1"
	  ::= { brzaccVLAUNewAdbEntry 49 }
	
 brzaccVLNewAdbAIFS	OBJECT-TYPE
	  SYNTAX INTEGER  
	  MAX-ACCESS read-only
	  STATUS current
	  DESCRIPTION	
      "Applicable to AU/BU only with SW version 5.0 and higher. 
	  The Arbitration Inter-Frame Spacing (AIFS) of relevant SU/RB.
	  Not available for SU-EZ and it returns 0."
	  ::= { brzaccVLAUNewAdbEntry 50 }
	  	  

 brzaccVLNewAdbMinimumCW OBJECT-TYPE
	  SYNTAX INTEGER  
	  MAX-ACCESS read-only
	  STATUS current
	  DESCRIPTION	
      "Applicable to AU/BU only with SW version 5.0 and higher. 
	   The Minimum Contention Window of relevant SU/RB.
	   Not available for SU-EZ and it returns 0."
	  ::= { brzaccVLAUNewAdbEntry 51 }

 brzaccVLNewAdbMaximumCW OBJECT-TYPE
	  SYNTAX INTEGER  
	  MAX-ACCESS read-only
	  STATUS current
	  DESCRIPTION	
      "Applicable to AU/BU only with SW version 5.0 and higher. 
	   The Maximum Contention Window of relevant SU/RB.
	   Not available for SU-EZ and it returns 0."
	  ::= { brzaccVLAUNewAdbEntry 52 }

brzaccVLNewAdbESSID	OBJECT-TYPE
	  SYNTAX DisplayString (SIZE(0..31))  
	  MAX-ACCESS read-only
	  STATUS current
	  DESCRIPTION	
      "Applicable to AU/BU only with SW version 5.0 and higher. 
	   The ESSID of relevant SU/RB.
       The ESSID is accessible only with the write community 
             string (administrator password)."
	  ::= { brzaccVLAUNewAdbEntry 53 }

brzaccVLNewAdbRSSI OBJECT-TYPE
	SYNTAX INTEGER  
	MAX-ACCESS read-only
	STATUS current
	DESCRIPTION 
	 "Applicable to AU/BU only with SW version 5.1 and higher. 
	 The average Received Signal Strength Indication of frames received by 
	 the AU/BU from the relevant SU/RB.
	 This value is given in dBm units."
	::= { brzaccVLAUNewAdbEntry 54 }

brzaccVLNewAdbDfsOption OBJECT-TYPE
	SYNTAX INTEGER { disable (1), enable (2)}
	MAX-ACCESS read-only
	STATUS current
	DESCRIPTION 
	 "Applicable to AU/BU only with SW version 5.5.21 and higher. 
	 The DFS option configuration received by 
	 the AU/BU from the relevant SU/RB."
	::= { brzaccVLAUNewAdbEntry 55 }


brzaccVLAggregateMIRCIR OBJECT IDENTIFIER ::= { brzaccVLAUMacAddressDatabase 4 }

brzaccVLAggregateMIRUplink OBJECT-TYPE
	SYNTAX INTEGER
	MAX-ACCESS read-only
	STATUS current
	DESCRIPTION 
	"Applicable to AU only with SW version 6.0 and higher. 
	Aggregate MIR uplink."
	::= { brzaccVLAggregateMIRCIR 1 }
	
brzaccVLAggregateMIRDownlink OBJECT-TYPE
	SYNTAX INTEGER
	MAX-ACCESS read-only
	STATUS current
	DESCRIPTION 
	"Applicable to AU only with SW version 6.0 and higher. 
	Aggregate MIR downlink."
	::= { brzaccVLAggregateMIRCIR 2 }
	
brzaccVLAggregateCIRUplink OBJECT-TYPE
	SYNTAX INTEGER
	MAX-ACCESS read-only
	STATUS current
	DESCRIPTION 
	"Applicable to AU only with SW version 6.0 and higher. 
	Aggregate CIR uplink."
	::= { brzaccVLAggregateMIRCIR 3 }
	
brzaccVLAggregateCIRDownlink OBJECT-TYPE
	SYNTAX INTEGER
	MAX-ACCESS read-only
	STATUS current
	DESCRIPTION 
	"Applicable to AU only with SW version 6.0 and higher. 
	Aggregate CIR downlink."
	::= { brzaccVLAggregateMIRCIR 4 }
	
brzaccVLUpLinkQualityIndicator  OBJECT IDENTIFIER ::= { brzaccVLSiteSurvey 6}

brzaccVLMeasureUpLinkQualityIndicator	 OBJECT-TYPE
	  SYNTAX INTEGER { start (1) , cancel (2)}
	  MAX-ACCESS read-write
	  STATUS current
	  DESCRIPTION	
	  "Applicable to SU/RB. 
	   Starts calculation of LQI. 
	   The calculation will be for a period of 10 seconds."  
	  ::= { brzaccVLUpLinkQualityIndicator 1 }


brzaccVLReadUpLinkQualityIndicator	 OBJECT-TYPE
	  SYNTAX INTEGER 
	  MAX-ACCESS read-only
	  STATUS current
	  DESCRIPTION	
	  "Applicable to SU/RB. 
	   The results of the last LQI calculation. 
	   Range: 1 to 8."  
	  ::= { brzaccVLUpLinkQualityIndicator 2 }
 

brzaccVLUpLinkQualityIndicatorStatus	 OBJECT-TYPE
	  SYNTAX INTEGER  {fullTest(1) , limitedTest(2)}
	  MAX-ACCESS read-only
	  STATUS current
	  DESCRIPTION	
	  "Applicable to SU/RB Only. 
	   Indicates the test conditions. 
	   fullTest means that there are no limitations 
	   on the range of available modulation levels, and that all modulation levels 
	   from 1 to 8 can be used. 
	   limitedTest indicates that the results may not indicate the true quality since 
	   the available range is limited - by HW (HW Revision A), 
	   or by the applicable parameters in the country code, 
	   or by the configurable Maximum Modulation Level parameter."  
	  ::= { brzaccVLUpLinkQualityIndicator 3 }
	  
-- AC pinpoint table end
	  
brzaccVLMacPinpoint   OBJECT IDENTIFIER ::= {brzaccVLSiteSurvey 7}

          brzaccVLMacPinpointTable OBJECT-TYPE
              SYNTAX  SEQUENCE OF BrzaccVLMacPinpointEntry
              MAX-ACCESS  not-accessible
              STATUS  current
              DESCRIPTION
                      "Applicable to AU/BU only.
                      A table that contains information about wireless device
                      used by a certain Ethernet station in order to
                      connect to the wireless network"
              ::= { brzaccVLMacPinpoint 1 }

          brzaccVLMacPinpointEntry OBJECT-TYPE
              SYNTAX  BrzaccVLMacPinpointEntry
              MAX-ACCESS  not-accessible
              STATUS  current
              DESCRIPTION
                      "Applicable to AU/BU only. An entry in the MAC Pinpoint Table.
                      Each entry contains an Ethernet station MAC address and the MAC
                      address of the wireless device used to connect it to the wireless 
                      network"
              INDEX   { mptEthernetStationMACAddress }
              ::= { brzaccVLMacPinpointTable 1 }

          BrzaccVLMacPinpointEntry ::=
              SEQUENCE {
                  mptEthernetStationMACAddress
                      MacAddress,
                  mptUnitMACAddress
                      MacAddress
              }

          mptEthernetStationMACAddress OBJECT-TYPE
              SYNTAX  MacAddress
              MAX-ACCESS  read-only
              STATUS  current
              DESCRIPTION
                      "Applicable to AU/BU only.
                      The MAC address of the Ethernet station. It is used as an 
                      index in the MAC Pinpoint Table."
              ::= { brzaccVLMacPinpointEntry 1 }
              
          mptUnitMACAddress OBJECT-TYPE
              SYNTAX  MacAddress
              MAX-ACCESS  read-only
              STATUS  current
              DESCRIPTION
                      "Applicable to AU/BU only. The MAC address of the wireless 
                      device used by the station with the MAC Address from the 
                      index in order to access the wireless network."
              ::= { brzaccVLMacPinpointEntry 2 }
-- AC pinpoint table end

-- GATEWAY TABLE BEGIN

brzaccVLDrapGatewaysTable OBJECT-TYPE
        SYNTAX SEQUENCE OF BrzaccVLDrapGatewayEntry
        MAX-ACCESS not-accessible
        STATUS current
        DESCRIPTION
		"This table provides information about Gateways supporting DRAP that are
		registered at the AU"
        ::= { brzaccVLSiteSurvey 8 }
        
brzaccVLHiddenESSIDTable OBJECT-TYPE
		SYNTAX SEQUENCE OF BrzaccVLHiddenESSIDEntry
		MAX-ACCESS not-accessible
		STATUS current
		DESCRIPTION
        "Applicable to SU/RB only with SW version 5.0 and higher.
        The AU/BU units that rejected the subcribers because 
        of worng ESSID"
		::= {brzaccVLSiteSurvey 9}
		
brzaccVLHiddenESSIDEntry OBJECT-TYPE
   SYNTAX BrzaccVLHiddenESSIDEntry
   MAX-ACCESS not-accessible
   STATUS current
          DESCRIPTION
         "Applicable to SU/RB only with SW version 5.0 and higher. 
          An entry in the Hidden ESSID table."
   INDEX { brzaccVLHiddenESSIDMacAddress }
   ::= { brzaccVLHiddenESSIDTable 1 }
 
      
BrzaccVLHiddenESSIDEntry ::= SEQUENCE {
  brzaccVLHiddenESSIDMacAddress  MacAddress,  
  brzaccVLHiddenESSIDAge   INTEGER
                }
 
brzaccVLHiddenESSIDMacAddress  OBJECT-TYPE
   SYNTAX MacAddress  
   MAX-ACCESS read-only
   STATUS current
   DESCRIPTION
          "The MAC Address of the staion that rejected the subscriber
          beacuse of wrong ESSID"
   ::= { brzaccVLHiddenESSIDEntry 1 }
 
brzaccVLHiddenESSIDAge OBJECT-TYPE
   SYNTAX INTEGER
   MAX-ACCESS read-only
   STATUS current
   DESCRIPTION
          "The time (in second) passed since the corresponding AU/BU 
          rejected the subscriber because of wrong ESSID"
   ::= { brzaccVLHiddenESSIDEntry 2 }


brzaccVLDrapGatewayEntry  OBJECT-TYPE
        SYNTAX BrzaccVLDrapGatewayEntry
        MAX-ACCESS not-accessible
        STATUS current
        DESCRIPTION
        "A Drap Gateway Entry." 
        INDEX { brzaccVLDrapGatewayIndex }
        ::= { brzaccVLDrapGatewaysTable 1 }

BrzaccVLDrapGatewayEntry ::= SEQUENCE {
		brzaccVLDrapGatewayIndex					INTEGER,
		brzaccVLDrapGatewayIP 					    IpAddress,
       	brzaccVLDrapGatewayType					    INTEGER,
        brzaccVLDrapGatewayNoOfActiveVoiceCalls		INTEGER
        }
            
brzaccVLDrapGatewayIndex OBJECT-TYPE
        SYNTAX INTEGER	(1..512)  
        MAX-ACCESS read-only
        STATUS current
        DESCRIPTION 
        "Gateway Entry's Index"
        ::= { brzaccVLDrapGatewayEntry 1 }
        
brzaccVLDrapGatewayIP OBJECT-TYPE
        SYNTAX IpAddress  
        MAX-ACCESS read-only
        STATUS current
        DESCRIPTION 
        "The IP address of the Gateway"
        ::= { brzaccVLDrapGatewayEntry 2 }

brzaccVLDrapGatewayType OBJECT-TYPE
        SYNTAX INTEGER  { vgDataVoice (4), vgData1Voice1 (5), 
                          vgData4Voice2 (6), vgDataVoice2(7), 
                          ngData4Wireless (11),
                          vgUnknown(255)
                         }
        MAX-ACCESS read-only
        STATUS current
        DESCRIPTION 
        "The Gateway type"
        ::= { brzaccVLDrapGatewayEntry 3 }

brzaccVLDrapGatewayNoOfActiveVoiceCalls OBJECT-TYPE
        SYNTAX INTEGER  
        MAX-ACCESS read-only
        STATUS current
        DESCRIPTION 
        "The current number of active voice calls handled by the Gateway"
        ::= { brzaccVLDrapGatewayEntry 4 }

brzaccVLAverageReceiveRSSI  OBJECT-TYPE
            SYNTAX INTEGER
            MAX-ACCESS read-only
            STATUS current
            DESCRIPTION 
            "Applicable to SU/RB only. 
             The average Received Signal Strength Indication of frames.
             This value is given in dBm units."
            ::= { brzaccVLSiteSurvey 10 }

brzaccVLCurrentNoiseFloor  OBJECT-TYPE
            SYNTAX INTEGER
            MAX-ACCESS read-only
            STATUS current
            DESCRIPTION 
            "Applicable to all units. 
             The current Noise Floor of the unit."
            ::= { brzaccVLSiteSurvey 11 }

brzaccVLAverageSignalInterferenceRatio  OBJECT-TYPE
            SYNTAX INTEGER
            MAX-ACCESS read-only
            STATUS current
            DESCRIPTION 
            "Applicable to all units. 
             The current Average Signal Interference Ratio of the unit."
            ::= { brzaccVLSiteSurvey 12 }



-- GATEWAY TABLE END 

-- ****************************************************************************************
--  TRAP defenitions: 
-- ****************************************************************************************

brzaccVLTraps OBJECT IDENTIFIER ::= { breezeAccessVLMib 14 }

brzaccVLTrapSUMacAddr OBJECT-TYPE
    SYNTAX  MacAddress
    MAX-ACCESS  read-only  
    STATUS current
    DESCRIPTION
    "Applicable to AU/BU only.
     SU/RB MAC Address."
    ::= { brzaccVLTraps 1 }

--brzaccVLTrapSNRQuality   OBJECT-TYPE
--    SYNTAX INTEGER
--    MAX-ACCESS read-only  
--    STATUS current
--    DESCRIPTION
--    "Applicable to SU only.
--     SNR of received signal."
--    ::= { brzaccVLTraps 2 }

brzaccVLTrapText  OBJECT-TYPE
    SYNTAX DisplayString
    MAX-ACCESS read-only
    STATUS current
    DESCRIPTION
    "Textual string for future use."
    ::= { brzaccVLTraps 3 }

brzaccVLTrapToggle    OBJECT-TYPE
    SYNTAX INTEGER{
        on (1),
        off (2)
        }
    MAX-ACCESS read-only
    STATUS current
    DESCRIPTION
    "Applicable to AU/BU only.
     An On/Off toggle status." 
    ::= { brzaccVLTraps 4 }

brzaccVLTrapParameterChanged  OBJECT-TYPE
    SYNTAX INTEGER{ cirOrMir (1),
                    ipFilter (2), 
                    vlan (4)}
    MAX-ACCESS read-only
    STATUS current
    DESCRIPTION
    "Not applicable starting with version 5.0.
	 Applicable to all units.
     A modification to one of the parameters related to CIR/MIR,  
     IP Filtering or VLAN."
    ::= { brzaccVLTraps 5 }

brzaccVLTrapAccessRights  OBJECT-TYPE
    SYNTAX INTEGER{ notLoggedIn   (1), 
                    readOnly      (2), 
                    installer     (3), 
                    administrator (4),  
                    factory       (5) }
    MAX-ACCESS read-only
    STATUS current
    DESCRIPTION
    "Applicable to all units.
     The access rights used for login."
    ::= { brzaccVLTraps 6 }

brzaccVLTrapLog   OBJECT-TYPE
    SYNTAX INTEGER{ telnetLogin  (3), 
                    telnetLogout (4) }
    MAX-ACCESS read-only
    STATUS current
    DESCRIPTION
    "Applicable to all units.
     Login or logout to the Monitor program via Telnet."
    ::= { brzaccVLTraps 7 }

brzaccVLTrapTelnetUserIpAddress   OBJECT-TYPE
    SYNTAX  IpAddress  
    MAX-ACCESS read-only
    STATUS current
    DESCRIPTION
    "Applicable to all units.
     The IP address of a Telnet user."
    ::= { brzaccVLTraps 8 }

brzaccVLTrapRTx   OBJECT-TYPE
    SYNTAX INTEGER
    MAX-ACCESS read-only  
    STATUS current
    DESCRIPTION
    "Applicable to AU/BU only. 
     Retransmissions as a percentage of total transmissions."
    ::= { brzaccVLTraps 9 }

brzaccVLTrapFtpOrTftpStatus    OBJECT-TYPE
    SYNTAX INTEGER{
        successful (1),
        failed (2)
        }
    MAX-ACCESS read-only
    STATUS current
    DESCRIPTION
    "Applicable to all units.
     The status of the last FTP/TFTP loading procedure." 
    ::= { brzaccVLTraps 10 }
 
brzaccVLDFSMoveFreq    OBJECT-TYPE
    SYNTAX INTEGER
    MAX-ACCESS read-only
    STATUS current
    DESCRIPTION
    "Applicable to AU/BU with HW revision B and lower 
     (for units with HW revision C and higher replaced by 
     brzaccVLTrapDFSMoveFreq New to support a resolution of 0.5 MHz). 
     The new frequency in MHz after detecting radar on a previous channel."    
    ::= { brzaccVLTraps 11 }
 
brzaccVLDFSMoveFreqNew    OBJECT-TYPE
    SYNTAX DisplayString
    MAX-ACCESS read-only
    STATUS current
    DESCRIPTION
    "Applicable to AU/BU. 
     The new frequency in MHz after detecting radar on a previous channel. 
     (Replaces brzaccVLDFSMoveFreq to support a resolution of 0.5 MHz for 
     units with HW revision C and higher. If HW revision is B it will contain the same 
     value as brzaccVLDFSMoveFreq, but represented as string.)."
    ::= { brzaccVLTraps 12 }

    
brzaccVLEthBroadcastThresholdExceeded    OBJECT-TYPE
    SYNTAX INTEGER
    MAX-ACCESS read-only
    STATUS current
    DESCRIPTION
    "Applicable to all units. 
    The number of packets that are dropped by the ethernet broadcast/multicast limiter."
    ::= { brzaccVLTraps 13 }
 
 
brzaccVLTrapSubscriberType    OBJECT-TYPE
    SYNTAX INTEGER{ unknownSubscriberType(0), 
                    su-3(3)  , su-6(6)  , rb-14(14), 
                    su-24(24), rb-28(28), su-54(54), su-8(8), 
                    rb-100(100) }
    MAX-ACCESS read-only
    STATUS current
    DESCRIPTION
    "Applicable to AUS only.
    The type of subscriber that was rejected by AUS" 
    ::= { brzaccVLTraps 14 }


brzaccVLTrapMACAddress   OBJECT-TYPE
    SYNTAX MacAddress
    MAX-ACCESS read-only
    STATUS current
    DESCRIPTION
    "Applicable to BU/RB only.
    The MAC address of the BNET B unit whose type has been changed" 
    ::= { brzaccVLTraps 15 }
    
brzaccVLNewUnitTypeTrap  OBJECT-TYPE
    SYNTAX INTEGER { bu(1), rb(2) }
    MAX-ACCESS read-only
    STATUS current
    DESCRIPTION
    "Applicable to BU/RB only.
    The new type of the BNET B unit." 
    ::= { brzaccVLTraps 16 }
    
brzaccVLTrapSWVersion  OBJECT-TYPE
    SYNTAX DisplayString
    MAX-ACCESS read-only
    STATUS current
    DESCRIPTION
    "The SW version of the SU that tries to associate 
    with a station that has Wireless Link Prioritization Enabled"
    ::= { brzaccVLTraps 17 }    
            
brzaccVLTrapSequenceNumber    OBJECT-TYPE
    SYNTAX INTEGER
    MAX-ACCESS read-only
    STATUS current
    DESCRIPTION
    "Apllicable to AU/BU only. 
    Trap Variable indicating the sequence number of the last trap generated."
    ::= { brzaccVLTraps 18 }
    
brzaccVLTrapUnitMacAddr OBJECT-TYPE
    SYNTAX  MacAddress
    MAX-ACCESS  read-only  
    STATUS current
    DESCRIPTION
    "Applicable to all units.
    The MAC Address of the unit that is initiating the trap."
    ::= { brzaccVLTraps 19 }

brzaccVLTrapParameterGroupCode    OBJECT-TYPE
    SYNTAX INTEGER
    MAX-ACCESS read-only
    STATUS current
    DESCRIPTION
    "Applicable to AU/BU only.
    The code of group parameter that was changed."
    ::= { brzaccVLTraps 20 }

brzaccVLTrapNewIP    OBJECT-TYPE
    SYNTAX IpAddress
    MAX-ACCESS read-only
    STATUS current
    DESCRIPTION
    "Applicable to AU/BU only.
    The code of group parameter that was changed."
    ::= { brzaccVLTraps 21 }    
           
--
-- Private Traps for BreezeAccessVL
--

brzaccVLSUassociatedAUTRAP NOTIFICATION-TYPE
        OBJECTS
        {
           brzaccVLTrapSUMacAddr,     -- SU MAC address
           brzaccVLTrapSequenceNumber
        }
        STATUS current
        DESCRIPTION
        "An AU/BU trap indicating a new association with an SU/RB."
    ::= { brzAccessVLProducts 2 }

brzaccVLAUdisassociatedTRAP NOTIFICATION-TYPE
        OBJECTS
        {
           brzaccVLTrapSUMacAddr,      --Unit MAC address
           brzaccVLTrapSequenceNumber
        }
        STATUS current
        DESCRIPTION
        "An AU/BU trap indicating that an SU/RB has been disassociated from the AU/BU."
    ::= { brzAccessVLProducts 3 }

brzaccVLAUagingTRAP NOTIFICATION-TYPE
        OBJECTS
        {
     	  brzaccVLTrapSUMacAddr,  	-- Unit MAC address
     	  brzaccVLTrapSequenceNumber
        }
        STATUS current
        DESCRIPTION
	    "An AU/BU trap indicating that the unit association was aged out
	     and removed from the Association database following its failure
	     to acknowledge a specified number of consecutive frames."
    ::= { brzAccessVLProducts 4 }

brzaccVLSUassociatedTRAP NOTIFICATION-TYPE		--Not available in version 5.0
        OBJECTS
        {
--         brzaccVLLastAUMacAddress,          Old AU mac address
           brzaccVLAssociatedAU               -- New AU mac address
--         brzaccVLTrapLastSNRQuality,          Average SNR with old AU
        }
        STATUS current
        DESCRIPTION
        "Starting with 5.0 this trap is not generated.
         An SU/RB trap indicating association with an AU/BU. 
         In addition to the MAC address information of the AU/BU, the 
         trap also includes information on the average SNR of frames 
         received from the AU/BU."
    ::= { brzAccessVLProducts 6 }

brzaccVLAUwirelessQualityTRAP NOTIFICATION-TYPE
        OBJECTS
        {
          brzaccVLTrapToggle,
          brzaccVLTrapUnitMacAddr,
          brzaccVLTrapRTx,
          brzaccVLTrapSequenceNumber
        }
        STATUS current
        DESCRIPTION
        "An AU/BU trap, indicating that the quality of the wireless 
         link (retransmissions rate) has changed and dropped below (Off) or increased  
         above (On) a threshold , defined by the *brzaccVLWirelessTrapThreshold. 
         The threshold for AU/BU is a percentage of retransmissions."
    ::= { brzAccessVLProducts 20 }

brzaccVLPowerUpFromReset NOTIFICATION-TYPE
        OBJECTS
        {
           brzaccVLUnitMacAddress,    -- Unit MAC address
           brzaccVLTrapSequenceNumber
        }
        STATUS current
        DESCRIPTION
        "An AU/BU trap indicating power up after Reset."
    ::= { brzAccessVLProducts 101 }

brzaccVLTelnetStatusTRAP NOTIFICATION-TYPE
        OBJECTS
        {
          brzaccVLTrapLog,
          brzaccVLTrapTelnetUserIpAddress,
          brzaccVLTrapAccessRights,
          brzaccVLTrapUnitMacAddr,
          brzaccVLTrapSequenceNumber
        }
        STATUS current
        DESCRIPTION
        "Applicable to all units.
         A trap indicating that a log-in or log-out has been performed 
         via Telnet. Includes the log-in access 
         right and the IP address of the PC performing Telnet."
    ::= { brzAccessVLProducts 102 }

brzaccVLParameterChangedTRAP NOTIFICATION-TYPE
        OBJECTS
        {
           brzaccVLTrapParameterChanged,
           brzaccVLTrapSequenceNumber
        }
        STATUS current
        DESCRIPTION
        "Starting with version 5.0, this trap is not generated.
         It is replaced by brzaccVLParameterChangeTRAP.
         Applicable to all units. A trap indicating a change in a CIR/MIR, IP Filter 
         or VLAN parameter."
    ::= { brzAccessVLProducts 103 }

brzaccVLLoadingStatusTRAP NOTIFICATION-TYPE
        OBJECTS
        {
          brzaccVLTrapFtpOrTftpStatus,
		  brzaccVLUnitMacAddress,
		  brzaccVLTrapSequenceNumber
        }
        STATUS current
        DESCRIPTION
        "Applicable to all units.
         A trap indicating that last FTP/TFTP firmware loading process has been 
         finished successfully or failed. "
    ::= { brzAccessVLProducts 104 }

brzaccVLPromiscuousModeTRAP NOTIFICATION-TYPE
        OBJECTS
        {
          brzaccVLTrapToggle,
		  brzaccVLUnitMacAddress,
		  brzaccVLTrapSequenceNumber
        }
        STATUS current
        DESCRIPTION
        "An AU/BU trap, indicating that the AU/BU In (On) Promiscuous Mode or 
         out (Off) Promiscuous Mode." 
    ::= { brzAccessVLProducts 105 }

brzaccVLDFSRadarDetectedTRAP NOTIFICATION-TYPE
        OBJECTS
        {
          brzaccVLTrapSequenceNumber
        }
        STATUS current
        DESCRIPTION
        "DFS: Applicable to AU/BU only.
         A trap indicating that a radar was detected. "
    ::= { brzAccessVLProducts 106 }

brzaccVLDFSFrequencyTRAP NOTIFICATION-TYPE
        OBJECTS
        {
          brzaccVLDFSMoveFreq, 
          brzaccVLDFSMoveFreqNew,
          brzaccVLTrapSequenceNumber
        }
        STATUS current
        DESCRIPTION
        "Applicable to AU/BU only.
         A trap indicating that the unit moved to a new frequency. "
    ::= { brzAccessVLProducts 107 }

brzaccVLDFSNoFreeChannelsExistsTRAP NOTIFICATION-TYPE
        OBJECTS
        {
          brzaccVLTrapSequenceNumber
        }
        STATUS current
        DESCRIPTION
        "Applicable to AU/BU only.
         A trap indicating that a radar was detected and there is no 
         free channel. "
    ::= { brzAccessVLProducts 108 }

brzaccVLEthBroadcastMulticastLimiterTRAP NOTIFICATION-TYPE
        OBJECTS
        {
			brzaccVLEthBroadcastThresholdExceeded,
			brzaccVLTrapUnitMacAddr,
			brzaccVLTrapSequenceNumber
		}
        STATUS current
        DESCRIPTION
		"Applicable to all units. The trap is sent if the 
		ethernet broadcast filter threshold is exceeded
		and it contains the number of dropped packets."
    ::= { brzAccessVLProducts 109 }

brzaccVLAUSUnsupportedSubscriberTypeTRAP NOTIFICATION-TYPE
        OBJECTS
        {
			brzaccVLTrapSUMacAddr,
			brzaccVLTrapSubscriberType,
			brzaccVLTrapSequenceNumber
		}
        STATUS current
        DESCRIPTION
		"Applicable to AUS only.
		This trap is generated when a subscriber with unsupported type tries to associate to AUS.
        The AUS supports only SU-3, SU-6, SU-V. If licensed, SU-54 is supported too.
        For 900 MHz band, AUS supports only SU-3. If licensed, SU-8 is supported too.
		The first variable of the trap is the subscriber MAC Address.
		The second variable is the type of subscriber"
    ::= { brzAccessVLProducts 110 }
  

brzaccVLUnitTypeChangedTRAP NOTIFICATION-TYPE
        OBJECTS
        {
			brzaccVLTrapMACAddress,
			brzaccVLNewUnitTypeTrap,
			brzaccVLTrapSequenceNumber
		}
        STATUS current
        DESCRIPTION
		"Applicable to BU/RB only.
		This trap is generated when the user changes the type of the BreezeNET B unit.
		The RB can be converted in BU or vice versa.
		The first variable of the trap is the unit MAC Address.
		The second variable is the new type of the unit"
    ::= { brzAccessVLProducts 111 }

brzaccVLWLPrioritizationNotSupportedBySUTRAP NOTIFICATION-TYPE
        OBJECTS
        {
			brzaccVLTrapSUMacAddr,
			brzaccVLTrapSWVersion,
			brzaccVLTrapSequenceNumber
		}
        STATUS current
        DESCRIPTION
		"Applicable to AU/BU only.
         This trap is generated when an SU/RB with a SW version below 4.0 
         that does not support Wireless Link Prioritization is associated 
         with an AU/BU with thw Wireless Link Prioritization Option enabled. 
		 The first variable of the trap is the SU/RB MAC Address.
		 The second variable is the SW version of the SU/RB"
    ::= { brzAccessVLProducts 112 }

brzaccVLParameterChangeTRAP NOTIFICATION-TYPE
        OBJECTS
        {
			brzaccVLTrapUnitMacAddr,
			brzaccVLTrapParameterGroupCode,
			brzaccVLTrapSequenceNumber
		}
        STATUS current
        DESCRIPTION
		"Applicable to AU/BU only with SW version 5.0 or higher.
		This trap is generated by AU/BU when a parameter from a group
		was changed. Also, if an SU/RB parameter is changed and if the 
		parameter is in ADB the Au/BU will generate the trap for that SU/RB.
		brzaccVLTrapSequenceNumber	  - trap sequence number
		brzaccVLTrapUnitMacAddr		  - MAC Address of the AU/BU if the parametr 
									    was changed in AU/BU
									  - MAC Address of the SU/RB if the parameter 
									    was changed in SU/RB
		brzaccVLTrapParameterGroupCode- Code of Parameter Group  
		"
    ::= { brzAccessVLProducts 113 } 

brzaccVLRunTimeIPChangeTRAP NOTIFICATION-TYPE
        OBJECTS
        {
			brzaccVLTrapUnitMacAddr,
			brzaccVLTrapNewIP,
			brzaccVLTrapSequenceNumber
		}
        STATUS current
        DESCRIPTION
		"Applicable to AU/BU only with SW version 5.0 or higher.
		This trap is generated by AU/BU when the running IP of the unit was changed. 
		Also, if the running IP of an associated SU/RB is changed this trap will
		be genarated by AU/BU.
		brzaccVLTrapSequenceNumber	  - trap sequence number
		brzaccVLTrapUnitMacAddr		  - MAC Address of the AU/BU if the running IP
		                                was changed in AU/BU
									  - MAC Address of the SU/RB if the running IP 
									    was changed in SU/RB
		brzaccVLTrapNewIP			  - New IP of the unit.
		"
    ::= { brzAccessVLProducts 114 } 
    
brzaccVLDisassociateAllStationsTRAP NOTIFICATION-TYPE
        OBJECTS
        {
          brzaccVLTrapSequenceNumber
        }
        STATUS current
        DESCRIPTION
        "Applicable to AU/BU only.
         A trap indicating that all stations were disassociated. "
    ::= { brzAccessVLProducts 115 }
    
END
