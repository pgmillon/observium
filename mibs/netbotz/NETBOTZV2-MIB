--
-- NETBOTZV2-MIB       module definition
--
NETBOTZV2-MIB DEFINITIONS ::= BEGIN
IMPORTS
   DisplayString FROM RFC1213-MIB
   TRAP-TYPE FROM RFC-1215
   IpAddress FROM RFC1155-SMI
   MODULE-IDENTITY, OBJECT-TYPE, OBJECT-IDENTITY,
      NOTIFICATION-TYPE, enterprises,
      Integer32, TimeTicks, INTEGER          FROM SNMPv2-SMI
   TEXTUAL-CONVENTION, DisplayString, TimeStamp,
        RowPointer, DateAndTime                FROM SNMPv2-TC;

netBotz			OBJECT IDENTIFIER ::= { enterprises 5528 }
netBotzV2		OBJECT IDENTIFIER ::= { netBotz 100 }
netBotzV2Traps		OBJECT IDENTIFIER ::= { netBotzV2 10 }
netBotzV2TrapParms	OBJECT IDENTIFIER ::= { netBotzV2 11 }
netBotzV2Products	OBJECT IDENTIFIER ::= { netBotzV2 20 }

netBotzV2GenericTraps	OBJECT IDENTIFIER ::= { netBotzV2Traps 1 }
netBotzV2SensorTraps	OBJECT IDENTIFIER ::= { netBotzV2Traps 2 }
netBotzV2PodTraps	OBJECT IDENTIFIER ::= { netBotzV2Traps 3 }
netBotzV2PortTraps	OBJECT IDENTIFIER ::= { netBotzV2Traps 4 }

netBotzV2TempSensorTraps	OBJECT IDENTIFIER ::= { netBotzV2SensorTraps 1 }
netBotzV2HumiditySensorTraps	OBJECT IDENTIFIER ::= { netBotzV2SensorTraps 2 }
netBotzV2DewPointSensorTraps	OBJECT IDENTIFIER ::= { netBotzV2SensorTraps 3 }
netBotzV2AirFlowSensorTraps	OBJECT IDENTIFIER ::= { netBotzV2SensorTraps 4 }
netBotzV2AudioSensorTraps	OBJECT IDENTIFIER ::= { netBotzV2SensorTraps 5 }
netBotzV2AmpDetectSensorTraps	OBJECT IDENTIFIER ::= { netBotzV2SensorTraps 6 }
netBotzV2DryContactSensorTraps	OBJECT IDENTIFIER ::= { netBotzV2SensorTraps 7 }
netBotzV2CameraMotionSensorTraps OBJECT IDENTIFIER ::= { netBotzV2SensorTraps 8 }
netBotzV2DoorSensorTraps	OBJECT IDENTIFIER ::= { netBotzV2SensorTraps 9 }

netBotzV2BasePodTraps	OBJECT IDENTIFIER ::= { netBotzV2PodTraps 1 }
netBotzV2SensorPodTraps	OBJECT IDENTIFIER ::= { netBotzV2PodTraps 2 }
netBotzV2CameraPodTraps	OBJECT IDENTIFIER ::= { netBotzV2PodTraps 3 }

netBotzV2Botz			OBJECT IDENTIFIER ::= { netBotzV2Products 10 }

netBotzWallBotz500	 OBJECT IDENTIFIER ::= { netBotzV2Botz 2000 }

--        MODULE-COMPLIANCE, OBJECT-GROUP,
--        NOTIFICATION-GROUP                     FROM SNMPv2-CONF;


OperStatus ::= TEXTUAL-CONVENTION
    STATUS current
    DESCRIPTION
        "The operational status of the device entity."
    SYNTAX INTEGER { disconnected(0), error(1), normal(2) }

ErrorStatus ::= TEXTUAL-CONVENTION
    STATUS current
    DESCRIPTION
        "The error status of the device entity.  If there are no error conditions
         reported for the entity, the status is normal.  Otherwise, the status is
         reported as the severity value of the highest severity error condition
         that is not resolved for the entity."
    SYNTAX INTEGER { normal(0), info(1), warning(2), error(3), critical(4), failure(5) }

BoolValue ::= TEXTUAL-CONVENTION
    STATUS current
    DESCRIPTION
        "A boolean value."
    SYNTAX INTEGER { no(0), yes(1), n_a(2) }

--BoolValue ::= TEXTUAL-CONVENTION
--    STATUS current
--    DESCRIPTION
--        "A boolean value."
--    SYNTAX INTEGER { no(0), yes(1), n_a(2) }

netBotzEnclosures        OBJECT IDENTIFIER ::= { netBotzV2 2 }
netBotzPorts             OBJECT IDENTIFIER ::= { netBotzV2 3 }
netBotzSensors           OBJECT IDENTIFIER ::= { netBotzV2 4 }
netBotzErrors            OBJECT IDENTIFIER ::= { netBotzV2 5 }

netBotzNumericSensors    OBJECT IDENTIFIER ::= { netBotzSensors 1 }
netBotzStateSensors      OBJECT IDENTIFIER ::= { netBotzSensors 2 }

--
-- Enclosures
--

enclosureTable OBJECT-TYPE
    SYNTAX     SEQUENCE OF EnclosureEntry
    MAX-ACCESS not-accessible
    STATUS     current
    DESCRIPTION
        "A list of enclosures (base enclosure and pods)."
    ::= { netBotzEnclosures 1 }

enclosureEntry OBJECT-TYPE
    SYNTAX     EnclosureEntry
    MAX-ACCESS not-accessible
    STATUS     current
    DESCRIPTION
        "Enclosure entry."
    INDEX { enclosureId }
    ::= { enclosureTable 1 }

EnclosureEntry ::= SEQUENCE {
    enclosureId                          DisplayString,
    enclosureStatus                      OperStatus,
    enclosureErrorStatus                 ErrorStatus,
    enclosureLabel                       DisplayString,
    enclosureParentEncId                 DisplayString,
    enclosureDockedToEncId               DisplayString
}

enclosureId OBJECT-TYPE
    SYNTAX     DisplayString
    MAX-ACCESS read-only
    STATUS     current
    DESCRIPTION
        "The id of the physical enclosure."
    ::= { enclosureEntry 1 }

enclosureStatus OBJECT-TYPE
    SYNTAX     OperStatus 
    MAX-ACCESS read-only
    STATUS     current
    DESCRIPTION
        "The operational status of the enclosure."
    ::= { enclosureEntry 2 }
    
enclosureErrorStatus OBJECT-TYPE
    SYNTAX     ErrorStatus
    MAX-ACCESS read-only
    STATUS     current
    DESCRIPTION
        "The error status of the enclosure.  If there are no error conditions
         reported for the enclosure, the status is normal.  Otherwise, the status is
         reported as the severity value of the highest severity error condition
         that is not resolved for the enclosure."
    ::= { enclosureEntry 3 }

enclosureLabel OBJECT-TYPE
    SYNTAX     DisplayString
    MAX-ACCESS read-only
    STATUS     current
    DESCRIPTION
        "The unique label assigned to the enclosure (or pod)."
    ::= { enclosureEntry 4 }

enclosureParentEncId OBJECT-TYPE
    SYNTAX     DisplayString
    MAX-ACCESS read-only
    STATUS     current
    DESCRIPTION
        "The id of the parent enclosure this enclosure is attached to."
    ::= { enclosureEntry 5 }
    
enclosureDockedToEncId OBJECT-TYPE
    SYNTAX     DisplayString
    MAX-ACCESS read-only
    STATUS     current
    DESCRIPTION
        "The id of the enclosure this enclosure is hard-docked with,
         i.e. as when sensor and camera pods are docked with the base
         system unit."
    ::= { enclosureEntry 6 }

--
-- Ports
--

dinPortTable OBJECT-TYPE
    SYNTAX     SEQUENCE OF DINPortEntry
    MAX-ACCESS not-accessible
    STATUS     current
    DESCRIPTION
        "A list of DIN port entries."
    ::= { netBotzPorts 1 }

dinPortEntry OBJECT-TYPE
    SYNTAX     DINPortEntry
    MAX-ACCESS not-accessible
    STATUS     current
    DESCRIPTION
        "DIN port entry."
    INDEX { dinPortId }
    ::= { dinPortTable 1 }

DINPortEntry ::= SEQUENCE {
    dinPortId                            DisplayString,
    dinPortStatus                        OperStatus,
    dinPortLabel                         DisplayString,
    dinPortEncId                         DisplayString,
    dinPortSensorIdSuffix                DisplayString,
    dinPortSupportsAverage               BoolValue,
    dinPortSupportsRMS                   BoolValue,
    dinPortSupportsDryContact            BoolValue
}

dinPortId OBJECT-TYPE
    SYNTAX     DisplayString
    MAX-ACCESS read-only
    STATUS     current
    DESCRIPTION
        "The unique id of the port."
    ::= { dinPortEntry 1 }

dinPortStatus OBJECT-TYPE
    SYNTAX     OperStatus 
    MAX-ACCESS read-only
    STATUS     current
    DESCRIPTION
        "The operational status of the port."
    ::= { dinPortEntry 2 }

dinPortLabel OBJECT-TYPE
    SYNTAX     DisplayString
    MAX-ACCESS read-only
    STATUS     current
    DESCRIPTION
        "The unique label assigned to the port."
    ::= { dinPortEntry 3 }

dinPortEncId OBJECT-TYPE
    SYNTAX     DisplayString
    MAX-ACCESS read-only
    STATUS     current
    DESCRIPTION
        "The id of the physical enclosure containing the port."
    ::= { dinPortEntry 4 }

dinPortSensorIdSuffix OBJECT-TYPE
    SYNTAX     DisplayString
    MAX-ACCESS read-only
    STATUS     current
    DESCRIPTION
        "The ID suffix added to a sensor plugged into the port.
         The ID suffix is combined with the sensor class ID when
         generating a local unique id for the DIN sensor."
    ::= { dinPortEntry 5 }

dinPortSupportsAverage OBJECT-TYPE
    SYNTAX     BoolValue
    MAX-ACCESS read-only
    STATUS     current
    DESCRIPTION
        "Whether the port supports returning the average voltage
         reading of the sensor.  This is used to determine which
         classes of sensors are supported by the port."
    ::= { dinPortEntry 6 }

dinPortSupportsRMS OBJECT-TYPE
    SYNTAX     BoolValue
    MAX-ACCESS read-only
    STATUS     current
    DESCRIPTION
        "Whether the port supports returning the AC RMS voltage
         reading of the sensor.  This is used to determine which
         classes of sensors are supported by the port."
    ::= { dinPortEntry 7 }

dinPortSupportsDryContact OBJECT-TYPE
    SYNTAX     BoolValue
    MAX-ACCESS read-only
    STATUS     current
    DESCRIPTION
        "Whether the port supports generating the 'open' and
         'closed' state of a dry contact sensor. This information
         is used to determine which classes of sensors are supported
         by the port."
    ::= { dinPortEntry 8 }

otherPortTable OBJECT-TYPE
    SYNTAX     SEQUENCE OF OtherPortEntry
    MAX-ACCESS not-accessible
    STATUS     current
    DESCRIPTION
        "A list of other port entries."
    ::= { netBotzPorts 10 }

otherPortEntry OBJECT-TYPE
    SYNTAX     OtherPortEntry
    MAX-ACCESS not-accessible
    STATUS     current
    DESCRIPTION
        "Other port entry."
    INDEX { otherPortId }
    ::= { otherPortTable 1 }

OtherPortEntry ::= SEQUENCE {
    otherPortId                            DisplayString,
    otherPortStatus                        OperStatus,
    otherPortLabel                         DisplayString,
    otherPortEncId                         DisplayString
}

otherPortId OBJECT-TYPE
    SYNTAX     DisplayString
    MAX-ACCESS read-only
    STATUS     current
    DESCRIPTION
        "The unique id of the port."
    ::= { otherPortEntry 1 }

otherPortStatus OBJECT-TYPE
    SYNTAX     OperStatus 
    MAX-ACCESS read-only
    STATUS     current
    DESCRIPTION
        "The operational status of the port."
    ::= { otherPortEntry 2 }

otherPortLabel OBJECT-TYPE
    SYNTAX     DisplayString
    MAX-ACCESS read-only
    STATUS     current
    DESCRIPTION
        "The unique label assigned to the port."
    ::= { otherPortEntry 3 }

otherPortEncId OBJECT-TYPE
    SYNTAX     DisplayString
    MAX-ACCESS read-only
    STATUS     current
    DESCRIPTION
        "The id of the physical enclosure containing the port."
    ::= { otherPortEntry 4 }

-- Numeric Sensors Group
-- This group defines sensors for which the concepts of "less than"
-- and "greater than" are meaningful.

tempSensorTable OBJECT-TYPE
    SYNTAX     SEQUENCE OF TempSensorEntry
    MAX-ACCESS not-accessible
    STATUS     current
    DESCRIPTION
        "A list of temperature sensor entries."
    ::= { netBotzNumericSensors 1 }

tempSensorEntry OBJECT-TYPE
    SYNTAX     TempSensorEntry
    MAX-ACCESS not-accessible
    STATUS     current
    DESCRIPTION
        "A temperature sensor entry."
    INDEX { tempSensorId }
    ::= { tempSensorTable 1 }

TempSensorEntry ::= SEQUENCE {
    tempSensorId                       DisplayString,
    tempSensorValue                    Integer32,
    tempSensorErrorStatus              ErrorStatus,
    tempSensorLabel                    DisplayString,
    tempSensorEncId                    DisplayString,
    tempSensorPortId                   DisplayString,
    tempSensorValueStr                 DisplayString
}

tempSensorId   OBJECT-TYPE
    SYNTAX     DisplayString
    MAX-ACCESS read-only
    STATUS     current
    DESCRIPTION
        "The unique id of the sensor."
    ::= { tempSensorEntry 1 }

tempSensorValue OBJECT-TYPE
    SYNTAX     Integer32 (-500..1000)
    MAX-ACCESS read-only
    STATUS     current
    DESCRIPTION
        "The temperature measured by the sensor in tenths of a degree Celsius."
    ::= { tempSensorEntry 2 }

tempSensorErrorStatus OBJECT-TYPE
    SYNTAX     ErrorStatus
    MAX-ACCESS read-only
    STATUS     current
    DESCRIPTION
        "The error status of the sensor.  If there are no error conditions
         reported for the sensor, the status is normal.  Otherwise, the status is
         reported as the severity value of the highest severity error condition
         that is not resolved for the sensor."
    ::= { tempSensorEntry 3 }

tempSensorLabel OBJECT-TYPE
    SYNTAX     DisplayString
    MAX-ACCESS read-only
    STATUS     current
    DESCRIPTION
        "The unique label assigned to the sensor."
    ::= { tempSensorEntry 4 }

tempSensorEncId OBJECT-TYPE
    SYNTAX     DisplayString
    MAX-ACCESS read-only
    STATUS     current
    DESCRIPTION
        "The id of the physical enclosure containing the sensor."
    ::= { tempSensorEntry 5 }

tempSensorPortId OBJECT-TYPE
    SYNTAX     DisplayString
    MAX-ACCESS read-only
    STATUS     current
    DESCRIPTION
        "The id of the port the sensor is plugged into (or empty string
         if it is not plugged into a port)."
    ::= { tempSensorEntry 6 }

tempSensorValueStr OBJECT-TYPE
    SYNTAX     DisplayString
    MAX-ACCESS read-only
    STATUS     current
    DESCRIPTION
        "The temperature reading, in degrees celsius, shown as a string (or empty string
         if it is not plugged into a port)."
    ::= { tempSensorEntry 7 }

humiSensorTable OBJECT-TYPE
    SYNTAX     SEQUENCE OF HumiSensorEntry
    MAX-ACCESS not-accessible
    STATUS     current
    DESCRIPTION
        "A list of humidity sensor entries."
    ::= { netBotzNumericSensors 2 }

humiSensorEntry OBJECT-TYPE
    SYNTAX     HumiSensorEntry
    MAX-ACCESS not-accessible
    STATUS     current
    DESCRIPTION
        "A humidity sensor entry."
    INDEX { humiSensorId }
    ::= { humiSensorTable 1 }

HumiSensorEntry ::= SEQUENCE {
    humiSensorId                       DisplayString,
    humiSensorValue                    Integer32,
    humiSensorErrorStatus              ErrorStatus,
    humiSensorLabel                    DisplayString,
    humiSensorEncId                    DisplayString,
    humiSensorPortId                   DisplayString,
    humiSensorValueStr                 DisplayString
}

humiSensorId   OBJECT-TYPE
    SYNTAX     DisplayString
    MAX-ACCESS read-only
    STATUS     current
    DESCRIPTION
        "The unique id of the sensor."
    ::= { humiSensorEntry 1 }

humiSensorValue OBJECT-TYPE
    SYNTAX     Integer32 (0..1000)
    MAX-ACCESS read-only
    STATUS     current
    DESCRIPTION
        "The relative humidity measured by the sensor in tenths of a percent."
    ::= { humiSensorEntry 2 }
    
humiSensorErrorStatus OBJECT-TYPE
    SYNTAX     ErrorStatus
    MAX-ACCESS read-only
    STATUS     current
    DESCRIPTION
        "The error status of the sensor.  If there are no error conditions
         reported for the sensor, the status is normal.  Otherwise, the status is
         reported as the severity value of the highest severity error condition
         that is not resolved for the sensor."
    ::= { humiSensorEntry 3 }

humiSensorLabel OBJECT-TYPE
    SYNTAX     DisplayString
    MAX-ACCESS read-only
    STATUS     current
    DESCRIPTION
        "The unique label assigned to the sensor."
    ::= { humiSensorEntry 4 }

humiSensorEncId OBJECT-TYPE
    SYNTAX     DisplayString
    MAX-ACCESS read-only
    STATUS     current
    DESCRIPTION
        "The id of the physical enclosure containing the sensor."
    ::= { humiSensorEntry 5 }

humiSensorPortId OBJECT-TYPE
    SYNTAX     DisplayString
    MAX-ACCESS read-only
    STATUS     current
    DESCRIPTION
        "The id of the port the sensor is plugged into (or empty string
         if it is not plugged into a port)."
    ::= { humiSensorEntry 6 }

humiSensorValueStr OBJECT-TYPE
    SYNTAX     DisplayString
    MAX-ACCESS read-only
    STATUS     current
    DESCRIPTION
        "The humidity reading, in percent, shown as a string (or empty string
         if it is not plugged into a port)."
    ::= { humiSensorEntry 7 }

dewPointSensorTable OBJECT-TYPE
    SYNTAX     SEQUENCE OF DewPointSensorEntry
    MAX-ACCESS not-accessible
    STATUS     current
    DESCRIPTION
        "A list of dew point sensor entries."
    ::= { netBotzNumericSensors 3 }

dewPointSensorEntry OBJECT-TYPE
    SYNTAX     AmpDetectSensorEntry
    MAX-ACCESS not-accessible
    STATUS     current
    DESCRIPTION
        "An ampere sensor entry."
    INDEX { dewPointSensorId }
    ::= { dewPointSensorTable 1 }

DewPointSensorEntry ::= SEQUENCE {
    dewPointSensorId                      DisplayString,
    dewPointSensorValue                   Integer32,
    dewPointSensorErrorStatus             ErrorStatus,
    dewPointSensorLabel                   DisplayString,
    dewPointSensorEncId                   DisplayString,
    dewPointSensorPortId                  DisplayString,
    dewPointSensorValueStr                DisplayString
}

dewPointSensorId OBJECT-TYPE
    SYNTAX     DisplayString
    MAX-ACCESS read-only
    STATUS     current
    DESCRIPTION
        "The unique id of the sensor."
    ::= { dewPointSensorEntry 1 }

dewPointSensorValue OBJECT-TYPE
    SYNTAX     Integer32 (1..65535)
    MAX-ACCESS read-only
    STATUS     current
    DESCRIPTION
        "The dew point value measured by the sensor in tenths of a degree Celsius."
    ::= { dewPointSensorEntry 2 }
    
dewPointSensorErrorStatus OBJECT-TYPE
    SYNTAX     ErrorStatus
    MAX-ACCESS read-only
    STATUS     current
    DESCRIPTION
        "The operational status of the sensor.  If there are no error conditions
         reported for the sensor, the status is normal.  Otherwise, the status is
         reported as the severity value of the highest severity error condition
         that is not resolved for the sensor."
    ::= { dewPointSensorEntry 3 }

dewPointSensorLabel OBJECT-TYPE
    SYNTAX     DisplayString
    MAX-ACCESS read-only
    STATUS     current
    DESCRIPTION
        "The unique label assigned to the sensor."
    ::= { dewPointSensorEntry 4 }

dewPointSensorEncId OBJECT-TYPE
    SYNTAX     DisplayString
    MAX-ACCESS read-only
    STATUS     current
    DESCRIPTION
        "The id of the physical enclosure containing the sensor."
    ::= { dewPointSensorEntry 5 }

dewPointSensorPortId OBJECT-TYPE
    SYNTAX     DisplayString
    MAX-ACCESS read-only
    STATUS     current
    DESCRIPTION
        "The id of the port the sensor is plugged into (or empty string
         if it is not plugged into a port)."
    ::= { dewPointSensorEntry 6 }

dewPointSensorValueStr OBJECT-TYPE
    SYNTAX     DisplayString
    MAX-ACCESS read-only
    STATUS     current
    DESCRIPTION
        "The dew point reading, in degrees celsius, shown as a string (or empty string
         if it is not plugged into a port)."
    ::= { dewPointSensorEntry 7 }

audioSensorTable OBJECT-TYPE
    SYNTAX     SEQUENCE OF AudioSensorEntry
    MAX-ACCESS not-accessible
    STATUS     current
    DESCRIPTION
        "A list of audio sensor entries."
    ::= { netBotzNumericSensors 4 }

audioSensorEntry OBJECT-TYPE
    SYNTAX     AudioSensorEntry
    MAX-ACCESS not-accessible
    STATUS     current
    DESCRIPTION
        "An audio sensor entry."
    INDEX { audioSensorId }
    ::= { audioSensorTable 1 }

AudioSensorEntry ::= SEQUENCE {
    audioSensorId                      DisplayString,
    audioSensorValue                   Integer32,
    audioSensorErrorStatus             ErrorStatus,
    audioSensorLabel                   DisplayString,
    audioSensorEncId                   DisplayString,
    audioSensorPortId                  DisplayString,
    audioSensorValueStr                DisplayString
}

audioSensorId  OBJECT-TYPE
    SYNTAX     DisplayString
    MAX-ACCESS read-only
    STATUS     current
    DESCRIPTION
        "The unique id of the sensor."
    ::= { audioSensorEntry 1 }

audioSensorValue OBJECT-TYPE
    SYNTAX     Integer32
    MAX-ACCESS read-only
    STATUS     current
    DESCRIPTION
        "The (unitless) audio level measured by the sensor."
    ::= { audioSensorEntry 2 }
    
audioSensorErrorStatus OBJECT-TYPE
    SYNTAX     ErrorStatus
    MAX-ACCESS read-only
    STATUS     current
    DESCRIPTION
        "The error status of the sensor.  If there are no error conditions
         reported for the sensor, the status is normal.  Otherwise, the status is
         reported as the severity value of the highest severity error condition
         that is not resolved for the sensor."
    ::= { audioSensorEntry 3 }

audioSensorLabel OBJECT-TYPE
    SYNTAX     DisplayString
    MAX-ACCESS read-only
    STATUS     current
    DESCRIPTION
        "The unique label assigned to the sensor."
   ::= { audioSensorEntry 4 }

audioSensorEncId OBJECT-TYPE
    SYNTAX     DisplayString
    MAX-ACCESS read-only
    STATUS     current
    DESCRIPTION
        "The id of the physical enclosure containing the sensor."
    ::= { audioSensorEntry 5 }

audioSensorPortId OBJECT-TYPE
    SYNTAX     DisplayString
    MAX-ACCESS read-only
    STATUS     current
    DESCRIPTION
        "The id of the port the sensor is plugged into (or empty string
         if it is not plugged into a port)."
    ::= { audioSensorEntry 6 }

audioSensorValueStr OBJECT-TYPE
    SYNTAX     DisplayString
    MAX-ACCESS read-only
    STATUS     current
    DESCRIPTION
        "The audio reading shown as a string (or empty string
         if it is not plugged into a port)."
    ::= { audioSensorEntry 7 }

airFlowSensorTable OBJECT-TYPE
    SYNTAX     SEQUENCE OF AirFlowSensorEntry
    MAX-ACCESS not-accessible
    STATUS     current
    DESCRIPTION
        "A list of airflow sensor entries."
    ::= { netBotzNumericSensors 5 }

airFlowSensorEntry OBJECT-TYPE
    SYNTAX     AirFlowSensorEntry
    MAX-ACCESS not-accessible
    STATUS     current
    DESCRIPTION
        "An air flow sensor entry."
    INDEX { airFlowSensorId }
    ::= { airFlowSensorTable 1 }

AirFlowSensorEntry ::= SEQUENCE {
    airFlowSensorId                      DisplayString,
    airFlowSensorValue                   Integer32,
    airFlowSensorErrorStatus             ErrorStatus,
    airFlowSensorLabel                   DisplayString,
    airFlowSensorEncId                   DisplayString,
    airFlowSensorPortId                  DisplayString,
    airFlowSensorValueStr                DisplayString
}

airFlowSensorId OBJECT-TYPE
    SYNTAX     DisplayString
    MAX-ACCESS read-only
    STATUS     current
    DESCRIPTION
        "The unique id of the sensor."
    ::= { airFlowSensorEntry 1 }

airFlowSensorValue OBJECT-TYPE
    SYNTAX     Integer32 (0..512)
    MAX-ACCESS read-only
    STATUS     current
    DESCRIPTION
        "The air flow measured by the sensor in tenths of a meter per minute."
    ::= { airFlowSensorEntry 2 }

airFlowSensorErrorStatus OBJECT-TYPE
    SYNTAX     ErrorStatus
    MAX-ACCESS read-only
    STATUS     current
    DESCRIPTION
        "The error status of the sensor.  If there are no error conditions
         reported for the sensor, the status is normal.  Otherwise, the status is
         reported as the severity value of the highest severity error condition
         that is not resolved for the sensor."
    ::= { airFlowSensorEntry 3 }

airFlowSensorLabel OBJECT-TYPE
    SYNTAX     DisplayString
    MAX-ACCESS read-only
    STATUS     current
    DESCRIPTION
        "The unique label assigned to the sensor."
    ::= { airFlowSensorEntry 4 }

airFlowSensorEncId OBJECT-TYPE
    SYNTAX     DisplayString
    MAX-ACCESS read-only
    STATUS     current
    DESCRIPTION
        "The id of the physical enclosure containing the sensor."
    ::= { airFlowSensorEntry 5 }

airFlowSensorPortId OBJECT-TYPE
    SYNTAX     DisplayString
    MAX-ACCESS read-only
    STATUS     current
    DESCRIPTION
        "The id of the port the sensor is plugged into (or empty string
         if it is not plugged into a port)."
    ::= { airFlowSensorEntry 6 }

airFlowSensorValueStr OBJECT-TYPE
    SYNTAX     DisplayString
    MAX-ACCESS read-only
    STATUS     current
    DESCRIPTION
        "The airflow reading, in meters per minute, shown as a string (or empty string
         if it is not plugged into a port)."
    ::= { airFlowSensorEntry 7 }

ampDetectSensorTable OBJECT-TYPE
    SYNTAX     SEQUENCE OF AmpDetectSensorEntry
    MAX-ACCESS not-accessible
    STATUS     current
    DESCRIPTION
        "A list of amp detect sensor entries."
    ::= { netBotzNumericSensors 6 }

ampDetectSensorEntry OBJECT-TYPE
    SYNTAX     AmpDetectSensorEntry
    MAX-ACCESS not-accessible
    STATUS     current
    DESCRIPTION
        "An ampere sensor entry."
    INDEX { ampDetectSensorId }
    ::= { ampDetectSensorTable 1 }

AmpDetectSensorEntry ::= SEQUENCE {
    ampDetectSensorId                      DisplayString,
    ampDetectSensorValue                   Integer32,
    ampDetectSensorErrorStatus             ErrorStatus,
    ampDetectSensorLabel                   DisplayString,
    ampDetectSensorEncId                   DisplayString,
    ampDetectSensorPortId                  DisplayString,
    ampDetectSensorValueStr                DisplayString
}

ampDetectSensorId OBJECT-TYPE
    SYNTAX     DisplayString
    MAX-ACCESS read-only
    STATUS     current
    DESCRIPTION
        "The unique id of the sensor."
    ::= { ampDetectSensorEntry 1 }

ampDetectSensorValue OBJECT-TYPE
    SYNTAX     Integer32 (1..65535)
    MAX-ACCESS read-only
    STATUS     current
    DESCRIPTION
        "The value measured by the sensor in tenths of an ampere."
    ::= { ampDetectSensorEntry 2 }

ampDetectSensorErrorStatus OBJECT-TYPE
    SYNTAX     ErrorStatus
    MAX-ACCESS read-only
    STATUS     current
    DESCRIPTION
        "The operational status of the sensor.  If there are no error conditions
         reported for the sensor, the status is normal.  Otherwise, the status is
         reported as the severity value of the highest severity error condition
         that is not resolved for the sensor."
    ::= { ampDetectSensorEntry 3 }

ampDetectSensorLabel OBJECT-TYPE
    SYNTAX     DisplayString
    MAX-ACCESS read-only
    STATUS     current
    DESCRIPTION
        "The unique label assigned to the sensor."
    ::= { ampDetectSensorEntry 4 }

ampDetectSensorEncId OBJECT-TYPE
    SYNTAX     DisplayString
    MAX-ACCESS read-only
    STATUS     current
    DESCRIPTION
        "The id of the physical enclosure containing the sensor."
    ::= { ampDetectSensorEntry 5 }

ampDetectSensorPortId OBJECT-TYPE
    SYNTAX     DisplayString
    MAX-ACCESS read-only
    STATUS     current
    DESCRIPTION
        "The id of the port the sensor is plugged into (or empty string
         if it is not plugged into a port)."
    ::= { ampDetectSensorEntry 6 }

ampDetectSensorValueStr OBJECT-TYPE
    SYNTAX     DisplayString
    MAX-ACCESS read-only
    STATUS     current
    DESCRIPTION
        "The amp detect reading, in amperes, shown as a string (or empty string
         if it is not plugged into a port)."
    ::= { ampDetectSensorEntry 7 }

otherNumericSensorTable OBJECT-TYPE
    SYNTAX     SEQUENCE OF OtherNumericSensorEntry
    MAX-ACCESS not-accessible
    STATUS     current
    DESCRIPTION
        "A list of other numeric sensor entries."
    ::= { netBotzNumericSensors 10 }

otherNumericSensorEntry OBJECT-TYPE
    SYNTAX     OtherNumericSensorEntry
    MAX-ACCESS not-accessible
    STATUS     current
    DESCRIPTION
        "Other numeric sensor entry."
    INDEX { otherNumericSensorId }
    ::= { otherNumericSensorTable 1 }

OtherNumericSensorEntry ::= SEQUENCE {
    otherNumericSensorId                      DisplayString,
    otherNumericSensorValue                   Integer32,
    otherNumericSensorErrorStatus             ErrorStatus,
    otherNumericSensorLabel                   DisplayString,
    otherNumericSensorEncId                   DisplayString,
    otherNumericSensorPortId                  DisplayString,
    otherNumericSensorValueStr                DisplayString,
    otherNumericSensorUnits                   DisplayString
}

otherNumericSensorId OBJECT-TYPE
    SYNTAX     DisplayString
    MAX-ACCESS read-only
    STATUS     current
    DESCRIPTION
        "The unique id of the sensor."
    ::= { otherNumericSensorEntry 1 }

otherNumericSensorValue OBJECT-TYPE
    SYNTAX     Integer32
    MAX-ACCESS read-only
    STATUS     current
    DESCRIPTION
        "The value measured by the sensor in tenths of the unit of measure."
    ::= { otherNumericSensorEntry 2 }

otherNumericSensorErrorStatus OBJECT-TYPE
    SYNTAX     ErrorStatus
    MAX-ACCESS read-only
    STATUS     current
    DESCRIPTION
        "The operational status of the sensor.  If there are no error conditions
         reported for the sensor, the status is normal.  Otherwise, the status is
         reported as the severity value of the highest severity error condition
         that is not resolved for the sensor."
    ::= { otherNumericSensorEntry 3 }

otherNumericSensorLabel OBJECT-TYPE
    SYNTAX     DisplayString
    MAX-ACCESS read-only
    STATUS     current
    DESCRIPTION
        "The unique label assigned to the sensor."
    ::= { otherNumericSensorEntry 4 }

otherNumericSensorEncId OBJECT-TYPE
    SYNTAX     DisplayString
    MAX-ACCESS read-only
    STATUS     current
    DESCRIPTION
        "The id of the physical enclosure containing the sensor."
    ::= { otherNumericSensorEntry 5 }

otherNumericSensorPortId OBJECT-TYPE
    SYNTAX     DisplayString
    MAX-ACCESS read-only
    STATUS     current
    DESCRIPTION
        "The id of the port the sensor is plugged into (or empty string
         if it is not plugged into a port)."
    ::= { otherNumericSensorEntry 6 }

otherNumericSensorValueStr OBJECT-TYPE
    SYNTAX     DisplayString
    MAX-ACCESS read-only
    STATUS     current
    DESCRIPTION
        "The sensor reading shown as a string (or empty string
         if it is not plugged into a port)."
    ::= { otherNumericSensorEntry 7 }

otherNumericSensorUnits OBJECT-TYPE
    SYNTAX     DisplayString
    MAX-ACCESS read-only
    STATUS     current
    DESCRIPTION
        "The unit of measure for the sensor value."
    ::= { otherNumericSensorEntry 8 }

-- State Sensors Group
-- This group defines sensors having an integer value which is
-- a defined state id or index.

dryContactSensorTable OBJECT-TYPE
    SYNTAX     SEQUENCE OF DryContactSensorEntry
    MAX-ACCESS not-accessible
    STATUS     current
    DESCRIPTION
        "A list of dry contact sensor entries."
    ::= { netBotzStateSensors 1 }

dryContactSensorEntry OBJECT-TYPE
    SYNTAX     DryContactSensorEntry
    MAX-ACCESS not-accessible
    STATUS     current
    DESCRIPTION
        "Dry contact sensor entry."
    INDEX { dryContactSensorId }
    ::= { dryContactSensorTable 1 }

DryContactSensorEntry ::= SEQUENCE {
    dryContactSensorId                      DisplayString,
    dryContactSensorValue                   INTEGER,
    dryContactSensorErrorStatus             ErrorStatus,
    dryContactSensorLabel                   DisplayString,
    dryContactSensorEncId                   DisplayString,
    dryContactSensorPortId                  DisplayString,
    dryContactSensorValueStr              DisplayString
}

dryContactSensorId OBJECT-TYPE
    SYNTAX     DisplayString
    MAX-ACCESS read-only
    STATUS     current
    DESCRIPTION
        "The unique id of the sensor."
    ::= { dryContactSensorEntry 1 }

dryContactSensorValue OBJECT-TYPE
    SYNTAX     INTEGER { n_a(-1), open(0), closed(1) }
    MAX-ACCESS read-only
    STATUS     current
    DESCRIPTION
        "Whether the dry sensor contact is open or closed."
    ::= { dryContactSensorEntry 2 }

dryContactSensorErrorStatus OBJECT-TYPE
    SYNTAX     ErrorStatus
    MAX-ACCESS read-only
    STATUS     current
    DESCRIPTION
        "The operational status of the sensor.  If there are no error conditions
         reported for the sensor, the status is normal.  Otherwise, the status is
         reported as the severity value of the highest severity error condition
         that is not resolved for the sensor."
    ::= { dryContactSensorEntry 3 }

dryContactSensorLabel OBJECT-TYPE
    SYNTAX     DisplayString
    MAX-ACCESS read-only
    STATUS     current
    DESCRIPTION
        "The unique label assigned to the sensor."
    ::= { dryContactSensorEntry 4 }

dryContactSensorEncId OBJECT-TYPE
    SYNTAX     DisplayString
    MAX-ACCESS read-only
    STATUS     current
    DESCRIPTION
        "The id of the physical enclosure containing the sensor."
    ::= { dryContactSensorEntry 5 }

dryContactSensorPortId OBJECT-TYPE
    SYNTAX     DisplayString
    MAX-ACCESS read-only
    STATUS     current
    DESCRIPTION
        "The id of the port the sensor is plugged into (or empty string
         if it is not plugged into a port)."
    ::= { dryContactSensorEntry 6 }

dryContactSensorValueStr OBJECT-TYPE
    SYNTAX     DisplayString
    MAX-ACCESS read-only
    STATUS     current
    DESCRIPTION
        "The enum value label for the state reported by the sensor."
    ::= { dryContactSensorEntry 7 }

doorSwitchSensorTable OBJECT-TYPE
    SYNTAX     SEQUENCE OF DoorSwitchSensorEntry
    MAX-ACCESS not-accessible
    STATUS     current
    DESCRIPTION
        "A list of door switch sensor entries."
    ::= { netBotzStateSensors 2 }

doorSwitchSensorEntry OBJECT-TYPE
    SYNTAX     DoorSwitchSensorEntry
    MAX-ACCESS not-accessible
    STATUS     current
    DESCRIPTION
        "Door switch sensor entry."
    INDEX { doorSwitchSensorId }
    ::= { doorSwitchSensorTable 1 }

DoorSwitchSensorEntry ::= SEQUENCE {
    doorSwitchSensorId                      DisplayString,
    doorSwitchSensorValue                   INTEGER,
    doorSwitchSensorErrorStatus             ErrorStatus,
    doorSwitchSensorLabel                   DisplayString,
    doorSwitchSensorEncId                   DisplayString,
    doorSwitchSensorPortId                  DisplayString,
    doorSwitchSensorValueStr              DisplayString
}

doorSwitchSensorId OBJECT-TYPE
    SYNTAX     DisplayString
    MAX-ACCESS read-only
    STATUS     current
    DESCRIPTION
        "The unique id of the sensor."
    ::= { doorSwitchSensorEntry 1 }

doorSwitchSensorValue OBJECT-TYPE
    SYNTAX     INTEGER { n_a(-1), open(0), closed(1) }
    MAX-ACCESS read-only
    STATUS     current
    DESCRIPTION
        "Whether the door is open or closed."
    ::= { doorSwitchSensorEntry 2 }

doorSwitchSensorErrorStatus OBJECT-TYPE
    SYNTAX     ErrorStatus
    MAX-ACCESS read-only
    STATUS     current
    DESCRIPTION
        "The operational status of the sensor.  If there are no error conditions
         reported for the sensor, the status is normal.  Otherwise, the status is
         reported as the severity value of the highest severity error condition
         that is not resolved for the sensor."
    ::= { doorSwitchSensorEntry 3 }

doorSwitchSensorLabel OBJECT-TYPE
    SYNTAX     DisplayString
    MAX-ACCESS read-only
    STATUS     current
    DESCRIPTION
        "The unique label assigned to the sensor."
    ::= { doorSwitchSensorEntry 4 }

doorSwitchSensorEncId OBJECT-TYPE
    SYNTAX     DisplayString
    MAX-ACCESS read-only
    STATUS     current
    DESCRIPTION
        "The id of the physical enclosure containing the sensor."
    ::= { doorSwitchSensorEntry 5 }

doorSwitchSensorPortId OBJECT-TYPE
    SYNTAX     DisplayString
    MAX-ACCESS read-only
    STATUS     current
    DESCRIPTION
        "The id of the port the sensor is plugged into (or empty string
         if it is not plugged into a port)."
    ::= { doorSwitchSensorEntry 6 }

doorSwitchSensorValueStr OBJECT-TYPE
    SYNTAX     DisplayString
    MAX-ACCESS read-only
    STATUS     current
    DESCRIPTION
        "The enum value label for the state reported by the sensor."
    ::= { doorSwitchSensorEntry 7 }

cameraMotionSensorTable OBJECT-TYPE
    SYNTAX     SEQUENCE OF CameraMotionSensorEntry
    MAX-ACCESS not-accessible
    STATUS     current
    DESCRIPTION
        "A list of camera motion sensor entries."
    ::= { netBotzStateSensors 3 }

cameraMotionSensorEntry OBJECT-TYPE
    SYNTAX     CameraMotionSensorEntry
    MAX-ACCESS not-accessible
    STATUS     current
    DESCRIPTION
        "Camera motion sensor entry."
    INDEX { cameraMotionSensorId }
    ::= { cameraMotionSensorTable 1 }

CameraMotionSensorEntry ::= SEQUENCE {
    cameraMotionSensorId                      DisplayString,
    cameraMotionSensorValue                   INTEGER,
    cameraMotionSensorErrorStatus             ErrorStatus,
    cameraMotionSensorLabel                   DisplayString,
    cameraMotionSensorEncId                   DisplayString,
    cameraMotionSensorPortId                  DisplayString,
    cameraMotionSensorValueStr              DisplayString
}

cameraMotionSensorId OBJECT-TYPE
    SYNTAX     DisplayString
    MAX-ACCESS read-only
    STATUS     current
    DESCRIPTION
        "The unique id of the sensor."
    ::= { cameraMotionSensorEntry 1 }

cameraMotionSensorValue OBJECT-TYPE
    SYNTAX     INTEGER { n_a(-1), no_motion(0), motion_detected(1) }
    MAX-ACCESS read-only
    STATUS     current
    DESCRIPTION
        "Whether motion is detected by the camera sensor."
    ::= { cameraMotionSensorEntry 2 }

cameraMotionSensorErrorStatus OBJECT-TYPE
    SYNTAX     ErrorStatus
    MAX-ACCESS read-only
    STATUS     current
    DESCRIPTION
        "The operational status of the sensor.  If there are no error conditions
         reported for the sensor, the status is normal.  Otherwise, the status is
         reported as the severity value of the highest severity error condition
         that is not resolved for the sensor."
    ::= { cameraMotionSensorEntry 3 }

cameraMotionSensorLabel OBJECT-TYPE
    SYNTAX     DisplayString
    MAX-ACCESS read-only
    STATUS     current
    DESCRIPTION
        "The unique label assigned to the sensor."
    ::= { cameraMotionSensorEntry 4 }

cameraMotionSensorEncId OBJECT-TYPE
    SYNTAX     DisplayString
    MAX-ACCESS read-only
    STATUS     current
    DESCRIPTION
        "The id of the physical enclosure containing the sensor."
    ::= { cameraMotionSensorEntry 5 }

cameraMotionSensorPortId OBJECT-TYPE
    SYNTAX     DisplayString
    MAX-ACCESS read-only
    STATUS     current
    DESCRIPTION
        "The id of the port the sensor is plugged into (or empty string
         if it is not plugged into a port)."
    ::= { cameraMotionSensorEntry 6 }

cameraMotionSensorValueStr OBJECT-TYPE
    SYNTAX     DisplayString
    MAX-ACCESS read-only
    STATUS     current
    DESCRIPTION
        "The enum value label for the state reported by the sensor."
    ::= { cameraMotionSensorEntry 7 }

otherStateSensorTable OBJECT-TYPE
    SYNTAX     SEQUENCE OF OtherStateSensorEntry
    MAX-ACCESS not-accessible
    STATUS     current
    DESCRIPTION
        "A list of other state sensor entries."
    ::= { netBotzStateSensors 10 }

otherStateSensorEntry OBJECT-TYPE
    SYNTAX     OtherStateSensorEntry
    MAX-ACCESS not-accessible
    STATUS     current
    DESCRIPTION
        "Other state sensor entry."
    INDEX { otherStateSensorId }
    ::= { otherStateSensorTable 1 }

OtherStateSensorEntry ::= SEQUENCE {
    otherStateSensorId                      DisplayString,
    otherStateSensorValue                   Integer32,
    otherStateSensorErrorStatus             ErrorStatus,
    otherStateSensorLabel                   DisplayString,
    otherStateSensorEncId                   DIsplayString,
    otherStateSensorPortId                  DisplayString,
    otherStateSensorValueStr              DisplayString
}

otherStateSensorId OBJECT-TYPE
    SYNTAX     DisplayString
    MAX-ACCESS read-only
    STATUS     current
    DESCRIPTION
        "The unique id of the sensor."
    ::= { otherStateSensorEntry 1 }

otherStateSensorValue OBJECT-TYPE
    SYNTAX     INTEGER
    MAX-ACCESS read-only
    STATUS     current
    DESCRIPTION
        "State value reported by the sensor."
    ::= { otherStateSensorEntry 2 }
    
otherStateSensorErrorStatus OBJECT-TYPE
    SYNTAX     ErrorStatus
    MAX-ACCESS read-only
    STATUS     current
    DESCRIPTION
        "The operational status of the sensor.  If there are no error conditions
         reported for the sensor, the status is normal.  Otherwise, the status is
         reported as the severity value of the highest severity error condition
         that is not resolved for the sensor."
    ::= { otherStateSensorEntry 3 }

otherStateSensorLabel OBJECT-TYPE
    SYNTAX     DisplayString
    MAX-ACCESS read-only
    STATUS     current
    DESCRIPTION
        "The unique label assigned to the sensor."
    ::= { otherStateSensorEntry 4 }

otherStateSensorEncId OBJECT-TYPE
    SYNTAX     DisplayString
    MAX-ACCESS read-only
    STATUS     current
    DESCRIPTION
        "The id of the physical enclosure containing the sensor."
    ::= { otherStateSensorEntry 5 }

otherStateSensorPortId OBJECT-TYPE
    SYNTAX     DisplayString
    MAX-ACCESS read-only
    STATUS     current
    DESCRIPTION
        "The id of port the sensor is plugged into (or empty string
         if it is not plugged into a port)."
    ::= { otherStateSensorEntry 6 }

otherStateSensorValueStr OBJECT-TYPE
    SYNTAX     DisplayString
    MAX-ACCESS read-only
    STATUS     current
    DESCRIPTION
        "The enum value label for the state reported by the sensor."
    ::= { otherStateSensorEntry 7 }

-- Error Conditions Group
--

errorCondTable OBJECT-TYPE
    SYNTAX     SEQUENCE OF ErrorCondEntry
    MAX-ACCESS not-accessible
    STATUS     current
    DESCRIPTION
        "A list of active and resolved error conditions."
    ::= { netBotzErrors 1 }

errorCondEntry OBJECT-TYPE
    SYNTAX     ErrorCondEntry
    MAX-ACCESS not-accessible
    STATUS     current
    DESCRIPTION
        "Error condition entry."
    INDEX { errorCondId }
    ::= { errorCondTable 1 }

ErrorCondEntry ::= SEQUENCE {
    errorCondId                          DisplayString,
    errorCondSeverity                    ErrorStatus,
    errorCondTypeId                      DisplayString,
    errorCondStartTime                   DateAndTime,
    errorCondStartTimeStr                DisplayString,
    errorCondResolved                    BoolValue,
    errorCondResolvedTime                DateAndTime,
    errorCondResolvedTimeStr             DisplayString,
    errorCondEncId                       DisplayString,
    errorCondPortId                      DisplayString,
    errorCondSensorId                    DisplayString
}

errorCondId    OBJECT-TYPE
    SYNTAX     DisplayString
    MAX-ACCESS read-only
    STATUS     current
    DESCRIPTION
        "The unique id of the error condition."
    ::= { errorCondEntry 1 }

errorCondSeverity OBJECT-TYPE
    SYNTAX     ErrorStatus
    MAX-ACCESS read-only
    STATUS     current
    DESCRIPTION
        "The relative severity of the error condition."
    ::= { errorCondEntry 2 }

errorCondTypeId  OBJECT-TYPE
    SYNTAX     DisplayString
    MAX-ACCESS read-only
    STATUS     current
    DESCRIPTION
        "The error type id reported for the error condition."
    ::= { errorCondEntry 3 }

errorCondStartTime OBJECT-TYPE
    SYNTAX     DateAndTime
    MAX-ACCESS read-only
    STATUS     current
    DESCRIPTION
        "The start time of the error condition, in msec since 1/1/1970."
    ::= { errorCondEntry 4 }

errorCondStartTimeStr OBJECT-TYPE
    SYNTAX     DisplayString
    MAX-ACCESS read-only
    STATUS     current
    DESCRIPTION
        "The start time of the error condition, as ISO date-time formatted string (UTC)."
    ::= { errorCondEntry 5 }

errorCondResolved OBJECT-TYPE
    SYNTAX     BoolValue
    MAX-ACCESS read-only
    STATUS     current
    DESCRIPTION
        "Whether the error condition was resolved."
    ::= { errorCondEntry 6 }

errorCondResolvedTime OBJECT-TYPE
    SYNTAX     DateAndTime
    MAX-ACCESS read-only
    STATUS     current
    DESCRIPTION
        "The time the error condition was resolved (if it was resolved), in msec since 1/1/1970."
    ::= { errorCondEntry 7 }

errorCondResolvedTimeStr OBJECT-TYPE
    SYNTAX     DisplayString
    MAX-ACCESS read-only
    STATUS     current
    DESCRIPTION
        "The time the error condition was resolved (if it was resolved), as ISO date-time formatted string (UTC)."
    ::= { errorCondEntry 8 }

errorCondEncId OBJECT-TYPE
    SYNTAX     DisplayString
    MAX-ACCESS read-only
    STATUS     current
    DESCRIPTION
        "The id of the physical enclosure associated with the error."
    ::= { errorCondEntry 9 }

errorCondPortId OBJECT-TYPE
    SYNTAX     DisplayString
    MAX-ACCESS read-only
    STATUS     current
    DESCRIPTION
        "The id of the port associated with the error (or empty string
         if the error is not associated with a port)."
    ::= { errorCondEntry 10 }

errorCondSensorId OBJECT-TYPE
    SYNTAX     DisplayString
    MAX-ACCESS read-only
    STATUS     current
    DESCRIPTION
        "The id of the sensor associated with the error (or empty string
         if the error is not associated with a sensor.)"
    ::= { errorCondEntry 11 }


-- Alert specific definitions
--

netBotzV2TrapErrorID	OBJECT-TYPE
	SYNTAX		DisplayString
	ACCESS		read-only
	STATUS		mandatory
	DESCRIPTION 	"Unique ID of error condition that produced the trap"
	::= { netBotzV2TrapParms 1 }

netBotzV2TrapErrorType	OBJECT-TYPE
	SYNTAX		DisplayString
	ACCESS		read-only
	STATUS		mandatory
	DESCRIPTION 	"Symbolic ID of error type"
	::= { netBotzV2TrapParms 2 }


netBotzV2TrapErrorTypeLabel	OBJECT-TYPE
	SYNTAX		DisplayString
	ACCESS		read-only
	STATUS		mandatory
	DESCRIPTION 	"Label for error type"
	::= { netBotzV2TrapParms 3 }


netBotzV2TrapSensorID	OBJECT-TYPE
	SYNTAX		DisplayString
	ACCESS		read-only
	STATUS		mandatory
	DESCRIPTION 	"ID of sensor associated with error condition that produced the trap"
	::= { netBotzV2TrapParms 4 }

netBotzV2TrapSensorLabel	OBJECT-TYPE
	SYNTAX		DisplayString
	ACCESS		read-only
	STATUS		mandatory
	DESCRIPTION 	"Label of sensor associated with error condition that produced the trap"
	::= { netBotzV2TrapParms 5 }

netBotzV2TrapPodID	OBJECT-TYPE
	SYNTAX		DisplayString
	ACCESS		read-only
	STATUS		mandatory
	DESCRIPTION 	"ID of pod associated with error condition that produced the trap"
	::= { netBotzV2TrapParms 6 }

netBotzV2TrapPodLabel	OBJECT-TYPE
	SYNTAX		DisplayString
	ACCESS		read-only
	STATUS		mandatory
	DESCRIPTION 	"Label of pod associated with error condition that produced the trap"
	::= { netBotzV2TrapParms 7 }

netBotzV2TrapPortID	OBJECT-TYPE
	SYNTAX		DisplayString
	ACCESS		read-only
	STATUS		mandatory
	DESCRIPTION 	"ID of port associated with error condition that produced the trap"
	::= { netBotzV2TrapParms 8 }

netBotzV2TrapPortLabel	OBJECT-TYPE
	SYNTAX		DisplayString
	ACCESS		read-only
	STATUS		mandatory
	DESCRIPTION 	"Label of port associated with error condition that produced the trap"
	::= { netBotzV2TrapParms 9 }

netBotzV2TrapStartTime	OBJECT-TYPE
	SYNTAX		INTEGER
	ACCESS		read-only
	STATUS		mandatory
	DESCRIPTION	"Start time (in UTC seconds) for error that produced the trap"
	::= { netBotzV2TrapParms 10 }

netBotzV2TrapNotifyTime	OBJECT-TYPE
	SYNTAX		INTEGER
	ACCESS		read-only
	STATUS		mandatory
	DESCRIPTION	"Notification time (in UTC seconds) for error that produced the trap"
	::= { netBotzV2TrapParms 11 }

netBotzV2TrapResolveTime	OBJECT-TYPE
	SYNTAX		INTEGER
	ACCESS		read-only
	STATUS		mandatory
	DESCRIPTION	"Resolve time (in UTC seconds) for error that produced the trap"
	::= { netBotzV2TrapParms 12 }

netBotzV2TrapSeverity	OBJECT-TYPE
	SYNTAX		INTEGER {
			information(0),
			warning(1),
			error(2),
			critical(3),
			failure(4)
			}
	ACCESS		read-only
	STATUS		mandatory
	DESCRIPTION	"Severity of error that produced the trap"
	::= { netBotzV2TrapParms 13 }

netBotzV2TrapSensorValue	OBJECT-TYPE
	SYNTAX		DisplayString
	ACCESS		read-only
	STATUS		mandatory
	DESCRIPTION 	"String presentation of value of sensor"
	::= { netBotzV2TrapParms 14 }

netBotzV2TrapSensorValueInt	OBJECT-TYPE
	SYNTAX		INTEGER
	ACCESS		read-only
	STATUS		mandatory
	DESCRIPTION 	"Whole integer representation of value of sensor (without decimal portion)"
	::= { netBotzV2TrapParms 15 }

netBotzV2TrapSensorValueFraction	OBJECT-TYPE
	SYNTAX		INTEGER
	ACCESS		read-only
	STATUS		mandatory
	DESCRIPTION 	"Fractional portion of value of sensor (multiplied by 1000000)"
	::= { netBotzV2TrapParms 16 }


netBotzTempTooHigh TRAP-TYPE
	ENTERPRISE netBotzV2TempSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Temperature sensor value too high."
	::= 2

netBotzTempTooHighReturnToNormal TRAP-TYPE
	ENTERPRISE netBotzV2TempSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Temperature sensor value is not longer too high."
	::= 102

netBotzTempTooLow TRAP-TYPE
	ENTERPRISE netBotzV2TempSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Temperature sensor value too low."
	::= 3

netBotzTempTooLowReturnToNormal TRAP-TYPE
	ENTERPRISE netBotzV2TempSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Temperature sensor value is no longer too low."
	::= 103

netBotzTempTooHighTooLong TRAP-TYPE
	ENTERPRISE netBotzV2TempSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Temperature sensor value too high for too long."
	::= 4

netBotzTempTooHighTooLongReturnToNormal TRAP-TYPE
	ENTERPRISE netBotzV2TempSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Temperature sensor value is not longer too high for too long."
	::= 104

netBotzTempTooLowTooLong TRAP-TYPE
	ENTERPRISE netBotzV2TempSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Temperature sensor value too low for too long."
	::= 5

netBotzTempTooLowForTooLongReturnToNormal TRAP-TYPE
	ENTERPRISE netBotzV2TempSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Temperature sensor value is no longer too low for too long."
	::= 105

netBotzTempUnplugged TRAP-TYPE
	ENTERPRISE netBotzV2TempSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Temperature sensor unplugged."
	::= 6

netBotzTempReplugged TRAP-TYPE
	ENTERPRISE netBotzV2TempSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Temperature sensor no longer unplugged."
	::= 106

netBotzTempIncreasingTooQuickly TRAP-TYPE
	ENTERPRISE netBotzV2TempSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Temperature sensor value increasing too quickly."
	::= 8

netBotzTempNoLongerIncreasingTooQuickly TRAP-TYPE
	ENTERPRISE netBotzV2TempSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Temperature sensor value no longer increasing too quickly."
	::= 108

netBotzTempDecreasingTooQuickly TRAP-TYPE
	ENTERPRISE netBotzV2TempSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Temperature sensor value decreasing too quickly."
	::= 9

netBotzTempNoLongerDecreasingTooQuickly TRAP-TYPE
	ENTERPRISE netBotzV2TempSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Temperature sensor value no longer decreasing too quickly."
	::= 109

netBotzTempError TRAP-TYPE
	ENTERPRISE netBotzV2TempSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Temperature sensor error."
	::= 1

netBotzTempErrorReturnToNormal TRAP-TYPE
	ENTERPRISE netBotzV2TempSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Temperature sensor error resolved."
	::= 101

netBotzHumidityTooHigh TRAP-TYPE
	ENTERPRISE netBotzV2HumiditySensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Humidity sensor value too high."
	::= 2

netBotzHumidityTooHighReturnToNormal TRAP-TYPE
	ENTERPRISE netBotzV2HumiditySensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Humidity sensor value is not longer too high."
	::= 102

netBotzHumidityTooLow TRAP-TYPE
	ENTERPRISE netBotzV2HumiditySensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Humidity sensor value too low."
	::= 3

netBotzHumidityTooLowReturnToNormal TRAP-TYPE
	ENTERPRISE netBotzV2HumiditySensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Humidity sensor value is no longer too low."
	::= 103

netBotzHumidityTooHighTooLong TRAP-TYPE
	ENTERPRISE netBotzV2HumiditySensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Humidity sensor value too high for too long."
	::= 4

netBotzHumidityTooHighTooLongReturnToNormal TRAP-TYPE
	ENTERPRISE netBotzV2HumiditySensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Humidity sensor value is not longer too high for too long."
	::= 104

netBotzHumidityTooLowTooLong TRAP-TYPE
	ENTERPRISE netBotzV2HumiditySensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Humidity sensor value too low for too long."
	::= 5

netBotzHumidityTooLowForTooLongReturnToNormal TRAP-TYPE
	ENTERPRISE netBotzV2HumiditySensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Humidity sensor value is no longer too low for too long."
	::= 105

netBotzHumidityUnplugged TRAP-TYPE
	ENTERPRISE netBotzV2HumiditySensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Humidity sensor unplugged."
	::= 6

netBotzHumidityReplugged TRAP-TYPE
	ENTERPRISE netBotzV2HumiditySensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Humidity sensor no longer unplugged."
	::= 106

netBotzHumidityIncreasingTooQuickly TRAP-TYPE
	ENTERPRISE netBotzV2HumiditySensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Humidity sensor value increasing too quickly."
	::= 8

netBotzHumidityNoLongerIncreasingTooQuickly TRAP-TYPE
	ENTERPRISE netBotzV2HumiditySensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Humidity sensor value no longer increasing too quickly."
	::= 108

netBotzHumidityDecreasingTooQuickly TRAP-TYPE
	ENTERPRISE netBotzV2HumiditySensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Humidity sensor value decreasing too quickly."
	::= 9

netBotzHumidityNoLongerDecreasingTooQuickly TRAP-TYPE
	ENTERPRISE netBotzV2HumiditySensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Humidity sensor value no longer decreasing too quickly."
	::= 109

netBotzHumidityError TRAP-TYPE
	ENTERPRISE netBotzV2HumiditySensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Humidity sensor error."
	::= 1

netBotzHumidityErrorReturnToNormal TRAP-TYPE
	ENTERPRISE netBotzV2HumiditySensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Humidity sensor error resolved."
	::= 101

netBotzDewPointTooHigh TRAP-TYPE
	ENTERPRISE netBotzV2DewPointSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"DewPoint sensor value too high."
	::= 2

netBotzDewPointTooHighReturnToNormal TRAP-TYPE
	ENTERPRISE netBotzV2DewPointSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"DewPoint sensor value is not longer too high."
	::= 102

netBotzDewPointTooLow TRAP-TYPE
	ENTERPRISE netBotzV2DewPointSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"DewPoint sensor value too low."
	::= 3

netBotzDewPointTooLowReturnToNormal TRAP-TYPE
	ENTERPRISE netBotzV2DewPointSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"DewPoint sensor value is no longer too low."
	::= 103

netBotzDewPointTooHighTooLong TRAP-TYPE
	ENTERPRISE netBotzV2DewPointSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"DewPoint sensor value too high for too long."
	::= 4

netBotzDewPointTooHighTooLongReturnToNormal TRAP-TYPE
	ENTERPRISE netBotzV2DewPointSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"DewPoint sensor value is not longer too high for too long."
	::= 104

netBotzDewPointTooLowTooLong TRAP-TYPE
	ENTERPRISE netBotzV2DewPointSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"DewPoint sensor value too low for too long."
	::= 5

netBotzDewPointTooLowForTooLongReturnToNormal TRAP-TYPE
	ENTERPRISE netBotzV2DewPointSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"DewPoint sensor value is no longer too low for too long."
	::= 105

netBotzDewPointUnplugged TRAP-TYPE
	ENTERPRISE netBotzV2DewPointSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"DewPoint sensor unplugged."
	::= 6

netBotzDewPointReplugged TRAP-TYPE
	ENTERPRISE netBotzV2DewPointSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"DewPoint sensor no longer unplugged."
	::= 106

netBotzDewPointIncreasingTooQuickly TRAP-TYPE
	ENTERPRISE netBotzV2DewPointSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"DewPoint sensor value increasing too quickly."
	::= 8

netBotzDewPointNoLongerIncreasingTooQuickly TRAP-TYPE
	ENTERPRISE netBotzV2DewPointSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"DewPoint sensor value no longer increasing too quickly."
	::= 108

netBotzDewPointDecreasingTooQuickly TRAP-TYPE
	ENTERPRISE netBotzV2DewPointSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"DewPoint sensor value decreasing too quickly."
	::= 9

netBotzDewPointNoLongerDecreasingTooQuickly TRAP-TYPE
	ENTERPRISE netBotzV2DewPointSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"DewPoint sensor value no longer decreasing too quickly."
	::= 109

netBotzDewPointError TRAP-TYPE
	ENTERPRISE netBotzV2DewPointSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"DewPoint sensor error."
	::= 1

netBotzDewPointErrorReturnToNormal TRAP-TYPE
	ENTERPRISE netBotzV2DewPointSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"DewPoint sensor error resolved."
	::= 101

netBotzAirFlowTooHigh TRAP-TYPE
	ENTERPRISE netBotzV2AirFlowSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"AirFlow sensor value too high."
	::= 2

netBotzAirFlowTooHighReturnToNormal TRAP-TYPE
	ENTERPRISE netBotzV2AirFlowSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"AirFlow sensor value is not longer too high."
	::= 102

netBotzAirFlowTooLow TRAP-TYPE
	ENTERPRISE netBotzV2AirFlowSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"AirFlow sensor value too low."
	::= 3

netBotzAirFlowTooLowReturnToNormal TRAP-TYPE
	ENTERPRISE netBotzV2AirFlowSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"AirFlow sensor value is no longer too low."
	::= 103

netBotzAirFlowTooHighTooLong TRAP-TYPE
	ENTERPRISE netBotzV2AirFlowSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"AirFlow sensor value too high for too long."
	::= 4

netBotzAirFlowTooHighTooLongReturnToNormal TRAP-TYPE
	ENTERPRISE netBotzV2AirFlowSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"AirFlow sensor value is not longer too high for too long."
	::= 104

netBotzAirFlowTooLowTooLong TRAP-TYPE
	ENTERPRISE netBotzV2AirFlowSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"AirFlow sensor value too low for too long."
	::= 5

netBotzAirFlowTooLowForTooLongReturnToNormal TRAP-TYPE
	ENTERPRISE netBotzV2AirFlowSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"AirFlow sensor value is no longer too low for too long."
	::= 105

netBotzAirFlowUnplugged TRAP-TYPE
	ENTERPRISE netBotzV2AirFlowSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"AirFlow sensor unplugged."
	::= 6

netBotzAirFlowReplugged TRAP-TYPE
	ENTERPRISE netBotzV2AirFlowSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"AirFlow sensor no longer unplugged."
	::= 106

netBotzAirFlowIncreasingTooQuickly TRAP-TYPE
	ENTERPRISE netBotzV2AirFlowSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"AirFlow sensor value increasing too quickly."
	::= 8

netBotzAirFlowNoLongerIncreasingTooQuickly TRAP-TYPE
	ENTERPRISE netBotzV2AirFlowSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"AirFlow sensor value no longer increasing too quickly."
	::= 108

netBotzAirFlowDecreasingTooQuickly TRAP-TYPE
	ENTERPRISE netBotzV2AirFlowSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"AirFlow sensor value decreasing too quickly."
	::= 9

netBotzAirFlowNoLongerDecreasingTooQuickly TRAP-TYPE
	ENTERPRISE netBotzV2AirFlowSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"AirFlow sensor value no longer decreasing too quickly."
	::= 109

netBotzAirFlowError TRAP-TYPE
	ENTERPRISE netBotzV2AirFlowSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"AirFlow sensor error."
	::= 1

netBotzAirFlowErrorReturnToNormal TRAP-TYPE
	ENTERPRISE netBotzV2AirFlowSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"AirFlow sensor error resolved."
	::= 101

netBotzAudioTooHigh TRAP-TYPE
	ENTERPRISE netBotzV2AudioSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Audio sensor value too high."
	::= 2

netBotzAudioTooHighReturnToNormal TRAP-TYPE
	ENTERPRISE netBotzV2AudioSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Audio sensor value is not longer too high."
	::= 102

netBotzAudioTooLow TRAP-TYPE
	ENTERPRISE netBotzV2AudioSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Audio sensor value too low."
	::= 3

netBotzAudioTooLowReturnToNormal TRAP-TYPE
	ENTERPRISE netBotzV2AudioSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Audio sensor value is no longer too low."
	::= 103

netBotzAudioTooHighTooLong TRAP-TYPE
	ENTERPRISE netBotzV2AudioSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Audio sensor value too high for too long."
	::= 4

netBotzAudioTooHighTooLongReturnToNormal TRAP-TYPE
	ENTERPRISE netBotzV2AudioSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Audio sensor value is not longer too high for too long."
	::= 104

netBotzAudioTooLowTooLong TRAP-TYPE
	ENTERPRISE netBotzV2AudioSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Audio sensor value too low for too long."
	::= 5

netBotzAudioTooLowForTooLongReturnToNormal TRAP-TYPE
	ENTERPRISE netBotzV2AudioSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Audio sensor value is no longer too low for too long."
	::= 105

netBotzAudioUnplugged TRAP-TYPE
	ENTERPRISE netBotzV2AudioSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Audio sensor unplugged."
	::= 6

netBotzAudioReplugged TRAP-TYPE
	ENTERPRISE netBotzV2AudioSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Audio sensor no longer unplugged."
	::= 106

netBotzAudioIncreasingTooQuickly TRAP-TYPE
	ENTERPRISE netBotzV2AudioSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Audio sensor value increasing too quickly."
	::= 8

netBotzAudioNoLongerIncreasingTooQuickly TRAP-TYPE
	ENTERPRISE netBotzV2AudioSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Audio sensor value no longer increasing too quickly."
	::= 108

netBotzAudioDecreasingTooQuickly TRAP-TYPE
	ENTERPRISE netBotzV2AudioSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Audio sensor value decreasing too quickly."
	::= 9

netBotzAudioNoLongerDecreasingTooQuickly TRAP-TYPE
	ENTERPRISE netBotzV2AudioSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Audio sensor value no longer decreasing too quickly."
	::= 109

netBotzAudioError TRAP-TYPE
	ENTERPRISE netBotzV2AudioSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Audio sensor error."
	::= 1

netBotzAudioErrorReturnToNormal TRAP-TYPE
	ENTERPRISE netBotzV2AudioSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Audio sensor error resolved."
	::= 101

netBotzAmpDetectTooHigh TRAP-TYPE
	ENTERPRISE netBotzV2AmpDetectSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Amp Detectsensor value too high."
	::= 2

netBotzAmpDetectTooHighReturnToNormal TRAP-TYPE
	ENTERPRISE netBotzV2AmpDetectSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Amp Detectsensor value is not longer too high."
	::= 102

netBotzAmpDetectTooLow TRAP-TYPE
	ENTERPRISE netBotzV2AmpDetectSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Amp Detectsensor value too low."
	::= 3

netBotzAmpDetectTooLowReturnToNormal TRAP-TYPE
	ENTERPRISE netBotzV2AmpDetectSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Amp Detectsensor value is no longer too low."
	::= 103

netBotzAmpDetectTooHighTooLong TRAP-TYPE
	ENTERPRISE netBotzV2AmpDetectSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Amp Detectsensor value too high for too long."
	::= 4

netBotzAmpDetectTooHighTooLongReturnToNormal TRAP-TYPE
	ENTERPRISE netBotzV2AmpDetectSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Amp Detectsensor value is not longer too high for too long."
	::= 104

netBotzAmpDetectTooLowTooLong TRAP-TYPE
	ENTERPRISE netBotzV2AmpDetectSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Amp Detectsensor value too low for too long."
	::= 5

netBotzAmpDetectTooLowForTooLongReturnToNormal TRAP-TYPE
	ENTERPRISE netBotzV2AmpDetectSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Amp Detectsensor value is no longer too low for too long."
	::= 105

netBotzAmpDetectUnplugged TRAP-TYPE
	ENTERPRISE netBotzV2AmpDetectSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Amp Detectsensor unplugged."
	::= 6

netBotzAmpDetectReplugged TRAP-TYPE
	ENTERPRISE netBotzV2AmpDetectSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Amp Detectsensor no longer unplugged."
	::= 106

netBotzAmpDetectIncreasingTooQuickly TRAP-TYPE
	ENTERPRISE netBotzV2AmpDetectSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Amp Detectsensor value increasing too quickly."
	::= 8

netBotzAmpDetectNoLongerIncreasingTooQuickly TRAP-TYPE
	ENTERPRISE netBotzV2AmpDetectSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Amp Detectsensor value no longer increasing too quickly."
	::= 108

netBotzAmpDetectDecreasingTooQuickly TRAP-TYPE
	ENTERPRISE netBotzV2AmpDetectSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Amp Detectsensor value decreasing too quickly."
	::= 9

netBotzAmpDetectNoLongerDecreasingTooQuickly TRAP-TYPE
	ENTERPRISE netBotzV2AmpDetectSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Amp Detectsensor value no longer decreasing too quickly."
	::= 109

netBotzAmpDetectError TRAP-TYPE
	ENTERPRISE netBotzV2AmpDetectSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Amp Detectsensor error."
	::= 1

netBotzAmpDetectErrorReturnToNormal TRAP-TYPE
	ENTERPRISE netBotzV2AmpDetectSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Amp Detectsensor error resolved."
	::= 101

netBotzDryContactUnplugged TRAP-TYPE
	ENTERPRISE netBotzV2DryContactSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Dry Contact sensor unplugged."
	::= 6

netBotzDryContactReplugged TRAP-TYPE
	ENTERPRISE netBotzV2DryContactSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Dry Contact sensor no longer unplugged."
	::= 106

netBotzDryContactError TRAP-TYPE
	ENTERPRISE netBotzV2DryContactSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Dry Contact sensor error."
	::= 1

netBotzDryContactErrorReturnToNormal TRAP-TYPE
	ENTERPRISE netBotzV2DryContactSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Dry Contact sensor error resolved."
	::= 101

netBotzDryContactValueError TRAP-TYPE
	ENTERPRISE netBotzV2DryContactSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Dry Contact sensor value error."
	::= 10

netBotzDryContactValueErrorReturnToNormal TRAP-TYPE
	ENTERPRISE netBotzV2DryContactSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Dry Contact sensor value error resolved."
	::= 110

netBotzCameraMotionSensorUnplugged TRAP-TYPE
	ENTERPRISE netBotzV2CameraMotionSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Camera Motion Sensor sensor unplugged."
	::= 6

netBotzCameraMotionSensorReplugged TRAP-TYPE
	ENTERPRISE netBotzV2CameraMotionSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Camera Motion Sensor sensor no longer unplugged."
	::= 106

netBotzCameraMotionSensorError TRAP-TYPE
	ENTERPRISE netBotzV2CameraMotionSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Camera Motion Sensor sensor error."
	::= 1

netBotzCameraMotionSensorErrorReturnToNormal TRAP-TYPE
	ENTERPRISE netBotzV2CameraMotionSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Camera Motion Sensor sensor error resolved."
	::= 101

netBotzCameraMotionSensorValueError TRAP-TYPE
	ENTERPRISE netBotzV2CameraMotionSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Camera Motion Sensor sensor value error."
	::= 10

netBotzCameraMotionSensorValueErrorReturnToNormal TRAP-TYPE
	ENTERPRISE netBotzV2CameraMotionSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Camera Motion Sensor sensor value error resolved."
	::= 110

netBotzDoorSensorUnplugged TRAP-TYPE
	ENTERPRISE netBotzV2DoorSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Door Sensor sensor unplugged."
	::= 6

netBotzDoorSensorReplugged TRAP-TYPE
	ENTERPRISE netBotzV2DoorSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Door Sensor sensor no longer unplugged."
	::= 106

netBotzDoorSensorError TRAP-TYPE
	ENTERPRISE netBotzV2DoorSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Door Sensor sensor error."
	::= 1

netBotzDoorSensorErrorReturnToNormal TRAP-TYPE
	ENTERPRISE netBotzV2DoorSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Door Sensor sensor error resolved."
	::= 101

netBotzDoorSensorValueError TRAP-TYPE
	ENTERPRISE netBotzV2DoorSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Door Sensor sensor value error."
	::= 10

netBotzDoorSensorValueErrorReturnToNormal TRAP-TYPE
	ENTERPRISE netBotzV2DoorSensorTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Door Sensor sensor value error resolved."
	::= 110

netBotzPodUnplugged TRAP-TYPE
	ENTERPRISE netBotzV2PodTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Pod unplugged."
	::= 7

netBotzPodReplugged TRAP-TYPE
	ENTERPRISE netBotzV2PodTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Pod no longer unplugged."
	::= 107

netBotzSensorPodUnplugged TRAP-TYPE
	ENTERPRISE netBotzV2SensorPodTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Sensor Pod unplugged."
	::= 7

netBotzSensorPodReplugged TRAP-TYPE
	ENTERPRISE netBotzV2SensorPodTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Sensor Pod no longer unplugged."
	::= 107

netBotzCameraPodUnplugged TRAP-TYPE
	ENTERPRISE netBotzV2CameraPodTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Camera Pod unplugged."
	::= 7

netBotzCameraPodReplugged TRAP-TYPE
	ENTERPRISE netBotzV2CameraPodTraps
	VARIABLES {
		netBotzV2TrapErrorID,	
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION 
	"Camera Pod no longer unplugged."
	::= 107

netBotzLogonError TRAP-TYPE
	ENTERPRISE netBotzV2PodTraps
	VARIABLES {
		netBotzV2TrapErrorID,
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION
	"Multiple failed logon attempts."
	::= 11

netBotzLogonErrorResolved TRAP-TYPE
	ENTERPRISE netBotzV2PodTraps
	VARIABLES {
		netBotzV2TrapErrorID,
		netBotzV2TrapErrorType,
		netBotzV2TrapErrorTypeLabel,
		netBotzV2TrapSensorID,
		netBotzV2TrapSensorLabel,
		netBotzV2TrapPodID,
		netBotzV2TrapPodLabel,
		netBotzV2TrapPortID,
		netBotzV2TrapPortLabel,
		netBotzV2TrapStartTime,
		netBotzV2TrapNotifyTime,
		netBotzV2TrapResolveTime,
		netBotzV2TrapSeverity,
		netBotzV2TrapSensorValue,
		netBotzV2TrapSensorValueInt,
		netBotzV2TrapSensorValueFraction
		}
	DESCRIPTION
	"Failed logon attempts stopped, or logon succeeded."
	::= 111

END
