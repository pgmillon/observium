NETBOTZ-DEVICE-MIB DEFINITIONS ::= BEGIN

IMPORTS
   OBJECT-TYPE FROM RFC-1212
   IpAddress FROM RFC1155-SMI
   DisplayString FROM RFC1213-MIB
   netBotz-device FROM NETBOTZ-MIB;

netBotz-dev-host	OBJECT-TYPE
	SYNTAX		DisplayString
	ACCESS		read-write
	STATUS		mandatory
	DESCRIPTION 	"Netbotz device's host name."
	REFERENCE 	"Netbotz Host"
	::= { netBotz-device 1 }

netBotz-dev-domain	OBJECT-TYPE
	SYNTAX		DisplayString
	ACCESS		read-write
	STATUS		mandatory
	DESCRIPTION	"Netbotz device's default DNS domain."
	REFERENCE 	"Netbotz Domain"
	::= { netBotz-device 2 }

netBotz-dev-ip		OBJECT-TYPE
	SYNTAX		IpAddress
	ACCESS		read-write
	STATUS		mandatory
	DESCRIPTION	"Netbotz device's IP address."
	REFERENCE 	"Netbotz IP address"
	::= { netBotz-device 3 }

netBotz-dev-netmask	OBJECT-TYPE
	SYNTAX		IpAddress
	ACCESS		read-write
	STATUS		mandatory
	DESCRIPTION	"Netbotz device's netmask."
	REFERENCE 	"Netbotz Device Netmask"
	::= { netBotz-device 4 }

netBotz-dev-gateway	OBJECT-TYPE
	SYNTAX		IpAddress
	ACCESS		read-write
	STATUS		mandatory
	DESCRIPTION	"Netbotz device's default gateway/router. 0.0.0.0 if not defined."
	REFERENCE 	"Netbotz Device Gateway"
	::= { netBotz-device 5 }

netBotz-dev-primarydns	OBJECT-TYPE
	SYNTAX		IpAddress
	ACCESS		read-write
	STATUS		mandatory
	DESCRIPTION	"Primary Domain Name Server. 0.0.0.0 if not defined."
	REFERENCE 	"Primary DNS"
	::= { netBotz-device 6 }

netBotz-dev-secondarydns	OBJECT-TYPE
	SYNTAX		IpAddress
	ACCESS		read-write
	STATUS		mandatory
	DESCRIPTION	"Secondary Domain Name Server. 0.0.0.0 if not defined."
	REFERENCE 	"Secondary DNS"
	::= { netBotz-device 7 }

netBotz-dev-smtp	OBJECT-TYPE
	SYNTAX		DisplayString
	ACCESS		read-write
	STATUS		mandatory
	DESCRIPTION	"SMTP server address.  This is the mail server used for sending alert e-mails."
	REFERENCE 	"SMTP"
	::= { netBotz-device 8 }

netBotz-dev-smtpport	OBJECT-TYPE
	SYNTAX		INTEGER
	ACCESS		read-write
	STATUS		mandatory
	DESCRIPTION	"SMTP port.  Port number of SMTP server used for sending alert e-mails."
	REFERENCE 	"SMTP Port"
	::= { netBotz-device 9 }

netBotz-dev-popport	OBJECT-TYPE
	SYNTAX		INTEGER
	ACCESS		read-write
	STATUS		mandatory
	DESCRIPTION	"POP port.  Currently, not used."
	REFERENCE 	"POP Port"
	::= { netBotz-device 10 }

netBotz-dev-loglevel	OBJECT-TYPE
	SYNTAX		INTEGER
	ACCESS		read-write
	STATUS		mandatory
	DESCRIPTION	
	"This field contains the log level of the Netbotz device.
	Log messages will be filtered, so that only same or lower-level
	messages will be passed. The default log level is 5, for warnings
	and lower levels. The log levels are the following:
	1 - emergency
	2 - alert
	3 - critical
	4 - error
	5 - warning
	6 - notice
	7 - info
	8 - trace"
	REFERENCE 	"Log Level"
	::= { netBotz-device 11 }

netBotz-dev-logaddress	OBJECT-TYPE
	SYNTAX		IpAddress
	ACCESS		read-write
	STATUS		mandatory
	DESCRIPTION 
	"This field contains an IP address to receive log messages
	from the Netbotz device. 0.0.0.0 for no external logging."
	REFERENCE 	"Log Address"
	::= { netBotz-device 12 }

netBotz-dev-logport	OBJECT-TYPE
	SYNTAX		INTEGER
	ACCESS		read-write
	STATUS		mandatory
	DESCRIPTION	"Port to use in conjunction with the log address,
	for log messages from the Netbotz device to be sent to an
	external IP address. 0 = no external logging."
	REFERENCE 	"Log Port"
	::= { netBotz-device 13 }

netBotz-dev-primaryemail	OBJECT-TYPE
	SYNTAX		DisplayString
	ACCESS		read-write
	STATUS		mandatory
	DESCRIPTION	"The primary email addresses for alerts and messages (list separated by commas for multiple addresses)."
	REFERENCE 	"Primary Email"
	::= { netBotz-device 14 }

netBotz-dev-secondaryemail	OBJECT-TYPE
	SYNTAX		DisplayString
	ACCESS		read-write
	STATUS		mandatory
	DESCRIPTION	"The secondary email address for alerts and messages (list separated by commas for multiple addresses)."
	REFERENCE 	"Secondary Email"
	::= { netBotz-device 15 }

netBotz-dev-pager	OBJECT-TYPE
	SYNTAX		DisplayString
	ACCESS		read-write
	STATUS		mandatory
	DESCRIPTION	"The pager number for alerts and messages.  Currently, not used."
	REFERENCE 	"Pager"
	::= { netBotz-device 16 }

netBotz-dev-serialno	OBJECT-TYPE
	SYNTAX		DisplayString
	ACCESS		read-only
	STATUS		mandatory
	DESCRIPTION	"The serial number of the Netbotz device."
	REFERENCE 	"Serial Number"
	::= { netBotz-device 17 }

netBotz-dev-pop	OBJECT-TYPE
	SYNTAX		DisplayString
	ACCESS		read-write
	STATUS		mandatory
	DESCRIPTION	"POP server name.  Currently, not used."
	REFERENCE 	"POP"
	::= { netBotz-device 18 }

netBotz-dev-version OBJECT-TYPE
	SYNTAX		DisplayString
	ACCESS		read-only
	STATUS		mandatory
	DESCRIPTION	"The current NetBotz device firmware version."
	REFERENCE	"Firmware Version"
	::= { netBotz-device 19 }

netBotz-dev-registered OBJECT-TYPE
	SYNTAX		INTEGER
	ACCESS		read-only
	STATUS		mandatory
	DESCRIPTION	"Indicates if the device has been registered with Netbotz, Inc. 1=registered, 0=not registered."
	REFERENCE	"Device Registered"
	::= { netBotz-device 20 }

netBotz-default-applet OBJECT-TYPE
	SYNTAX		INTEGER
	ACCESS		read-write
	STATUS		mandatory
	DESCRIPTION	"Setting to control if default web page should launch applet by default(1) or the HTML status page(0)."
	REFERENCE	"Default Applet"
	::= { netBotz-device 21 }

netBotz-guibar-color OBJECT-TYPE
	SYNTAX		INTEGER
	ACCESS		read-write
	STATUS		mandatory
	DESCRIPTION	"Setting for color of GUI bar (RGB). Value = 0xRRGGBB."
	REFERENCE	"GUI Bar Color"
	::= { netBotz-device 22 }

netBotz-locale OBJECT-TYPE
	SYNTAX		DisplayString
	ACCESS		read-write
	STATUS		mandatory
	DESCRIPTION	"The locale ID of the NetBotz device.  Format is ISO 639 language (lower case), 
            an underscore, and ISO 3166 country (upper case).  Some locales are just the ISO 639 language code."
	REFERENCE	"Locale"
	::= { netBotz-device 23 }

netBotz-timezone OBJECT-TYPE
	SYNTAX		DisplayString
	ACCESS		read-write
	STATUS		mandatory
	DESCRIPTION	"The timezone ID of the NetBotz device."
	REFERENCE	"TimeZone"
	::= { netBotz-device 24 }

netBotz-24hourpreferred	OBJECT-TYPE
	SYNTAX		INTEGER
	ACCESS		read-write
	STATUS		mandatory
	DESCRIPTION	"Indicates if 24-hour(1) versus 12-hour(0) time format is preferred."
	REFERENCE 	"24 hour format"
	::= { netBotz-device 25 }

netBotz-utc-clock	OBJECT-TYPE
	SYNTAX		INTEGER
	ACCESS		read-write
	STATUS		mandatory
	DESCRIPTION	"Current time of clock on NetBotz device, in UTC seconds (seconds since 1/1/1970 12:00am GMT)."
	REFERENCE 	"UTC Clock"
	::= { netBotz-device 26 }

netBotz-ismetric	OBJECT-TYPE
	SYNTAX		INTEGER
	ACCESS		read-only
	STATUS		mandatory
	DESCRIPTION	"Units are metric (1) or U.S. (0).  Applies to temperature and airflow rate."
	REFERENCE 	"Metric Units"
	::= { netBotz-device 27 }

netBotz-alert-url OBJECT-TYPE
	SYNTAX		DisplayString
	ACCESS		read-write
	STATUS		mandatory
	DESCRIPTION	"The URL, if defined, to which non-picture alerts are HTTP POSTed"
	REFERENCE	"Alert URL"
	::= { netBotz-device 28 }

netBotz-picture-alert-url OBJECT-TYPE
	SYNTAX		DisplayString
	ACCESS		read-write
	STATUS		mandatory
	DESCRIPTION	"The URL, if defined, to which picture alerts are HTTP POSTed, using multipart/form-data
		encoding."
	REFERENCE	"Picture Alert URL"
	::= { netBotz-device 29 }

netBotz-sensor-data-url OBJECT-TYPE
	SYNTAX		DisplayString
	ACCESS		read-write
	STATUS		mandatory
	DESCRIPTION	"The URL, if defined, to which sensor data is periodically HTTP POSTed."
	REFERENCE	"Sensor Data URL"
	::= { netBotz-device 30 }

netBotz-alert-url-logon OBJECT-TYPE
	SYNTAX		DisplayString
	ACCESS		read-write
	STATUS		mandatory
	DESCRIPTION	"The user ID and password, if defined, used for POSTing non-picture alerts.
		Field is write-only, and formatted /"
	REFERENCE	"Alert URL Logon"
	::= { netBotz-device 31 }

netBotz-picture-alert-url-logon OBJECT-TYPE
	SYNTAX		DisplayString
	ACCESS		read-write
	STATUS		mandatory
	DESCRIPTION	"The user ID and password, if defined, used for POSTing picture alerts.
		Field is write-only, and formatted /"
	REFERENCE	"Picture Alert URL Logon"
	::= { netBotz-device 32 }

netBotz-sensor-data-url-logon OBJECT-TYPE
	SYNTAX		DisplayString
	ACCESS		read-write
	STATUS		mandatory
	DESCRIPTION	"The user ID and password, if defined, used for POSTing sensor data.
		Field is write-only, and formatted /"
	REFERENCE	"Sensor Data URL Logon"
	::= { netBotz-device 33 }

netBotz-sensor-data-url-period	OBJECT-TYPE
	SYNTAX		INTEGER
	ACCESS		read-write
	STATUS		mandatory
	DESCRIPTION	"Default number of minutes between periodic sensor data HTTP POSTs."
	REFERENCE 	"Sensor Data URL Period"
	::= { netBotz-device 34 }

netBotz-sensor-data-url-flags	OBJECT-TYPE
	SYNTAX		INTEGER
	ACCESS		read-write
	STATUS		mandatory
	DESCRIPTION	"Option flags for data POSTs of sensor data.  Bit 0=1 if current picture
		should be included.  Bits 1-31 are reserved."
	REFERENCE 	"Sensor Data URL Flags"
	::= { netBotz-device 35 }

END
