JUNIPER-IVE-MIB DEFINITIONS ::= BEGIN
        IMPORTS 
        	NOTIFICATION-TYPE, MODULE-IDENTITY, enterprises
        		FROM SNMPv2-SMI
        	NetworkAddress
        		FROM RFC1155-SMI
        	IpAddress
        		FROM RFC1155-SMI;
        
juniper-ive MODULE-IDENTITY
    LAST-UPDATED "201005180000Z"
    ORGANIZATION "Juniper"
    CONTACT-INFO    
	 "Internet: https://www.juniper.net/cm/index.jsp"
    DESCRIPTION
	"This file defines the private Juniper Networks MIB extensions."
    REVISION     "201002221000Z"
    DESCRIPTION
	"Initial Version"
    ::= { enterprises 12532 }


logFullPercent OBJECT-TYPE
    SYNTAX	Gauge32
    MAX-ACCESS	read-only
    STATUS	current
    DESCRIPTION  
	"Percentage of log file full"
    ::= { juniper-ive 1 } 

signedInWebUsers OBJECT-TYPE
    SYNTAX	Gauge32
    MAX-ACCESS	read-only
    STATUS	current
    DESCRIPTION  
	"Number of Signed-In Web Users"
    ::= { juniper-ive 2 } 

signedInMailUsers OBJECT-TYPE
    SYNTAX	Gauge32
    MAX-ACCESS	read-only
    STATUS	current
    DESCRIPTION  
	"Number of Signed-In Mail Users"
    ::= { juniper-ive 3 } 

blockedIP OBJECT-TYPE
    SYNTAX      IpAddress
    MAX-ACCESS  accessible-for-notify
    STATUS      current
    DESCRIPTION
        "IP Address that is blocked due to consecutive failed login attempts"
    ::= { juniper-ive 4 }

authServerName OBJECT-TYPE
    SYNTAX      OCTET STRING
    MAX-ACCESS  accessible-for-notify
    STATUS      current
    DESCRIPTION
        "Name of an external authentication server"
    ::= { juniper-ive 5 }

productName OBJECT-TYPE
    SYNTAX      OCTET STRING
    MAX-ACCESS  read-only
    STATUS      current
    DESCRIPTION
        "IVE Licensed Product Name"
    ::= { juniper-ive 6 }

productVersion OBJECT-TYPE
    SYNTAX      OCTET STRING
    MAX-ACCESS  read-only
    STATUS      current
    DESCRIPTION
        "IVE System Software Version"
    ::= { juniper-ive 7 }
    
fileName OBJECT-TYPE
    SYNTAX      OCTET STRING
    MAX-ACCESS  accessible-for-notify
    STATUS      current
    DESCRIPTION
        "File name"
    ::= { juniper-ive 8 }
    
meetingUserCount OBJECT-TYPE
    SYNTAX	Gauge32
    MAX-ACCESS	accessible-for-notify
    STATUS	current
    DESCRIPTION  
	"the number of concurrent meeting users"
    ::= { juniper-ive 9 } 

    
iveCpuUtil OBJECT-TYPE
    SYNTAX	Gauge32
    MAX-ACCESS	read-only
    STATUS	current
    DESCRIPTION  
	"The CPU Utilization of the IVE system"
    ::= { juniper-ive 10 } 

iveMemoryUtil OBJECT-TYPE
    SYNTAX	Gauge32
    MAX-ACCESS	read-only
    STATUS	current
    DESCRIPTION  
	"The Memory Utilization of the IVE system"
    ::= { juniper-ive 11 } 

iveConcurrentUsers OBJECT-TYPE
    SYNTAX	Gauge32
    MAX-ACCESS	read-only
    STATUS	current
    DESCRIPTION  
	"The Total number of Users Logged In for the IVE Node"
    ::= { juniper-ive 12 } 

clusterConcurrentUsers OBJECT-TYPE
    SYNTAX       Gauge32
    MAX-ACCESS	read-only
    STATUS	current
    DESCRIPTION  
	"The Total number of Users Logged In for the Cluster"
    ::= { juniper-ive 13 } 

iveTotalHits OBJECT-TYPE
    SYNTAX      Counter64	
    MAX-ACCESS	read-only
    STATUS	current
    DESCRIPTION  
	"The Total number of hits to the IVE since last reboot"
    ::= { juniper-ive 14 } 

iveFileHits OBJECT-TYPE
    SYNTAX      Counter64	
    MAX-ACCESS	read-only
    STATUS	current
    DESCRIPTION  
	"The Total number of File hits to the IVE since last reboot"
    ::= { juniper-ive 15 } 

iveWebHits OBJECT-TYPE
    SYNTAX      Counter64	
    MAX-ACCESS	read-only
    STATUS	current
    DESCRIPTION  
	"The Total number of hits via the Web Interface since the last reboot"
    ::= { juniper-ive 16 } 

iveAppletHits OBJECT-TYPE
    SYNTAX      Counter64	
    MAX-ACCESS	read-only
    STATUS	current
    DESCRIPTION  
	"The Total number of applet hits to the IVE  since last reboot"
    ::= { juniper-ive 17 } 

ivetermHits OBJECT-TYPE
    SYNTAX      Counter64	
    MAX-ACCESS	read-only
    STATUS	current
    DESCRIPTION  
	"The Total number of terminal hits to the IVE since last reboot"
    ::= { juniper-ive 18 } 

iveSAMHits OBJECT-TYPE
    SYNTAX      Counter64	
    MAX-ACCESS	read-only
    STATUS	current
    DESCRIPTION  
	"The Total number of SAM(Secure Application manager)hits of since last reboot"
    ::= { juniper-ive 19 } 

iveNCHits OBJECT-TYPE
    SYNTAX      Counter64	
    MAX-ACCESS	read-only
    STATUS	current
    DESCRIPTION  
	"The Total number of NC(Network Connect) hits of since last reboot"
    ::= { juniper-ive 20 } 

meetingHits OBJECT-TYPE
    SYNTAX      Counter64	
    MAX-ACCESS	read-only
    STATUS	current
    DESCRIPTION  
	"The Total number of Meeting hits of since last reboot"
    ::= { juniper-ive 21 } 

meetingCount OBJECT-TYPE
    SYNTAX	Gauge32
    MAX-ACCESS	accessible-for-notify
    STATUS	current
    DESCRIPTION  
	"the number of concurrent meetings"
    ::= { juniper-ive 22 } 

logName OBJECT-TYPE
    SYNTAX      OCTET STRING
    MAX-ACCESS  accessible-for-notify
    STATUS      current
    DESCRIPTION
        "Name of the log (admin/user/event)"
    ::= { juniper-ive 23 }

iveSwapUtil OBJECT-TYPE
    SYNTAX	Gauge32
    MAX-ACCESS	read-only
    STATUS	current
    DESCRIPTION  
	"The Swap Utilization of the IVE system"
    ::= { juniper-ive 24 } 

diskFullPercent OBJECT-TYPE
    SYNTAX	Gauge32
    MAX-ACCESS	read-only
    STATUS	current
    DESCRIPTION  
	"Percentage of disk space full"
    ::= { juniper-ive 25 } 

blockedIPList OBJECT-TYPE
    SYNTAX	SEQUENCE OF IPEntry
    MAX-ACCESS	read-only
    STATUS	current
    DESCRIPTION  
	"Table of 10 most recently blocked IPs"
    ::= { juniper-ive 26 } 

ipEntry OBJECT-TYPE
    SYNTAX      IPEntry
    MAX-ACCESS  not-accessible
    STATUS      current
    DESCRIPTION
        "An entry containing a blocked IP"
    INDEX       { ipIndex }
    ::= { blockedIPList 1 }

IPEntry	::= SEQUENCE {
    ipIndex	Integer32,
    ipValue	NetworkAddress
}

ipIndex OBJECT-TYPE
    SYNTAX      Integer32 
    MAX-ACCESS  read-only
    STATUS      current
    DESCRIPTION
        "Index for IP Table"
    ::= { ipEntry 1 }

ipValue OBJECT-TYPE
    SYNTAX      NetworkAddress
    MAX-ACCESS  read-only
    STATUS      current
    DESCRIPTION
        "Blocked IP Entry"
    ::= { ipEntry 2 }

logID OBJECT-TYPE
    SYNTAX      OCTET STRING
    MAX-ACCESS  accessible-for-notify
    STATUS      current
    DESCRIPTION
	    "The unique ID of the log message."
    ::= { juniper-ive 27 }

logType OBJECT-TYPE
    SYNTAX      OCTET STRING
    MAX-ACCESS  accessible-for-notify
    STATUS      current
    DESCRIPTION
	    "String stating whether log message is major or critical."
    ::= { juniper-ive 28 }

logDescription OBJECT-TYPE
    SYNTAX      OCTET STRING
    MAX-ACCESS  accessible-for-notify
    STATUS      current
    DESCRIPTION
	    "The actual log message string."
    ::= { juniper-ive 29 }

ivsName OBJECT-TYPE
    SYNTAX      OCTET STRING
    MAX-ACCESS  accessible-for-notify
    STATUS      current
    DESCRIPTION
        "Virtual System name"
    ::= { juniper-ive 30 }

ocspResponderURL OBJECT-TYPE
    SYNTAX      OCTET STRING
    MAX-ACCESS  accessible-for-notify
    STATUS      current
    DESCRIPTION
        "Name of an OCSP Responder"
    ::= { juniper-ive 31 }
 
fanDescription OBJECT-TYPE
    SYNTAX      OCTET STRING
    MAX-ACCESS  accessible-for-notify
    STATUS      current
    DESCRIPTION
	    "The status of the fans"
    ::= { juniper-ive 32 }

psDescription OBJECT-TYPE
    SYNTAX      OCTET STRING
    MAX-ACCESS  accessible-for-notify
    STATUS      current
    DESCRIPTION
	    "The status of the power supplies"
    ::= { juniper-ive 33 }

raidDescription OBJECT-TYPE
    SYNTAX      OCTET STRING
    MAX-ACCESS  accessible-for-notify
    STATUS      current
    DESCRIPTION
	    "The status of the RAID"
    ::= { juniper-ive 34 }



-- J&J traps

clusterName OBJECT-TYPE
    SYNTAX      OCTET STRING
    MAX-ACCESS  accessible-for-notify
    STATUS      current
    DESCRIPTION
	    "Cluster Name"
    ::= { juniper-ive 35 }


nodeList OBJECT-TYPE
    SYNTAX	OCTET STRING
    MAX-ACCESS  accessible-for-notify
    STATUS	current
    DESCRIPTION  
	"List of disabled nodes"
    ::= { juniper-ive 36 } 


vipType OBJECT-TYPE
    SYNTAX      OCTET STRING
    MAX-ACCESS  accessible-for-notify
    STATUS      current
    DESCRIPTION
	    "Whether the VIP is external or internal"
    ::= { juniper-ive 37 }

currentVIP OBJECT-TYPE
    SYNTAX      OCTET STRING
    MAX-ACCESS  accessible-for-notify
    STATUS      current
    DESCRIPTION
	    "Current value of VIP being changed"
    ::= { juniper-ive 38 }

newVIP OBJECT-TYPE
    SYNTAX      OCTET STRING
    MAX-ACCESS  accessible-for-notify
    STATUS      current
    DESCRIPTION
	    "New value for the VIp being changed"
    ::= { juniper-ive 39 }


nicEvent OBJECT-TYPE
    SYNTAX	OCTET STRING
    MAX-ACCESS  accessible-for-notify
    STATUS	current
    DESCRIPTION  
	"Type of event that generated a the Trap: admin, external"
    ::= { juniper-ive 40 } 

nodeName OBJECT-TYPE
    SYNTAX	OCTET STRING
    MAX-ACCESS  accessible-for-notify
    STATUS	current
    DESCRIPTION  
	"Node Name"
    ::= { juniper-ive 41 } 

iveTemperature OBJECT-TYPE
    SYNTAX	Gauge32
    MAX-ACCESS	read-only
    STATUS	current
    DESCRIPTION  
	"The Temperature of MAG application blade. Other platform such as SA and IC will return 0"
    ::= { juniper-ive 42 } 

iveTraps OBJECT IDENTIFIER ::= { juniper-ive 251 }

-- iveTraps.1 and iveTraps.2 are loaded incorrectly in HP OpenView 
-- so avoid defining them
    
iveLogNearlyFull NOTIFICATION-TYPE
    OBJECTS { logFullPercent, logName }
    STATUS	current
    DESCRIPTION
	"Log file nearly full"
    ::= { iveTraps 4 }

iveLogFull NOTIFICATION-TYPE
    OBJECTS { logName }
    STATUS	current
    DESCRIPTION
	"Log file full"
    ::= { iveTraps 5 }

iveMaxConcurrentUsersSignedIn NOTIFICATION-TYPE
    STATUS	current
    DESCRIPTION
	"Maximum number of concurrent users signed in"
    ::= { iveTraps 6 }
    
iveTooManyFailedLoginAttempts NOTIFICATION-TYPE
    OBJECTS { blockedIP }
    STATUS	current
    DESCRIPTION
	"Too many failed login attempts"
    ::= { iveTraps 7 }

externalAuthServerUnreachable NOTIFICATION-TYPE
    OBJECTS { authServerName }
    STATUS	current
    DESCRIPTION
	"External authentication server is not responding"
    ::= { iveTraps 8 }

iveStart NOTIFICATION-TYPE
    STATUS	current
    DESCRIPTION
	"IVE startup under administrator's instruction."
    ::= { iveTraps 9 }

iveShutdown NOTIFICATION-TYPE
    STATUS	current
    DESCRIPTION
	"IVE shutdown under administrator's instruction."
    ::= { iveTraps 10 }

iveReboot NOTIFICATION-TYPE
    STATUS	current
    DESCRIPTION
	"IVE reboot under administrator's instruction."
    ::= { iveTraps 11 }
    
archiveServerUnreachable NOTIFICATION-TYPE
    STATUS	current
    DESCRIPTION
	"Archive server is not responding"
    ::= { iveTraps 12 }

archiveServerLoginFailed NOTIFICATION-TYPE
    STATUS	current
    DESCRIPTION
	"Could not login into archive server. Verify FTP username and password."
    ::= { iveTraps 13 }
    
archiveFileTransferFailed NOTIFICATION-TYPE   
    OBJECTS { fileName }
    STATUS	current
    DESCRIPTION
	"Could not store file on archive server"
    ::= { iveTraps 14 }
    
    
meetingUserLimit NOTIFICATION-TYPE
    OBJECTS { meetingUserCount }
    STATUS	current
    DESCRIPTION
	"Concurrent user count over license limit"
    ::= { iveTraps 15 }

iveRestart NOTIFICATION-TYPE
    STATUS	current
    DESCRIPTION
	"IVE has restarted under administrator's instruction."
    ::= { iveTraps 16 }

meetingLimit NOTIFICATION-TYPE
    OBJECTS { meetingCount }
    STATUS	current
    DESCRIPTION
	"Concurrent meeting count over license limit"
    ::= { iveTraps 17 }

iveDiskNearlyFull NOTIFICATION-TYPE
    OBJECTS { diskFullPercent }
    STATUS	current
    DESCRIPTION
	"Disk space nearly full"
    ::= { iveTraps 18 }

iveDiskFull NOTIFICATION-TYPE
    STATUS	current
    DESCRIPTION
	"Disk space full"
    ::= { iveTraps 19 }

logMessageTrap NOTIFICATION-TYPE
    OBJECTS { logID, logType, logDescription }
    STATUS  current
	DESCRIPTION
	    "The TRAP generated from a log message."
    ::= { iveTraps 20 }

memUtilNotify NOTIFICATION-TYPE
    OBJECTS { iveMemoryUtil }
    STATUS	current
    DESCRIPTION
	"IVE memory utilization above threshold"
    ::= { iveTraps 21 }

cpuUtilNotify NOTIFICATION-TYPE
    OBJECTS { iveCpuUtil }
    STATUS	current
    DESCRIPTION
	"IVE CPU utilization above threshold"
    ::= { iveTraps 22 }

swapUtilNotify NOTIFICATION-TYPE
    OBJECTS { iveSwapUtil }
    STATUS	current
    DESCRIPTION
	"IVE swap utilization above threshold"
    ::= { iveTraps 23 }

iveMaxConcurrentUsersVirtualSystem NOTIFICATION-TYPE
    OBJECTS { ivsName }
    STATUS	current
    DESCRIPTION
	"Maximum number of concurrent Virtual System users signed in"
    ::= { iveTraps 24 }

ocspResponderConnectionFailed NOTIFICATION-TYPE
    OBJECTS { ocspResponderURL }
    STATUS	current
    DESCRIPTION
	"OCSP Responder cannot be connected"
    ::= { iveTraps 25 }

iveFanNotify NOTIFICATION-TYPE
    OBJECTS { fanDescription }
    STATUS	current
    DESCRIPTION
	"The status of the fans has changed"
    ::= { iveTraps 26 }
    
ivePowerSupplyNotify NOTIFICATION-TYPE
    OBJECTS { psDescription }
    STATUS	current
    DESCRIPTION
	"The status of the power supplies has changed"
    ::= { iveTraps 27 }
    
iveRaidNotify NOTIFICATION-TYPE
    OBJECTS { raidDescription }
    STATUS	current
    DESCRIPTION
	"The status of the RAID has changed"
    ::= { iveTraps 28 }

iveClusterDisableNodeTrap NOTIFICATION-TYPE
    OBJECTS { clusterName, nodeList }
    STATUS	current
    DESCRIPTION
	"A Given node(s) in a cluster has(have) been disabled"
    ::= { iveTraps 29 }

iveClusterChangedVIPTrap NOTIFICATION-TYPE
    OBJECTS { vipType, currentVIP, newVIP }
    STATUS	current
    DESCRIPTION
	"A external/internal VIP has changed from its current value to a new one"
    ::= { iveTraps 30 }

iveNetExternalInterfaceDownTrap NOTIFICATION-TYPE
    OBJECTS { nicEvent }
    STATUS	current
    DESCRIPTION
	"The External interface has gone down, reason is in nicEvent"
    ::= { iveTraps 31 }

iveClusterDeleteTrap NOTIFICATION-TYPE
    OBJECTS { nodeName }
    STATUS	current
    DESCRIPTION
	"Cluster delete inititaed by nodeName"
    ::= { iveTraps 32 }

iveNetInternalInterfaceDownTrap NOTIFICATION-TYPE
    OBJECTS { nicEvent }
    STATUS	current
    DESCRIPTION
	"The Internal interface has gone down, reason is in nicEvent"
    ::= { iveTraps 33 }

iveNetManagementInterfaceDownTrap NOTIFICATION-TYPE
    OBJECTS { nicEvent }
    STATUS	current
    DESCRIPTION
	"The Management interface has gone down, reason is in nicEvent"
    ::= { iveTraps 34 }

iveTemperatureNotify NOTIFICATION-TYPE
    OBJECTS { iveTemperature }
    STATUS	current
    DESCRIPTION
	"IVE Temperature is above threshold"
    ::= { iveTraps 35 }

-- Product Name
iveSAProduct OBJECT IDENTIFIER ::= { juniper-ive 252 }
iveICProduct OBJECT IDENTIFIER ::= { juniper-ive 253 }
iveMAGProduct OBJECT IDENTIFIER ::= { juniper-ive 254 }

iveProductSA700   OBJECT IDENTIFIER ::= {iveSAProduct 1}
iveProductSA2000  OBJECT IDENTIFIER ::= {iveSAProduct 2 }
iveProductSA2500  OBJECT IDENTIFIER ::= {iveSAProduct 3 }
iveProductSA4000  OBJECT IDENTIFIER ::= {iveSAProduct 4 }
iveProductSA4500  OBJECT IDENTIFIER ::= {iveSAProduct 5 }
iveProductSA6000 OBJECT IDENTIFIER ::= {iveSAProduct 6 }
iveProductSA6500 OBJECT IDENTIFIER ::= {iveSAProduct 7 }

iveProductIC4000  OBJECT IDENTIFIER ::= {iveICProduct 1 }
iveProductIC4500  OBJECT IDENTIFIER ::= {iveICProduct 2 }
iveProductIC6000 OBJECT IDENTIFIER ::= {iveICProduct 3 }
iveProductIC6500 OBJECT IDENTIFIER ::= {iveICProduct 4 }

--MAG platform
iveProductMAG2600  OBJECT IDENTIFIER ::= {iveMAGProduct 1 }
iveProductMAG4610  OBJECT IDENTIFIER ::= {iveMAGProduct 2 }
iveProductSM160  OBJECT IDENTIFIER ::= {iveMAGProduct 3 }
iveProductSM360 OBJECT IDENTIFIER ::= {iveMAGProduct 4 }

--SA 
iveSA700   OBJECT IDENTIFIER ::= {iveProductSA700 1}
iveSA2000   OBJECT IDENTIFIER ::= {iveProductSA2000 1}
iveSA2500   OBJECT IDENTIFIER ::= {iveProductSA2500 1}
iveSA4000   OBJECT IDENTIFIER ::= {iveProductSA4000 1}
iveSA4500   OBJECT IDENTIFIER ::= {iveProductSA4500 1}
iveSA4000FIPS  OBJECT IDENTIFIER ::= {iveProductSA4000 2}
iveSA4500FIPS   OBJECT IDENTIFIER ::= {iveProductSA4500 2}
iveSA6000   OBJECT IDENTIFIER ::= {iveProductSA6000 1}
iveSA6500   OBJECT IDENTIFIER ::= {iveProductSA6500 1}
iveSA6000FIPS  OBJECT IDENTIFIER ::= {iveProductSA6000 2}
iveSA6500FIPS   OBJECT IDENTIFIER ::= {iveProductSA6500 2}

--IC
iveIC4000   OBJECT IDENTIFIER ::= {iveProductIC4000 1}
iveIC6000   OBJECT IDENTIFIER ::= {iveProductIC6000 1}
iveIC4500   OBJECT IDENTIFIER ::= {iveProductIC4500 1}
iveIC6500   OBJECT IDENTIFIER ::= {iveProductIC6500 1}
iveIC6000FIPS  OBJECT IDENTIFIER ::=  {iveProductIC6000 2}

--MAG platform incase we have other rev
iveMAG2600  OBJECT IDENTIFIER ::= {iveProductMAG2600 1}
iveMAG4610  OBJECT IDENTIFIER ::= {iveProductMAG4610 1}
iveMAGSM160   OBJECT IDENTIFIER ::= {iveProductSM160 1}
iveMAGSM360   OBJECT IDENTIFIER ::= {iveProductSM360 1}

END
