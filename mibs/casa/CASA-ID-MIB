CASA-ID-MIB DEFINITIONS ::= BEGIN

  IMPORTS
        casa
                FROM CASA-MIB

        MODULE-IDENTITY
                FROM SNMPv2-SMI;

casaIdMib MODULE-IDENTITY
        LAST-UPDATED    "200608150000Z" -- Aug. 15, 2006
        ORGANIZATION    "CASA SYSTEMS INC"
        CONTACT-INFO
                    "PENG LUO
                     CASA SYSTEMS INC.
                     10 NEW ENGLAND BUSINESS CENTER DRIVE, SUITE 110 
                     ANDOVER, MA 
                     U.S.A.      
             Phone:  +1 978 409 6281 - EXT 15 
             E-mail: pluo@casa-systems.com"
        DESCRIPTION
            "CASA SYSTEMS' enterprise MIB Module"

        REVISION "0004070000Z"
        DESCRIPTION
            "Initial Version"
        ::= { casa 2  }


casa2100System  OBJECT IDENTIFIER ::= { casaIdMib 1   } 
casa2200System  OBJECT IDENTIFIER ::= { casaIdMib 20  } 
casa2300System  OBJECT IDENTIFIER ::= { casaIdMib 30  } 
casa2800System  OBJECT IDENTIFIER ::= { casaIdMib 40  } 
casa3000System  OBJECT IDENTIFIER ::= { casaIdMib 50  } 
casa6000System  OBJECT IDENTIFIER ::= { casaIdMib 100 }
casa10000System  OBJECT IDENTIFIER ::= { casaIdMib 200 } 
 
END
