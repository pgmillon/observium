CASA-ENTITY-EXT-MIB DEFINITIONS ::= BEGIN
 
		IMPORTS
			casa			
				FROM CASA-MIB			
			entPhysicalEntry			
				FROM ENTITY-MIB			
			OBJECT-GROUP, MODULE-COMPLIANCE			
				FROM SNMPv2-CONF			
			Unsigned32, OBJECT-TYPE, MODULE-IDENTITY			
				FROM SNMPv2-SMI;
	
	
		-- 1.3.6.1.4.1.20858.10.13
		casaModuleCpuMemMib MODULE-IDENTITY 
			LAST-UPDATED "200809040922Z"		-- September 04, 2008 at 09:22 GMT
			ORGANIZATION 
				"Casa Systems Inc"
			CONTACT-INFO 
				"Guangzhou Casa Communications Ltd.     
				No.206 YueHe Bld,Huacui Str.             
				Tianhe Industrial Park Guangzhou       
				TEL:020 85545002/85577786 ext.212      
				FAX:020 85545002 ext.230		
				E-mail: huangxiaole@casachina.com.cn"
			DESCRIPTION 
				"This is the enterprise MIB Module for CASA systems IPQAM. "
			::= { casaMgmt 13 }

		
	
	
--
-- Node definitions
--
	
		-- 1.3.6.1.4.1.20858.10
		casaMgmt OBJECT IDENTIFIER ::= { casa 10 }

		
		-- 1.3.6.1.4.1.20858.10.13.1
		casaModuleCpuMemObjects OBJECT IDENTIFIER ::= { casaModuleCpuMemMib 1 }

		
		-- 1.3.6.1.4.1.20858.10.13.1.1
		casaModuleCpuMemTable OBJECT-TYPE
			SYNTAX SEQUENCE OF CasaModuleCpuMemEntry
			MAX-ACCESS not-accessible
			STATUS current
			DESCRIPTION
				"Description."
			::= { casaModuleCpuMemObjects 1 }

		
		-- 1.3.6.1.4.1.20858.10.13.1.1.1
		casaModuleCpuMemEntry OBJECT-TYPE
			SYNTAX CasaModuleCpuMemEntry
			MAX-ACCESS not-accessible
			STATUS current
			DESCRIPTION
				"Description."
      AUGMENTS    { entPhysicalEntry }
			::= { casaModuleCpuMemTable 1 }

		
		CasaModuleCpuMemEntry ::=
			SEQUENCE { 
				casaModuleTotalAllocatableMem
					Unsigned32,
				casaModuleTotalMemAllocated
					Unsigned32,
				casaModuleTotalFreeMem
					Unsigned32,
				casaModuleTotalCpuUtilization
					Unsigned32
			 }

		-- 1.3.6.1.4.1.20858.10.13.1.1.1.1
		casaModuleTotalAllocatableMem OBJECT-TYPE
			SYNTAX Unsigned32
			UNITS "KBytes"
			MAX-ACCESS read-only
			STATUS current
			DESCRIPTION
				"TotalAllocatableMem Byte"
			::= { casaModuleCpuMemEntry 1 }

		
		-- 1.3.6.1.4.1.20858.10.13.1.1.1.2
		casaModuleTotalMemAllocated OBJECT-TYPE
			SYNTAX Unsigned32
			UNITS "KBytes"
			MAX-ACCESS read-only
			STATUS current
			DESCRIPTION
				"TotalMemAllocated Byte"
			::= { casaModuleCpuMemEntry 2 }

		
		-- 1.3.6.1.4.1.20858.10.13.1.1.1.3
		casaModuleTotalFreeMem OBJECT-TYPE
			SYNTAX Unsigned32
			UNITS "KBytes"
			MAX-ACCESS read-only
			STATUS current
			DESCRIPTION
				"TotalFreeMem Byte"
			::= { casaModuleCpuMemEntry 3 }

		
		-- 1.3.6.1.4.1.20858.10.13.1.1.1.4
		casaModuleTotalCpuUtilization OBJECT-TYPE
			SYNTAX Unsigned32
			UNITS "%"
			MAX-ACCESS read-only
			STATUS current
			DESCRIPTION
				"TotalCPUUtilization "
			::= { casaModuleCpuMemEntry 4 }

		
		-- 1.3.6.1.4.1.20858.10.13.2
		casaCmtsCpuMemGroups OBJECT IDENTIFIER ::= { casaModuleCpuMemMib 2 }

		
		-- 1.3.6.1.4.1.20858.10.13.2.1
		casaCmtsCpuMemGroup OBJECT-GROUP
			OBJECTS { casaModuleTotalAllocatableMem, casaModuleTotalMemAllocated, casaModuleTotalFreeMem, casaModuleTotalCpuUtilization }
			STATUS current
			DESCRIPTION 
				"Description."
			::= { casaCmtsCpuMemGroups 1 }

		
		-- 1.3.6.1.4.1.20858.10.13.3
		casaCmtsCpuMemCompliances OBJECT IDENTIFIER ::= { casaModuleCpuMemMib 3 }

		
		-- 1.3.6.1.4.1.20858.10.13.3.1
		casaCmtsCpuMemCompliance MODULE-COMPLIANCE
			STATUS current
			DESCRIPTION 
				"Description."
			MODULE CASA-CABLE-CPUMEMINFO-MIB
				MANDATORY-GROUPS { casaCmtsCpuMemGroup }
			::= { casaCmtsCpuMemCompliances 1 }

		
	
	END

--
-- CASA-ENTITY-EXT-MIB.my
--
