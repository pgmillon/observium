-- *****************************************************************************
-- PACKETFRONT-TC.mib  Packetfront MIB Textual Conventions
--   
-- Copyright (c) 2007,2009 Packetfront Systems AB
-- All rights reserved.
--   
-- *****************************************************************************

PACKETFRONT-TC DEFINITIONS ::= BEGIN

IMPORTS
  MODULE-IDENTITY
    FROM SNMPv2-SMI

  TEXTUAL-CONVENTION
    FROM SNMPv2-TC

  pfModules
    FROM PACKETFRONT-SMI;


pfTextualConventions MODULE-IDENTITY
    LAST-UPDATED    "200903231040Z"
    ORGANIZATION    "PacketFront Systems AB"
    CONTACT-INFO
        "PacketFront Systems AB
         Customer Service

         Mail : Isafjordsgatan 35
                SE-164 28 Kista
                Sweden

         Tel  : +46 8 5090 1500

         E-mail: snmp@packetfront.com
         Web   : http://www.packetfront.com"
    DESCRIPTION
        "This module defines textual conventions used throughout
        Packetfront enterprise mibs."

    REVISION    "200903231040Z"
    DESCRIPTION
        "Update telephone number in contact-info, reorder revision information"
    REVISION    "200805010839Z"
    DESCRIPTION
        "Added Unsigned64 object type"
    REVISION    "200705180000Z"
    DESCRIPTION
        "Added PortList object type"
          ::= { pfModules 1 }


PortList ::= TEXTUAL-CONVENTION
  STATUS      current
  DESCRIPTION
  "Each octet within this value specifies a set of eight
  ports, with the first octet specifying ports 1 through
  8, the second octet specifying ports 9 through 16, etc.
  Within each octet, the most significant bit represents
  the lowest numbered port, and the least significant bit
  represents the highest numbered port.  Thus, each port
  of the bridge is represented by a single bit within the
  value of this object.  If that bit has a value of '1'
  then that port is included in the set of ports; the port
  is not included if its bit has a value of '0'."
  SYNTAX  OCTET STRING


END
