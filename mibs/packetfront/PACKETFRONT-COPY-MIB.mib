PACKETFRONT-COPY-MIB DEFINITIONS ::= BEGIN
--
-- This is the Packetfront MIB definition for the iBOS file copy function
--
-- Copyright (c) 2002 PacketFront Sweden AB
-- Copyright (c) 2007-2010 PacketFront Systems AB
-- Copyright (c) 2011 PacketFront International AB

IMPORTS
    MODULE-IDENTITY,
    OBJECT-TYPE,
        Unsigned32
	FROM SNMPv2-SMI
	
	DisplayString
	FROM SNMPv2-TC
	
        pfExperiment
        FROM PACKETFRONT-SMI;


pfCopy  MODULE-IDENTITY
    LAST-UPDATED "201101111735Z"
    ORGANIZATION "PacketFront International AB"
    CONTACT-INFO
        "PacketFront International AB
         Customer Service

         Mail : Isafjordsgatan 35
                SE-164 28 Kista
                Sweden

         Tel  : +46 8 5090 1500

         E-mail: snmp@packetfront.com
         Web   : http://www.packetfront.com"
    DESCRIPTION
        "MIB describing the file copy functions available on Packetfront ASRs"

    REVISION "201101111735Z"	-- January 11th, 2011
    DESCRIPTION
        "Updated company name"
    REVISION "200903231117Z"
    DESCRIPTION
        "Updated telephone information in contact-info"
    REVISION "200809101538Z"
    DESCRIPTION
        "Initial - moved pfCopy from PACKETFRONT-MIB"

        ::= { pfExperiment 2 }


-- Get filehandle
pfCopyNextState	OBJECT-TYPE
                SYNTAX Unsigned32
                MAX-ACCESS read-only
                STATUS current
                DESCRIPTION
                        "Generate a unique filehandle. The filehandle is
                         used with the other objects in the pfCopy branch
                         to set the source and destination and commence
                         file transfer activities."
                ::= { pfCopy 1 }

-- the pf Copy table
-- Table with states of current copy sessions.
pfCopyTable 	OBJECT-TYPE
		SYNTAX SEQUENCE OF PfCopyEntry
		MAX-ACCESS not-accessible
		STATUS current
		DESCRIPTION
			"A list of current copy sessions. The next available entry is
			 given by the value of pfCopyNextState."
		::= { pfCopy 2 }

pfCopyEntry	OBJECT-TYPE
		SYNTAX PfCopyEntry 
		MAX-ACCESS not-accessible
		STATUS current
		DESCRIPTION
			"An entry for a copy session."
		INDEX { pfCopyIndex }
		::= { pfCopyTable 1 }

PfCopyEntry ::=
	SEQUENCE {
		pfCopyIndex		Unsigned32,
		pfCopySource		DisplayString,
		pfCopyDestination	DisplayString,
		pfCopyStatus		INTEGER,
		pfCopyError		DisplayString
	}


pfCopyIndex	OBJECT-TYPE
		SYNTAX Unsigned32
		MAX-ACCESS read-only
		STATUS current
		DESCRIPTION
			"A unique value for each copy session."
		::= { pfCopyEntry 1 }

-- Set copy source
pfCopySource 	OBJECT-TYPE
                SYNTAX DisplayString (SIZE (0..255))
                MAX-ACCESS read-write
                STATUS current
                DESCRIPTION
                        "The source URL for a filhandle. The string 
                         provided must match an acceptable URL as 
                         typed in the command line interface copy command."
                ::= { pfCopyEntry 2 }

-- Set copy destination
pfCopyDestination	OBJECT-TYPE
                        SYNTAX DisplayString (SIZE (0..255))
                        MAX-ACCESS read-write
                        STATUS current
                        DESCRIPTION
                                "The destination filename for a filehandle. The
                                 string provided must match an acceptable destination
                                 as typed in the command line interface copy command."
                        ::= { pfCopyEntry 3 }

-- Set/Get copy status
pfCopyStatus   	OBJECT-TYPE
                SYNTAX INTEGER {
                       notused(0),
                       start(1),
                       stop(2),
                       destroy(3),
                       init(4),
                       inprogress(5),
                       failed(6),
                       finished(7)
                }
                MAX-ACCESS read-write
                STATUS current
                DESCRIPTION
                        "The status of a filehandle

                         notused - Get: The filehandle has not been used during the last 24 hours
                                   Set: Not possible
                         start - Get: Not possible
                                 Set: Start filetransfer
                         stop - Get: Not possible
                                Set: Stop filetransfer in progress
                         destroy - Get: Not possible
                                   Set: Remove source and destination entries for filehandle
                         init - Get: Filtransfer started
                                Set: Not possible
                         inprogress - Get: Filetransfer in progress
                                      Set: Not possible
                         failed - Get: A failure occured during last filetransfer
                                  Set: Not possible
                         finished - Get: The file was successfully transferred and stored 
                                    Set: not possible
                        "
                ::= { pfCopyEntry 4 }

pfCopyError	OBJECT-TYPE
                SYNTAX DisplayString (SIZE (0..255))
                MAX-ACCESS read-only
                STATUS current
                DESCRIPTION
                        "A textual description of the filehandle last
                         error status. If the filehandle does not exist or
                         has not been used for the last 24 hours, a 'No Error'
                         message is returned."
                ::= { pfCopyEntry 5 }


END
