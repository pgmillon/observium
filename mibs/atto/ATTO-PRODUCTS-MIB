------------------------------------------------------------------------------
--
--   ATTO-PRODUCTS-MIB:  ATTO Technology Product Object Identifier Assignments
--
--   THIS PROGRAM AND THE INFORMATION CONTAINED HEREIN IS THE PROPERTY OF
--   ATTO TECHNOLOGY, INC. AND SHALL NOT BE REPRODUCED, COPIED, OR USED IN
--   WHOLE OR IN PART OTHER THAN AS PROVIDED FOR IN THE LICENSE AGREEMENT
--   PURSUANT TO WHICH IT WAS FURNISHED.
--
--   COPYRIGHT (c) ATTO TECHNOLOGY, INC. 2013
--   ALL RIGHTS RESERVED.
--
------------------------------------------------------------------------------

-------------------------------------------------------------------------------
-- Standard version
-------------------------------------------------------------------------------
ATTO-PRODUCTS-MIB DEFINITIONS ::= BEGIN
    IMPORTS
        enterprises, MODULE-IDENTITY
            FROM SNMPv2-SMI;

--
-- According to ftp://ftp.isi.edu/in-notes/iana/assignments/enterprise-numbers,
-- ATTO's enterprise number is registered as being 4597.
--
attoProductsMIB MODULE-IDENTITY
    LAST-UPDATED "201304191345Z"             -- 19 Apr 2013  09:45 AM
    ORGANIZATION "ATTO Technology, Inc."
    CONTACT-INFO
           "ATTO Technology
            155 Crosspoint Parkway
            Amherst NY 14068
            EMail: <support@attotech.com>"
    DESCRIPTION
           "This modules defines object identifiers assigned to various
            hardware platforms, which are returned as values for sysObjectID."

    REVISION "201304191345Z"                 -- 19 Apr 2013  09:45 AM
    DESCRIPTION
           "Initial version of this module."
    ::= { attoModules 2 }

attotech                OBJECT IDENTIFIER ::= { enterprises 4547 }
attoProducts            OBJECT IDENTIFIER ::= { attotech 1 }
attoMgmt                OBJECT IDENTIFIER ::= { attotech 2 }
attoModules             OBJECT IDENTIFIER ::= { attotech 3 }
attoAgentCapability     OBJECT IDENTIFIER ::= { attotech 4 }


-- Older bridges do not have a specific sysObjectID assigned, and will instead
-- report this ID, 1.3.6.1.4.1.4547.1.1
attoGenericDevice   OBJECT IDENTIFIER ::= { attoProducts 1 }

-- Note: attoProducts.2 is used by the bridge MIB

-- All capable HBAs in a system are managed via the single ConfigTool service
-- on the system, without regard to the type of HBA.
attoHba             OBJECT IDENTIFIER ::= { attoProducts 3 }

attoFB6500          OBJECT IDENTIFIER ::= { attoProducts 4 }
attoFB6500N         OBJECT IDENTIFIER ::= { attoProducts 5 }


END
