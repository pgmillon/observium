--
-- Copyright (c) 2010 by Ruckus Wireless, Inc.
-- All Rights Reserved
--

RUCKUS-VF2825-MIB DEFINITIONS ::= BEGIN

IMPORTS
    ruckusVF2825
        FROM RUCKUS-PRODUCTS-MIB
    ifIndex
        FROM IF-MIB
    DisplayString
        FROM SNMPv2-TC
    MODULE-IDENTITY,
    OBJECT-TYPE
        FROM SNMPv2-SMI
    OBJECT-GROUP
        FROM SNMPv2-CONF;

ruckusVF2825MIB MODULE-IDENTITY
    LAST-UPDATED "201010150800Z"
    ORGANIZATION "Ruckus Wireless, Inc."
    CONTACT-INFO
        "Ruckus Wireless, Inc.

        Postal:
        350 West Java Dr.
        Sunnyvale, CA 94089
        USA

        EMail: support@ruckuswireless.com

        Phone: +1-650-265-4200"
    DESCRIPTION
        "Ruckus VF2825 product specific mib."
    ::= { ruckusVF2825 1 }


-- Scalars and Tables
--

ruckusVF2825Objects OBJECT IDENTIFIER   ::= { ruckusVF2825MIB 1 }

ruckusVF2825Info OBJECT IDENTIFIER  ::= { ruckusVF2825Objects 1 }

ruckusVF2825NetworkTable OBJECT-TYPE
    SYNTAX  SEQUENCE OF RuckusVF2825NetworkEntry
    MAX-ACCESS not-accessible
    STATUS current
    DESCRIPTION
        "Specifies ruckusVF2825Network table."
    ::= { ruckusVF2825Info 1 }


ruckusVF2825NetworkEntry OBJECT-TYPE
    SYNTAX  RuckusVF2825NetworkEntry
    MAX-ACCESS not-accessible
    STATUS current
    DESCRIPTION
        "Specifies each network entry."
    INDEX {
        ruckusVF2825NetworkName,
        ifIndex }
    ::= { ruckusVF2825NetworkTable 1 }


RuckusVF2825NetworkEntry ::= SEQUENCE {

    ruckusVF2825NetworkName   DisplayString,
    ruckusVF2825NetworkIfName DisplayString }


ruckusVF2825NetworkName OBJECT-TYPE
    SYNTAX  DisplayString (SIZE (1..16))
    MAX-ACCESS not-accessible
    STATUS current
    DESCRIPTION
        "Specifies the network name.
        Valid network names are:
        wan, lan, or videoWan, ..."
    ::= { ruckusVF2825NetworkEntry 1 }


ruckusVF2825NetworkIfName OBJECT-TYPE
    SYNTAX  DisplayString (SIZE (1..16))
    MAX-ACCESS read-only
    STATUS current
    DESCRIPTION
        "Specifies the interface name."
    ::= { ruckusVF2825NetworkEntry 2 }


-- Notification Types
--

ruckusVF2825Events OBJECT IDENTIFIER    ::= { ruckusVF2825MIB 2 }

-- Conformance
--

ruckusVF2825Conf OBJECT IDENTIFIER  ::= { ruckusVF2825MIB 3 }

-- Groups
--

ruckusVF2825Groups OBJECT IDENTIFIER    ::= { ruckusVF2825Conf 1 }

-- Compliance
--

END
