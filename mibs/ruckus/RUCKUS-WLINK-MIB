--
-- Copyright (c) 2010 by Ruckus Wireless, Inc.
-- All Rights Reserved
--

RUCKUS-WLINK-MIB DEFINITIONS ::= BEGIN

IMPORTS
    ruckusCommonWLINKModule
        FROM RUCKUS-ROOT-MIB
    RuckusSSID
        FROM RUCKUS-TC-MIB
    DisplayString,
    MacAddress
        FROM SNMPv2-TC
    ifIndex,
    InterfaceIndex
        FROM IF-MIB
    MODULE-IDENTITY,
    OBJECT-TYPE,
    Counter32,
    Integer32,
    Unsigned32
        FROM SNMPv2-SMI;

ruckusWLINKMIB MODULE-IDENTITY
    LAST-UPDATED "201010150800Z"
    ORGANIZATION "Ruckus Wireless, Inc."
    CONTACT-INFO
        "Ruckus Wireless, Inc.

        Postal:
        350 West Java Dr.
        Sunnyvale, CA 94089
        USA

        EMail: support@ruckuswireless.com

        Phone: +1-650-265-4200"
    DESCRIPTION
        "Ruckus Wireless Link mib"
    ::= { ruckusCommonWLINKModule 1 }


-- Groups
--

ruckusWLINKObjects OBJECT IDENTIFIER ::= { ruckusWLINKMIB 1 }

ruckusWLINKInfo OBJECT IDENTIFIER    ::= { ruckusWLINKObjects 1 }

ruckusWLINKEvents OBJECT IDENTIFIER  ::= { ruckusWLINKMIB 2 }


-- This is the Wireless Link table.
--

ruckusWLINKTable OBJECT-TYPE
    SYNTAX  SEQUENCE OF RuckusWLINKEntry
    MAX-ACCESS not-accessible
    STATUS current
    DESCRIPTION
        "WLINK table."
    ::= { ruckusWLINKInfo 1 }


ruckusWLINKEntry OBJECT-TYPE
    SYNTAX  RuckusWLINKEntry
    MAX-ACCESS not-accessible
    STATUS current
    DESCRIPTION
        "Specifies each WLINK entry."
    INDEX {
        ruckusWLINKIndex }
    ::= { ruckusWLINKTable 1 }


RuckusWLINKEntry ::= SEQUENCE {

	ruckusWLINKIndex			 	 InterfaceIndex,
    ruckusWLINKSSID                  RuckusSSID,
    ruckusWLINKRole                  INTEGER,
    ruckusWLINKLocalMAC              MacAddress,
    ruckusWLINKRemoteMAC             MacAddress,
    ruckusWLINKTxPkts                Counter32,
    ruckusWLINKTxBytes               Counter32,
    ruckusWLINKRxPkts                Counter32,
    ruckusWLINKRxBytes               Counter32,
    ruckusWLINKEstablishTime         DisplayString,
    ruckusWLINKUpTime                Unsigned32,
    ruckusWLINKRssi                  Integer32,
    ruckusWLINKUpCount               Integer32,
    ruckusWLINKDownCount             Integer32 }

ruckusWLINKIndex OBJECT-TYPE
    SYNTAX  InterfaceIndex
    MAX-ACCESS read-only
    STATUS current
    DESCRIPTION
        "The index."
    ::= { ruckusWLINKEntry 200 }

ruckusWLINKSSID OBJECT-TYPE
    SYNTAX  RuckusSSID
    MAX-ACCESS read-only
    STATUS current
    DESCRIPTION
        "Specifies the name of the SSID."
    ::= { ruckusWLINKEntry 1 }

ruckusWLINKRole OBJECT-TYPE
    SYNTAX  INTEGER {
            rootBridge(1),
            nonRootBridge(2),
            notDecided(3),
            notAvailable(4) }
    MAX-ACCESS read-only
    STATUS current
    DESCRIPTION
        "Specifies the name of the SSID."
    ::= { ruckusWLINKEntry 2 }

ruckusWLINKLocalMAC OBJECT-TYPE
    SYNTAX  MacAddress
    MAX-ACCESS read-only
    STATUS current
    DESCRIPTION
        "It is the 48-bit MAC address of the wireless interface of local side."
    ::= { ruckusWLINKEntry 3 }


ruckusWLINKRemoteMAC OBJECT-TYPE
    SYNTAX  MacAddress
    MAX-ACCESS read-only
    STATUS current
    DESCRIPTION
        "It is the 48-bit MAC address of the wireless interface of remote side."
    ::= { ruckusWLINKEntry 4 }


ruckusWLINKTxPkts OBJECT-TYPE
    SYNTAX  Counter32
    MAX-ACCESS read-only
    STATUS current
    DESCRIPTION
        "Number of tx packets."
    ::= { ruckusWLINKEntry 5 }


ruckusWLINKTxBytes OBJECT-TYPE
    SYNTAX  Counter32
    MAX-ACCESS read-only
    STATUS current
    DESCRIPTION
        "Number of tx bytes."
    ::= { ruckusWLINKEntry 6 }


ruckusWLINKRxPkts OBJECT-TYPE
    SYNTAX  Counter32
    MAX-ACCESS read-only
    STATUS current
    DESCRIPTION
        "Number of rx packets."
    ::= { ruckusWLINKEntry 7 }


ruckusWLINKRxBytes OBJECT-TYPE
    SYNTAX  Counter32
    MAX-ACCESS read-only
    STATUS current
    DESCRIPTION
        "Number of rx bytes."
    ::= { ruckusWLINKEntry 8 }


ruckusWLINKEstablishTime OBJECT-TYPE
    SYNTAX  DisplayString (SIZE (1..64))
    MAX-ACCESS read-only
    STATUS current
    DESCRIPTION
        "The establish time of the link (UTC)."
    ::= { ruckusWLINKEntry 9 }


ruckusWLINKUpTime OBJECT-TYPE
    SYNTAX  Unsigned32
    MAX-ACCESS read-only
    STATUS current
    DESCRIPTION
        "The up time of the link in seconds."
    ::= { ruckusWLINKEntry 10 }


ruckusWLINKRssi OBJECT-TYPE
    SYNTAX  Integer32
    MAX-ACCESS read-only
    STATUS current
    DESCRIPTION
        "Link RSSI."
    ::= { ruckusWLINKEntry 11 }


ruckusWLINKUpCount OBJECT-TYPE
    SYNTAX  Integer32
    MAX-ACCESS read-only
    STATUS current
    DESCRIPTION
        "The link up count during its uptime."
    ::= { ruckusWLINKEntry 12 }


ruckusWLINKDownCount OBJECT-TYPE
    SYNTAX  Integer32
    MAX-ACCESS read-only
    STATUS current
    DESCRIPTION
        "The link down count during its uptime."
    ::= { ruckusWLINKEntry 13 }

ruckusWLINKIITable OBJECT-TYPE
    SYNTAX  SEQUENCE OF RuckusWLINKIIEntry
    MAX-ACCESS not-accessible
    STATUS current
    DESCRIPTION
        "WLINKII table."
    ::= { ruckusWLINKInfo 2 }

ruckusWLINKIIEntry OBJECT-TYPE
    SYNTAX  RuckusWLINKIIEntry
    MAX-ACCESS not-accessible
    STATUS current
    DESCRIPTION
        "Specifies each WLINKII entry."
    INDEX {
        ifIndex,
        ruckusWLINKIIStaIndex }
    ::= { ruckusWLINKIITable 1 }

RuckusWLINKIIEntry ::= SEQUENCE {
	ruckusWLINKIIStaIndex               INTEGER,
    ruckusWLINKIISSID					RuckusSSID,
    ruckusWLINKIIRole					INTEGER,
    ruckusWLINKIILocalMAC				MacAddress,
    ruckusWLINKIIRemoteMAC				MacAddress,
    ruckusWLINKIITxPkts                	Counter32,
    ruckusWLINKIITxBytes				Counter32,
    ruckusWLINKIIRxPkts					Counter32,
    ruckusWLINKIIRxBytes				Counter32,
    ruckusWLINKIIEstablishTime			DisplayString,
    ruckusWLINKIIUpTime					Unsigned32,
    ruckusWLINKIIRssi					Integer32,
    ruckusWLINKIIUpCount				Integer32,
    ruckusWLINKIIDownCount				Integer32 }

ruckusWLINKIIStaIndex OBJECT-TYPE
    SYNTAX  INTEGER 
    MAX-ACCESS read-only
    STATUS current
    DESCRIPTION
        "Station index."
    ::= { ruckusWLINKIIEntry 1 }

ruckusWLINKIISSID OBJECT-TYPE
    SYNTAX  RuckusSSID
    MAX-ACCESS read-only
    STATUS current
    DESCRIPTION
        "Specifies the name of the SSID."
    ::= { ruckusWLINKIIEntry 2 }

ruckusWLINKIIRole OBJECT-TYPE
    SYNTAX  INTEGER {
            rootBridge(1),
            nonRootBridge(2),
            notDecided(3),
            notAvailable(4) }
    MAX-ACCESS read-only
    STATUS current
    DESCRIPTION
        "Specifies the name of the SSID."
    ::= { ruckusWLINKIIEntry 3 }

ruckusWLINKIILocalMAC OBJECT-TYPE
    SYNTAX  MacAddress
    MAX-ACCESS read-only
    STATUS current
    DESCRIPTION
        "It is the 48-bit MAC address of the wireless interface of local side."
    ::= { ruckusWLINKIIEntry 4 }

ruckusWLINKIIRemoteMAC OBJECT-TYPE
    SYNTAX  MacAddress
    MAX-ACCESS read-only
    STATUS current
    DESCRIPTION
        "It is the 48-bit MAC address of the wireless interface of remote side."
    ::= { ruckusWLINKIIEntry 5 }

ruckusWLINKIITxPkts OBJECT-TYPE
    SYNTAX  Counter32
    MAX-ACCESS read-only
    STATUS current
    DESCRIPTION
        "Number of tx packets."
    ::= { ruckusWLINKIIEntry 6 }

ruckusWLINKIITxBytes OBJECT-TYPE
    SYNTAX  Counter32
    MAX-ACCESS read-only
    STATUS current
    DESCRIPTION
        "Number of tx bytes."
    ::= { ruckusWLINKIIEntry 7 }

ruckusWLINKIIRxPkts OBJECT-TYPE
    SYNTAX  Counter32
    MAX-ACCESS read-only
    STATUS current
    DESCRIPTION
        "Number of rx packets."
    ::= { ruckusWLINKIIEntry 8 }

ruckusWLINKIIRxBytes OBJECT-TYPE
    SYNTAX  Counter32
    MAX-ACCESS read-only
    STATUS current
    DESCRIPTION
        "Number of rx bytes."
    ::= { ruckusWLINKIIEntry 9 }

ruckusWLINKIIEstablishTime OBJECT-TYPE
    SYNTAX  DisplayString (SIZE (1..64))
    MAX-ACCESS read-only
    STATUS current
    DESCRIPTION
        "The establish time of the link (UTC)."
    ::= { ruckusWLINKIIEntry 10 }

ruckusWLINKIIUpTime OBJECT-TYPE
    SYNTAX  Unsigned32
    MAX-ACCESS read-only
    STATUS current
    DESCRIPTION
        "The up time of the link in seconds."
    ::= { ruckusWLINKIIEntry 11 }

ruckusWLINKIIRssi OBJECT-TYPE
    SYNTAX  Integer32
    MAX-ACCESS read-only
    STATUS current
    DESCRIPTION
        "Link RSSI."
    ::= { ruckusWLINKIIEntry 12 }

ruckusWLINKIIUpCount OBJECT-TYPE
    SYNTAX  Integer32
    MAX-ACCESS read-only
    STATUS current
    DESCRIPTION
        "The link up count during its uptime."
    ::= { ruckusWLINKIIEntry 13 }

ruckusWLINKIIDownCount OBJECT-TYPE
    SYNTAX  Integer32
    MAX-ACCESS read-only
    STATUS current
    DESCRIPTION
        "The link down count during its uptime."
    ::= { ruckusWLINKIIEntry 14 }

-- Conformance & Compliance
--

END
