--
-- Copyright 2010-2013 Ruckus Wireless, Inc. All rights reserved.
--

RUCKUS-ROOT-MIB DEFINITIONS ::= BEGIN

IMPORTS
    enterprises,
    MODULE-IDENTITY
        FROM SNMPv2-SMI;

ruckusRootMIB MODULE-IDENTITY
    LAST-UPDATED "201010150800Z"
    ORGANIZATION "Ruckus Wireless, Inc."
    CONTACT-INFO
        "Ruckus Wireless, Inc.

        Postal:
        350 West Java Dr.
        Sunnyvale, CA 94089
        USA

        EMail: support@ruckuswireless.com

        Phone: +1-650-265-4200"
    DESCRIPTION
        "Ruckus top level mib."
    ::= { enterprises 25053 }


-- Groups
--

ruckusObjects OBJECT IDENTIFIER  ::= { ruckusRootMIB 1 }

ruckusCommon OBJECT IDENTIFIER   ::= { ruckusObjects 1 }

ruckusCommonTCModule OBJECT IDENTIFIER      ::= { ruckusCommon 1 }

ruckusCommonHwInfoModule OBJECT IDENTIFIER  ::= { ruckusCommon 2 }

ruckusCommonSwInfoModule OBJECT IDENTIFIER  ::= { ruckusCommon 3 }

ruckusCommonDeviceModule OBJECT IDENTIFIER  ::= { ruckusCommon 4 }

ruckusCommonUpgradeModule OBJECT IDENTIFIER ::= { ruckusCommon 5 }

ruckusCommonWLANModule OBJECT IDENTIFIER    ::= { ruckusCommon 6 }

ruckusCommonDHCPModule OBJECT IDENTIFIER    ::= { ruckusCommon 7 }

ruckusCommonPPPOEModule OBJECT IDENTIFIER   ::= { ruckusCommon 8 }

ruckusCommonAdapterModule OBJECT IDENTIFIER ::= { ruckusCommon 9 }

ruckusCommonQosModule OBJECT IDENTIFIER     ::= { ruckusCommon 10 }

ruckusCommonSystemModule OBJECT IDENTIFIER  ::= { ruckusCommon 11 }

ruckusCommonRadioModule OBJECT IDENTIFIER   ::= { ruckusCommon 12 }

ruckusCommonEthModule OBJECT IDENTIFIER     ::= { ruckusCommon 13 }

ruckusCommonL2TPModule OBJECT IDENTIFIER    ::= { ruckusCommon 14 }

ruckusCommonWLINKModule OBJECT IDENTIFIER   ::= { ruckusCommon 15 }

ruckusZD OBJECT IDENTIFIER   ::= { ruckusObjects 2 }

ruckusZDSystemModule OBJECT IDENTIFIER      ::= { ruckusZD 1 }

ruckusZDWLANModule OBJECT IDENTIFIER        ::= { ruckusZD 2 }

ruckusEvents OBJECT IDENTIFIER    ::= { ruckusRootMIB 2 }

ruckusProducts OBJECT IDENTIFIER  ::= { ruckusRootMIB 3 }

-- Conformance & Complliance
--

ruckusConformance OBJECT IDENTIFIER  ::= { ruckusRootMIB 4 }

ruckusConfGroups OBJECT IDENTIFIER   ::= { ruckusConformance 1 }

ruckusCompliances OBJECT IDENTIFIER  ::= { ruckusConformance 2 }

END
