--
-- Copyright (c) 2010 by Ruckus Wireless, Inc.
-- All Rights Reserved
--

RUCKUS-DHCP-MIB DEFINITIONS ::= BEGIN

IMPORTS
    ruckusCommonDHCPModule
        FROM RUCKUS-ROOT-MIB
    MODULE-IDENTITY,
    OBJECT-TYPE,
    IpAddress,
    Unsigned32
        FROM SNMPv2-SMI
    OBJECT-GROUP,
    MODULE-COMPLIANCE
        FROM SNMPv2-CONF
    MacAddress,
    TruthValue
        FROM SNMPv2-TC;

ruckusDHCPMIB MODULE-IDENTITY
    LAST-UPDATED "201010150800Z"
    ORGANIZATION "Ruckus Wireless, Inc."
    CONTACT-INFO
        "Ruckus Wireless Inc.

        Postal:
        350 West Java Dr.
        Sunnyvale, CA 94089
        USA

        EMail: support@ruckuswireless.com

        Phone: +1-650-265-4200."
    DESCRIPTION
        "Ruckus DHCP mib module."
    ::= { ruckusCommonDHCPModule 1 }


-- Groups
--

ruckusDHCPObjects OBJECT IDENTIFIER     ::= { ruckusDHCPMIB 1 }

ruckusDHCPClientInfo OBJECT IDENTIFIER  ::= { ruckusDHCPObjects 1 }

ruckusDHCPClientExternal OBJECT IDENTIFIER  ::= { ruckusDHCPObjects 2 }

ruckusDHCPClientEvents OBJECT IDENTIFIER    ::= { ruckusDHCPMIB 2 }

-- DHCP CLient Table
--

ruckusDHCPClientTable OBJECT-TYPE
    SYNTAX  SEQUENCE OF RuckusDHCPClientEntry
    MAX-ACCESS not-accessible
    STATUS current
    DESCRIPTION
        "Specifies dhcp client table."
    ::= { ruckusDHCPClientInfo 1 }


ruckusDHCPClientEntry OBJECT-TYPE
    SYNTAX  RuckusDHCPClientEntry
    MAX-ACCESS not-accessible
    STATUS current
    DESCRIPTION
        "Specifies each dhcp client entry."
    INDEX {
        ruckusDHCPClientHWAddress }
    ::= { ruckusDHCPClientTable 1 }


RuckusDHCPClientEntry ::= SEQUENCE {

    ruckusDHCPClientHWAddress  MacAddress,
    ruckusDHCPClientIPAddress  IpAddress,
    ruckusDHCPClientSubnetMask IpAddress,
    ruckusDHCPClientLeaseTime  Unsigned32 }


ruckusDHCPClientHWAddress OBJECT-TYPE
    SYNTAX  MacAddress
    MAX-ACCESS not-accessible
    STATUS current
    DESCRIPTION
        "Macaddress of the client, an index into the table."
    ::= { ruckusDHCPClientEntry 1 }


ruckusDHCPClientIPAddress OBJECT-TYPE
    SYNTAX  IpAddress
    MAX-ACCESS read-only
    STATUS current
    DESCRIPTION
        "Specifies the IP address of the client."
    ::= { ruckusDHCPClientEntry 2 }


ruckusDHCPClientSubnetMask OBJECT-TYPE
    SYNTAX  IpAddress
    MAX-ACCESS read-only
    STATUS current
    DESCRIPTION
        "Specifies the subnet mask of the client."
    ::= { ruckusDHCPClientEntry 3 }


ruckusDHCPClientLeaseTime OBJECT-TYPE
    SYNTAX  Unsigned32
    UNITS
        "seconds"
    MAX-ACCESS read-only
    STATUS current
    DESCRIPTION
        "Specifies the lease time."
    ::= { ruckusDHCPClientEntry 4 }


--
--

ruckusDHCPClientExternalRenew OBJECT-TYPE
    SYNTAX  TruthValue
    MAX-ACCESS read-write
    STATUS current
    DESCRIPTION
        "Specifies if the IP address needs to be
        renewed or not from the service provider."
    DEFVAL { true }
    ::= { ruckusDHCPClientExternal 1 }


-- Conformance & Compliance
--


END
