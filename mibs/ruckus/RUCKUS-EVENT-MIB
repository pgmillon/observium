--
-- Copyright (c) 2010 by Ruckus Wireless, Inc.
-- All Rights Reserved
--

RUCKUS-EVENT-MIB DEFINITIONS ::= BEGIN

IMPORTS
    ruckusEvents
        FROM RUCKUS-ROOT-MIB
    MacAddress,
    DisplayString
        FROM SNMPv2-TC
    OBJECT-GROUP,
    MODULE-COMPLIANCE
        FROM SNMPv2-CONF
    MODULE-IDENTITY,
    OBJECT-TYPE,
    Unsigned32
        FROM SNMPv2-SMI;

ruckusEventMIB MODULE-IDENTITY
    LAST-UPDATED "201010150000Z"
    ORGANIZATION "Ruckus Wireless, Inc."
    CONTACT-INFO
        "Ruckus Wireless Inc.

        Postal:
        350 West Java Dr.
        Sunnyvale, CA 94089
        USA

        EMail: support@ruckuswireless.com

        Phone: +1-650-265-4200"
    DESCRIPTION
        "Ruckus event objects, including trap OID and trap payload."
    ::= {ruckusEvents 1}

-- Groups
--

ruckusEventTraps OBJECT IDENTIFIER      ::= {ruckusEventMIB 1}
ruckusEventObjects OBJECT IDENTIFIER    ::= {ruckusEventMIB 2}

-- Ruckus Traps
--

ruckusEventAssocTrap NOTIFICATION-TYPE
    OBJECTS {ruckusEventClientMacAddr}
    STATUS  current
    DESCRIPTION
        "Trigger when there is an client association event.
         The client's MAC address is enclosed."
    ::= {ruckusEventTraps 1}

ruckusEventDiassocTrap NOTIFICATION-TYPE
    OBJECTS {ruckusEventClientMacAddr}
    STATUS  current
    DESCRIPTION
        "Trigger when there is an client diassociation event.
         The client's MAC address is enclosed."
    ::= {ruckusEventTraps 2}

ruckusEventSetErrorTrap NOTIFICATION-TYPE
    OBJECTS {ruckusEventSetErrorOID}
    STATUS  current
    DESCRIPTION
        "Trigger when there is an snmp-set error event.
         The OID of the snmp-set is enclosed."
    ::= {ruckusEventTraps 3}

ruckusEventConnectTrap NOTIFICATION-TYPE
    OBJECTS {ruckusEventClientMacAddr}
    STATUS  current
    DESCRIPTION
        "Trigger when there is an AP connect event.
         The AP's MAC address is enclosed."
    ::= {ruckusEventTraps 25}

ruckusEventDisconnectTrap NOTIFICATION-TYPE
    OBJECTS {ruckusEventClientMacAddr}
    STATUS  current
    DESCRIPTION
        "Trigger when there is an AP disconnect event.
         The AP's MAC address is enclosed."
    ::= {ruckusEventTraps 26}

ruckusEventAPFactoryTrap NOTIFICATION-TYPE
    OBJECTS {ruckusEventClientMacAddr}
    STATUS  current
    DESCRIPTION
        "Trigger when AP is reset.
         The AP's MAC address is enclosed."
    ::= {ruckusEventTraps 30}

ruckusEventFailApplconfTrap NOTIFICATION-TYPE
    OBJECTS {ruckusEventClientMacAddr}
    STATUS  current
    DESCRIPTION
        "Trigger when AP failed to apply configuration.
         The AP's MAC address is enclosed."
    ::= {ruckusEventTraps 31}

ruckusEventFailDownTrap NOTIFICATION-TYPE
    OBJECTS {ruckusEventClientMacAddr}
    STATUS  current
    DESCRIPTION
        "Trigger when AP failed to download.
         The AP's MAC address is enclosed."
    ::= {ruckusEventTraps 32}

ruckusEventIPChangeTrap NOTIFICATION-TYPE
    OBJECTS {ruckusEventClientMacAddr}
    STATUS  current
    DESCRIPTION
        "Trigger when AP's ip changed.
         The AP's MAC address is enclosed."
    ::= {ruckusEventTraps 33}

ruckusEventAPTunDownTrap NOTIFICATION-TYPE
    OBJECTS {ruckusEventClientMacAddr}
    STATUS  current
    DESCRIPTION
        "Trigger when AP tunnel is down.
         The AP's MAC address is enclosed."
    ::= {ruckusEventTraps 34}

ruckusEventFailUpgradeTrap NOTIFICATION-TYPE
    OBJECTS {ruckusEventClientMacAddr}
    STATUS  current
    DESCRIPTION
        "Trigger when AP failed to upgrade.
         The AP's MAC address is enclosed."
    ::= {ruckusEventTraps 35}

ruckusEventParameterErrTrap NOTIFICATION-TYPE
    OBJECTS {ruckusEventClientMacAddr}
    STATUS  current
    DESCRIPTION
        "Trigger when parameters error in configuration file.
         The AP's MAC address is enclosed."
    ::= {ruckusEventTraps 36}

ruckusEventNoRecongTrap NOTIFICATION-TYPE
    OBJECTS {ruckusEventClientMacAddr}
    STATUS  current
    DESCRIPTION
        "Trigger when command is not recognized.
         The AP's MAC address is enclosed."
    ::= {ruckusEventTraps 37}

ruckusEventFailTakeEffectTrap NOTIFICATION-TYPE
    OBJECTS {ruckusEventClientMacAddr}
    STATUS  current
    DESCRIPTION
        "Trigger when command does not take effect.
         The AP's MAC address is enclosed."
    ::= {ruckusEventTraps 38}

ruckusEventUpgradeSuccTrap NOTIFICATION-TYPE
    OBJECTS {ruckusEventClientMacAddr}
    STATUS  current
    DESCRIPTION
        "Trigger when ap upgrades successfully.
         The AP's MAC address is enclosed."
    ::= {ruckusEventTraps 39}

ruckusEventDownloadSuccTrap NOTIFICATION-TYPE
    OBJECTS {ruckusEventClientMacAddr}
    STATUS  current
    DESCRIPTION
        "Trigger when ap downloads configure file successfully.
         The AP's MAC address is enclosed."
    ::= {ruckusEventTraps 40}

ruckusEventCongFileTakeEffectTrap NOTIFICATION-TYPE
    OBJECTS {ruckusEventClientMacAddr}
    STATUS  current
    DESCRIPTION
        "Trigger when configure file applies successfully.
         The AP's MAC address is enclosed."
    ::= {ruckusEventTraps 41}

ruckusEventTunnelUpTrap NOTIFICATION-TYPE
    OBJECTS {ruckusEventClientMacAddr}
    STATUS  current
    DESCRIPTION
        "Trigger when gre-tunnel is ready.
         The AP's MAC address is enclosed."
    ::= {ruckusEventTraps 42}

--  Trap payload
--

ruckusEventClientMacAddr OBJECT-TYPE
    SYNTAX      OCTET STRING
    MAX-ACCESS  accessible-for-notify
    STATUS      current
    DESCRIPTION
        "The client's MAC address."
    ::= {ruckusEventObjects 15}

ruckusEventSetErrorOID OBJECT-TYPE
    SYNTAX      OBJECT IDENTIFIER
    MAX-ACCESS  accessible-for-notify
    STATUS      current
    DESCRIPTION
        "OID of the error snmp-set."
    ::= {ruckusEventObjects 20}

ruckusEventAPSerialNumber OBJECT-TYPE
    SYNTAX      OCTET STRING
    MAX-ACCESS  accessible-for-notify
    STATUS      current
    DESCRIPTION
        "AP's serial number."
    ::= {ruckusEventObjects 30}

ruckusEventAPMacAddr OBJECT-TYPE
    SYNTAX      OCTET STRING
    MAX-ACCESS  accessible-for-notify
    STATUS      current
    DESCRIPTION
        "The AP's MAC address."
    ::= {ruckusEventObjects 31}

ruckusEventContent OBJECT-TYPE
    SYNTAX      OCTET STRING
    MAX-ACCESS  accessible-for-notify
    STATUS      current
    DESCRIPTION
        "trap contents."
    ::= {ruckusEventObjects 32}

-- Conformance & Compliance
--

END
