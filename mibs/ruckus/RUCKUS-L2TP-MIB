--
-- Copyright (c) 2010 by Ruckus Wireless, Inc.
-- All Rights Reserved
--

RUCKUS-L2TP-MIB DEFINITIONS ::= BEGIN

IMPORTS
    ruckusCommonL2TPModule
        FROM RUCKUS-ROOT-MIB
    MODULE-IDENTITY,
    OBJECT-TYPE
        FROM SNMPv2-SMI
    OBJECT-GROUP,
    MODULE-COMPLIANCE
        FROM SNMPv2-CONF
    TruthValue,
    DisplayString
        FROM SNMPv2-TC
    InterfaceIndex
        FROM IF-MIB;

ruckusL2TPMIB MODULE-IDENTITY
    LAST-UPDATED "201010150800Z"
    ORGANIZATION "Ruckus Wireless, Inc"
    CONTACT-INFO
        "Ruckus Wireless Inc.

        Postal:
        350 West Java Dr.
        Sunnyvale, CA 94089
        USA

        EMail: support@ruckuswireless.com

        Phone: +1-650-265-4200."
    DESCRIPTION
        "Ruckus L2TP mib objects."
    ::= { ruckusCommonL2TPModule 1 }


-- Groups
--

ruckusL2TPObjects OBJECT IDENTIFIER    ::= { ruckusL2TPMIB 1 }

ruckusL2TPInfo OBJECT IDENTIFIER   ::= { ruckusL2TPObjects 1 }

ruckusL2TPEvents OBJECT IDENTIFIER     ::= { ruckusL2TPMIB 2 }

-- L2TP Information
--

ruckusL2TPServiceStatus OBJECT-TYPE
    SYNTAX  INTEGER {
            enabled(1),
            disabled(2) }
    MAX-ACCESS read-only
    STATUS current
    DESCRIPTION
        "Enable/disable L2TP service."
    DEFVAL { true }
    ::= { ruckusL2TPInfo 1 }


ruckusL2TPConnectionStatus OBJECT-TYPE
    SYNTAX  INTEGER {
            connected(1),
            disconnected(2), 
            disabled(3) }
    MAX-ACCESS read-only
    STATUS current
    DESCRIPTION
        "Specifies L2TP connection status.  Return up(1) if connection is 
        up, down(2) if connection is down, disabled(3) if L2TP is disabled."
    ::= { ruckusL2TPInfo 2 }


ruckusL2TPServerIP OBJECT-TYPE
    SYNTAX  IpAddress
    MAX-ACCESS read-only
    STATUS current
    DESCRIPTION
        "IP of L2TP server."
    ::= { ruckusL2TPInfo 3 }


ruckusL2TPSharedSecret  OBJECT-TYPE
    SYNTAX  DisplayString 
    MAX-ACCESS read-only
    STATUS current
    DESCRIPTION
        "Specifies L2TP Server Shared Secert."
    ::= { ruckusL2TPInfo 4 }


ruckusL2TPUserName OBJECT-TYPE
    SYNTAX  DisplayString 
    MAX-ACCESS read-only
    STATUS current
    DESCRIPTION
        "Specifies L2TP user name.  NOSUCHNAME error returned if L2TP
        is diabled"
    ::= { ruckusL2TPInfo 5 }


ruckusL2TPPassword OBJECT-TYPE
    SYNTAX  DisplayString 
    MAX-ACCESS read-only
    STATUS current
    DESCRIPTION
        "Specifies L2TP password.  NOSUCHNAME error returned if L2TP is diabled"
    ::= { ruckusL2TPInfo 6 }


ruckusL2TPIfIPAddr OBJECT-TYPE
    SYNTAX  IpAddress
    MAX-ACCESS read-only
    STATUS current
    DESCRIPTION
        "IP of L2TP management interface."
    ::= { ruckusL2TPInfo 7 }


ruckusL2TPIfNetMask OBJECT-TYPE
    SYNTAX  IpAddress
    MAX-ACCESS read-only
    STATUS current
    DESCRIPTION
        "Netmask of L2TP management interface."
    ::= { ruckusL2TPInfo 8 }


ruckusL2TPIfGateway OBJECT-TYPE
    SYNTAX  IpAddress
    MAX-ACCESS read-only
    STATUS current
    DESCRIPTION
        "Default route of L2TP management interface."
    ::= { ruckusL2TPInfo 9 }


-- Conformance & Compliance
--

END
