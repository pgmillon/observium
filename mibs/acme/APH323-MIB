------------------------------------------------------------------------------
-- ACMEPACKET-SMGM-MIB.txt:  Acme Packet system management MIB file
--
-- February 2003
--
-- Copyright (c) by Acme Packet, Inc.
-- All rights reserved.
--------------------------------------------------------------------------------
-- This MIB provides a means to gather system management information generated 
-- by Acme Packet Session Router and Session Director
-- 

APH323-MIB DEFINITIONS ::= BEGIN

IMPORTS
	MODULE-IDENTITY, OBJECT-TYPE, NOTIFICATION-TYPE,
	TimeTicks, Integer32, Unsigned32, Counter32, IpAddress
					FROM SNMPv2-SMI
        InetAddress, InetAddressType, InetAddressPrefixLength, InetVersion, InetZoneIndex 
                                        FROM INET-ADDRESS-MIB
        TEXTUAL-CONVENTION		FROM SNMPv2-TC
	DisplayString			FROM SNMPv2-TC
        MODULE-COMPLIANCE, OBJECT-GROUP, NOTIFICATION-GROUP
					FROM SNMPv2-CONF
	acmepacketMgmt			FROM ACMEPACKET-SMI;
     
apH323Module   MODULE-IDENTITY
	       LAST-UPDATED     "201207160000Z"
   	       ORGANIZATION     "Acme Packet, Inc"
	       CONTACT-INFO
			  "       Customer Service
                        Postal: Acme Packet, Inc
                                100 Crosby Drive
                                Bedford, MA 01730
                                US
                        Tel:    1-781-328-4400
                        E-mail: support@acmepacket.com"

                
		DESCRIPTION
			" The H323 MIB for Acme Packet,
			now includes statistical data for H323 entities."
                REVISION        "201207160000Z"       
                DESCRIPTION      "Updated contact info."
		::= { acmepacketMgmt 10 }


   	apH323MIBObjects OBJECT IDENTIFIER ::= { apH323Module 1 }
	apH323NotificationObjects OBJECT IDENTIFIER ::= { apH323Module 2 }
        apH323NotificationPrefix OBJECT IDENTIFIER ::= { apH323Module 3 }
	apH323Conformance OBJECT IDENTIFIER ::= { apH323Module 4 }	
          
        apH323Notifications OBJECT IDENTIFIER ::= { apH323NotificationPrefix 0 }
	apH323Groups OBJECT IDENTIFIER ::= { apH323Conformance 1 }		
        apH323NotificationGroups OBJECT IDENTIFIER ::= { apH323Conformance 2 }
	
        apH323StackTable OBJECT-TYPE
        	SYNTAX	SEQUENCE OF ApH323StackEntry
        	MAX-ACCESS      not-accessible
        	STATUS  	current
        	DESCRIPTION
                	"h323 stack table"
        	::= { apH323MIBObjects 1 }

	 apH323StackEntry OBJECT-TYPE
        	SYNTAX  ApH323StackEntry
        	MAX-ACCESS      not-accessible
        	STATUS  	current
        	DESCRIPTION
                	"A h323 stack entry"
        	INDEX     { IMPLIED apH323StackName }
        	::= { apH323StackTable 1}


	  ApH323StackEntry ::=
        	SEQUENCE {
                  apH323StackName       DisplayString,
                  apH323StackCurrentCalls	Unsigned32
                 }
	
	  apH323StackName OBJECT-TYPE
        	SYNTAX  DisplayString (SIZE (1..255))
        	MAX-ACCESS      read-only
        	STATUS          current
        	DESCRIPTION     
                	"configured h323 stack name"
        	::= { apH323StackEntry 1 }

        apH323StackCurrentCalls OBJECT-TYPE
        SYNTAX			Unsigned32
        MAX-ACCESS		read-only
        STATUS			current
        DESCRIPTION     
	          "Number of current calls."
	::= { apH323StackEntry 2}
        
       apH323StackMaxCalls OBJECT-TYPE
        SYNTAX			Unsigned32
        MAX-ACCESS		accessible-for-notify
        STATUS			current
        DESCRIPTION     
	          "Number of max calls."
	::= { apH323NotificationObjects 1}
 
       apH323StackMaxCallsThreshold OBJECT-TYPE	
        SYNTAX			          Unsigned32
        MAX-ACCESS		          accessible-for-notify
        STATUS			          current
        DESCRIPTION
		"Threshold value is the percentage of max calls."
	 ::= { apH323NotificationObjects 2}

        apH323StackMaxCallThresholdTrap NOTIFICATION-TYPE
               OBJECTS {
	               apH323StackName,
		       apH323StackMaxCalls,
                       apH323StackMaxCallsThreshold,
                       apH323StackCurrentCalls
		}
	STATUS  current
        DESCRIPTION
                "This trap is sent if the number of h323 calls increases percentage of the max-calls threshold "
        ::= { apH323Notifications 1 }

        apH323StackMaxCallThresholdClearTrap NOTIFICATION-TYPE
               OBJECTS {
	               apH323StackName,
		       apH323StackMaxCalls,
                       apH323StackMaxCallsThreshold,
                       apH323StackCurrentCalls
		}
	STATUS  current
        DESCRIPTION
                "This trap is sent if the number of h323 calls decreases to below the lowest max-calls threshold"
        ::= { apH323Notifications 2 }

        apH323StackObjectsGroup OBJECT-GROUP
	OBJECTS  {
	         apH323StackName,	
	         apH323StackCurrentCalls
	        }
	STATUS		current
	DESCRIPTION
		"A collection of objects providing h323 stack information"
	::= {  apH323Groups 1}

  

       -- notifications groups

        apH323StackNotificationsGroup NOTIFICATION-GROUP
	NOTIFICATIONS  {
		apH323StackMaxCallThresholdTrap,
                apH323StackMaxCallThresholdClearTrap
	}
	STATUS   current
        DESCRIPTION
                 "A collection of h323 stack notifications"
	::= {   apH323NotificationGroups 1 }
END
