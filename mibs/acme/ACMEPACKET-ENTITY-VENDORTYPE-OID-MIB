-- *****************************************************************
-- ACMEPACKET-ENTITY-VENDORTYPE-OID-MIB: OID assignments for 
-- Acme Packet Components for use by the ENTITY-MIB
--
--February 2004
--
-- Copyright (c) by Acme Packet, Inc.
-- 
-- *****************************************************************


ACMEPACKET-ENTITY-VENDORTYPE-OID-MIB DEFINITIONS ::= BEGIN

IMPORTS
	MODULE-IDENTITY
		FROM SNMPv2-SMI
	acmepacketModules
		FROM ACMEPACKET-SMI;

acmepacketEntityVendortypeOIDMIB MODULE-IDENTITY
		LAST-UPDATED	"200402121100Z"
		ORGANIZATION	"Acme Packet, Inc."
		CONTACT-INFO
			  "       Customer Service
                        Postal: Acme Packet, Inc
                                100 Crosby Drive
                                Bedford, MA 01730
                                US
                        Tel:    1-781-328-4400
                        E-mail: support@acmepacket.com"
        DESCRIPTION
		"This module defines the object identifiers that are
		assigned to various components on Acme Packet products,
		which are used by the entPhysicalTable of the ENTITY-MIB
		to uniquely identify the type of each physical entry."
	::= { acmepacketModules 1 }


apevMIBObjects  	
	OBJECT IDENTIFIER ::= { acmepacketEntityVendortypeOIDMIB 1 }

apevOther			OBJECT IDENTIFIER ::= { apevMIBObjects 1 }

-- apevOther objects are partitioned into sub-groups based on
-- the functionality of the objects e.g., cpu-type cards have their
-- own sub-group, fabric cards have another sub-group etc.
apevUnknown 			OBJECT IDENTIFIER ::= { apevMIBObjects 2 }


-- chassis OID assignments
apevChassis 			OBJECT IDENTIFIER ::= { apevMIBObjects 3 }

apevChassisUnknown		OBJECT IDENTIFIER ::= { apevChassis 1 }

-- Session Director
apevChassisSD 			OBJECT IDENTIFIER ::= { apevChassis 2 }

apevChassisSDUnknown		OBJECT IDENTIFIER ::= { apevChassisSD 1}
apevChassisSD1			OBJECT IDENTIFIER ::= { apevChassisSD 2}
-- SD2 without QoS 
apevChassisSD2 			OBJECT IDENTIFIER ::= { apevChassisSD 3 }
-- SD2 with QoS
apevChassisSD2QoS		OBJECT IDENTIFIER ::= { apevChassisSD 4 }
apevChassisSD3 			OBJECT IDENTIFIER ::= { apevChassisSD 5 }
apevChassisSD4 			OBJECT IDENTIFIER ::= { apevChassisSD 6 }

-- Session Router
apevChassisSR                   OBJECT IDENTIFIER ::= { apevChassis 3 }


-- Container OID assignments
apevContainer			OBJECT IDENTIFIER ::= { apevMIBObjects 4 }

apevContainerUnknown		OBJECT IDENTIFIER ::= { apevContainer 1 }

-- represents slots on the chassis, 
-- the slot presents that the card can be removed during running time
apevContainerSlot	 	OBJECT IDENTIFIER ::= { apevContainer 2 }
apevContainerSlotUnknown    	OBJECT IDENTIFIER ::= { apevContainerSlot 1 }
apevContainerSlotPHY    	OBJECT IDENTIFIER ::= { apevContainerSlot 2 }
apevContainerSlotPCMCIA             OBJECT IDENTIFIER ::= { apevContainerSlot 3 }

-- represents daughter card container
-- the card contained in it can not be removed during running time
apevContainerDaughterCard	OBJECT IDENTIFIER ::= { apevContainer 3 }	
apevContainerDaughterCardUnknown OBJECT IDENTIFIER ::= { apevContainerDaughterCard 1 }
apevContainerDaughterCardCAM	 OBJECT IDENTIFIER ::= { apevContainerDaughterCard 2 }
apevContainerDaughterCardCPU	 OBJECT IDENTIFIER ::= { apevContainerDaughterCard 3 }
apevContainerDaughterCardPMC     OBJECT IDENTIFIER ::= { apevContainerDaughterCard 4 }
apevContainerDaughterCardMemory  OBJECT IDENTIFIER ::= { apevContainerDaughterCard 5 }
apevContainerDaughterCardTLS     OBJECT IDENTIFIER ::= { apevContainerDaughterCard 6 }


-- Power Supply Tray for all Chassises
apevContainerPowerTray		OBJECT IDENTIFIER ::= { apevContainer 4 }

-- Fan Tray Container, containing 3 fans
apevContainerFanTray		OBJECT IDENTIFIER ::= { apevContainer 5 }	

-- slot containers for sd4 
apevContainerModules	OBJECT IDENTIFIER ::= { apevContainer 6 }


-- Power supply OID assignments
apevPowerSupply		OBJECT IDENTIFIER ::= { apevMIBObjects 5 }
apevPowerSupplyUnknown	OBJECT IDENTIFIER ::= { apevPowerSupply 1 }
apevPowerSupply150W	OBJECT IDENTIFIER ::= { apevPowerSupply 2 }
apevPowerSupply300W	OBJECT IDENTIFIER ::= { apevPowerSupply 3 }

-- Fan OID assignments
apevFan			OBJECT IDENTIFIER ::= { apevMIBObjects 6 }
apevFanUnknown		OBJECT IDENTIFIER ::= { apevFan 1 }
apevFan40x20		OBJECT IDENTIFIER ::= { apevFan 2 }
apevFan40x28		OBJECT IDENTIFIER ::= { apevFan 3 }


-- Sensor OID assignments
apevSensor			OBJECT IDENTIFIER ::= { apevMIBObjects 7 }
-- Unknown sensor
apevSensorUnknown		OBJECT IDENTIFIER ::= { apevSensor 1 }	
-- Temperature sensor 
apevSensorTemperature	OBJECT IDENTIFIER ::= { apevSensor 2 }	
-- QoS FPGA Voltage sensor
apevSensorVoltage		OBJECT IDENTIFIER ::= { apevSensor 3 }		
-- Fan Speed sensor
apevSensorFanSpeed	OBJECT IDENTIFIER ::= { apevSensor 4 }		



-- Module OID assignments
apevModule			OBJECT IDENTIFIER ::= { apevMIBObjects 8 }

apevModuleUnknown		OBJECT IDENTIFIER ::= { apevModule 1 }

apevModulePHYCard		OBJECT IDENTIFIER ::= { apevModule 2 }
apevPHYCardUnknown	        OBJECT IDENTIFIER ::= { apevModulePHYCard 1 }
-- 1 Gig port multi mode
apevPHY1GigPortMultiMode	OBJECT IDENTIFIER ::= { apevModulePHYCard 2 }
-- 1 Gig port single mode
apevPHY1GigPortSingleMode	OBJECT IDENTIFIER ::= { apevModulePHYCard 3 }
-- 2 Gig ports multi mode
apevPHY2GigPortstMultiMode	OBJECT IDENTIFIER ::= { apevModulePHYCard 4 }
-- 2 Gig ports single mode
apevPHY2GigPortsSingleMode      OBJECT IDENTIFIER ::= { apevModulePHYCard 5 }
-- 4 Port 10/100 Base-TX Phy
apecPHY4FEPorts			OBJECT IDENTIFIER ::= { apevModulePHYCard 6 }
-- 4 Port 10/100 Base-TX Phy (1089)
apevPHY4FEPorts1089		OBJECT IDENTIFIER ::= { apevModulePHYCard 7 }
-- 2 Port gig copper with security
apevPHY2GigPortsSec		OBJECT IDENTIFIER ::= { apevModulePHYCard 8 }
-- 2 Port gig fiber with security
apevPHY2FEPortsSec		OBJECT IDENTIFIER ::= { apevModulePHYCard 9 }

apevPHY4GigPorts 		OBJECT IDENTIFIER ::= { apevModulePHYCard 10 }
apevPHY4SFPPorts 		OBJECT IDENTIFIER ::= { apevModulePHYCard 11 }
apevPHY44SFPPortsSecQos		OBJECT IDENTIFIER ::= { apevModulePHYCard 12 }
apevPHY4SFPPortsQos		OBJECT IDENTIFIER ::= { apevModulePHYCard 13 }
apevPHY4SFPPortsSec		OBJECT IDENTIFIER ::= { apevModulePHYCard 14 }
apevPHY8FEPorts 		OBJECT IDENTIFIER ::= { apevModulePHYCard 15 }
apevPHY4SFPPortsSecQosCav       OBJECT IDENTIFIER ::= { apevModulePHYCard 16 }

apevModuleCAM			OBJECT IDENTIFIER ::= { apevModule 3 }
apevModuleCAMUnknown    	OBJECT IDENTIFIER ::= { apevModuleCAM 1 }
apevModuleCAMAMCC 		OBJECT IDENTIFIER ::= { apevModuleCAM 2 }
apevModuleCAMIDT		OBJECT IDENTIFIER ::= { apevModuleCAM 3 }

apevModuleHostProcessor		OBJECT IDENTIFIER ::= { apevModule 4 }
apevModuleHPUnknown 	   	OBJECT IDENTIFIER ::= { apevModuleHostProcessor 1 }
apevModuleHP7451		OBJECT IDENTIFIER ::= { apevModuleHostProcessor 2 }
apevModuleHP7455		OBJECT IDENTIFIER ::= { apevModuleHostProcessor 3 }
-- types of 7457 
apevModuleHP7457		OBJECT IDENTIFIER ::= { apevModuleHostProcessor 4 }
apevModuleHPT2500		OBJECT IDENTIFIER ::= { apevModuleHostProcessor 5 }
apevModuleHPCeleron		OBJECT IDENTIFIER ::= { apevModuleHostProcessor 6 }
apevModuleHPT9400               OBJECT IDENTIFIER ::= { apevModuleHostProcessor 7 }

apevHP7457Unknown		OBJECT IDENTIFIER ::= { apevModuleHP7457 1 }
apevHP7457DC8MB			OBJECT IDENTIFIER ::= { apevModuleHP7457 2 }
apevHP7457DC4MB			OBJECT IDENTIFIER ::= { apevModuleHP7457 3 }
apevHP7457AC8MB			OBJECT IDENTIFIER ::= { apevModuleHP7457 4 }
apevHP7457AC4MB			OBJECT IDENTIFIER ::= { apevModuleHP7457 5 }
apevHP7457ACDC8MB		OBJECT IDENTIFIER ::= { apevModuleHP7457 6 }


apevModulePMC			OBJECT IDENTIFIER ::= { apevModule 5 }
apevModulePMCUnknown            OBJECT IDENTIFIER ::= { apevModulePMC 1 }

apevModulePCMCIA		OBJECT IDENTIFIER ::= { apevModule 6 }
apevModulePCMCIAUnknown         OBJECT IDENTIFIER ::= { apevModulePCMCIA 1 }
apevModulePCMCIAATA		OBJECT IDENTIFIER ::= { apevModulePCMCIA 2 }
apevModulePCMCIALinear		OBJECT IDENTIFIER ::= { apevModulePCMCIA 3 }

apevModuleMemory		OBJECT IDENTIFIER ::= { apevModule 7 }
apevModuleMemoryUnknown         OBJECT IDENTIFIER ::= { apevModuleMemory 1 }
apevModuleMemory1G		OBJECT IDENTIFIER ::= { apevModuleMemory 2 }
apevModuleMemory4G		OBJECT IDENTIFIER ::= { apevModuleMemory 3 }

apevModuleCard		OBJECT IDENTIFIER ::= { apevModule 8 }
apevModuleSPU		OBJECT IDENTIFIER ::= { apevModuleCard 1 }
apevModuleNPU		OBJECT IDENTIFIER ::= { apevModuleCard 2 }
apevModuleTCU		OBJECT IDENTIFIER ::= { apevModuleCard 3 }
apevModuleMIU		OBJECT IDENTIFIER ::= { apevModuleCard 4 }
apevModulePHY		OBJECT IDENTIFIER ::= { apevModuleCard 5 }
apevModuleTLS		OBJECT IDENTIFIER ::= { apevModuleCard 6 }


-- Port
apevPort	 		OBJECT IDENTIFIER ::= { apevMIBObjects 9 }
apevPortUnknown			OBJECT IDENTIFIER ::= { apevPort 1 }
apevPortGigE			OBJECT IDENTIFIER ::= { apevPort 2 }	
apevPortFE			OBJECT IDENTIFIER ::= { apevPort 3 }
apevPort2Gig			OBJECT IDENTIFIER ::= { apevPort 4 }
apevPortMMFiber			OBJECT IDENTIFIER ::= { apevPort 5 }
apevPortSMFiber			OBJECT IDENTIFIER ::= { apevPort 6 }
apevPort10GFiber		OBJECT IDENTIFIER ::= { apevPort 7 }

-- Stack
-- So far no any stack in our system
apevStack			OBJECT IDENTIFIER ::= { apevMIBObjects 10 }

END
