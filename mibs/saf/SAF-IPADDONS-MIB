SAF-IPADDONS DEFINITIONS ::= BEGIN
-- name: SAF-IPADDONS
--
-- Mib for:   SAF CFIP FODU v1.3x, v1.4x and SAF CFIP FODU GE (Lumina) v1.4x
--            CFIP IDU (Phoenix), FreeMile
--                  released after 2012.05.31
-- Version:         1.0.0
-- Date/Time:       2012.06.01 12:00
-- Customer suport: <techsupport@saftehnika.com>
-- Author:          Andris Kluga
--
-- 2012.06.01  first public release

IMPORTS
        enterprises,  NetworkAddress, IpAddress,
        Counter, Gauge, TimeTicks    FROM RFC1155-SMI
        OBJECT-TYPE              FROM RFC-1212
        DisplayString        FROM RFC1213-MIB
        DateAndTime      FROM SNMPv2-TC
        TRAP-TYPE    FROM RFC-1215;


saf                 OBJECT IDENTIFIER ::=   { enterprises 7571 }
tehnika             OBJECT IDENTIFIER ::=   { saf 100 }
microwaveRadio      OBJECT IDENTIFIER ::=   { tehnika  1}
pointToPoint        OBJECT IDENTIFIER ::=   { microwaveRadio 1 }

safip           OBJECT IDENTIFIER ::=   { pointToPoint 5 }
safipaddons     OBJECT IDENTIFIER ::=   { safip 15}

ipaddSys    		OBJECT IDENTIFIER ::=   { safipaddons 1 }
-- we have 2 types of eth sw - B and T type
-- B type used in Lumina, Phoenix and Marathon
-- T type in 100Mb products and Freemile
ipaddIfB     		OBJECT IDENTIFIER ::=   { safipaddons 2 }
ipaddIfM     		OBJECT IDENTIFIER ::=   { safipaddons 3 }


-- Modem temperature
modemTemperature OBJECT-TYPE
         SYNTAX  DisplayString
         ACCESS  read-only
         STATUS  mandatory
         DESCRIPTION
                 "Unit temperature in degrees by Celsius. degrees"
         ::= { ipaddSys 1 }

-- Input voltage
iduInputVoltage OBJECT-TYPE
         SYNTAX  DisplayString
         ACCESS  read-only
         STATUS  mandatory
         DESCRIPTION
                 "IDU input voltage [V]"
-- N/A Freemile
         ::= { ipaddSys 2 }

iduInputCurrent OBJECT-TYPE
         SYNTAX  DisplayString
         ACCESS  read-only
         STATUS  mandatory
         DESCRIPTION
                 "IDU input current [A]"
-- N/A Freemile
         ::= { ipaddSys 3 }

iduPowerConsumption OBJECT-TYPE
         SYNTAX  DisplayString
         ACCESS  read-only
         STATUS  mandatory
         DESCRIPTION
                 "IDU power consumption [W]"
-- N/A Freemile
         ::= { ipaddSys 4 }

oduTemperature OBJECT-TYPE
         SYNTAX  DisplayString
         ACCESS  read-only
         STATUS  mandatory
         DESCRIPTION
                 "Odu or radio temperature in degrees by Celsius."
-- N/A Lumina Freemile
         ::= { ipaddSys 5 }

oduPsuState OBJECT-TYPE
         SYNTAX  INTEGER  {
                init(1),
                off(2),
                idle(3),
                ok(4),
                overload(5),
                short(6),
                fault(7)
              }
         ACCESS  read-only
         STATUS  mandatory
         DESCRIPTION
                 "Odu or radio PSU state"
-- N/A Lumina Freemile
         ::= { ipaddSys 6 }


iduOutputVoltageToOdu OBJECT-TYPE
         SYNTAX  DisplayString
         ACCESS  read-only
         STATUS  mandatory
         DESCRIPTION
                 "IDU output voltage to radio [V]"
-- N/A Lumina Freemile
         ::= { ipaddSys 7 }

iduOutputCurrentToOdu OBJECT-TYPE
         SYNTAX  DisplayString
         ACCESS  read-only
         STATUS  mandatory
         DESCRIPTION
                 "IDU output current to radio [A]"
-- N/A Lumina Freemile
         ::= { ipaddSys 8 }

oduPowerConsumption OBJECT-TYPE
         SYNTAX  DisplayString
         ACCESS  read-only
         STATUS  mandatory
         DESCRIPTION
                 "ODU (radio) power consumption [W]"
-- N/A Lumina Freemile
         ::= { ipaddSys 9 }

oduCableAttenuation OBJECT-TYPE
         SYNTAX  INTEGER 
         ACCESS  read-only
         STATUS  mandatory
         DESCRIPTION
                 "ODU cable attenuation [dB]"
-- N/A Lumina Freemile
         ::= { ipaddSys 10 }


ipaddIfBTable OBJECT-TYPE
   SYNTAX      SEQUENCE OF IpaddIfBEntry
   MAX-ACCESS  not-accessible
   STATUS      current
   DESCRIPTION "IF addons table."
-- represents parameters not defined in strandart mib-s bor B-type sw
   ::= { ipaddIfB 2 }

ipaddIfBEntry  OBJECT-TYPE
   SYNTAX      IpaddIfBEntry
   MAX-ACCESS  not-accessible
   STATUS      current
   DESCRIPTION "Entries of table."
      INDEX       { ipaddIfBIndex }
   ::= { ipaddIfBTable 1 }

IpaddIfBEntry ::= SEQUENCE {
    ipaddIfBIndex INTEGER,
    ipaddIfBduplex INTEGER,

    ipaddIfBRxFlow INTEGER,
    ipaddIfBTxFlow INTEGER,
    ipaddIfBRxState INTEGER,
    ipaddIfBTxTxState INTEGER,
-- 
    ipaddIfBTxQ0PKT INTEGER,
    ipaddIfBTxCollisions INTEGER,
    ipaddIfBTxSingleCollision INTEGER,
    ipaddIfBTxMultiCollision INTEGER,
    ipaddIfBRxPausePkts INTEGER,
    ipaddIfBRxFCSErrors INTEGER,
    ipaddIfBRxGoodOctets INTEGER,
    ipaddIfBRxSAChanges INTEGER,
    ipaddIfBRxExcessSizeDisc INTEGER,
    ipaddIfBRxSymbolError INTEGER,
    ipaddIfBRxPkts1523to2047Octets INTEGER,
    ipaddIfBRxPkts2048to4095Octets INTEGER,
    ipaddIfBRxPkts4096to8191Octets INTEGER,
    ipaddIfBRxPkts8192to9728Octets INTEGER
   }



    ipaddIfBIndex OBJECT-TYPE
         SYNTAX      INTEGER
         ACCESS  read-only
         STATUS  mandatory
   DESCRIPTION "INDEX the same value as ifIndex"
   ::= { ipaddIfBEntry 1 }

    ipaddIfBduplex OBJECT-TYPE
         SYNTAX      INTEGER
           {
           full (1),
           half (2)
           }
         ACCESS  read-only
         STATUS  mandatory
   DESCRIPTION ""
   ::= { ipaddIfBEntry 2 }

    ipaddIfBRxFlow OBJECT-TYPE
         SYNTAX      INTEGER
           {
           on (1),
           off (2)
           }
         ACCESS  read-only
         STATUS  mandatory
   DESCRIPTION ""
   ::= { ipaddIfBEntry 3 }

    ipaddIfBTxFlow OBJECT-TYPE
         SYNTAX      INTEGER
           {
           on (1),
           off (2)
           }
         ACCESS  read-only
         STATUS  mandatory
   DESCRIPTION ""
   ::= { ipaddIfBEntry 4 }

    ipaddIfBRxState OBJECT-TYPE
         SYNTAX      INTEGER
           {
           on (1),
           off (2)
           }
         ACCESS  read-only
         STATUS  mandatory
   DESCRIPTION ""
   ::= { ipaddIfBEntry 5 }

    ipaddIfBTxTxState OBJECT-TYPE
         SYNTAX      INTEGER
           {
           on (1),
           off (2)
           }
         ACCESS  read-only
         STATUS  mandatory
   DESCRIPTION ""
   ::= { ipaddIfBEntry 6 }

-- 
    ipaddIfBTxQ0PKT OBJECT-TYPE
         SYNTAX      INTEGER
         ACCESS  read-only
         STATUS  mandatory
   DESCRIPTION ""
   ::= { ipaddIfBEntry 7 }

    ipaddIfBTxCollisions OBJECT-TYPE
         SYNTAX      INTEGER
         ACCESS  read-only
         STATUS  mandatory
   DESCRIPTION ""
   ::= { ipaddIfBEntry 8 }

    ipaddIfBTxSingleCollision OBJECT-TYPE
         SYNTAX      INTEGER
         ACCESS  read-only
         STATUS  mandatory
   DESCRIPTION ""
   ::= { ipaddIfBEntry 9 }

    ipaddIfBTxMultiCollision OBJECT-TYPE
         SYNTAX      INTEGER
         ACCESS  read-only
         STATUS  mandatory
   DESCRIPTION ""
   ::= { ipaddIfBEntry 10 }

    ipaddIfBRxPausePkts OBJECT-TYPE
         SYNTAX      INTEGER
         ACCESS  read-only
         STATUS  mandatory
   DESCRIPTION ""
   ::= { ipaddIfBEntry 11 }

    ipaddIfBRxFCSErrors OBJECT-TYPE
         SYNTAX      INTEGER
         ACCESS  read-only
         STATUS  mandatory
   DESCRIPTION ""
   ::= { ipaddIfBEntry 12 }

    ipaddIfBRxGoodOctets OBJECT-TYPE
         SYNTAX      INTEGER
         ACCESS  read-only
         STATUS  mandatory
   DESCRIPTION ""
   ::= { ipaddIfBEntry 13 }

    ipaddIfBRxSAChanges OBJECT-TYPE
         SYNTAX      INTEGER
         ACCESS  read-only
         STATUS  mandatory
   DESCRIPTION ""
   ::= { ipaddIfBEntry 14 }

    ipaddIfBRxExcessSizeDisc OBJECT-TYPE
         SYNTAX      INTEGER
         ACCESS  read-only
         STATUS  mandatory
   DESCRIPTION ""
   ::= { ipaddIfBEntry 15 }

    ipaddIfBRxSymbolError OBJECT-TYPE
         SYNTAX      INTEGER
         ACCESS  read-only
         STATUS  mandatory
   DESCRIPTION ""
   ::= { ipaddIfBEntry 16 }

    ipaddIfBRxPkts1523to2047Octets OBJECT-TYPE
         SYNTAX      INTEGER
         ACCESS  read-only
         STATUS  mandatory
   DESCRIPTION ""
   ::= { ipaddIfBEntry 17 }

    ipaddIfBRxPkts2048to4095Octets OBJECT-TYPE
         SYNTAX      INTEGER
         ACCESS  read-only
         STATUS  mandatory
   DESCRIPTION ""
   ::= { ipaddIfBEntry 18 }

    ipaddIfBRxPkts4096to8191Octets OBJECT-TYPE
         SYNTAX      INTEGER
         ACCESS  read-only
         STATUS  mandatory
   DESCRIPTION ""
   ::= { ipaddIfBEntry 19 }

    ipaddIfBRxPkts8192to9728Octets OBJECT-TYPE
         SYNTAX      INTEGER
         ACCESS  read-only
         STATUS  mandatory
   DESCRIPTION ""
   ::= { ipaddIfBEntry 20 }




ipaddIfMTable OBJECT-TYPE
   SYNTAX      SEQUENCE OF IpaddIfMEntry
   MAX-ACCESS  not-accessible
   STATUS      current
   DESCRIPTION "IF addons table."
-- represents parameters not defined in strandart mib-s for M-type sw
   ::= { ipaddIfM 2 }

ipaddIfMEntry  OBJECT-TYPE
   SYNTAX      IpaddIfMEntry
   MAX-ACCESS  not-accessible
   STATUS      current
   DESCRIPTION "Entries of table."
      INDEX       { ipaddIfMIndex }
   ::= { ipaddIfMTable 1 }

IpaddIfMEntry ::= SEQUENCE {
    ipaddIfMIndex INTEGER,
    ipaddIfMduplex INTEGER,
    ipaddIfMFlowControl INTEGER,
    ipaddIfMRxLoPriorityByte INTEGER,
    ipaddIfMRxHiPriorityByte INTEGER,
    ipaddIfMRxSymbolError INTEGER,
    ipaddIfMRxCRCerror INTEGER,
    ipaddIfMRxControl8808Pkts INTEGER,
    ipaddIfMRxPausePkts INTEGER,
    ipaddIfMTxLoPriorityByte INTEGER,
    ipaddIfMTxHiPriorityByte INTEGER,
    ipaddIfMTxLateCollision INTEGER,
    ipaddIfMTxPausePkts INTEGER,
    ipaddIfMTxDeferred INTEGER,
    ipaddIfMTxTotalCollision INTEGER,
    ipaddIfMTxExcessiveCollision INTEGER,
    ipaddIfMTxSingleCollision INTEGER,
    ipaddIfMTxMultipleCollision INTEGER
   }

   ipaddIfMIndex  OBJECT-TYPE
         SYNTAX      INTEGER
         ACCESS  read-only
         STATUS  mandatory
   DESCRIPTION "Index"
   ::= { ipaddIfMEntry 1 }

    ipaddIfMduplex  OBJECT-TYPE
         SYNTAX      INTEGER
           {
           full (1),
           half (2)
           }
         ACCESS  read-only
         STATUS  mandatory
   DESCRIPTION ""
   ::= { ipaddIfMEntry 2 }

    ipaddIfMFlowControl  OBJECT-TYPE
         SYNTAX      INTEGER
           {
           on (1),
           off (2)
           }
         ACCESS  read-only
         STATUS  mandatory
   DESCRIPTION ""
   ::= { ipaddIfMEntry 3 }

    ipaddIfMRxLoPriorityByte  OBJECT-TYPE
         SYNTAX      INTEGER
         ACCESS  read-only
         STATUS  mandatory
   DESCRIPTION ""
   ::= { ipaddIfMEntry 4 }

    ipaddIfMRxHiPriorityByte  OBJECT-TYPE
         SYNTAX      INTEGER
         ACCESS  read-only
         STATUS  mandatory
   DESCRIPTION ""
   ::= { ipaddIfMEntry 5 }

    ipaddIfMRxSymbolError  OBJECT-TYPE
         SYNTAX      INTEGER
         ACCESS  read-only
         STATUS  mandatory
   DESCRIPTION ""
   ::= { ipaddIfMEntry 6 }

    ipaddIfMRxCRCerror  OBJECT-TYPE
         SYNTAX      INTEGER
         ACCESS  read-only
         STATUS  mandatory
   DESCRIPTION ""
   ::= { ipaddIfMEntry 7 }

    ipaddIfMRxControl8808Pkts  OBJECT-TYPE
         SYNTAX      INTEGER
         ACCESS  read-only
         STATUS  mandatory
   DESCRIPTION ""
   ::= { ipaddIfMEntry 8 }

    ipaddIfMRxPausePkts  OBJECT-TYPE
         SYNTAX      INTEGER
         ACCESS  read-only
         STATUS  mandatory
   DESCRIPTION ""
   ::= { ipaddIfMEntry 9 }

    ipaddIfMTxLoPriorityByte  OBJECT-TYPE
         SYNTAX      INTEGER
         ACCESS  read-only
         STATUS  mandatory
   DESCRIPTION ""
   ::= { ipaddIfMEntry 10 }

    ipaddIfMTxHiPriorityByte  OBJECT-TYPE
         SYNTAX      INTEGER
         ACCESS  read-only
         STATUS  mandatory
   DESCRIPTION ""
   ::= { ipaddIfMEntry 11 }

    ipaddIfMTxLateCollision  OBJECT-TYPE
         SYNTAX      INTEGER
         ACCESS  read-only
         STATUS  mandatory
   DESCRIPTION ""
   ::= { ipaddIfMEntry 12 }

    ipaddIfMTxPausePkts  OBJECT-TYPE
         SYNTAX      INTEGER
         ACCESS  read-only
         STATUS  mandatory
   DESCRIPTION ""
   ::= { ipaddIfMEntry 13 }

    ipaddIfMTxDeferred  OBJECT-TYPE
         SYNTAX      INTEGER
         ACCESS  read-only
         STATUS  mandatory
   DESCRIPTION ""
   ::= { ipaddIfMEntry 14 }

    ipaddIfMTxTotalCollision  OBJECT-TYPE
         SYNTAX      INTEGER
         ACCESS  read-only
         STATUS  mandatory
   DESCRIPTION ""
   ::= { ipaddIfMEntry 15 }

    ipaddIfMTxExcessiveCollision  OBJECT-TYPE
         SYNTAX      INTEGER
         ACCESS  read-only
         STATUS  mandatory
   DESCRIPTION ""
   ::= { ipaddIfMEntry 16 }

    ipaddIfMTxSingleCollision  OBJECT-TYPE
         SYNTAX      INTEGER
         ACCESS  read-only
         STATUS  mandatory
   DESCRIPTION ""
   ::= { ipaddIfMEntry 17 }

    ipaddIfMTxMultipleCollision  OBJECT-TYPE
         SYNTAX      INTEGER
         ACCESS  read-only
         STATUS  mandatory
   DESCRIPTION ""
   ::= { ipaddIfMEntry 18 }


--
END
