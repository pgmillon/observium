LANCOM-L54g-MIB DEFINITIONS ::= BEGIN

IMPORTS
    DisplayString, sysDescr, sysName
      FROM RFC1213-MIB
    MacAddress
      FROM SNMPv2-TC
    enterprises, OBJECT-TYPE,
    MODULE-IDENTITY, IpAddress, Counter32, TimeTicks, Counter64,
    NOTIFICATION-TYPE
      FROM SNMPv2-SMI;



lancom-systems OBJECT IDENTIFIER ::= { enterprises 2356 }

wlan-systems OBJECT IDENTIFIER ::= { lancom-systems 600 }

lan-router OBJECT IDENTIFIER ::= { wlan-systems 2 }

lancom-l54g OBJECT IDENTIFIER ::= { lan-router 54 }

sta OBJECT IDENTIFIER ::= { lancom-l54g 1 }
set OBJECT IDENTIFIER ::= { lancom-l54g 2 }
fir OBJECT IDENTIFIER ::= { lancom-l54g 3 }
oth OBJECT IDENTIFIER ::= { lancom-l54g 4 }

staOpera OBJECT-TYPE
         SYNTAX DisplayString
         MAX-ACCESS read-only
         STATUS current
         DESCRIPTION "Operating-Time"
         ::= {  sta 2 }

staWlan OBJECT IDENTIFIER ::= { sta 3}
staWlanInterfTable OBJECT-TYPE
                   SYNTAX SEQUENCE OF StaWlanInterfEntry
                   MAX-ACCESS not-accessible
                   STATUS current
                   DESCRIPTION "Interfaces"
                   ::= {  staWlan 51 }

staWlanInterfEntry OBJECT-TYPE
                   SYNTAX StaWlanInterfEntry
                   MAX-ACCESS not-accessible
                   STATUS current
                   DESCRIPTION "entry in table"
                   INDEX { staWlanInterfIfc }
                   ::= {  staWlanInterfTable 1 }

StaWlanInterfEntry ::= SEQUENCE {
                   staWlanInterfIfc DisplayString,
                   staWlanInterfOperatin INTEGER,
                   staWlanInterfOperatio INTEGER,
                   staWlanInterfCardid DisplayString,
                   staWlanInterfSerialnu DisplayString,
                   staWlanInterfFirmware DisplayString,
                   staWlanInterfMacaddre MacAddress,
                   staWlanInterfNumstati INTEGER,
                   staWlanInterfQueuepac INTEGER
                  }

staWlanInterfIfc OBJECT-TYPE
                      SYNTAX DisplayString (SIZE(0..255))
                      MAX-ACCESS read-only
                      STATUS current
                      DESCRIPTION "Ifc"
                      ::= {  staWlanInterfEntry 1 }

staWlanInterfOperatin OBJECT-TYPE
                      SYNTAX INTEGER{
                        no(0),
                        yes(1)
                      }
                      MAX-ACCESS read-only
                      STATUS current
                      DESCRIPTION "Operating"
                      ::= {  staWlanInterfEntry 3 }

staWlanInterfOperatio OBJECT-TYPE
                      SYNTAX INTEGER{
                        access-point(1),
                        managed-ap(4),
                        station(0)
                      }
                      MAX-ACCESS read-only
                      STATUS current
                      DESCRIPTION "Operation-Mode"
                      ::= {  staWlanInterfEntry 9 }

staWlanInterfCardid OBJECT-TYPE
                      SYNTAX DisplayString (SIZE(0..255))
                      MAX-ACCESS read-only
                      STATUS current
                      DESCRIPTION "Card-Id"
                      ::= {  staWlanInterfEntry 5 }

staWlanInterfSerialnu OBJECT-TYPE
                      SYNTAX DisplayString (SIZE(0..255))
                      MAX-ACCESS read-only
                      STATUS current
                      DESCRIPTION "Serial-Number"
                      ::= {  staWlanInterfEntry 7 }

staWlanInterfFirmware OBJECT-TYPE
                      SYNTAX DisplayString (SIZE(0..255))
                      MAX-ACCESS read-only
                      STATUS current
                      DESCRIPTION "Firmware-Version"
                      ::= {  staWlanInterfEntry 6 }

staWlanInterfMacaddre OBJECT-TYPE
                      SYNTAX MacAddress
                      MAX-ACCESS read-only
                      STATUS current
                      DESCRIPTION "MAC-Address"
                      ::= {  staWlanInterfEntry 2 }

staWlanInterfNumstati OBJECT-TYPE
                      SYNTAX INTEGER (0..65535)
                      MAX-ACCESS read-only
                      STATUS current
                      DESCRIPTION "Num-Stations"
                      ::= {  staWlanInterfEntry 8 }

staWlanInterfQueuepac OBJECT-TYPE
                      SYNTAX INTEGER (0..2147483647)
                      MAX-ACCESS read-only
                      STATUS current
                      DESCRIPTION "Queue-Packets"
                      ::= {  staWlanInterfEntry 4 }

staWlanNetworTable OBJECT-TYPE
                   SYNTAX SEQUENCE OF StaWlanNetworEntry
                   MAX-ACCESS not-accessible
                   STATUS current
                   DESCRIPTION "Networks"
                   ::= {  staWlan 56 }

staWlanNetworEntry OBJECT-TYPE
                   SYNTAX StaWlanNetworEntry
                   MAX-ACCESS not-accessible
                   STATUS current
                   DESCRIPTION "entry in table"
                   INDEX { staWlanNetworIfc }
                   ::= {  staWlanNetworTable 1 }

StaWlanNetworEntry ::= SEQUENCE {
                   staWlanNetworIfc DisplayString,
                   staWlanNetworOpe INTEGER,
                   staWlanNetworNet DisplayString,
                   staWlanNetworBss MacAddress,
                   staWlanNetworVla INTEGER,
                   staWlanNetworNum INTEGER,
                   staWlanNetworMca INTEGER
                  }

staWlanNetworIfc OBJECT-TYPE
                 SYNTAX DisplayString (SIZE(0..255))
                 MAX-ACCESS read-only
                 STATUS current
                 DESCRIPTION "Ifc"
                 ::= {  staWlanNetworEntry 1 }

staWlanNetworOpe OBJECT-TYPE
                 SYNTAX INTEGER{
                   no(0),
                   yes(1)
                 }
                 MAX-ACCESS read-only
                 STATUS current
                 DESCRIPTION "Operating"
                 ::= {  staWlanNetworEntry 2 }

staWlanNetworNet OBJECT-TYPE
                 SYNTAX DisplayString (SIZE(0..255))
                 MAX-ACCESS read-only
                 STATUS current
                 DESCRIPTION "Network-Name"
                 ::= {  staWlanNetworEntry 3 }

staWlanNetworBss OBJECT-TYPE
                 SYNTAX MacAddress
                 MAX-ACCESS read-only
                 STATUS current
                 DESCRIPTION "BSSID"
                 ::= {  staWlanNetworEntry 6 }

staWlanNetworVla OBJECT-TYPE
                 SYNTAX INTEGER (0..65535)
                 MAX-ACCESS read-only
                 STATUS current
                 DESCRIPTION "VLAN-Id"
                 ::= {  staWlanNetworEntry 7 }

staWlanNetworNum OBJECT-TYPE
                 SYNTAX INTEGER (0..65535)
                 MAX-ACCESS read-only
                 STATUS current
                 DESCRIPTION "Num-Stations"
                 ::= {  staWlanNetworEntry 4 }

staWlanNetworMca OBJECT-TYPE
                 SYNTAX INTEGER{
                   no(0),
                   yes(1)
                 }
                 MAX-ACCESS read-only
                 STATUS current
                 DESCRIPTION "MCast-Pwr-Save"
                 ::= {  staWlanNetworEntry 5 }

staWlanBytetrTable OBJECT-TYPE
                   SYNTAX SEQUENCE OF StaWlanBytetrEntry
                   MAX-ACCESS not-accessible
                   STATUS current
                   DESCRIPTION "Byte-Transport"
                   ::= {  staWlan 52 }

staWlanBytetrEntry OBJECT-TYPE
                   SYNTAX StaWlanBytetrEntry
                   MAX-ACCESS not-accessible
                   STATUS current
                   DESCRIPTION "entry in table"
                   INDEX { staWlanBytetrIfc }
                   ::= {  staWlanBytetrTable 1 }

StaWlanBytetrEntry ::= SEQUENCE {
                   staWlanBytetrIfc DisplayString,
                   staWlanBytetrTxbyte Counter64,
                   staWlanBytetrRxbyte Counter64,
                   staWlanBytetrThroug DisplayString,
                   staWlanBytetrMaxthr DisplayString,
                   staWlanBytetrBytest INTEGER,
                   staWlanBytetrBytesm INTEGER
                  }

staWlanBytetrIfc OBJECT-TYPE
                    SYNTAX DisplayString (SIZE(0..255))
                    MAX-ACCESS read-only
                    STATUS current
                    DESCRIPTION "Ifc"
                    ::= {  staWlanBytetrEntry 1 }

staWlanBytetrTxbyte OBJECT-TYPE
                    SYNTAX Counter64
                    MAX-ACCESS read-only
                    STATUS current
                    DESCRIPTION "Tx-Bytes"
                    ::= {  staWlanBytetrEntry 2 }

staWlanBytetrRxbyte OBJECT-TYPE
                    SYNTAX Counter64
                    MAX-ACCESS read-only
                    STATUS current
                    DESCRIPTION "Rx-Bytes"
                    ::= {  staWlanBytetrEntry 3 }

staWlanBytetrThroug OBJECT-TYPE
                    SYNTAX DisplayString (SIZE(0..255))
                    MAX-ACCESS read-only
                    STATUS current
                    DESCRIPTION "Throughput"
                    ::= {  staWlanBytetrEntry 4 }

staWlanBytetrMaxthr OBJECT-TYPE
                    SYNTAX DisplayString (SIZE(0..255))
                    MAX-ACCESS read-only
                    STATUS current
                    DESCRIPTION "Max.-Throughput"
                    ::= {  staWlanBytetrEntry 5 }

staWlanBytetrBytest OBJECT-TYPE
                    SYNTAX INTEGER (0..2147483647)
                    MAX-ACCESS read-only
                    STATUS current
                    DESCRIPTION "Bytes-Throughput"
                    ::= {  staWlanBytetrEntry 6 }

staWlanBytetrBytesm OBJECT-TYPE
                    SYNTAX INTEGER (0..2147483647)
                    MAX-ACCESS read-only
                    STATUS current
                    DESCRIPTION "Bytes-Max.-Throughput"
                    ::= {  staWlanBytetrEntry 7 }

staWlanPacketTable OBJECT-TYPE
                   SYNTAX SEQUENCE OF StaWlanPacketEntry
                   MAX-ACCESS not-accessible
                   STATUS current
                   DESCRIPTION "Packet-Transport"
                   ::= {  staWlan 53 }

staWlanPacketEntry OBJECT-TYPE
                   SYNTAX StaWlanPacketEntry
                   MAX-ACCESS not-accessible
                   STATUS current
                   DESCRIPTION "entry in table"
                   INDEX { staWlanPacketIfc }
                   ::= {  staWlanPacketTable 1 }

StaWlanPacketEntry ::= SEQUENCE {
                   staWlanPacketIfc DisplayString,
                   staWlanPacketRxp Counter32,
                   staWlanPacketTxp Counter32,
                   staWlanPacketRxb Counter32,
                   staWlanPacketRxm Counter32,
                   staWlanPacketRxu Counter32,
                   staWlanPacketRxc Counter32,
                   staWlanPacketTxb Counter32,
                   staWlanPacketTxm Counter32,
                   staWlanPacketTxu Counter32,
                   staWlanPacketTxc Counter32
                  }

staWlanPacketIfc OBJECT-TYPE
                 SYNTAX DisplayString (SIZE(0..255))
                 MAX-ACCESS read-only
                 STATUS current
                 DESCRIPTION "Ifc"
                 ::= {  staWlanPacketEntry 1 }

staWlanPacketRxp OBJECT-TYPE
                 SYNTAX Counter32
                 MAX-ACCESS read-only
                 STATUS current
                 DESCRIPTION "Rx-Packets"
                 ::= {  staWlanPacketEntry 2 }

staWlanPacketTxp OBJECT-TYPE
                 SYNTAX Counter32
                 MAX-ACCESS read-only
                 STATUS current
                 DESCRIPTION "Tx-Packets"
                 ::= {  staWlanPacketEntry 3 }

staWlanPacketRxb OBJECT-TYPE
                 SYNTAX Counter32
                 MAX-ACCESS read-only
                 STATUS current
                 DESCRIPTION "Rx-Broadcasts"
                 ::= {  staWlanPacketEntry 4 }

staWlanPacketRxm OBJECT-TYPE
                 SYNTAX Counter32
                 MAX-ACCESS read-only
                 STATUS current
                 DESCRIPTION "Rx-Multicasts"
                 ::= {  staWlanPacketEntry 5 }

staWlanPacketRxu OBJECT-TYPE
                 SYNTAX Counter32
                 MAX-ACCESS read-only
                 STATUS current
                 DESCRIPTION "Rx-Unicasts"
                 ::= {  staWlanPacketEntry 6 }

staWlanPacketRxc OBJECT-TYPE
                 SYNTAX Counter32
                 MAX-ACCESS read-only
                 STATUS current
                 DESCRIPTION "Rx-Compressed"
                 ::= {  staWlanPacketEntry 11 }

staWlanPacketTxb OBJECT-TYPE
                 SYNTAX Counter32
                 MAX-ACCESS read-only
                 STATUS current
                 DESCRIPTION "Tx-Broadcasts"
                 ::= {  staWlanPacketEntry 7 }

staWlanPacketTxm OBJECT-TYPE
                 SYNTAX Counter32
                 MAX-ACCESS read-only
                 STATUS current
                 DESCRIPTION "Tx-Multicasts"
                 ::= {  staWlanPacketEntry 8 }

staWlanPacketTxu OBJECT-TYPE
                 SYNTAX Counter32
                 MAX-ACCESS read-only
                 STATUS current
                 DESCRIPTION "Tx-Unicasts"
                 ::= {  staWlanPacketEntry 9 }

staWlanPacketTxc OBJECT-TYPE
                 SYNTAX Counter32
                 MAX-ACCESS read-only
                 STATUS current
                 DESCRIPTION "Tx-Compressed"
                 ::= {  staWlanPacketEntry 10 }

staWlanErrorsTable OBJECT-TYPE
                   SYNTAX SEQUENCE OF StaWlanErrorsEntry
                   MAX-ACCESS not-accessible
                   STATUS current
                   DESCRIPTION "Errors"
                   ::= {  staWlan 54 }

staWlanErrorsEntry OBJECT-TYPE
                   SYNTAX StaWlanErrorsEntry
                   MAX-ACCESS not-accessible
                   STATUS current
                   DESCRIPTION "entry in table"
                   INDEX { staWlanErrorsIfc }
                   ::= {  staWlanErrorsTable 1 }

StaWlanErrorsEntry ::= SEQUENCE {
                   staWlanErrorsIfc DisplayString,
                   staWlanErrorsRxerro Counter32,
                   staWlanErrorsTxerro Counter32,
                   staWlanErrorsStacke Counter32,
                   staWlanErrorsNicerr Counter32,
                   staWlanErrorsQueuee Counter32,
                   staWlanErrorsTxdisc Counter32,
                   staWlanErrorsRetrie Counter32,
                   staWlanErrorsMultip Counter32,
                   staWlanErrorsSoftre Counter32,
                   staWlanErrorsDupedi Counter32,
                   staWlanErrorsUndecr Counter32,
                   staWlanErrorsUndeco Counter32,
                   staWlanErrorsAged Counter32,
                   staWlanErrorsMichae Counter32,
                   staWlanErrorsIvsequ Counter32,
                   staWlanErrorsRxcrce Counter32
                  }

staWlanErrorsIfc OBJECT-TYPE
                    SYNTAX DisplayString (SIZE(0..255))
                    MAX-ACCESS read-only
                    STATUS current
                    DESCRIPTION "Ifc"
                    ::= {  staWlanErrorsEntry 1 }

staWlanErrorsRxerro OBJECT-TYPE
                    SYNTAX Counter32
                    MAX-ACCESS read-only
                    STATUS current
                    DESCRIPTION "Rx-Errors"
                    ::= {  staWlanErrorsEntry 2 }

staWlanErrorsTxerro OBJECT-TYPE
                    SYNTAX Counter32
                    MAX-ACCESS read-only
                    STATUS current
                    DESCRIPTION "Tx-Errors"
                    ::= {  staWlanErrorsEntry 3 }

staWlanErrorsStacke OBJECT-TYPE
                    SYNTAX Counter32
                    MAX-ACCESS read-only
                    STATUS current
                    DESCRIPTION "Stack-Errors"
                    ::= {  staWlanErrorsEntry 4 }

staWlanErrorsNicerr OBJECT-TYPE
                    SYNTAX Counter32
                    MAX-ACCESS read-only
                    STATUS current
                    DESCRIPTION "NIC-Errors"
                    ::= {  staWlanErrorsEntry 5 }

staWlanErrorsQueuee OBJECT-TYPE
                    SYNTAX Counter32
                    MAX-ACCESS read-only
                    STATUS current
                    DESCRIPTION "Queue-Errors"
                    ::= {  staWlanErrorsEntry 6 }

staWlanErrorsTxdisc OBJECT-TYPE
                    SYNTAX Counter32
                    MAX-ACCESS read-only
                    STATUS current
                    DESCRIPTION "Tx-Discarded"
                    ::= {  staWlanErrorsEntry 7 }

staWlanErrorsRetrie OBJECT-TYPE
                    SYNTAX Counter32
                    MAX-ACCESS read-only
                    STATUS current
                    DESCRIPTION "Retries"
                    ::= {  staWlanErrorsEntry 8 }

staWlanErrorsMultip OBJECT-TYPE
                    SYNTAX Counter32
                    MAX-ACCESS read-only
                    STATUS current
                    DESCRIPTION "Multiple-Retries"
                    ::= {  staWlanErrorsEntry 9 }

staWlanErrorsSoftre OBJECT-TYPE
                    SYNTAX Counter32
                    MAX-ACCESS read-only
                    STATUS current
                    DESCRIPTION "Soft-Retries"
                    ::= {  staWlanErrorsEntry 17 }

staWlanErrorsDupedi OBJECT-TYPE
                    SYNTAX Counter32
                    MAX-ACCESS read-only
                    STATUS current
                    DESCRIPTION "Dupe-Discarded"
                    ::= {  staWlanErrorsEntry 11 }

staWlanErrorsUndecr OBJECT-TYPE
                    SYNTAX Counter32
                    MAX-ACCESS read-only
                    STATUS current
                    DESCRIPTION "Undecryptables"
                    ::= {  staWlanErrorsEntry 10 }

staWlanErrorsUndeco OBJECT-TYPE
                    SYNTAX Counter32
                    MAX-ACCESS read-only
                    STATUS current
                    DESCRIPTION "Undecompressables"
                    ::= {  staWlanErrorsEntry 12 }

staWlanErrorsAged OBJECT-TYPE
                    SYNTAX Counter32
                    MAX-ACCESS read-only
                    STATUS current
                    DESCRIPTION "Aged"
                    ::= {  staWlanErrorsEntry 13 }

staWlanErrorsMichae OBJECT-TYPE
                    SYNTAX Counter32
                    MAX-ACCESS read-only
                    STATUS current
                    DESCRIPTION "Michael-Errors"
                    ::= {  staWlanErrorsEntry 14 }

staWlanErrorsIvsequ OBJECT-TYPE
                    SYNTAX Counter32
                    MAX-ACCESS read-only
                    STATUS current
                    DESCRIPTION "IV-Sequence-Errors"
                    ::= {  staWlanErrorsEntry 15 }

staWlanErrorsRxcrce OBJECT-TYPE
                    SYNTAX Counter32
                    MAX-ACCESS read-only
                    STATUS current
                    DESCRIPTION "Rx-CRC-Errors"
                    ::= {  staWlanErrorsEntry 16 }

staWlanWlanpaTable OBJECT-TYPE
                   SYNTAX SEQUENCE OF StaWlanWlanpaEntry
                   MAX-ACCESS not-accessible
                   STATUS current
                   DESCRIPTION "WLAN-Parameter"
                   ::= {  staWlan 55 }

staWlanWlanpaEntry OBJECT-TYPE
                   SYNTAX StaWlanWlanpaEntry
                   MAX-ACCESS not-accessible
                   STATUS current
                   DESCRIPTION "entry in table"
                   INDEX { staWlanWlanpaIfc }
                   ::= {  staWlanWlanpaTable 1 }

StaWlanWlanpaEntry ::= SEQUENCE {
                   staWlanWlanpaIfc DisplayString,
                   staWlanWlanpaRadioband INTEGER,
                   staWlanWlanpaRadiochannel INTEGER,
                   staWlanWlanpa108mbpsmode INTEGER,
                   staWlanWlanpaNoiselevel INTEGER,
                   staWlanWlanpaModemload INTEGER,
                   staWlanWlanpaTransmitpower DisplayString,
                   staWlanWlanpaEirp DisplayString,
                   staWlanWlanpaExceirp INTEGER,
                   staWlanWlanpaBeaconperiod INTEGER,
                   staWlanWlanpaRegulatorydoma INTEGER,
                   staWlanWlanpaPhytype INTEGER,
                   staWlanWlanpaWepsupport INTEGER,
                   staWlanWlanpaTkipsupport INTEGER,
                   staWlanWlanpaAessupport INTEGER,
                   staWlanWlanpaMinimumrate INTEGER,
                   staWlanWlanpaMaximumrate INTEGER,
                   staWlanWlanpaTemperatureran INTEGER,
                   staWlanWlanpaPhyvariant DisplayString,
                   staWlanWlanpaSupportedbands INTEGER,
                   staWlanWlanpaSupports108mbp INTEGER,
                   staWlanWlanpaSupportsshortp INTEGER,
                   staWlanWlanpaSupportsshorts INTEGER,
                   staWlanWlanpaSupportscompre INTEGER
                  }

staWlanWlanpaIfc OBJECT-TYPE
                            SYNTAX DisplayString (SIZE(0..255))
                            MAX-ACCESS read-only
                            STATUS current
                            DESCRIPTION "Ifc"
                            ::= {  staWlanWlanpaEntry 1 }

staWlanWlanpaRadioband OBJECT-TYPE
                            SYNTAX INTEGER{
                              unknown(0),
                              e2-4ghz(1),
                              e5ghz(2),
                              e2-4ghz-5ghz(3)
                            }
                            MAX-ACCESS read-only
                            STATUS current
                            DESCRIPTION "Radio-Band"
                            ::= {  staWlanWlanpaEntry 11 }

staWlanWlanpaRadiochannel OBJECT-TYPE
                            SYNTAX INTEGER (0..255)
                            MAX-ACCESS read-only
                            STATUS current
                            DESCRIPTION "Radio-Channel"
                            ::= {  staWlanWlanpaEntry 3 }

staWlanWlanpa108mbpsmode OBJECT-TYPE
                            SYNTAX INTEGER{
                              no(0),
                              yes(1)
                            }
                            MAX-ACCESS read-only
                            STATUS current
                            DESCRIPTION "108Mbps-Mode"
                            ::= {  staWlanWlanpaEntry 16 }

staWlanWlanpaNoiselevel OBJECT-TYPE
                            SYNTAX INTEGER (-32768..32767)
                            MAX-ACCESS read-only
                            STATUS current
                            DESCRIPTION "Noise-Level"
                            ::= {  staWlanWlanpaEntry 13 }

staWlanWlanpaModemload OBJECT-TYPE
                            SYNTAX INTEGER (0..255)
                            MAX-ACCESS read-only
                            STATUS current
                            DESCRIPTION "Modem-Load"
                            ::= {  staWlanWlanpaEntry 24 }

staWlanWlanpaTransmitpower OBJECT-TYPE
                            SYNTAX DisplayString (SIZE(0..255))
                            MAX-ACCESS read-only
                            STATUS current
                            DESCRIPTION "Transmit-Power"
                            ::= {  staWlanWlanpaEntry 15 }

staWlanWlanpaEirp OBJECT-TYPE
                            SYNTAX DisplayString (SIZE(0..255))
                            MAX-ACCESS read-only
                            STATUS current
                            DESCRIPTION "EIRP"
                            ::= {  staWlanWlanpaEntry 22 }

staWlanWlanpaExceirp OBJECT-TYPE
                            SYNTAX INTEGER{
                              no(0),
                              yes(1)
                            }
                            MAX-ACCESS read-only
                            STATUS current
                            DESCRIPTION "Exc.-EIRP"
                            ::= {  staWlanWlanpaEntry 23 }

staWlanWlanpaBeaconperiod OBJECT-TYPE
                            SYNTAX INTEGER (0..65535)
                            MAX-ACCESS read-only
                            STATUS current
                            DESCRIPTION "Beacon-Period"
                            ::= {  staWlanWlanpaEntry 25 }

staWlanWlanpaRegulatorydoma OBJECT-TYPE
                            SYNTAX INTEGER{
                              undefined(0),
                              fcc(16),
                              canada(32),
                              eu-etsi(48),
                              spain(49),
                              france(50),
                              mkk-japan(64),
                              mkk2-japan(65),
                              israel(80),
                              world(96)
                            }
                            MAX-ACCESS read-only
                            STATUS current
                            DESCRIPTION "Regulatory-Domain"
                            ::= {  staWlanWlanpaEntry 4 }

staWlanWlanpaPhytype OBJECT-TYPE
                            SYNTAX INTEGER{
                              proprietary(0),
                              fhss(1),
                              dsss(2),
                              infrared(3),
                              ofdm(4),
                              hr-dsss(5),
                              erp(6),
                              ht(7),
                              pbcc(254)
                            }
                            MAX-ACCESS read-only
                            STATUS current
                            DESCRIPTION "PHY-Type"
                            ::= {  staWlanWlanpaEntry 5 }

staWlanWlanpaWepsupport OBJECT-TYPE
                            SYNTAX INTEGER{
                              no(0),
                              yes-40-bits(1),
                              yes-104-bits(2),
                              yes-128-bits(3)
                            }
                            MAX-ACCESS read-only
                            STATUS current
                            DESCRIPTION "WEP-Support"
                            ::= {  staWlanWlanpaEntry 7 }

staWlanWlanpaTkipsupport OBJECT-TYPE
                            SYNTAX INTEGER{
                              no(0),
                              yes(1)
                            }
                            MAX-ACCESS read-only
                            STATUS current
                            DESCRIPTION "TKIP-Support"
                            ::= {  staWlanWlanpaEntry 18 }

staWlanWlanpaAessupport OBJECT-TYPE
                            SYNTAX INTEGER{
                              no(0),
                              ocb(1),
                              ccm(2),
                              ocb-plus-ccm(3)
                            }
                            MAX-ACCESS read-only
                            STATUS current
                            DESCRIPTION "AES-Support"
                            ::= {  staWlanWlanpaEntry 19 }

staWlanWlanpaMinimumrate OBJECT-TYPE
                            SYNTAX INTEGER{
                              unknown(0),
                              e1m(1),
                              e2m(2),
                              e5m(3),
                              e5-5m(4),
                              e8m(5),
                              e11m(6),
                              e6m(12),
                              e9m(13),
                              e12m(14),
                              e18m(15),
                              e24m(16),
                              e36m(17),
                              e48m(18),
                              e54m(19),
                              t-12m(20),
                              t-18m(21),
                              t-24m(22),
                              t-36m(23),
                              t-48m(24),
                              t-72m(25),
                              t-96m(26),
                              t-108m(27),
                              ht-1-6-5m(28),
                              ht-1-13m(29),
                              ht-1-19-5m(30),
                              ht-1-26m(31),
                              ht-1-39m(32),
                              ht-1-52m(33),
                              ht-1-58-5m(34),
                              ht-1-65m(35),
                              ht-2-13m(36),
                              ht-2-26m(37),
                              ht-2-39m(38),
                              ht-2-52m(39),
                              ht-2-78m(40),
                              ht-2-104m(41),
                              ht-2-117m(42),
                              ht-2-130m(43)
                            }
                            MAX-ACCESS read-only
                            STATUS current
                            DESCRIPTION "Minimum-Rate"
                            ::= {  staWlanWlanpaEntry 21 }

staWlanWlanpaMaximumrate OBJECT-TYPE
                            SYNTAX INTEGER{
                              unknown(0),
                              e1m(1),
                              e2m(2),
                              e5m(3),
                              e5-5m(4),
                              e8m(5),
                              e11m(6),
                              e6m(12),
                              e9m(13),
                              e12m(14),
                              e18m(15),
                              e24m(16),
                              e36m(17),
                              e48m(18),
                              e54m(19),
                              t-12m(20),
                              t-18m(21),
                              t-24m(22),
                              t-36m(23),
                              t-48m(24),
                              t-72m(25),
                              t-96m(26),
                              t-108m(27),
                              ht-1-6-5m(28),
                              ht-1-13m(29),
                              ht-1-19-5m(30),
                              ht-1-26m(31),
                              ht-1-39m(32),
                              ht-1-52m(33),
                              ht-1-58-5m(34),
                              ht-1-65m(35),
                              ht-2-13m(36),
                              ht-2-26m(37),
                              ht-2-39m(38),
                              ht-2-52m(39),
                              ht-2-78m(40),
                              ht-2-104m(41),
                              ht-2-117m(42),
                              ht-2-130m(43)
                            }
                            MAX-ACCESS read-only
                            STATUS current
                            DESCRIPTION "Maximum-Rate"
                            ::= {  staWlanWlanpaEntry 8 }

staWlanWlanpaTemperatureran OBJECT-TYPE
                            SYNTAX INTEGER{
                              unknown(0),
                              commercial-0-plus-40-degree-c(1),
                              industrial-minus-30-plus-70-degree-c(2)
                            }
                            MAX-ACCESS read-only
                            STATUS current
                            DESCRIPTION "Temperature-Range"
                            ::= {  staWlanWlanpaEntry 9 }

staWlanWlanpaPhyvariant OBJECT-TYPE
                            SYNTAX DisplayString (SIZE(0..15))
                            MAX-ACCESS read-only
                            STATUS current
                            DESCRIPTION "PHY-Variant"
                            ::= {  staWlanWlanpaEntry 10 }

staWlanWlanpaSupportedbands OBJECT-TYPE
                            SYNTAX INTEGER{
                              unknown(0),
                              e2-4ghz(1),
                              e5ghz(2),
                              e2-4ghz-5ghz(3)
                            }
                            MAX-ACCESS read-only
                            STATUS current
                            DESCRIPTION "Supported-Bands"
                            ::= {  staWlanWlanpaEntry 12 }

staWlanWlanpaSupports108mbp OBJECT-TYPE
                            SYNTAX INTEGER{
                              no(0),
                              yes(1)
                            }
                            MAX-ACCESS read-only
                            STATUS current
                            DESCRIPTION "Supports-108Mbps-Mode"
                            ::= {  staWlanWlanpaEntry 27 }

staWlanWlanpaSupportsshortp OBJECT-TYPE
                            SYNTAX INTEGER{
                              no(0),
                              yes(1)
                            }
                            MAX-ACCESS read-only
                            STATUS current
                            DESCRIPTION "Supports-Short-Preamble"
                            ::= {  staWlanWlanpaEntry 14 }

staWlanWlanpaSupportsshorts OBJECT-TYPE
                            SYNTAX INTEGER{
                              no(0),
                              yes(1)
                            }
                            MAX-ACCESS read-only
                            STATUS current
                            DESCRIPTION "Supports-Short-Slot-Time"
                            ::= {  staWlanWlanpaEntry 17 }

staWlanWlanpaSupportscompre OBJECT-TYPE
                            SYNTAX INTEGER{
                              no(0),
                              yes(1)
                            }
                            MAX-ACCESS read-only
                            STATUS current
                            DESCRIPTION "Supports-Compression"
                            ::= {  staWlanWlanpaEntry 20 }

staWlanRadiosTable OBJECT-TYPE
                   SYNTAX SEQUENCE OF StaWlanRadiosEntry
                   MAX-ACCESS not-accessible
                   STATUS current
                   DESCRIPTION "Radios"
                   ::= {  staWlan 57 }

staWlanRadiosEntry OBJECT-TYPE
                   SYNTAX StaWlanRadiosEntry
                   MAX-ACCESS not-accessible
                   STATUS current
                   DESCRIPTION "entry in table"
                   INDEX { staWlanRadiosIfc }
                   ::= {  staWlanRadiosTable 1 }

StaWlanRadiosEntry ::= SEQUENCE {
                   staWlanRadiosIfc DisplayString,
                   staWlanRadiosRadioband INTEGER,
                   staWlanRadiosRadiochannel INTEGER,
                   staWlanRadios108mbpsmode INTEGER,
                   staWlanRadiosExtchannel INTEGER,
                   staWlanRadiosNoiselevel INTEGER,
                   staWlanRadiosModemload INTEGER,
                   staWlanRadiosTransmitpower DisplayString,
                   staWlanRadiosEirp DisplayString,
                   staWlanRadiosExceirp INTEGER,
                   staWlanRadiosBackgroundscan INTEGER,
                   staWlanRadiosBackgroundscanu INTEGER
                  }

staWlanRadiosIfc OBJECT-TYPE
                             SYNTAX DisplayString (SIZE(0..255))
                             MAX-ACCESS read-only
                             STATUS current
                             DESCRIPTION "Ifc"
                             ::= {  staWlanRadiosEntry 1 }

staWlanRadiosRadioband OBJECT-TYPE
                             SYNTAX INTEGER{
                               unknown(0),
                               e2-4ghz(1),
                               e5ghz(2),
                               e2-4ghz-5ghz(3)
                             }
                             MAX-ACCESS read-only
                             STATUS current
                             DESCRIPTION "Radio-Band"
                             ::= {  staWlanRadiosEntry 2 }

staWlanRadiosRadiochannel OBJECT-TYPE
                             SYNTAX INTEGER (0..255)
                             MAX-ACCESS read-only
                             STATUS current
                             DESCRIPTION "Radio-Channel"
                             ::= {  staWlanRadiosEntry 3 }

staWlanRadios108mbpsmode OBJECT-TYPE
                             SYNTAX INTEGER{
                               no(0),
                               yes(1)
                             }
                             MAX-ACCESS read-only
                             STATUS current
                             DESCRIPTION "108Mbps-Mode"
                             ::= {  staWlanRadiosEntry 4 }

staWlanRadiosExtchannel OBJECT-TYPE
                             SYNTAX INTEGER{
                               none(0),
                               above(1),
                               below(3)
                             }
                             MAX-ACCESS read-only
                             STATUS current
                             DESCRIPTION "Ext.-Channel"
                             ::= {  staWlanRadiosEntry 11 }

staWlanRadiosNoiselevel OBJECT-TYPE
                             SYNTAX INTEGER (-32768..32767)
                             MAX-ACCESS read-only
                             STATUS current
                             DESCRIPTION "Noise-Level"
                             ::= {  staWlanRadiosEntry 5 }

staWlanRadiosModemload OBJECT-TYPE
                             SYNTAX INTEGER (0..255)
                             MAX-ACCESS read-only
                             STATUS current
                             DESCRIPTION "Modem-Load"
                             ::= {  staWlanRadiosEntry 6 }

staWlanRadiosTransmitpower OBJECT-TYPE
                             SYNTAX DisplayString (SIZE(0..255))
                             MAX-ACCESS read-only
                             STATUS current
                             DESCRIPTION "Transmit-Power"
                             ::= {  staWlanRadiosEntry 7 }

staWlanRadiosEirp OBJECT-TYPE
                             SYNTAX DisplayString (SIZE(0..255))
                             MAX-ACCESS read-only
                             STATUS current
                             DESCRIPTION "EIRP"
                             ::= {  staWlanRadiosEntry 8 }

staWlanRadiosExceirp OBJECT-TYPE
                             SYNTAX INTEGER{
                               no(0),
                               yes(1)
                             }
                             MAX-ACCESS read-only
                             STATUS current
                             DESCRIPTION "Exc.-EIRP"
                             ::= {  staWlanRadiosEntry 9 }

staWlanRadiosBackgroundscan OBJECT-TYPE
                             SYNTAX INTEGER (0..2147483647)
                             MAX-ACCESS read-only
                             STATUS current
                             DESCRIPTION "Background-Scan"
                             ::= {  staWlanRadiosEntry 10 }

staWlanRadiosBackgroundscanu OBJECT-TYPE
                             SYNTAX INTEGER{
                               seconds(0),
                               milliseconds(1),
                               microseconds(2),
                               minutes(3),
                               hours(4),
                               days(5),
                               weeks(6),
                               fortnights(7)
                             }
                             MAX-ACCESS read-only
                             STATUS current
                             DESCRIPTION "Background-Scan-Unit"
                             ::= {  staWlanRadiosEntry 12 }

staWlanScanreTable OBJECT-TYPE
                   SYNTAX SEQUENCE OF StaWlanScanreEntry
                   MAX-ACCESS not-accessible
                   STATUS current
                   DESCRIPTION "Scan-Results"
                   ::= {  staWlan 34 }

staWlanScanreEntry OBJECT-TYPE
                   SYNTAX StaWlanScanreEntry
                   MAX-ACCESS not-accessible
                   STATUS current
                   DESCRIPTION "entry in table"
                   INDEX { staWlanScanreBssid, staWlanScanreInterf }
                   ::= {  staWlanScanreTable 1 }

StaWlanScanreEntry ::= SEQUENCE {
                   staWlanScanreBssid MacAddress,
                   staWlanScanreInterf INTEGER,
                   staWlanScanreNetwor DisplayString,
                   staWlanScanreOperat INTEGER,
                   staWlanScanreEncryp INTEGER,
                   staWlanScanreBeacon INTEGER,
                   staWlanScanreDtimpe INTEGER,
                   staWlanScanrePcffun INTEGER,
                   staWlanScanreQos INTEGER,
                   staWlanScanreMaxamp INTEGER,
                   staWlanScanreMaxams INTEGER,
                   staWlanScanreRadiob INTEGER,
                   staWlanScanreRadioc INTEGER,
                   staWlanScanre108mbp INTEGER,
                   staWlanScanreExtcha INTEGER,
                   staWlanScanrePhysig INTEGER,
                   staWlanScanreSignal INTEGER,
                   staWlanScanreNoisel INTEGER,
                   staWlanScanreLoad DisplayString,
                   staWlanScanreShortp INTEGER,
                   staWlanScanreShorts INTEGER,
                   staWlanScanre40mhzm INTEGER,
                   staWlanScanre40mhzi INTEGER,
                   staWlanScanreShortg INTEGER,
                   staWlanScanreCompre INTEGER,
                   staWlanScanreAge INTEGER,
                   staWlanScanreRate INTEGER,
                   staWlanScanreNonerp INTEGER,
                   staWlanScanreIdenti DisplayString,
                   staWlanScanreInterp DisplayString
                  }

staWlanScanreBssid OBJECT-TYPE
                    SYNTAX MacAddress
                    MAX-ACCESS read-only
                    STATUS current
                    DESCRIPTION "BSSID"
                    ::= {  staWlanScanreEntry 1 }

staWlanScanreInterf OBJECT-TYPE
                    SYNTAX INTEGER{
                      wlan-1(0),
                      wlan-2(1),
                      wlan-3(2)
                    }
                    MAX-ACCESS read-only
                    STATUS current
                    DESCRIPTION "Interface"
                    ::= {  staWlanScanreEntry 15 }

staWlanScanreNetwor OBJECT-TYPE
                    SYNTAX DisplayString (SIZE(0..32))
                    MAX-ACCESS read-only
                    STATUS current
                    DESCRIPTION "Network-Name"
                    ::= {  staWlanScanreEntry 2 }

staWlanScanreOperat OBJECT-TYPE
                    SYNTAX INTEGER{
                      none(0),
                      adhoc(1),
                      infrastructure(2)
                    }
                    MAX-ACCESS read-only
                    STATUS current
                    DESCRIPTION "Operation-Mode"
                    ::= {  staWlanScanreEntry 3 }

staWlanScanreEncryp OBJECT-TYPE
                    SYNTAX INTEGER{
                      none(0),
                      wep(1),
                      tkip(2),
                      aes(3),
                      aes-plus-tkip(4)
                    }
                    MAX-ACCESS read-only
                    STATUS current
                    DESCRIPTION "Encryption"
                    ::= {  staWlanScanreEntry 13 }

staWlanScanreBeacon OBJECT-TYPE
                    SYNTAX INTEGER (0..65535)
                    MAX-ACCESS read-only
                    STATUS current
                    DESCRIPTION "Beacon-Period"
                    ::= {  staWlanScanreEntry 6 }

staWlanScanreDtimpe OBJECT-TYPE
                    SYNTAX INTEGER (0..65535)
                    MAX-ACCESS read-only
                    STATUS current
                    DESCRIPTION "DTIM-Period"
                    ::= {  staWlanScanreEntry 7 }

staWlanScanrePcffun OBJECT-TYPE
                    SYNTAX INTEGER{
                      none(0),
                      delivery(1),
                      delivery-plus-polling(2)
                    }
                    MAX-ACCESS read-only
                    STATUS current
                    DESCRIPTION "PCF-Functionality"
                    ::= {  staWlanScanreEntry 22 }

staWlanScanreQos OBJECT-TYPE
                    SYNTAX INTEGER{
                      no(0),
                      yes(1)
                    }
                    MAX-ACCESS read-only
                    STATUS current
                    DESCRIPTION "QoS"
                    ::= {  staWlanScanreEntry 24 }

staWlanScanreMaxamp OBJECT-TYPE
                    SYNTAX INTEGER (0..2147483647)
                    MAX-ACCESS read-only
                    STATUS current
                    DESCRIPTION "Max-A-MPDU-Len"
                    ::= {  staWlanScanreEntry 32 }

staWlanScanreMaxams OBJECT-TYPE
                    SYNTAX INTEGER (0..2147483647)
                    MAX-ACCESS read-only
                    STATUS current
                    DESCRIPTION "Max-A-MSDU-Len"
                    ::= {  staWlanScanreEntry 33 }

staWlanScanreRadiob OBJECT-TYPE
                    SYNTAX INTEGER{
                      unknown(0),
                      e2-4ghz(1),
                      e5ghz(2),
                      e2-4ghz-5ghz(3)
                    }
                    MAX-ACCESS read-only
                    STATUS current
                    DESCRIPTION "Radio-Band"
                    ::= {  staWlanScanreEntry 16 }

staWlanScanreRadioc OBJECT-TYPE
                    SYNTAX INTEGER (0..255)
                    MAX-ACCESS read-only
                    STATUS current
                    DESCRIPTION "Radio-Channel"
                    ::= {  staWlanScanreEntry 8 }

staWlanScanre108mbp OBJECT-TYPE
                    SYNTAX INTEGER{
                      no(0),
                      yes(1)
                    }
                    MAX-ACCESS read-only
                    STATUS current
                    DESCRIPTION "108Mbps-Mode"
                    ::= {  staWlanScanreEntry 17 }

staWlanScanreExtcha OBJECT-TYPE
                    SYNTAX INTEGER{
                      none(0),
                      above(1),
                      below(3)
                    }
                    MAX-ACCESS read-only
                    STATUS current
                    DESCRIPTION "Ext.-Channel"
                    ::= {  staWlanScanreEntry 28 }

staWlanScanrePhysig OBJECT-TYPE
                    SYNTAX INTEGER (0..65535)
                    MAX-ACCESS read-only
                    STATUS current
                    DESCRIPTION "Phy-Signal"
                    ::= {  staWlanScanreEntry 10 }

staWlanScanreSignal OBJECT-TYPE
                    SYNTAX INTEGER (-32768..32767)
                    MAX-ACCESS read-only
                    STATUS current
                    DESCRIPTION "Signal-Level"
                    ::= {  staWlanScanreEntry 26 }

staWlanScanreNoisel OBJECT-TYPE
                    SYNTAX INTEGER (-128..127)
                    MAX-ACCESS read-only
                    STATUS current
                    DESCRIPTION "Noise-Level"
                    ::= {  staWlanScanreEntry 11 }

staWlanScanreLoad OBJECT-TYPE
                    SYNTAX DisplayString (SIZE(0..255))
                    MAX-ACCESS read-only
                    STATUS current
                    DESCRIPTION "Load"
                    ::= {  staWlanScanreEntry 12 }

staWlanScanreShortp OBJECT-TYPE
                    SYNTAX INTEGER{
                      no(0),
                      yes(1)
                    }
                    MAX-ACCESS read-only
                    STATUS current
                    DESCRIPTION "Short-Preamble"
                    ::= {  staWlanScanreEntry 14 }

staWlanScanreShorts OBJECT-TYPE
                    SYNTAX INTEGER{
                      no(0),
                      yes(1)
                    }
                    MAX-ACCESS read-only
                    STATUS current
                    DESCRIPTION "Short-Slot-Time"
                    ::= {  staWlanScanreEntry 18 }

staWlanScanre40mhzm OBJECT-TYPE
                    SYNTAX INTEGER{
                      no(0),
                      yes(1)
                    }
                    MAX-ACCESS read-only
                    STATUS current
                    DESCRIPTION "40MHz-Mode"
                    ::= {  staWlanScanreEntry 29 }

staWlanScanre40mhzi OBJECT-TYPE
                    SYNTAX INTEGER{
                      no(0),
                      yes(1)
                    }
                    MAX-ACCESS read-only
                    STATUS current
                    DESCRIPTION "40MHz-Intolerant"
                    ::= {  staWlanScanreEntry 30 }

staWlanScanreShortg OBJECT-TYPE
                    SYNTAX INTEGER{
                      no(0),
                      e20mhz(1),
                      e40mhz(2),
                      e20-40mhz(3)
                    }
                    MAX-ACCESS read-only
                    STATUS current
                    DESCRIPTION "Short-Guard-Interval"
                    ::= {  staWlanScanreEntry 27 }

staWlanScanreCompre OBJECT-TYPE
                    SYNTAX INTEGER{
                      no(0),
                      yes(1)
                    }
                    MAX-ACCESS read-only
                    STATUS current
                    DESCRIPTION "Compression"
                    ::= {  staWlanScanreEntry 21 }

staWlanScanreAge OBJECT-TYPE
                    SYNTAX INTEGER (0..2147483647)
                    MAX-ACCESS read-only
                    STATUS current
                    DESCRIPTION "Age"
                    ::= {  staWlanScanreEntry 25 }

staWlanScanreRate OBJECT-TYPE
                    SYNTAX INTEGER{
                      unknown(0),
                      e1m(1),
                      e2m(2),
                      e5m(3),
                      e5-5m(4),
                      e8m(5),
                      e11m(6),
                      e6m(12),
                      e9m(13),
                      e12m(14),
                      e18m(15),
                      e24m(16),
                      e36m(17),
                      e48m(18),
                      e54m(19),
                      t-12m(20),
                      t-18m(21),
                      t-24m(22),
                      t-36m(23),
                      t-48m(24),
                      t-72m(25),
                      t-96m(26),
                      t-108m(27),
                      ht-1-6-5m(28),
                      ht-1-13m(29),
                      ht-1-19-5m(30),
                      ht-1-26m(31),
                      ht-1-39m(32),
                      ht-1-52m(33),
                      ht-1-58-5m(34),
                      ht-1-65m(35),
                      ht-2-13m(36),
                      ht-2-26m(37),
                      ht-2-39m(38),
                      ht-2-52m(39),
                      ht-2-78m(40),
                      ht-2-104m(41),
                      ht-2-117m(42),
                      ht-2-130m(43)
                    }
                    MAX-ACCESS read-only
                    STATUS current
                    DESCRIPTION "Rate"
                    ::= {  staWlanScanreEntry 19 }

staWlanScanreNonerp OBJECT-TYPE
                    SYNTAX INTEGER{
                      no(0),
                      yes(1)
                    }
                    MAX-ACCESS read-only
                    STATUS current
                    DESCRIPTION "NonERP-Present"
                    ::= {  staWlanScanreEntry 20 }

staWlanScanreIdenti OBJECT-TYPE
                    SYNTAX DisplayString (SIZE(0..16))
                    MAX-ACCESS read-only
                    STATUS current
                    DESCRIPTION "Identification"
                    ::= {  staWlanScanreEntry 23 }

staWlanScanreInterp OBJECT-TYPE
                    SYNTAX DisplayString (SIZE(0..16))
                    MAX-ACCESS read-only
                    STATUS current
                    DESCRIPTION "Interpoint-Peer-Name"
                    ::= {  staWlanScanreEntry 31 }

staWlanInterp OBJECT IDENTIFIER ::= { staWlan 36}
staWlanInterpAccTable OBJECT-TYPE
                      SYNTAX SEQUENCE OF StaWlanInterpAccEntry
                      MAX-ACCESS not-accessible
                      STATUS current
                      DESCRIPTION "Accesspoint-List"
                      ::= {  staWlanInterp 1 }

staWlanInterpAccEntry OBJECT-TYPE
                      SYNTAX StaWlanInterpAccEntry
                      MAX-ACCESS not-accessible
                      STATUS current
                      DESCRIPTION "entry in table"
                      INDEX { staWlanInterpAccIndex }
                      ::= {  staWlanInterpAccTable 1 }

StaWlanInterpAccEntry ::= SEQUENCE {
                      staWlanInterpAccIndex INTEGER,
                      staWlanInterpAccMacadd MacAddress,
                      staWlanInterpAccRxphys INTEGER,
                      staWlanInterpAccTxrate INTEGER,
                      staWlanInterpAccRxrate INTEGER,
                      staWlanInterpAccLinkph INTEGER,
                      staWlanInterpAccAntenn INTEGER,
                      staWlanInterpAccIdenti DisplayString,
                      staWlanInterpAccInterp DisplayString,
                      staWlanInterpAccQos INTEGER,
                      staWlanInterpAccShortp INTEGER,
                      staWlanInterpAccCompre INTEGER,
                      staWlanInterpAccKeyhan INTEGER,
                      staWlanInterpAccKeying INTEGER,
                      staWlanInterpAccWpaver INTEGER,
                      staWlanInterpAccTxbyte Counter64,
                      staWlanInterpAccRxbyte Counter64,
                      staWlanInterpAccThroug DisplayString,
                      staWlanInterpAccMaxthr DisplayString,
                      staWlanInterpAccBytest INTEGER,
                      staWlanInterpAccBytesm INTEGER,
                      staWlanInterpAccTxpack INTEGER,
                      staWlanInterpAccRxpack INTEGER,
                      staWlanInterpAccTxlimi INTEGER,
                      staWlanInterpAccRxlimi INTEGER
                     }

staWlanInterpAccIndex OBJECT-TYPE
                       SYNTAX INTEGER{
                         p2p-1-1(1),
                         p2p-1-2(2),
                         p2p-1-3(3),
                         p2p-1-4(4),
                         p2p-1-5(5),
                         p2p-1-6(6)
                       }
                       MAX-ACCESS read-only
                       STATUS current
                       DESCRIPTION "Index"
                       ::= {  staWlanInterpAccEntry 1 }

staWlanInterpAccMacadd OBJECT-TYPE
                       SYNTAX MacAddress
                       MAX-ACCESS read-only
                       STATUS current
                       DESCRIPTION "MAC-Address"
                       ::= {  staWlanInterpAccEntry 2 }

staWlanInterpAccRxphys OBJECT-TYPE
                       SYNTAX INTEGER (0..65535)
                       MAX-ACCESS read-only
                       STATUS current
                       DESCRIPTION "Rx-Phy-Signal"
                       ::= {  staWlanInterpAccEntry 13 }

staWlanInterpAccTxrate OBJECT-TYPE
                       SYNTAX INTEGER{
                         unknown(0),
                         e1m(1),
                         e2m(2),
                         e5m(3),
                         e5-5m(4),
                         e8m(5),
                         e11m(6),
                         e6m(8),
                         e9m(9),
                         e12m(10),
                         e18m(11),
                         e24m(12),
                         e36m(13),
                         e48m(14),
                         e54m(15),
                         t-12m(20),
                         t-18m(21),
                         t-24m(22),
                         t-36m(23),
                         t-48m(24),
                         t-72m(25),
                         t-96m(26),
                         t-108m(27)
                       }
                       MAX-ACCESS read-only
                       STATUS current
                       DESCRIPTION "Tx-Rate"
                       ::= {  staWlanInterpAccEntry 16 }

staWlanInterpAccRxrate OBJECT-TYPE
                       SYNTAX INTEGER{
                         unknown(0),
                         e1m(1),
                         e2m(2),
                         e5m(3),
                         e5-5m(4),
                         e8m(5),
                         e11m(6),
                         e6m(8),
                         e9m(9),
                         e12m(10),
                         e18m(11),
                         e24m(12),
                         e36m(13),
                         e48m(14),
                         e54m(15),
                         t-12m(20),
                         t-18m(21),
                         t-24m(22),
                         t-36m(23),
                         t-48m(24),
                         t-72m(25),
                         t-96m(26),
                         t-108m(27)
                       }
                       MAX-ACCESS read-only
                       STATUS current
                       DESCRIPTION "Rx-Rate"
                       ::= {  staWlanInterpAccEntry 5 }

staWlanInterpAccLinkph OBJECT-TYPE
                       SYNTAX INTEGER (0..65535)
                       MAX-ACCESS read-only
                       STATUS current
                       DESCRIPTION "Link-Phy-Signal"
                       ::= {  staWlanInterpAccEntry 14 }

staWlanInterpAccAntenn OBJECT-TYPE
                       SYNTAX INTEGER (0..255)
                       MAX-ACCESS read-only
                       STATUS current
                       DESCRIPTION "Antenna"
                       ::= {  staWlanInterpAccEntry 11 }

staWlanInterpAccIdenti OBJECT-TYPE
                       SYNTAX DisplayString (SIZE(0..24))
                       MAX-ACCESS read-only
                       STATUS current
                       DESCRIPTION "Identification"
                       ::= {  staWlanInterpAccEntry 15 }

staWlanInterpAccInterp OBJECT-TYPE
                       SYNTAX DisplayString (SIZE(0..16))
                       MAX-ACCESS read-only
                       STATUS current
                       DESCRIPTION "Interpoint-Peer-Name"
                       ::= {  staWlanInterpAccEntry 28 }

staWlanInterpAccQos OBJECT-TYPE
                       SYNTAX INTEGER{
                         no(0),
                         yes(1)
                       }
                       MAX-ACCESS read-only
                       STATUS current
                       DESCRIPTION "QoS"
                       ::= {  staWlanInterpAccEntry 27 }

staWlanInterpAccShortp OBJECT-TYPE
                       SYNTAX INTEGER{
                         no(0),
                         yes(1)
                       }
                       MAX-ACCESS read-only
                       STATUS current
                       DESCRIPTION "Short-Preamble"
                       ::= {  staWlanInterpAccEntry 32 }

staWlanInterpAccCompre OBJECT-TYPE
                       SYNTAX INTEGER{
                         none(0),
                         inactive(1),
                         active(2)
                       }
                       MAX-ACCESS read-only
                       STATUS current
                       DESCRIPTION "Compression"
                       ::= {  staWlanInterpAccEntry 9 }

staWlanInterpAccKeyhan OBJECT-TYPE
                       SYNTAX INTEGER{
                         none(0),
                         supplicant(1),
                         authenticator(2)
                       }
                       MAX-ACCESS read-only
                       STATUS current
                       DESCRIPTION "Key-Handshake-Role"
                       ::= {  staWlanInterpAccEntry 24 }

staWlanInterpAccKeying OBJECT-TYPE
                       SYNTAX INTEGER{
                         idle(0),
                         pending(1),
                         done(2)
                       }
                       MAX-ACCESS read-only
                       STATUS current
                       DESCRIPTION "Keying-State"
                       ::= {  staWlanInterpAccEntry 12 }

staWlanInterpAccWpaver OBJECT-TYPE
                       SYNTAX INTEGER{
                         wpa1(1),
                         wpa2(2),
                         none(0)
                       }
                       MAX-ACCESS read-only
                       STATUS current
                       DESCRIPTION "WPA-Version"
                       ::= {  staWlanInterpAccEntry 21 }

staWlanInterpAccTxbyte OBJECT-TYPE
                       SYNTAX Counter64
                       MAX-ACCESS read-only
                       STATUS current
                       DESCRIPTION "Tx-Bytes"
                       ::= {  staWlanInterpAccEntry 6 }

staWlanInterpAccRxbyte OBJECT-TYPE
                       SYNTAX Counter64
                       MAX-ACCESS read-only
                       STATUS current
                       DESCRIPTION "Rx-Bytes"
                       ::= {  staWlanInterpAccEntry 7 }

staWlanInterpAccThroug OBJECT-TYPE
                       SYNTAX DisplayString (SIZE(0..255))
                       MAX-ACCESS read-only
                       STATUS current
                       DESCRIPTION "Throughput"
                       ::= {  staWlanInterpAccEntry 8 }

staWlanInterpAccMaxthr OBJECT-TYPE
                       SYNTAX DisplayString (SIZE(0..255))
                       MAX-ACCESS read-only
                       STATUS current
                       DESCRIPTION "Max.-Throughput"
                       ::= {  staWlanInterpAccEntry 17 }

staWlanInterpAccBytest OBJECT-TYPE
                       SYNTAX INTEGER (0..2147483647)
                       MAX-ACCESS read-only
                       STATUS current
                       DESCRIPTION "Bytes-Throughput"
                       ::= {  staWlanInterpAccEntry 19 }

staWlanInterpAccBytesm OBJECT-TYPE
                       SYNTAX INTEGER (0..2147483647)
                       MAX-ACCESS read-only
                       STATUS current
                       DESCRIPTION "Bytes-Max.-Throughput"
                       ::= {  staWlanInterpAccEntry 20 }

staWlanInterpAccTxpack OBJECT-TYPE
                       SYNTAX INTEGER (0..2147483647)
                       MAX-ACCESS read-only
                       STATUS current
                       DESCRIPTION "Tx-Packets"
                       ::= {  staWlanInterpAccEntry 25 }

staWlanInterpAccRxpack OBJECT-TYPE
                       SYNTAX INTEGER (0..2147483647)
                       MAX-ACCESS read-only
                       STATUS current
                       DESCRIPTION "Rx-Packets"
                       ::= {  staWlanInterpAccEntry 26 }

staWlanInterpAccTxlimi OBJECT-TYPE
                       SYNTAX INTEGER (0..2147483647)
                       MAX-ACCESS read-only
                       STATUS current
                       DESCRIPTION "Tx-Limit"
                       ::= {  staWlanInterpAccEntry 22 }

staWlanInterpAccRxlimi OBJECT-TYPE
                       SYNTAX INTEGER (0..2147483647)
                       MAX-ACCESS read-only
                       STATUS current
                       DESCRIPTION "Rx-Limit"
                       ::= {  staWlanInterpAccEntry 23 }

staWlanInterpKeyTable OBJECT-TYPE
                      SYNTAX SEQUENCE OF StaWlanInterpKeyEntry
                      MAX-ACCESS not-accessible
                      STATUS current
                      DESCRIPTION "Key-List"
                      ::= {  staWlanInterp 3 }

staWlanInterpKeyEntry OBJECT-TYPE
                      SYNTAX StaWlanInterpKeyEntry
                      MAX-ACCESS not-accessible
                      STATUS current
                      DESCRIPTION "entry in table"
                      INDEX { staWlanInterpKeyInde }
                      ::= {  staWlanInterpKeyTable 1 }

StaWlanInterpKeyEntry ::= SEQUENCE {
                      staWlanInterpKeyInde INTEGER,
                      staWlanInterpKeySour INTEGER,
                      staWlanInterpKeyKeyt INTEGER,
                      staWlanInterpKeyKeyv DisplayString,
                      staWlanInterpKeyTsc DisplayString,
                      staWlanInterpKeyRsc DisplayString
                     }

staWlanInterpKeyInde OBJECT-TYPE
                     SYNTAX INTEGER{
                       p2p-1-1(1),
                       p2p-1-2(2),
                       p2p-1-3(3),
                       p2p-1-4(4),
                       p2p-1-5(5),
                       p2p-1-6(6)
                     }
                     MAX-ACCESS read-only
                     STATUS current
                     DESCRIPTION "Index"
                     ::= {  staWlanInterpKeyEntry 1 }

staWlanInterpKeySour OBJECT-TYPE
                     SYNTAX INTEGER{
                       none(0),
                       static(1),
                       dynamic(2)
                     }
                     MAX-ACCESS read-only
                     STATUS current
                     DESCRIPTION "Source"
                     ::= {  staWlanInterpKeyEntry 2 }

staWlanInterpKeyKeyt OBJECT-TYPE
                     SYNTAX INTEGER{
                       none(0),
                       unknown(1),
                       wep-40-bits(5),
                       wep-104-bits(13),
                       wep-128-bits(16),
                       tkip(64),
                       aes-ocb(65),
                       aes-ccm(66)
                     }
                     MAX-ACCESS read-only
                     STATUS current
                     DESCRIPTION "Key-Type"
                     ::= {  staWlanInterpKeyEntry 3 }

staWlanInterpKeyKeyv OBJECT-TYPE
                     SYNTAX DisplayString (SIZE(0..255))
                     MAX-ACCESS read-only
                     STATUS current
                     DESCRIPTION "Key-Value"
                     ::= {  staWlanInterpKeyEntry 4 }

staWlanInterpKeyTsc OBJECT-TYPE
                     SYNTAX DisplayString (SIZE(0..255))
                     MAX-ACCESS read-only
                     STATUS current
                     DESCRIPTION "TSC"
                     ::= {  staWlanInterpKeyEntry 5 }

staWlanInterpKeyRsc OBJECT-TYPE
                     SYNTAX DisplayString (SIZE(0..255))
                     MAX-ACCESS read-only
                     STATUS current
                     DESCRIPTION "RSC"
                     ::= {  staWlanInterpKeyEntry 6 }

staWlanIapptaTable OBJECT-TYPE
                   SYNTAX SEQUENCE OF StaWlanIapptaEntry
                   MAX-ACCESS not-accessible
                   STATUS current
                   DESCRIPTION "IAPP-Table"
                   ::= {  staWlan 38 }

staWlanIapptaEntry OBJECT-TYPE
                   SYNTAX StaWlanIapptaEntry
                   MAX-ACCESS not-accessible
                   STATUS current
                   DESCRIPTION "entry in table"
                   INDEX { staWlanIapptaBssid, staWlanIapptaIpadd, staWlanIapptaNetwo }
                   ::= {  staWlanIapptaTable 1 }

StaWlanIapptaEntry ::= SEQUENCE {
                   staWlanIapptaBssid MacAddress,
                   staWlanIapptaIpadd IpAddress,
                   staWlanIapptaNetwo DisplayString,
                   staWlanIapptaTimer INTEGER,
                   staWlanIapptaTimeo INTEGER,
                   staWlanIapptaCapab BITS
                  }

staWlanIapptaBssid OBJECT-TYPE
                   SYNTAX MacAddress
                   MAX-ACCESS read-only
                   STATUS current
                   DESCRIPTION "BSSID"
                   ::= {  staWlanIapptaEntry 2 }

staWlanIapptaIpadd OBJECT-TYPE
                   SYNTAX IpAddress
                   MAX-ACCESS read-only
                   STATUS current
                   DESCRIPTION "IP-Address"
                   ::= {  staWlanIapptaEntry 1 }

staWlanIapptaNetwo OBJECT-TYPE
                   SYNTAX DisplayString (SIZE(0..16))
                   MAX-ACCESS read-only
                   STATUS current
                   DESCRIPTION "Network-name"
                   ::= {  staWlanIapptaEntry 6 }

staWlanIapptaTimer OBJECT-TYPE
                   SYNTAX INTEGER (0..65535)
                   MAX-ACCESS read-only
                   STATUS current
                   DESCRIPTION "Timer"
                   ::= {  staWlanIapptaEntry 3 }

staWlanIapptaTimeo OBJECT-TYPE
                   SYNTAX INTEGER (0..65535)
                   MAX-ACCESS read-only
                   STATUS current
                   DESCRIPTION "Timeout"
                   ::= {  staWlanIapptaEntry 4 }

staWlanIapptaCapab OBJECT-TYPE
                   SYNTAX BITS{
                     wep(32),
                     forward(64)
                   }
                   MAX-ACCESS read-only
                   STATUS current
                   DESCRIPTION "Capabilities"
                   ::= {  staWlanIapptaEntry 5 }

staWlanForeigTable OBJECT-TYPE
                   SYNTAX SEQUENCE OF StaWlanForeigEntry
                   MAX-ACCESS not-accessible
                   STATUS current
                   DESCRIPTION "Foreign-Stations"
                   ::= {  staWlan 40 }

staWlanForeigEntry OBJECT-TYPE
                   SYNTAX StaWlanForeigEntry
                   MAX-ACCESS not-accessible
                   STATUS current
                   DESCRIPTION "entry in table"
                   INDEX { staWlanForeigMac }
                   ::= {  staWlanForeigTable 1 }

StaWlanForeigEntry ::= SEQUENCE {
                   staWlanForeigMac MacAddress
                  }

staWlanForeigMac OBJECT-TYPE
                 SYNTAX MacAddress
                 MAX-ACCESS read-only
                 STATUS current
                 DESCRIPTION "MAC-Address"
                 ::= {  staWlanForeigEntry 1 }

staWlanGroupeTable OBJECT-TYPE
                   SYNTAX SEQUENCE OF StaWlanGroupeEntry
                   MAX-ACCESS not-accessible
                   STATUS current
                   DESCRIPTION "Group-Encryption-Keys"
                   ::= {  staWlan 41 }

staWlanGroupeEntry OBJECT-TYPE
                   SYNTAX StaWlanGroupeEntry
                   MAX-ACCESS not-accessible
                   STATUS current
                   DESCRIPTION "entry in table"
                   INDEX { staWlanGroupeInde }
                   ::= {  staWlanGroupeTable 1 }

StaWlanGroupeEntry ::= SEQUENCE {
                   staWlanGroupeInde DisplayString,
                   staWlanGroupeSour INTEGER,
                   staWlanGroupeKeyt INTEGER,
                   staWlanGroupeKeyv DisplayString,
                   staWlanGroupeTsc DisplayString,
                   staWlanGroupeRsc DisplayString
                  }

staWlanGroupeInde OBJECT-TYPE
                  SYNTAX DisplayString (SIZE(0..255))
                  MAX-ACCESS read-only
                  STATUS current
                  DESCRIPTION "Index"
                  ::= {  staWlanGroupeEntry 1 }

staWlanGroupeSour OBJECT-TYPE
                  SYNTAX INTEGER{
                    none(0),
                    static(1),
                    dynamic(2)
                  }
                  MAX-ACCESS read-only
                  STATUS current
                  DESCRIPTION "Source"
                  ::= {  staWlanGroupeEntry 2 }

staWlanGroupeKeyt OBJECT-TYPE
                  SYNTAX INTEGER{
                    none(0),
                    unknown(1),
                    wep-40-bits(5),
                    wep-104-bits(13),
                    wep-128-bits(16),
                    tkip(64),
                    aes-ocb(65),
                    aes-ccm(66)
                  }
                  MAX-ACCESS read-only
                  STATUS current
                  DESCRIPTION "Key-Type"
                  ::= {  staWlanGroupeEntry 3 }

staWlanGroupeKeyv OBJECT-TYPE
                  SYNTAX DisplayString (SIZE(0..255))
                  MAX-ACCESS read-only
                  STATUS current
                  DESCRIPTION "Key-Value"
                  ::= {  staWlanGroupeEntry 4 }

staWlanGroupeTsc OBJECT-TYPE
                  SYNTAX DisplayString (SIZE(0..255))
                  MAX-ACCESS read-only
                  STATUS current
                  DESCRIPTION "TSC"
                  ::= {  staWlanGroupeEntry 5 }

staWlanGroupeRsc OBJECT-TYPE
                  SYNTAX DisplayString (SIZE(0..255))
                  MAX-ACCESS read-only
                  STATUS current
                  DESCRIPTION "RSC"
                  ::= {  staWlanGroupeEntry 6 }

staWlanChanneTable OBJECT-TYPE
                   SYNTAX SEQUENCE OF StaWlanChanneEntry
                   MAX-ACCESS not-accessible
                   STATUS current
                   DESCRIPTION "Channel-Scan-Results"
                   ::= {  staWlan 42 }

staWlanChanneEntry OBJECT-TYPE
                   SYNTAX StaWlanChanneEntry
                   MAX-ACCESS not-accessible
                   STATUS current
                   DESCRIPTION "entry in table"
                   INDEX { staWlanChanneRadiob, staWlanChanneRadioc }
                   ::= {  staWlanChanneTable 1 }

StaWlanChanneEntry ::= SEQUENCE {
                   staWlanChanneRadiob INTEGER,
                   staWlanChanneRadioc INTEGER,
                   staWlanChanne108mbp INTEGER,
                   staWlanChanneInterf INTEGER,
                   staWlanChanneDfssta INTEGER,
                   staWlanChanneRemtim INTEGER,
                   staWlanChanneScanne INTEGER,
                   staWlanChanneNoisel INTEGER,
                   staWlanChanneNumbss INTEGER,
                   staWlanChannePulsec INTEGER,
                   staWlanChanneRadard INTEGER,
                   staWlanChanneRadarp DisplayString
                  }

staWlanChanneRadiob OBJECT-TYPE
                    SYNTAX INTEGER{
                      unknown(0),
                      e2-4ghz(1),
                      e5ghz(2),
                      e2-4ghz-5ghz(3)
                    }
                    MAX-ACCESS read-only
                    STATUS current
                    DESCRIPTION "Radio-Band"
                    ::= {  staWlanChanneEntry 9 }

staWlanChanneRadioc OBJECT-TYPE
                    SYNTAX INTEGER (0..255)
                    MAX-ACCESS read-only
                    STATUS current
                    DESCRIPTION "Radio-Channel"
                    ::= {  staWlanChanneEntry 1 }

staWlanChanne108mbp OBJECT-TYPE
                    SYNTAX INTEGER{
                      no(0),
                      yes(1)
                    }
                    MAX-ACCESS read-only
                    STATUS current
                    DESCRIPTION "108Mbps-Mode"
                    ::= {  staWlanChanneEntry 8 }

staWlanChanneInterf OBJECT-TYPE
                    SYNTAX INTEGER{
                      wlan-1(0),
                      wlan-2(1),
                      wlan-3(2)
                    }
                    MAX-ACCESS read-only
                    STATUS current
                    DESCRIPTION "Interface"
                    ::= {  staWlanChanneEntry 2 }

staWlanChanneDfssta OBJECT-TYPE
                    SYNTAX INTEGER{
                      unknown(2),
                      clear(0),
                      blocked(1)
                    }
                    MAX-ACCESS read-only
                    STATUS current
                    DESCRIPTION "DFS-State"
                    ::= {  staWlanChanneEntry 12 }

staWlanChanneRemtim OBJECT-TYPE
                    SYNTAX INTEGER (0..2147483647)
                    MAX-ACCESS read-only
                    STATUS current
                    DESCRIPTION "Rem.-Time"
                    ::= {  staWlanChanneEntry 11 }

staWlanChanneScanne OBJECT-TYPE
                    SYNTAX INTEGER{
                      no(0),
                      yes(1)
                    }
                    MAX-ACCESS read-only
                    STATUS current
                    DESCRIPTION "Scanned"
                    ::= {  staWlanChanneEntry 3 }

staWlanChanneNoisel OBJECT-TYPE
                    SYNTAX INTEGER (-128..127)
                    MAX-ACCESS read-only
                    STATUS current
                    DESCRIPTION "Noise-Level"
                    ::= {  staWlanChanneEntry 4 }

staWlanChanneNumbss OBJECT-TYPE
                    SYNTAX INTEGER (0..65535)
                    MAX-ACCESS read-only
                    STATUS current
                    DESCRIPTION "Num-BSS"
                    ::= {  staWlanChanneEntry 6 }

staWlanChannePulsec OBJECT-TYPE
                    SYNTAX INTEGER (0..2147483647)
                    MAX-ACCESS read-only
                    STATUS current
                    DESCRIPTION "Pulse-Count"
                    ::= {  staWlanChanneEntry 10 }

staWlanChanneRadard OBJECT-TYPE
                    SYNTAX INTEGER{
                      no(0),
                      yes(1)
                    }
                    MAX-ACCESS read-only
                    STATUS current
                    DESCRIPTION "Radar-Detected"
                    ::= {  staWlanChanneEntry 7 }

staWlanChanneRadarp OBJECT-TYPE
                    SYNTAX DisplayString (SIZE(0..40))
                    MAX-ACCESS read-only
                    STATUS current
                    DESCRIPTION "Radar-Pattern"
                    ::= {  staWlanChanneEntry 13 }

staWlanClient OBJECT IDENTIFIER ::= { staWlan 43}
staWlanClientIptranTable OBJECT-TYPE
                         SYNTAX SEQUENCE OF StaWlanClientIptranEntry
                         MAX-ACCESS not-accessible
                         STATUS current
                         DESCRIPTION "IP-Translation-Table"
                         ::= {  staWlanClient 1 }

staWlanClientIptranEntry OBJECT-TYPE
                         SYNTAX StaWlanClientIptranEntry
                         MAX-ACCESS not-accessible
                         STATUS current
                         DESCRIPTION "entry in table"
                         INDEX { staWlanClientIptranIpa }
                         ::= {  staWlanClientIptranTable 1 }

StaWlanClientIptranEntry ::= SEQUENCE {
                         staWlanClientIptranIpa IpAddress,
                         staWlanClientIptranMac MacAddress,
                         staWlanClientIptranAge INTEGER
                        }

staWlanClientIptranIpa OBJECT-TYPE
                       SYNTAX IpAddress
                       MAX-ACCESS read-only
                       STATUS current
                       DESCRIPTION "IP-Address"
                       ::= {  staWlanClientIptranEntry 1 }

staWlanClientIptranMac OBJECT-TYPE
                       SYNTAX MacAddress
                       MAX-ACCESS read-only
                       STATUS current
                       DESCRIPTION "MAC-Address"
                       ::= {  staWlanClientIptranEntry 2 }

staWlanClientIptranAge OBJECT-TYPE
                       SYNTAX INTEGER (0..2147483647)
                       MAX-ACCESS read-only
                       STATUS current
                       DESCRIPTION "Age"
                       ::= {  staWlanClientIptranEntry 3 }

staWlanClientPppoeiTable OBJECT-TYPE
                         SYNTAX SEQUENCE OF StaWlanClientPppoeiEntry
                         MAX-ACCESS not-accessible
                         STATUS current
                         DESCRIPTION "PPPoE-ID-Translation-Table"
                         ::= {  staWlanClient 10 }

staWlanClientPppoeiEntry OBJECT-TYPE
                         SYNTAX StaWlanClientPppoeiEntry
                         MAX-ACCESS not-accessible
                         STATUS current
                         DESCRIPTION "entry in table"
                         INDEX { staWlanClientPppoeiSes }
                         ::= {  staWlanClientPppoeiTable 1 }

StaWlanClientPppoeiEntry ::= SEQUENCE {
                         staWlanClientPppoeiSes INTEGER,
                         staWlanClientPppoeiMac MacAddress,
                         staWlanClientPppoeiAge INTEGER
                        }

staWlanClientPppoeiSes OBJECT-TYPE
                       SYNTAX INTEGER (0..65535)
                       MAX-ACCESS read-only
                       STATUS current
                       DESCRIPTION "Session-Id"
                       ::= {  staWlanClientPppoeiEntry 1 }

staWlanClientPppoeiMac OBJECT-TYPE
                       SYNTAX MacAddress
                       MAX-ACCESS read-only
                       STATUS current
                       DESCRIPTION "MAC-Address"
                       ::= {  staWlanClientPppoeiEntry 2 }

staWlanClientPppoeiAge OBJECT-TYPE
                       SYNTAX INTEGER (0..2147483647)
                       MAX-ACCESS read-only
                       STATUS current
                       DESCRIPTION "Age"
                       ::= {  staWlanClientPppoeiEntry 3 }

staWlanClientPppoeuTable OBJECT-TYPE
                         SYNTAX SEQUENCE OF StaWlanClientPppoeuEntry
                         MAX-ACCESS not-accessible
                         STATUS current
                         DESCRIPTION "PPPoE-Uniq-Translation-Table"
                         ::= {  staWlanClient 11 }

staWlanClientPppoeuEntry OBJECT-TYPE
                         SYNTAX StaWlanClientPppoeuEntry
                         MAX-ACCESS not-accessible
                         STATUS current
                         DESCRIPTION "entry in table"
                         INDEX { staWlanClientPppoeuHostuniql, staWlanClientPppoeuHostuniq }
                         ::= {  staWlanClientPppoeuTable 1 }

StaWlanClientPppoeuEntry ::= SEQUENCE {
                         staWlanClientPppoeuHostuniql INTEGER,
                         staWlanClientPppoeuHostuniq DisplayString,
                         staWlanClientPppoeuMacaddres MacAddress,
                         staWlanClientPppoeuAge INTEGER
                        }

staWlanClientPppoeuHostuniql OBJECT-TYPE
                             SYNTAX INTEGER (0..65535)
                             MAX-ACCESS read-only
                             STATUS current
                             DESCRIPTION "Host-Uniq-Len"
                             ::= {  staWlanClientPppoeuEntry 1 }

staWlanClientPppoeuHostuniq OBJECT-TYPE
                             SYNTAX DisplayString (SIZE(0..255))
                             MAX-ACCESS read-only
                             STATUS current
                             DESCRIPTION "Host-Uniq"
                             ::= {  staWlanClientPppoeuEntry 2 }

staWlanClientPppoeuMacaddres OBJECT-TYPE
                             SYNTAX MacAddress
                             MAX-ACCESS read-only
                             STATUS current
                             DESCRIPTION "MAC-Address"
                             ::= {  staWlanClientPppoeuEntry 3 }

staWlanClientPppoeuAge OBJECT-TYPE
                             SYNTAX INTEGER (0..2147483647)
                             MAX-ACCESS read-only
                             STATUS current
                             DESCRIPTION "Age"
                             ::= {  staWlanClientPppoeuEntry 4 }

staWlanClientInterfTable OBJECT-TYPE
                         SYNTAX SEQUENCE OF StaWlanClientInterfEntry
                         MAX-ACCESS not-accessible
                         STATUS current
                         DESCRIPTION "Interfaces"
                         ::= {  staWlanClient 51 }

staWlanClientInterfEntry OBJECT-TYPE
                         SYNTAX StaWlanClientInterfEntry
                         MAX-ACCESS not-accessible
                         STATUS current
                         DESCRIPTION "entry in table"
                         INDEX { staWlanClientInterfIfc }
                         ::= {  staWlanClientInterfTable 1 }

StaWlanClientInterfEntry ::= SEQUENCE {
                         staWlanClientInterfIfc DisplayString,
                         staWlanClientInterfState INTEGER,
                         staWlanClientInterfStatio INTEGER,
                         staWlanClientInterfConnec INTEGER,
                         staWlanClientInterfAid INTEGER,
                         staWlanClientInterfPhysig INTEGER,
                         staWlanClientInterfLinkph INTEGER,
                         staWlanClientInterfLinksi INTEGER,
                         staWlanClientInterfAntenn INTEGER,
                         staWlanClientInterfIdenti DisplayString,
                         staWlanClientInterfTxrate INTEGER,
                         staWlanClientInterfRxrate INTEGER,
                         staWlanClientInterfTxbyte Counter64,
                         staWlanClientInterfRxbyte Counter64,
                         staWlanClientInterfThroug DisplayString,
                         staWlanClientInterfMaxthr DisplayString,
                         staWlanClientInterfBytest INTEGER,
                         staWlanClientInterfBytesm INTEGER,
                         staWlanClientInterfTxpack Counter32,
                         staWlanClientInterfRxpack Counter32,
                         staWlanClientInterfTxlimi INTEGER,
                         staWlanClientInterfRxlimi INTEGER,
                         staWlanClientInterfCompre INTEGER,
                         staWlanClientInterfClbrgs INTEGER,
                         staWlanClientInterfWpaver INTEGER,
                         staWlanClientInterfQos INTEGER
                        }

staWlanClientInterfIfc OBJECT-TYPE
                          SYNTAX DisplayString (SIZE(0..255))
                          MAX-ACCESS read-only
                          STATUS current
                          DESCRIPTION "Ifc"
                          ::= {  staWlanClientInterfEntry 1 }

staWlanClientInterfState OBJECT-TYPE
                          SYNTAX INTEGER{
                            none(0),
                            scanning(6),
                            joined(5),
                            challenge(7),
                            authenticated(2),
                            associated(9),
                            e1x-negotiation(10),
                            key-handshake(8),
                            connected(3)
                          }
                          MAX-ACCESS read-only
                          STATUS current
                          DESCRIPTION "State"
                          ::= {  staWlanClientInterfEntry 2 }

staWlanClientInterfStatio OBJECT-TYPE
                          SYNTAX INTEGER{
                            none(0),
                            adhoc(1),
                            infrastructure(2)
                          }
                          MAX-ACCESS read-only
                          STATUS current
                          DESCRIPTION "Station-Mode"
                          ::= {  staWlanClientInterfEntry 3 }

staWlanClientInterfConnec OBJECT-TYPE
                          SYNTAX INTEGER (0..2147483647)
                          MAX-ACCESS read-only
                          STATUS current
                          DESCRIPTION "Connect-Time"
                          ::= {  staWlanClientInterfEntry 25 }

staWlanClientInterfAid OBJECT-TYPE
                          SYNTAX INTEGER (0..65535)
                          MAX-ACCESS read-only
                          STATUS current
                          DESCRIPTION "AID"
                          ::= {  staWlanClientInterfEntry 23 }

staWlanClientInterfPhysig OBJECT-TYPE
                          SYNTAX INTEGER (0..65535)
                          MAX-ACCESS read-only
                          STATUS current
                          DESCRIPTION "Phy-Signal"
                          ::= {  staWlanClientInterfEntry 7 }

staWlanClientInterfLinkph OBJECT-TYPE
                          SYNTAX INTEGER (0..65535)
                          MAX-ACCESS read-only
                          STATUS current
                          DESCRIPTION "Link-Phy-Signal"
                          ::= {  staWlanClientInterfEntry 22 }

staWlanClientInterfLinksi OBJECT-TYPE
                          SYNTAX INTEGER (-32768..32767)
                          MAX-ACCESS read-only
                          STATUS current
                          DESCRIPTION "Link-Signal-Level"
                          ::= {  staWlanClientInterfEntry 26 }

staWlanClientInterfAntenn OBJECT-TYPE
                          SYNTAX INTEGER (0..255)
                          MAX-ACCESS read-only
                          STATUS current
                          DESCRIPTION "Antenna"
                          ::= {  staWlanClientInterfEntry 4 }

staWlanClientInterfIdenti OBJECT-TYPE
                          SYNTAX DisplayString (SIZE(0..24))
                          MAX-ACCESS read-only
                          STATUS current
                          DESCRIPTION "Identification"
                          ::= {  staWlanClientInterfEntry 24 }

staWlanClientInterfTxrate OBJECT-TYPE
                          SYNTAX INTEGER{
                            unknown(0),
                            e1m(1),
                            e2m(2),
                            e5m(3),
                            e5-5m(4),
                            e8m(5),
                            e11m(6),
                            e6m(8),
                            e9m(9),
                            e12m(10),
                            e18m(11),
                            e24m(12),
                            e36m(13),
                            e48m(14),
                            e54m(15),
                            t-12m(20),
                            t-18m(21),
                            t-24m(22),
                            t-36m(23),
                            t-48m(24),
                            t-72m(25),
                            t-96m(26),
                            t-108m(27)
                          }
                          MAX-ACCESS read-only
                          STATUS current
                          DESCRIPTION "Tx-Rate"
                          ::= {  staWlanClientInterfEntry 9 }

staWlanClientInterfRxrate OBJECT-TYPE
                          SYNTAX INTEGER{
                            unknown(0),
                            e1m(1),
                            e2m(2),
                            e5m(3),
                            e5-5m(4),
                            e8m(5),
                            e11m(6),
                            e6m(8),
                            e9m(9),
                            e12m(10),
                            e18m(11),
                            e24m(12),
                            e36m(13),
                            e48m(14),
                            e54m(15),
                            t-12m(20),
                            t-18m(21),
                            t-24m(22),
                            t-36m(23),
                            t-48m(24),
                            t-72m(25),
                            t-96m(26),
                            t-108m(27)
                          }
                          MAX-ACCESS read-only
                          STATUS current
                          DESCRIPTION "Rx-Rate"
                          ::= {  staWlanClientInterfEntry 5 }

staWlanClientInterfTxbyte OBJECT-TYPE
                          SYNTAX Counter64
                          MAX-ACCESS read-only
                          STATUS current
                          DESCRIPTION "Tx-Bytes"
                          ::= {  staWlanClientInterfEntry 11 }

staWlanClientInterfRxbyte OBJECT-TYPE
                          SYNTAX Counter64
                          MAX-ACCESS read-only
                          STATUS current
                          DESCRIPTION "Rx-Bytes"
                          ::= {  staWlanClientInterfEntry 12 }

staWlanClientInterfThroug OBJECT-TYPE
                          SYNTAX DisplayString (SIZE(0..14))
                          MAX-ACCESS read-only
                          STATUS current
                          DESCRIPTION "Throughput"
                          ::= {  staWlanClientInterfEntry 6 }

staWlanClientInterfMaxthr OBJECT-TYPE
                          SYNTAX DisplayString (SIZE(0..14))
                          MAX-ACCESS read-only
                          STATUS current
                          DESCRIPTION "Max.-Throughput"
                          ::= {  staWlanClientInterfEntry 10 }

staWlanClientInterfBytest OBJECT-TYPE
                          SYNTAX INTEGER (0..2147483647)
                          MAX-ACCESS read-only
                          STATUS current
                          DESCRIPTION "Bytes-Throughput"
                          ::= {  staWlanClientInterfEntry 13 }

staWlanClientInterfBytesm OBJECT-TYPE
                          SYNTAX INTEGER (0..2147483647)
                          MAX-ACCESS read-only
                          STATUS current
                          DESCRIPTION "Bytes-Max.-Throughput"
                          ::= {  staWlanClientInterfEntry 14 }

staWlanClientInterfTxpack OBJECT-TYPE
                          SYNTAX Counter32
                          MAX-ACCESS read-only
                          STATUS current
                          DESCRIPTION "Tx-Packets"
                          ::= {  staWlanClientInterfEntry 20 }

staWlanClientInterfRxpack OBJECT-TYPE
                          SYNTAX Counter32
                          MAX-ACCESS read-only
                          STATUS current
                          DESCRIPTION "Rx-Packets"
                          ::= {  staWlanClientInterfEntry 21 }

staWlanClientInterfTxlimi OBJECT-TYPE
                          SYNTAX INTEGER (0..2147483647)
                          MAX-ACCESS read-only
                          STATUS current
                          DESCRIPTION "Tx-Limit"
                          ::= {  staWlanClientInterfEntry 17 }

staWlanClientInterfRxlimi OBJECT-TYPE
                          SYNTAX INTEGER (0..2147483647)
                          MAX-ACCESS read-only
                          STATUS current
                          DESCRIPTION "Rx-Limit"
                          ::= {  staWlanClientInterfEntry 18 }

staWlanClientInterfCompre OBJECT-TYPE
                          SYNTAX INTEGER{
                            none(0),
                            inactive(1),
                            active(2)
                          }
                          MAX-ACCESS read-only
                          STATUS current
                          DESCRIPTION "Compression"
                          ::= {  staWlanClientInterfEntry 8 }

staWlanClientInterfClbrgs OBJECT-TYPE
                          SYNTAX INTEGER{
                            no(0),
                            yes(1)
                          }
                          MAX-ACCESS read-only
                          STATUS current
                          DESCRIPTION "Cl.-Brg.-Support"
                          ::= {  staWlanClientInterfEntry 15 }

staWlanClientInterfWpaver OBJECT-TYPE
                          SYNTAX INTEGER{
                            wpa1(1),
                            wpa2(2),
                            none(0)
                          }
                          MAX-ACCESS read-only
                          STATUS current
                          DESCRIPTION "WPA-Version"
                          ::= {  staWlanClientInterfEntry 16 }

staWlanClientInterfQos OBJECT-TYPE
                          SYNTAX INTEGER{
                            no(0),
                            yes(1)
                          }
                          MAX-ACCESS read-only
                          STATUS current
                          DESCRIPTION "QoS"
                          ::= {  staWlanClientInterfEntry 19 }

staWlanSeenclTable OBJECT-TYPE
                   SYNTAX SEQUENCE OF StaWlanSeenclEntry
                   MAX-ACCESS not-accessible
                   STATUS current
                   DESCRIPTION "Seen-Clients"
                   ::= {  staWlan 45 }

staWlanSeenclEntry OBJECT-TYPE
                   SYNTAX StaWlanSeenclEntry
                   MAX-ACCESS not-accessible
                   STATUS current
                   DESCRIPTION "entry in table"
                   INDEX { staWlanSeenclMac, staWlanSeenclInt }
                   ::= {  staWlanSeenclTable 1 }

StaWlanSeenclEntry ::= SEQUENCE {
                   staWlanSeenclMac MacAddress,
                   staWlanSeenclInt INTEGER,
                   staWlanSeenclSig INTEGER,
                   staWlanSeenclRxp INTEGER,
                   staWlanSeenclAge INTEGER,
                   staWlanSeenclNum Counter32,
                   staWlanSeenclNet DisplayString
                  }

staWlanSeenclMac OBJECT-TYPE
                 SYNTAX MacAddress
                 MAX-ACCESS read-only
                 STATUS current
                 DESCRIPTION "MAC-Address"
                 ::= {  staWlanSeenclEntry 1 }

staWlanSeenclInt OBJECT-TYPE
                 SYNTAX INTEGER{
                   wlan-1(0),
                   wlan-2(1),
                   wlan-3(2)
                 }
                 MAX-ACCESS read-only
                 STATUS current
                 DESCRIPTION "Interface"
                 ::= {  staWlanSeenclEntry 2 }

staWlanSeenclSig OBJECT-TYPE
                 SYNTAX INTEGER (-128..127)
                 MAX-ACCESS read-only
                 STATUS current
                 DESCRIPTION "Signal-Level"
                 ::= {  staWlanSeenclEntry 3 }

staWlanSeenclRxp OBJECT-TYPE
                 SYNTAX INTEGER (0..65535)
                 MAX-ACCESS read-only
                 STATUS current
                 DESCRIPTION "Rx-Phy-Signal"
                 ::= {  staWlanSeenclEntry 6 }

staWlanSeenclAge OBJECT-TYPE
                 SYNTAX INTEGER (0..2147483647)
                 MAX-ACCESS read-only
                 STATUS current
                 DESCRIPTION "Age"
                 ::= {  staWlanSeenclEntry 4 }

staWlanSeenclNum OBJECT-TYPE
                 SYNTAX Counter32
                 MAX-ACCESS read-only
                 STATUS current
                 DESCRIPTION "Num-Probes"
                 ::= {  staWlanSeenclEntry 7 }

staWlanSeenclNet OBJECT-TYPE
                 SYNTAX DisplayString (SIZE(0..32))
                 MAX-ACCESS read-only
                 STATUS current
                 DESCRIPTION "Network-Name"
                 ::= {  staWlanSeenclEntry 5 }

staWlanLogtabTable OBJECT-TYPE
                   SYNTAX SEQUENCE OF StaWlanLogtabEntry
                   MAX-ACCESS not-accessible
                   STATUS current
                   DESCRIPTION "Log-Table"
                   ::= {  staWlan 46 }

staWlanLogtabEntry OBJECT-TYPE
                   SYNTAX StaWlanLogtabEntry
                   MAX-ACCESS not-accessible
                   STATUS current
                   DESCRIPTION "entry in table"
                   INDEX { staWlanLogtabInd }
                   ::= {  staWlanLogtabTable 1 }

StaWlanLogtabEntry ::= SEQUENCE {
                   staWlanLogtabInd INTEGER,
                   staWlanLogtabTim DisplayString,
                   staWlanLogtabInt INTEGER,
                   staWlanLogtabEve DisplayString,
                   staWlanLogtabAdd MacAddress,
                   staWlanLogtabRea DisplayString
                  }

staWlanLogtabInd OBJECT-TYPE
                 SYNTAX INTEGER (0..2147483647)
                 MAX-ACCESS read-only
                 STATUS current
                 DESCRIPTION "Index"
                 ::= {  staWlanLogtabEntry 1 }

staWlanLogtabTim OBJECT-TYPE
                 SYNTAX DisplayString (SIZE(0..19))
                 MAX-ACCESS read-only
                 STATUS current
                 DESCRIPTION "Time"
                 ::= {  staWlanLogtabEntry 2 }

staWlanLogtabInt OBJECT-TYPE
                 SYNTAX INTEGER{
                   wlan-1(1),
                   wlan-1-2(16),
                   wlan-1-3(17),
                   wlan-1-4(18),
                   wlan-1-5(19),
                   wlan-1-6(20),
                   wlan-1-7(21),
                   wlan-1-8(22)
                 }
                 MAX-ACCESS read-only
                 STATUS current
                 DESCRIPTION "Interface"
                 ::= {  staWlanLogtabEntry 3 }

staWlanLogtabEve OBJECT-TYPE
                 SYNTAX DisplayString (SIZE(0..90))
                 MAX-ACCESS read-only
                 STATUS current
                 DESCRIPTION "Event"
                 ::= {  staWlanLogtabEntry 4 }

staWlanLogtabAdd OBJECT-TYPE
                 SYNTAX MacAddress
                 MAX-ACCESS read-only
                 STATUS current
                 DESCRIPTION "Address"
                 ::= {  staWlanLogtabEntry 5 }

staWlanLogtabRea OBJECT-TYPE
                 SYNTAX DisplayString (SIZE(0..127))
                 MAX-ACCESS read-only
                 STATUS current
                 DESCRIPTION "Reason"
                 ::= {  staWlanLogtabEntry 6 }

staWlanDelete OBJECT-TYPE
              SYNTAX DisplayString
              MAX-ACCESS read-write
              STATUS current
              DESCRIPTION "Delete-Values"
              ::= {  staWlan 11 }

staWlanPairwiTable OBJECT-TYPE
                   SYNTAX SEQUENCE OF StaWlanPairwiEntry
                   MAX-ACCESS not-accessible
                   STATUS current
                   DESCRIPTION "Pairwise-Keys"
                   ::= {  staWlan 47 }

staWlanPairwiEntry OBJECT-TYPE
                   SYNTAX StaWlanPairwiEntry
                   MAX-ACCESS not-accessible
                   STATUS current
                   DESCRIPTION "entry in table"
                   INDEX { staWlanPairwiInde }
                   ::= {  staWlanPairwiTable 1 }

StaWlanPairwiEntry ::= SEQUENCE {
                   staWlanPairwiInde INTEGER,
                   staWlanPairwiKeyt INTEGER,
                   staWlanPairwiKeyv DisplayString,
                   staWlanPairwiTsc DisplayString,
                   staWlanPairwiRsc DisplayString
                  }

staWlanPairwiInde OBJECT-TYPE
                  SYNTAX INTEGER (0..65535)
                  MAX-ACCESS read-only
                  STATUS current
                  DESCRIPTION "Index"
                  ::= {  staWlanPairwiEntry 1 }

staWlanPairwiKeyt OBJECT-TYPE
                  SYNTAX INTEGER{
                    none(0),
                    unknown(1),
                    wep-40-bits(5),
                    wep-104-bits(13),
                    wep-128-bits(16),
                    tkip(64),
                    aes-ocb(65),
                    aes-ccm(66)
                  }
                  MAX-ACCESS read-only
                  STATUS current
                  DESCRIPTION "Key-Type"
                  ::= {  staWlanPairwiEntry 3 }

staWlanPairwiKeyv OBJECT-TYPE
                  SYNTAX DisplayString (SIZE(0..255))
                  MAX-ACCESS read-only
                  STATUS current
                  DESCRIPTION "Key-Value"
                  ::= {  staWlanPairwiEntry 4 }

staWlanPairwiTsc OBJECT-TYPE
                  SYNTAX DisplayString (SIZE(0..255))
                  MAX-ACCESS read-only
                  STATUS current
                  DESCRIPTION "TSC"
                  ::= {  staWlanPairwiEntry 5 }

staWlanPairwiRsc OBJECT-TYPE
                  SYNTAX DisplayString (SIZE(0..255))
                  MAX-ACCESS read-only
                  STATUS current
                  DESCRIPTION "RSC"
                  ::= {  staWlanPairwiEntry 6 }

staWlanStatioTable OBJECT-TYPE
                   SYNTAX SEQUENCE OF StaWlanStatioEntry
                   MAX-ACCESS not-accessible
                   STATUS current
                   DESCRIPTION "Station-Table"
                   ::= {  staWlan 32 }

staWlanStatioEntry OBJECT-TYPE
                   SYNTAX StaWlanStatioEntry
                   MAX-ACCESS not-accessible
                   STATUS current
                   DESCRIPTION "entry in table"
                   INDEX { staWlanStatioIndex }
                   ::= {  staWlanStatioTable 1 }

StaWlanStatioEntry ::= SEQUENCE {
                   staWlanStatioIndex INTEGER,
                   staWlanStatioAid INTEGER,
                   staWlanStatioInterf INTEGER,
                   staWlanStatioNetwor INTEGER,
                   staWlanStatioVlanid INTEGER,
                   staWlanStatioIdleti INTEGER,
                   staWlanStatioPhysig INTEGER,
                   staWlanStatioMacadd MacAddress,
                   staWlanStatioUserna DisplayString,
                   staWlanStatioIdenti DisplayString,
                   staWlanStatioTxbyte Counter64,
                   staWlanStatioRxbyte Counter64,
                   staWlanStatioThroug DisplayString,
                   staWlanStatioMaxthr DisplayString,
                   staWlanStatioBytest INTEGER,
                   staWlanStatioBytesm INTEGER,
                   staWlanStatioTxpack Counter32,
                   staWlanStatioRxpack Counter32,
                   staWlanStatioTxlimi INTEGER,
                   staWlanStatioRxlimi INTEGER,
                   staWlanStatioState INTEGER,
                   staWlanStatioMacche INTEGER,
                   staWlanStatioLastev INTEGER,
                   staWlanStatioLaster INTEGER,
                   staWlanStatioTxrate INTEGER,
                   staWlanStatioRxrate INTEGER,
                   staWlanStatioAntenn INTEGER,
                   staWlanStatioWpaver INTEGER,
                   staWlanStatioQos INTEGER,
                   staWlanStatioKeytyp INTEGER,
                   staWlanStatioPowers INTEGER,
                   staWlanStatioListen INTEGER,
                   staWlanStatioConnec INTEGER,
                   staWlanStatioShortp INTEGER,
                   staWlanStatioShorts INTEGER,
                   staWlanStatioCompre INTEGER,
                   staWlanStatioClbrgs INTEGER,
                   staWlanStatioIpaddr IpAddress
                  }

staWlanStatioIndex OBJECT-TYPE
                    SYNTAX INTEGER (0..65535)
                    MAX-ACCESS read-only
                    STATUS current
                    DESCRIPTION "Index"
                    ::= {  staWlanStatioEntry 1 }

staWlanStatioAid OBJECT-TYPE
                    SYNTAX INTEGER (0..65535)
                    MAX-ACCESS read-only
                    STATUS current
                    DESCRIPTION "AID"
                    ::= {  staWlanStatioEntry 19 }

staWlanStatioInterf OBJECT-TYPE
                    SYNTAX INTEGER{
                      wlan-1(0),
                      wlan-2(1),
                      wlan-3(2)
                    }
                    MAX-ACCESS read-only
                    STATUS current
                    DESCRIPTION "Interface"
                    ::= {  staWlanStatioEntry 15 }

staWlanStatioNetwor OBJECT-TYPE
                    SYNTAX INTEGER{
                      e1(0),
                      e2(1),
                      e3(2),
                      e4(3),
                      e5(4),
                      e6(5),
                      e7(6),
                      e8(7)
                    }
                    MAX-ACCESS read-only
                    STATUS current
                    DESCRIPTION "Network"
                    ::= {  staWlanStatioEntry 25 }

staWlanStatioVlanid OBJECT-TYPE
                    SYNTAX INTEGER (0..65535)
                    MAX-ACCESS read-only
                    STATUS current
                    DESCRIPTION "VLAN-Id"
                    ::= {  staWlanStatioEntry 38 }

staWlanStatioIdleti OBJECT-TYPE
                    SYNTAX INTEGER (0..2147483647)
                    MAX-ACCESS read-only
                    STATUS current
                    DESCRIPTION "Idle-Timeout"
                    ::= {  staWlanStatioEntry 43 }

staWlanStatioPhysig OBJECT-TYPE
                    SYNTAX INTEGER (0..65535)
                    MAX-ACCESS read-only
                    STATUS current
                    DESCRIPTION "Phy-Signal"
                    ::= {  staWlanStatioEntry 26 }

staWlanStatioMacadd OBJECT-TYPE
                    SYNTAX MacAddress
                    MAX-ACCESS read-only
                    STATUS current
                    DESCRIPTION "MAC-Address"
                    ::= {  staWlanStatioEntry 4 }

staWlanStatioUserna OBJECT-TYPE
                    SYNTAX DisplayString (SIZE(0..255))
                    MAX-ACCESS read-only
                    STATUS current
                    DESCRIPTION "User-Name"
                    ::= {  staWlanStatioEntry 39 }

staWlanStatioIdenti OBJECT-TYPE
                    SYNTAX DisplayString (SIZE(0..24))
                    MAX-ACCESS read-only
                    STATUS current
                    DESCRIPTION "Identification"
                    ::= {  staWlanStatioEntry 9 }

staWlanStatioTxbyte OBJECT-TYPE
                    SYNTAX Counter64
                    MAX-ACCESS read-only
                    STATUS current
                    DESCRIPTION "Tx-Bytes"
                    ::= {  staWlanStatioEntry 6 }

staWlanStatioRxbyte OBJECT-TYPE
                    SYNTAX Counter64
                    MAX-ACCESS read-only
                    STATUS current
                    DESCRIPTION "Rx-Bytes"
                    ::= {  staWlanStatioEntry 7 }

staWlanStatioThroug OBJECT-TYPE
                    SYNTAX DisplayString (SIZE(0..14))
                    MAX-ACCESS read-only
                    STATUS current
                    DESCRIPTION "Throughput"
                    ::= {  staWlanStatioEntry 20 }

staWlanStatioMaxthr OBJECT-TYPE
                    SYNTAX DisplayString (SIZE(0..14))
                    MAX-ACCESS read-only
                    STATUS current
                    DESCRIPTION "Max.-Throughput"
                    ::= {  staWlanStatioEntry 29 }

staWlanStatioBytest OBJECT-TYPE
                    SYNTAX INTEGER (0..2147483647)
                    MAX-ACCESS read-only
                    STATUS current
                    DESCRIPTION "Bytes-Throughput"
                    ::= {  staWlanStatioEntry 30 }

staWlanStatioBytesm OBJECT-TYPE
                    SYNTAX INTEGER (0..2147483647)
                    MAX-ACCESS read-only
                    STATUS current
                    DESCRIPTION "Bytes-Max.-Throughput"
                    ::= {  staWlanStatioEntry 31 }

staWlanStatioTxpack OBJECT-TYPE
                    SYNTAX Counter32
                    MAX-ACCESS read-only
                    STATUS current
                    DESCRIPTION "Tx-Packets"
                    ::= {  staWlanStatioEntry 41 }

staWlanStatioRxpack OBJECT-TYPE
                    SYNTAX Counter32
                    MAX-ACCESS read-only
                    STATUS current
                    DESCRIPTION "Rx-Packets"
                    ::= {  staWlanStatioEntry 42 }

staWlanStatioTxlimi OBJECT-TYPE
                    SYNTAX INTEGER (0..2147483647)
                    MAX-ACCESS read-only
                    STATUS current
                    DESCRIPTION "Tx-Limit"
                    ::= {  staWlanStatioEntry 35 }

staWlanStatioRxlimi OBJECT-TYPE
                    SYNTAX INTEGER (0..2147483647)
                    MAX-ACCESS read-only
                    STATUS current
                    DESCRIPTION "Rx-Limit"
                    ::= {  staWlanStatioEntry 36 }

staWlanStatioState OBJECT-TYPE
                    SYNTAX INTEGER{
                      none(0),
                      adhoc(1),
                      authenticated(2),
                      connected(3),
                      associated(9),
                      mac-check(4),
                      e1x-negotiation(10),
                      key-handshake(8)
                    }
                    MAX-ACCESS read-only
                    STATUS current
                    DESCRIPTION "State"
                    ::= {  staWlanStatioEntry 10 }

staWlanStatioMacche OBJECT-TYPE
                    SYNTAX INTEGER{
                      none(0),
                      local(1),
                      radius(2)
                    }
                    MAX-ACCESS read-only
                    STATUS current
                    DESCRIPTION "MAC-Check"
                    ::= {  staWlanStatioEntry 40 }

staWlanStatioLastev OBJECT-TYPE
                    SYNTAX INTEGER{
                      none(0),
                      auth-success(1),
                      deauth(2),
                      assoc-success(3),
                      reassoc-success(4),
                      disassoc(5),
                      radius-success(6),
                      auth-reject(7),
                      assoc-reject(8),
                      keyhandshake-success(9),
                      keyhandshake-timeout(10),
                      keyhandshake-failure(11),
                      radius-reject(12),
                      supervision(13),
                      e802-1x-success(14),
                      e802-1x-failure(15),
                      idle-timeout(16),
                      admin-deassoc(17),
                      roamed(18)
                    }
                    MAX-ACCESS read-only
                    STATUS current
                    DESCRIPTION "Last-Event"
                    ::= {  staWlanStatioEntry 34 }

staWlanStatioLaster OBJECT-TYPE
                    SYNTAX INTEGER{
                      none(0),
                      auth-success(1),
                      deauth(2),
                      assoc-success(3),
                      reassoc-success(4),
                      disassoc(5),
                      radius-success(6),
                      auth-reject(7),
                      assoc-reject(8),
                      keyhandshake-success(9),
                      keyhandshake-timeout(10),
                      keyhandshake-failure(11),
                      radius-reject(12),
                      supervision(13),
                      e802-1x-success(14),
                      e802-1x-failure(15),
                      idle-timeout(16),
                      admin-deassoc(17),
                      roamed(18)
                    }
                    MAX-ACCESS read-only
                    STATUS current
                    DESCRIPTION "Last-Error"
                    ::= {  staWlanStatioEntry 44 }

staWlanStatioTxrate OBJECT-TYPE
                    SYNTAX INTEGER{
                      unknown(0),
                      e1m(1),
                      e2m(2),
                      e5m(3),
                      e5-5m(4),
                      e8m(5),
                      e11m(6),
                      e6m(8),
                      e9m(9),
                      e12m(10),
                      e18m(11),
                      e24m(12),
                      e36m(13),
                      e48m(14),
                      e54m(15),
                      t-12m(20),
                      t-18m(21),
                      t-24m(22),
                      t-36m(23),
                      t-48m(24),
                      t-72m(25),
                      t-96m(26),
                      t-108m(27)
                    }
                    MAX-ACCESS read-only
                    STATUS current
                    DESCRIPTION "Tx-Rate"
                    ::= {  staWlanStatioEntry 28 }

staWlanStatioRxrate OBJECT-TYPE
                    SYNTAX INTEGER{
                      unknown(0),
                      e1m(1),
                      e2m(2),
                      e5m(3),
                      e5-5m(4),
                      e8m(5),
                      e11m(6),
                      e6m(8),
                      e9m(9),
                      e12m(10),
                      e18m(11),
                      e24m(12),
                      e36m(13),
                      e48m(14),
                      e54m(15),
                      t-12m(20),
                      t-18m(21),
                      t-24m(22),
                      t-36m(23),
                      t-48m(24),
                      t-72m(25),
                      t-96m(26),
                      t-108m(27)
                    }
                    MAX-ACCESS read-only
                    STATUS current
                    DESCRIPTION "Rx-Rate"
                    ::= {  staWlanStatioEntry 13 }

staWlanStatioAntenn OBJECT-TYPE
                    SYNTAX INTEGER (0..255)
                    MAX-ACCESS read-only
                    STATUS current
                    DESCRIPTION "Antenna"
                    ::= {  staWlanStatioEntry 24 }

staWlanStatioWpaver OBJECT-TYPE
                    SYNTAX INTEGER{
                      wpa1(1),
                      wpa2(2),
                      none(0)
                    }
                    MAX-ACCESS read-only
                    STATUS current
                    DESCRIPTION "WPA-Version"
                    ::= {  staWlanStatioEntry 33 }

staWlanStatioQos OBJECT-TYPE
                    SYNTAX INTEGER{
                      no(0),
                      yes(1)
                    }
                    MAX-ACCESS read-only
                    STATUS current
                    DESCRIPTION "QoS"
                    ::= {  staWlanStatioEntry 37 }

staWlanStatioKeytyp OBJECT-TYPE
                    SYNTAX INTEGER{
                      none(0),
                      unknown(1),
                      wep-40-bits(5),
                      wep-104-bits(13),
                      wep-128-bits(16),
                      tkip(64),
                      aes-ocb(65),
                      aes-ccm(66)
                    }
                    MAX-ACCESS read-only
                    STATUS current
                    DESCRIPTION "Key-Type"
                    ::= {  staWlanStatioEntry 14 }

staWlanStatioPowers OBJECT-TYPE
                    SYNTAX INTEGER{
                      unknown(0),
                      inactive(1),
                      active(2)
                    }
                    MAX-ACCESS read-only
                    STATUS current
                    DESCRIPTION "Power-Saving"
                    ::= {  staWlanStatioEntry 16 }

staWlanStatioListen OBJECT-TYPE
                    SYNTAX INTEGER (0..65535)
                    MAX-ACCESS read-only
                    STATUS current
                    DESCRIPTION "Listen-Interval"
                    ::= {  staWlanStatioEntry 17 }

staWlanStatioConnec OBJECT-TYPE
                    SYNTAX INTEGER (0..2147483647)
                    MAX-ACCESS read-only
                    STATUS current
                    DESCRIPTION "Connect-Time"
                    ::= {  staWlanStatioEntry 18 }

staWlanStatioShortp OBJECT-TYPE
                    SYNTAX INTEGER{
                      no(0),
                      yes(1)
                    }
                    MAX-ACCESS read-only
                    STATUS current
                    DESCRIPTION "Short-Preamble"
                    ::= {  staWlanStatioEntry 23 }

staWlanStatioShorts OBJECT-TYPE
                    SYNTAX INTEGER{
                      no(0),
                      yes(1)
                    }
                    MAX-ACCESS read-only
                    STATUS current
                    DESCRIPTION "Short-Slot-Time"
                    ::= {  staWlanStatioEntry 21 }

staWlanStatioCompre OBJECT-TYPE
                    SYNTAX INTEGER{
                      none(0),
                      inactive(1),
                      active(2)
                    }
                    MAX-ACCESS read-only
                    STATUS current
                    DESCRIPTION "Compression"
                    ::= {  staWlanStatioEntry 22 }

staWlanStatioClbrgs OBJECT-TYPE
                    SYNTAX INTEGER{
                      no(0),
                      yes(1)
                    }
                    MAX-ACCESS read-only
                    STATUS current
                    DESCRIPTION "Cl.-Brg.-Support"
                    ::= {  staWlanStatioEntry 32 }

staWlanStatioIpaddr OBJECT-TYPE
                    SYNTAX IpAddress
                    MAX-ACCESS read-only
                    STATUS current
                    DESCRIPTION "IP-Address"
                    ::= {  staWlanStatioEntry 27 }

staWlanDeasso OBJECT-TYPE
              SYNTAX DisplayString
              MAX-ACCESS read-write
              STATUS current
              DESCRIPTION "Deassoc-Station"
              ::= {  staWlan 37 }

staWlanCompetTable OBJECT-TYPE
                   SYNTAX SEQUENCE OF StaWlanCompetEntry
                   MAX-ACCESS not-accessible
                   STATUS current
                   DESCRIPTION "Competing-Networks"
                   ::= {  staWlan 44 }

staWlanCompetEntry OBJECT-TYPE
                   SYNTAX StaWlanCompetEntry
                   MAX-ACCESS not-accessible
                   STATUS current
                   DESCRIPTION "entry in table"
                   INDEX { staWlanCompetBssid, staWlanCompetInterf }
                   ::= {  staWlanCompetTable 1 }

StaWlanCompetEntry ::= SEQUENCE {
                   staWlanCompetBssid MacAddress,
                   staWlanCompetInterf INTEGER,
                   staWlanCompetNetwor DisplayString,
                   staWlanCompetOperat INTEGER,
                   staWlanCompetEncryp INTEGER,
                   staWlanCompetBeacon INTEGER,
                   staWlanCompetDtimpe INTEGER,
                   staWlanCompetPcffun INTEGER,
                   staWlanCompetQos INTEGER,
                   staWlanCompetMaxamp INTEGER,
                   staWlanCompetMaxams INTEGER,
                   staWlanCompetRadiob INTEGER,
                   staWlanCompetRadioc INTEGER,
                   staWlanCompet108mbp INTEGER,
                   staWlanCompetExtcha INTEGER,
                   staWlanCompetPhysig INTEGER,
                   staWlanCompetSignal INTEGER,
                   staWlanCompetNoisel INTEGER,
                   staWlanCompetLoad DisplayString,
                   staWlanCompetShortp INTEGER,
                   staWlanCompetShorts INTEGER,
                   staWlanCompet40mhzm INTEGER,
                   staWlanCompet40mhzi INTEGER,
                   staWlanCompetShortg INTEGER,
                   staWlanCompetCompre INTEGER,
                   staWlanCompetAge INTEGER,
                   staWlanCompetRate INTEGER,
                   staWlanCompetNonerp INTEGER,
                   staWlanCompetIdenti DisplayString,
                   staWlanCompetInterp DisplayString
                  }

staWlanCompetBssid OBJECT-TYPE
                    SYNTAX MacAddress
                    MAX-ACCESS read-only
                    STATUS current
                    DESCRIPTION "BSSID"
                    ::= {  staWlanCompetEntry 1 }

staWlanCompetInterf OBJECT-TYPE
                    SYNTAX INTEGER{
                      wlan-1(0),
                      wlan-2(1),
                      wlan-3(2)
                    }
                    MAX-ACCESS read-only
                    STATUS current
                    DESCRIPTION "Interface"
                    ::= {  staWlanCompetEntry 15 }

staWlanCompetNetwor OBJECT-TYPE
                    SYNTAX DisplayString (SIZE(0..32))
                    MAX-ACCESS read-only
                    STATUS current
                    DESCRIPTION "Network-Name"
                    ::= {  staWlanCompetEntry 2 }

staWlanCompetOperat OBJECT-TYPE
                    SYNTAX INTEGER{
                      none(0),
                      adhoc(1),
                      infrastructure(2)
                    }
                    MAX-ACCESS read-only
                    STATUS current
                    DESCRIPTION "Operation-Mode"
                    ::= {  staWlanCompetEntry 3 }

staWlanCompetEncryp OBJECT-TYPE
                    SYNTAX INTEGER{
                      none(0),
                      wep(1),
                      tkip(2),
                      aes(3),
                      aes-plus-tkip(4)
                    }
                    MAX-ACCESS read-only
                    STATUS current
                    DESCRIPTION "Encryption"
                    ::= {  staWlanCompetEntry 13 }

staWlanCompetBeacon OBJECT-TYPE
                    SYNTAX INTEGER (0..65535)
                    MAX-ACCESS read-only
                    STATUS current
                    DESCRIPTION "Beacon-Period"
                    ::= {  staWlanCompetEntry 6 }

staWlanCompetDtimpe OBJECT-TYPE
                    SYNTAX INTEGER (0..65535)
                    MAX-ACCESS read-only
                    STATUS current
                    DESCRIPTION "DTIM-Period"
                    ::= {  staWlanCompetEntry 7 }

staWlanCompetPcffun OBJECT-TYPE
                    SYNTAX INTEGER{
                      none(0),
                      delivery(1),
                      delivery-plus-polling(2)
                    }
                    MAX-ACCESS read-only
                    STATUS current
                    DESCRIPTION "PCF-Functionality"
                    ::= {  staWlanCompetEntry 22 }

staWlanCompetQos OBJECT-TYPE
                    SYNTAX INTEGER{
                      no(0),
                      yes(1)
                    }
                    MAX-ACCESS read-only
                    STATUS current
                    DESCRIPTION "QoS"
                    ::= {  staWlanCompetEntry 24 }

staWlanCompetMaxamp OBJECT-TYPE
                    SYNTAX INTEGER (0..2147483647)
                    MAX-ACCESS read-only
                    STATUS current
                    DESCRIPTION "Max-A-MPDU-Len"
                    ::= {  staWlanCompetEntry 32 }

staWlanCompetMaxams OBJECT-TYPE
                    SYNTAX INTEGER (0..2147483647)
                    MAX-ACCESS read-only
                    STATUS current
                    DESCRIPTION "Max-A-MSDU-Len"
                    ::= {  staWlanCompetEntry 33 }

staWlanCompetRadiob OBJECT-TYPE
                    SYNTAX INTEGER{
                      unknown(0),
                      e2-4ghz(1),
                      e5ghz(2),
                      e2-4ghz-5ghz(3)
                    }
                    MAX-ACCESS read-only
                    STATUS current
                    DESCRIPTION "Radio-Band"
                    ::= {  staWlanCompetEntry 16 }

staWlanCompetRadioc OBJECT-TYPE
                    SYNTAX INTEGER (0..255)
                    MAX-ACCESS read-only
                    STATUS current
                    DESCRIPTION "Radio-Channel"
                    ::= {  staWlanCompetEntry 8 }

staWlanCompet108mbp OBJECT-TYPE
                    SYNTAX INTEGER{
                      no(0),
                      yes(1)
                    }
                    MAX-ACCESS read-only
                    STATUS current
                    DESCRIPTION "108Mbps-Mode"
                    ::= {  staWlanCompetEntry 17 }

staWlanCompetExtcha OBJECT-TYPE
                    SYNTAX INTEGER{
                      none(0),
                      above(1),
                      below(3)
                    }
                    MAX-ACCESS read-only
                    STATUS current
                    DESCRIPTION "Ext.-Channel"
                    ::= {  staWlanCompetEntry 28 }

staWlanCompetPhysig OBJECT-TYPE
                    SYNTAX INTEGER (0..65535)
                    MAX-ACCESS read-only
                    STATUS current
                    DESCRIPTION "Phy-Signal"
                    ::= {  staWlanCompetEntry 10 }

staWlanCompetSignal OBJECT-TYPE
                    SYNTAX INTEGER (-32768..32767)
                    MAX-ACCESS read-only
                    STATUS current
                    DESCRIPTION "Signal-Level"
                    ::= {  staWlanCompetEntry 26 }

staWlanCompetNoisel OBJECT-TYPE
                    SYNTAX INTEGER (-128..127)
                    MAX-ACCESS read-only
                    STATUS current
                    DESCRIPTION "Noise-Level"
                    ::= {  staWlanCompetEntry 11 }

staWlanCompetLoad OBJECT-TYPE
                    SYNTAX DisplayString (SIZE(0..255))
                    MAX-ACCESS read-only
                    STATUS current
                    DESCRIPTION "Load"
                    ::= {  staWlanCompetEntry 12 }

staWlanCompetShortp OBJECT-TYPE
                    SYNTAX INTEGER{
                      no(0),
                      yes(1)
                    }
                    MAX-ACCESS read-only
                    STATUS current
                    DESCRIPTION "Short-Preamble"
                    ::= {  staWlanCompetEntry 14 }

staWlanCompetShorts OBJECT-TYPE
                    SYNTAX INTEGER{
                      no(0),
                      yes(1)
                    }
                    MAX-ACCESS read-only
                    STATUS current
                    DESCRIPTION "Short-Slot-Time"
                    ::= {  staWlanCompetEntry 18 }

staWlanCompet40mhzm OBJECT-TYPE
                    SYNTAX INTEGER{
                      no(0),
                      yes(1)
                    }
                    MAX-ACCESS read-only
                    STATUS current
                    DESCRIPTION "40MHz-Mode"
                    ::= {  staWlanCompetEntry 29 }

staWlanCompet40mhzi OBJECT-TYPE
                    SYNTAX INTEGER{
                      no(0),
                      yes(1)
                    }
                    MAX-ACCESS read-only
                    STATUS current
                    DESCRIPTION "40MHz-Intolerant"
                    ::= {  staWlanCompetEntry 30 }

staWlanCompetShortg OBJECT-TYPE
                    SYNTAX INTEGER{
                      no(0),
                      e20mhz(1),
                      e40mhz(2),
                      e20-40mhz(3)
                    }
                    MAX-ACCESS read-only
                    STATUS current
                    DESCRIPTION "Short-Guard-Interval"
                    ::= {  staWlanCompetEntry 27 }

staWlanCompetCompre OBJECT-TYPE
                    SYNTAX INTEGER{
                      no(0),
                      yes(1)
                    }
                    MAX-ACCESS read-only
                    STATUS current
                    DESCRIPTION "Compression"
                    ::= {  staWlanCompetEntry 21 }

staWlanCompetAge OBJECT-TYPE
                    SYNTAX INTEGER (0..2147483647)
                    MAX-ACCESS read-only
                    STATUS current
                    DESCRIPTION "Age"
                    ::= {  staWlanCompetEntry 25 }

staWlanCompetRate OBJECT-TYPE
                    SYNTAX INTEGER{
                      unknown(0),
                      e1m(1),
                      e2m(2),
                      e5m(3),
                      e5-5m(4),
                      e8m(5),
                      e11m(6),
                      e6m(12),
                      e9m(13),
                      e12m(14),
                      e18m(15),
                      e24m(16),
                      e36m(17),
                      e48m(18),
                      e54m(19),
                      t-12m(20),
                      t-18m(21),
                      t-24m(22),
                      t-36m(23),
                      t-48m(24),
                      t-72m(25),
                      t-96m(26),
                      t-108m(27),
                      ht-1-6-5m(28),
                      ht-1-13m(29),
                      ht-1-19-5m(30),
                      ht-1-26m(31),
                      ht-1-39m(32),
                      ht-1-52m(33),
                      ht-1-58-5m(34),
                      ht-1-65m(35),
                      ht-2-13m(36),
                      ht-2-26m(37),
                      ht-2-39m(38),
                      ht-2-52m(39),
                      ht-2-78m(40),
                      ht-2-104m(41),
                      ht-2-117m(42),
                      ht-2-130m(43)
                    }
                    MAX-ACCESS read-only
                    STATUS current
                    DESCRIPTION "Rate"
                    ::= {  staWlanCompetEntry 19 }

staWlanCompetNonerp OBJECT-TYPE
                    SYNTAX INTEGER{
                      no(0),
                      yes(1)
                    }
                    MAX-ACCESS read-only
                    STATUS current
                    DESCRIPTION "NonERP-Present"
                    ::= {  staWlanCompetEntry 20 }

staWlanCompetIdenti OBJECT-TYPE
                    SYNTAX DisplayString (SIZE(0..16))
                    MAX-ACCESS read-only
                    STATUS current
                    DESCRIPTION "Identification"
                    ::= {  staWlanCompetEntry 23 }

staWlanCompetInterp OBJECT-TYPE
                    SYNTAX DisplayString (SIZE(0..16))
                    MAX-ACCESS read-only
                    STATUS current
                    DESCRIPTION "Interpoint-Peer-Name"
                    ::= {  staWlanCompetEntry 31 }

staWlanRadiusTable OBJECT-TYPE
                   SYNTAX SEQUENCE OF StaWlanRadiusEntry
                   MAX-ACCESS not-accessible
                   STATUS current
                   DESCRIPTION "RADIUS-Cache"
                   ::= {  staWlan 48 }

staWlanRadiusEntry OBJECT-TYPE
                   SYNTAX StaWlanRadiusEntry
                   MAX-ACCESS not-accessible
                   STATUS current
                   DESCRIPTION "entry in table"
                   INDEX { staWlanRadiusMac }
                   ::= {  staWlanRadiusTable 1 }

StaWlanRadiusEntry ::= SEQUENCE {
                   staWlanRadiusMac MacAddress,
                   staWlanRadiusAll INTEGER,
                   staWlanRadiusAge INTEGER
                  }

staWlanRadiusMac OBJECT-TYPE
                 SYNTAX MacAddress
                 MAX-ACCESS read-only
                 STATUS current
                 DESCRIPTION "MAC-Address"
                 ::= {  staWlanRadiusEntry 1 }

staWlanRadiusAll OBJECT-TYPE
                 SYNTAX INTEGER{
                   no(0),
                   yes(1)
                 }
                 MAX-ACCESS read-only
                 STATUS current
                 DESCRIPTION "Allowed"
                 ::= {  staWlanRadiusEntry 2 }

staWlanRadiusAge OBJECT-TYPE
                 SYNTAX INTEGER (0..2147483647)
                 MAX-ACCESS read-only
                 STATUS current
                 DESCRIPTION "Age"
                 ::= {  staWlanRadiusEntry 3 }

staWan OBJECT IDENTIFIER ::= { sta 4}
staWanBytetransTable OBJECT-TYPE
                     SYNTAX SEQUENCE OF StaWanBytetransEntry
                     MAX-ACCESS not-accessible
                     STATUS current
                     DESCRIPTION "Byte-Transport"
                     ::= {  staWan 1 }

staWanBytetransEntry OBJECT-TYPE
                     SYNTAX StaWanBytetransEntry
                     MAX-ACCESS not-accessible
                     STATUS current
                     DESCRIPTION "entry in table"
                     INDEX { staWanBytetransIfc }
                     ::= {  staWanBytetransTable 1 }

StaWanBytetransEntry ::= SEQUENCE {
                     staWanBytetransIfc INTEGER,
                     staWanBytetransCrx Counter32,
                     staWanBytetransRxb Counter32,
                     staWanBytetransTxb Counter32,
                     staWanBytetransCtx Counter32
                    }

staWanBytetransIfc OBJECT-TYPE
                   SYNTAX INTEGER{
                     dsl-ch-1(1),
                     ext(2)
                   }
                   MAX-ACCESS read-only
                   STATUS current
                   DESCRIPTION "Ifc"
                   ::= {  staWanBytetransEntry 1 }

staWanBytetransCrx OBJECT-TYPE
                   SYNTAX Counter32
                   MAX-ACCESS read-only
                   STATUS current
                   DESCRIPTION "CRx-Bytes"
                   ::= {  staWanBytetransEntry 2 }

staWanBytetransRxb OBJECT-TYPE
                   SYNTAX Counter32
                   MAX-ACCESS read-only
                   STATUS current
                   DESCRIPTION "Rx-Bytes"
                   ::= {  staWanBytetransEntry 3 }

staWanBytetransTxb OBJECT-TYPE
                   SYNTAX Counter32
                   MAX-ACCESS read-only
                   STATUS current
                   DESCRIPTION "Tx-Bytes"
                   ::= {  staWanBytetransEntry 4 }

staWanBytetransCtx OBJECT-TYPE
                   SYNTAX Counter32
                   MAX-ACCESS read-only
                   STATUS current
                   DESCRIPTION "CTx-Bytes"
                   ::= {  staWanBytetransEntry 5 }

staWanPackettraTable OBJECT-TYPE
                     SYNTAX SEQUENCE OF StaWanPackettraEntry
                     MAX-ACCESS not-accessible
                     STATUS current
                     DESCRIPTION "Packet-Transport"
                     ::= {  staWan 2 }

staWanPackettraEntry OBJECT-TYPE
                     SYNTAX StaWanPackettraEntry
                     MAX-ACCESS not-accessible
                     STATUS current
                     DESCRIPTION "entry in table"
                     INDEX { staWanPackettraIfc }
                     ::= {  staWanPackettraTable 1 }

StaWanPackettraEntry ::= SEQUENCE {
                     staWanPackettraIfc INTEGER,
                     staWanPackettraRx Counter32,
                     staWanPackettraTxt Counter32,
                     staWanPackettraTxn Counter32,
                     staWanPackettraTxr Counter32,
                     staWanPackettraTxu Counter32
                    }

staWanPackettraIfc OBJECT-TYPE
                   SYNTAX INTEGER{
                     dsl-ch-1(1),
                     ext(2)
                   }
                   MAX-ACCESS read-only
                   STATUS current
                   DESCRIPTION "Ifc"
                   ::= {  staWanPackettraEntry 1 }

staWanPackettraRx OBJECT-TYPE
                   SYNTAX Counter32
                   MAX-ACCESS read-only
                   STATUS current
                   DESCRIPTION "Rx"
                   ::= {  staWanPackettraEntry 2 }

staWanPackettraTxt OBJECT-TYPE
                   SYNTAX Counter32
                   MAX-ACCESS read-only
                   STATUS current
                   DESCRIPTION "Tx-total"
                   ::= {  staWanPackettraEntry 3 }

staWanPackettraTxn OBJECT-TYPE
                   SYNTAX Counter32
                   MAX-ACCESS read-only
                   STATUS current
                   DESCRIPTION "Tx-normal"
                   ::= {  staWanPackettraEntry 4 }

staWanPackettraTxr OBJECT-TYPE
                   SYNTAX Counter32
                   MAX-ACCESS read-only
                   STATUS current
                   DESCRIPTION "Tx-reliable"
                   ::= {  staWanPackettraEntry 5 }

staWanPackettraTxu OBJECT-TYPE
                   SYNTAX Counter32
                   MAX-ACCESS read-only
                   STATUS current
                   DESCRIPTION "Tx-urgent"
                   ::= {  staWanPackettraEntry 6 }

staWanErrorsTable OBJECT-TYPE
                     SYNTAX SEQUENCE OF StaWanErrorsEntry
                     MAX-ACCESS not-accessible
                     STATUS current
                     DESCRIPTION "Errors"
                     ::= {  staWan 3 }

staWanErrorsEntry OBJECT-TYPE
                     SYNTAX StaWanErrorsEntry
                     MAX-ACCESS not-accessible
                     STATUS current
                     DESCRIPTION "entry in table"
                     INDEX { staWanErrorsIfc }
                     ::= {  staWanErrorsTable 1 }

StaWanErrorsEntry ::= SEQUENCE {
                     staWanErrorsIfc INTEGER,
                     staWanErrorsRxl1 Counter32,
                     staWanErrorsRxl2 Counter32,
                     staWanErrorsRxl3 Counter32,
                     staWanErrorsStac Counter32,
                     staWanErrorsTxer Counter32
                    }

staWanErrorsIfc OBJECT-TYPE
                 SYNTAX INTEGER{
                   dsl-ch-1(1),
                   ext(2)
                 }
                 MAX-ACCESS read-only
                 STATUS current
                 DESCRIPTION "Ifc"
                 ::= {  staWanErrorsEntry 1 }

staWanErrorsRxl1 OBJECT-TYPE
                 SYNTAX Counter32
                 MAX-ACCESS read-only
                 STATUS current
                 DESCRIPTION "Rx-l1-Error"
                 ::= {  staWanErrorsEntry 2 }

staWanErrorsRxl2 OBJECT-TYPE
                 SYNTAX Counter32
                 MAX-ACCESS read-only
                 STATUS current
                 DESCRIPTION "Rx-l2-Error"
                 ::= {  staWanErrorsEntry 3 }

staWanErrorsRxl3 OBJECT-TYPE
                 SYNTAX Counter32
                 MAX-ACCESS read-only
                 STATUS current
                 DESCRIPTION "Rx-l3-Error"
                 ::= {  staWanErrorsEntry 4 }

staWanErrorsStac OBJECT-TYPE
                 SYNTAX Counter32
                 MAX-ACCESS read-only
                 STATUS current
                 DESCRIPTION "Stack-Error"
                 ::= {  staWanErrorsEntry 5 }

staWanErrorsTxer OBJECT-TYPE
                 SYNTAX Counter32
                 MAX-ACCESS read-only
                 STATUS current
                 DESCRIPTION "Tx-Error"
                 ::= {  staWanErrorsEntry 6 }

staWanWantxdisc OBJECT-TYPE
                SYNTAX Counter32
                MAX-ACCESS read-only
                STATUS current
                DESCRIPTION "WAN-Tx-Discarded"
                ::= {  staWan 4 }

staWanWanheappa OBJECT-TYPE
                SYNTAX INTEGER
                MAX-ACCESS read-only
                STATUS current
                DESCRIPTION "WAN-Heap-Packets"
                ::= {  staWan 5 }

staWanWanqueuep OBJECT-TYPE
                SYNTAX INTEGER
                MAX-ACCESS read-only
                STATUS current
                DESCRIPTION "WAN-Queue-Packets"
                ::= {  staWan 6 }

staWanWanqueuee OBJECT-TYPE
                SYNTAX Counter32
                MAX-ACCESS read-only
                STATUS current
                DESCRIPTION "WAN-Queue-Errors"
                ::= {  staWan 7 }

staWanWanqueuem OBJECT-TYPE
                SYNTAX Counter32
                MAX-ACCESS read-only
                STATUS current
                DESCRIPTION "WAN-Queue-Mgt-Drop"
                ::= {  staWan 21 }

staWanThroughpuTable OBJECT-TYPE
                     SYNTAX SEQUENCE OF StaWanThroughpuEntry
                     MAX-ACCESS not-accessible
                     STATUS current
                     DESCRIPTION "Throughput"
                     ::= {  staWan 8 }

staWanThroughpuEntry OBJECT-TYPE
                     SYNTAX StaWanThroughpuEntry
                     MAX-ACCESS not-accessible
                     STATUS current
                     DESCRIPTION "entry in table"
                     INDEX { staWanThroughpuIfc }
                     ::= {  staWanThroughpuTable 1 }

StaWanThroughpuEntry ::= SEQUENCE {
                     staWanThroughpuIfc INTEGER,
                     staWanThroughpuRxsc INTEGER,
                     staWanThroughpuTxsc INTEGER,
                     staWanThroughpuRxsa INTEGER,
                     staWanThroughpuTxsa INTEGER
                    }

staWanThroughpuIfc OBJECT-TYPE
                    SYNTAX INTEGER{
                      dsl-ch-1(1),
                      ext(2)
                    }
                    MAX-ACCESS read-only
                    STATUS current
                    DESCRIPTION "Ifc"
                    ::= {  staWanThroughpuEntry 1 }

staWanThroughpuRxsc OBJECT-TYPE
                    SYNTAX INTEGER (0..2147483647)
                    MAX-ACCESS read-only
                    STATUS current
                    DESCRIPTION "Rx/s current"
                    ::= {  staWanThroughpuEntry 2 }

staWanThroughpuTxsc OBJECT-TYPE
                    SYNTAX INTEGER (0..2147483647)
                    MAX-ACCESS read-only
                    STATUS current
                    DESCRIPTION "Tx/s current"
                    ::= {  staWanThroughpuEntry 3 }

staWanThroughpuRxsa OBJECT-TYPE
                    SYNTAX INTEGER (0..2147483647)
                    MAX-ACCESS read-only
                    STATUS current
                    DESCRIPTION "Rx/s average"
                    ::= {  staWanThroughpuEntry 4 }

staWanThroughpuTxsa OBJECT-TYPE
                    SYNTAX INTEGER (0..2147483647)
                    MAX-ACCESS read-only
                    STATUS current
                    DESCRIPTION "Tx/s average"
                    ::= {  staWanThroughpuEntry 5 }

staWanDeleteval OBJECT-TYPE
                SYNTAX DisplayString
                MAX-ACCESS read-write
                STATUS current
                DESCRIPTION "Delete-Values"
                ::= {  staWan 9 }

staWanConnectio OBJECT-TYPE
                SYNTAX INTEGER
                MAX-ACCESS read-only
                STATUS current
                DESCRIPTION "Connections"
                ::= {  staWan 10 }

staWanMtuTable OBJECT-TYPE
                     SYNTAX SEQUENCE OF StaWanMtuEntry
                     MAX-ACCESS not-accessible
                     STATUS current
                     DESCRIPTION "MTU"
                     ::= {  staWan 11 }

staWanMtuEntry OBJECT-TYPE
                     SYNTAX StaWanMtuEntry
                     MAX-ACCESS not-accessible
                     STATUS current
                     DESCRIPTION "entry in table"
                     INDEX { staWanMtuPee }
                     ::= {  staWanMtuTable 1 }

StaWanMtuEntry ::= SEQUENCE {
                     staWanMtuPee DisplayString,
                     staWanMtuMtu INTEGER
                    }

staWanMtuPee OBJECT-TYPE
             SYNTAX DisplayString (SIZE(0..16))
             MAX-ACCESS read-write
             STATUS current
             DESCRIPTION "Peer"
             ::= {  staWanMtuEntry 1 }

staWanMtuMtu OBJECT-TYPE
             SYNTAX INTEGER (0..65535)
             MAX-ACCESS read-write
             STATUS current
             DESCRIPTION "MTU"
             ::= {  staWanMtuEntry 2 }

staWanActions OBJECT IDENTIFIER ::= { staWan 20}
staWanActionsActTable OBJECT-TYPE
                      SYNTAX SEQUENCE OF StaWanActionsActEntry
                      MAX-ACCESS not-accessible
                      STATUS current
                      DESCRIPTION "Action-Table"
                      ::= {  staWanActions 1 }

staWanActionsActEntry OBJECT-TYPE
                      SYNTAX StaWanActionsActEntry
                      MAX-ACCESS not-accessible
                      STATUS current
                      DESCRIPTION "entry in table"
                      INDEX { staWanActionsActTim }
                      ::= {  staWanActionsActTable 1 }

StaWanActionsActEntry ::= SEQUENCE {
                      staWanActionsActTim DisplayString,
                      staWanActionsActAct DisplayString,
                      staWanActionsActRes DisplayString
                     }

staWanActionsActTim OBJECT-TYPE
                    SYNTAX DisplayString (SIZE(0..19))
                    MAX-ACCESS read-only
                    STATUS current
                    DESCRIPTION "Time"
                    ::= {  staWanActionsActEntry 1 }

staWanActionsActAct OBJECT-TYPE
                    SYNTAX DisplayString (SIZE(0..255))
                    MAX-ACCESS read-only
                    STATUS current
                    DESCRIPTION "Action"
                    ::= {  staWanActionsActEntry 2 }

staWanActionsActRes OBJECT-TYPE
                    SYNTAX DisplayString (SIZE(0..100))
                    MAX-ACCESS read-only
                    STATUS current
                    DESCRIPTION "Result"
                    ::= {  staWanActionsActEntry 3 }

staWanActionsLocTable OBJECT-TYPE
                      SYNTAX SEQUENCE OF StaWanActionsLocEntry
                      MAX-ACCESS not-accessible
                      STATUS current
                      DESCRIPTION "Lock-Table"
                      ::= {  staWanActions 2 }

staWanActionsLocEntry OBJECT-TYPE
                      SYNTAX StaWanActionsLocEntry
                      MAX-ACCESS not-accessible
                      STATUS current
                      DESCRIPTION "entry in table"
                      INDEX { staWanActionsLocInd }
                      ::= {  staWanActionsLocTable 1 }

StaWanActionsLocEntry ::= SEQUENCE {
                      staWanActionsLocInd INTEGER,
                      staWanActionsLocRem INTEGER
                     }

staWanActionsLocInd OBJECT-TYPE
                    SYNTAX INTEGER (0..65535)
                    MAX-ACCESS read-only
                    STATUS current
                    DESCRIPTION "Index"
                    ::= {  staWanActionsLocEntry 1 }

staWanActionsLocRem OBJECT-TYPE
                    SYNTAX INTEGER (0..2147483647)
                    MAX-ACCESS read-only
                    STATUS current
                    DESCRIPTION "Remaining-Locktime"
                    ::= {  staWanActionsLocEntry 2 }

staLan OBJECT IDENTIFIER ::= { sta 5}
staLanLanh OBJECT-TYPE
           SYNTAX INTEGER
           MAX-ACCESS read-only
           STATUS current
           DESCRIPTION "LAN-Heap-Packets"
           ::= {  staLan 7 }

staLanDele OBJECT-TYPE
           SYNTAX DisplayString
           MAX-ACCESS read-write
           STATUS current
           DESCRIPTION "Delete-Values"
           ::= {  staLan 11 }

staLanLanq OBJECT-TYPE
           SYNTAX Counter32
           MAX-ACCESS read-only
           STATUS current
           DESCRIPTION "LAN-Queue-Mgt-Drop"
           ::= {  staLan 60 }

staLanIeee OBJECT IDENTIFIER ::= { staLan 80}
staLanIeeeSupTable OBJECT-TYPE
                   SYNTAX SEQUENCE OF StaLanIeeeSupEntry
                   MAX-ACCESS not-accessible
                   STATUS current
                   DESCRIPTION "Supplicant-Ifc-State"
                   ::= {  staLanIeee 1 }

staLanIeeeSupEntry OBJECT-TYPE
                   SYNTAX StaLanIeeeSupEntry
                   MAX-ACCESS not-accessible
                   STATUS current
                   DESCRIPTION "entry in table"
                   INDEX { staLanIeeeSupIfc }
                   ::= {  staLanIeeeSupTable 1 }

StaLanIeeeSupEntry ::= SEQUENCE {
                   staLanIeeeSupIfc INTEGER,
                   staLanIeeeSupMet INTEGER,
                   staLanIeeeSupSta INTEGER,
                   staLanIeeeSupAut MacAddress
                  }

staLanIeeeSupIfc OBJECT-TYPE
                 SYNTAX INTEGER{
                   lan-1(1)
                 }
                 MAX-ACCESS read-only
                 STATUS current
                 DESCRIPTION "Ifc"
                 ::= {  staLanIeeeSupEntry 1 }

staLanIeeeSupMet OBJECT-TYPE
                 SYNTAX INTEGER{
                   none(0),
                   md5(1024),
                   tls(3328),
                   ttls-pap(5383),
                   ttls-chap(5384),
                   ttls-mschap(5567),
                   ttls-mschapv2(5402),
                   ttls-md5(5380),
                   peap-mschapv2(6426),
                   peap-gtc(6406)
                 }
                 MAX-ACCESS read-only
                 STATUS current
                 DESCRIPTION "Method"
                 ::= {  staLanIeeeSupEntry 2 }

staLanIeeeSupSta OBJECT-TYPE
                 SYNTAX INTEGER{
                   idle(0),
                   unauthorized(1),
                   authorized(2)
                 }
                 MAX-ACCESS read-only
                 STATUS current
                 DESCRIPTION "State"
                 ::= {  staLanIeeeSupEntry 3 }

staLanIeeeSupAut OBJECT-TYPE
                 SYNTAX MacAddress
                 MAX-ACCESS read-only
                 STATUS current
                 DESCRIPTION "Authenticator-Address"
                 ::= {  staLanIeeeSupEntry 4 }

staLanInteTable OBJECT-TYPE
                SYNTAX SEQUENCE OF StaLanInteEntry
                MAX-ACCESS not-accessible
                STATUS current
                DESCRIPTION "Interfaces"
                ::= {  staLan 51 }

staLanInteEntry OBJECT-TYPE
                SYNTAX StaLanInteEntry
                MAX-ACCESS not-accessible
                STATUS current
                DESCRIPTION "entry in table"
                INDEX { staLanInteIfc }
                ::= {  staLanInteTable 1 }

StaLanInteEntry ::= SEQUENCE {
                staLanInteIfc DisplayString,
                staLanInteQue INTEGER,
                staLanInteLin INTEGER,
                staLanInteCon INTEGER,
                staLanInteNeg INTEGER,
                staLanInteFlo INTEGER,
                staLanInteMdi INTEGER
               }

staLanInteIfc OBJECT-TYPE
              SYNTAX DisplayString (SIZE(0..255))
              MAX-ACCESS read-only
              STATUS current
              DESCRIPTION "Ifc"
              ::= {  staLanInteEntry 1 }

staLanInteQue OBJECT-TYPE
              SYNTAX INTEGER (0..2147483647)
              MAX-ACCESS read-only
              STATUS current
              DESCRIPTION "Queue-Packets"
              ::= {  staLanInteEntry 2 }

staLanInteLin OBJECT-TYPE
              SYNTAX INTEGER{
                no(0),
                yes(1)
              }
              MAX-ACCESS read-only
              STATUS current
              DESCRIPTION "Link-Active"
              ::= {  staLanInteEntry 3 }

staLanInteCon OBJECT-TYPE
              SYNTAX INTEGER{
                none(0),
                e10b-2(33),
                e10b-5(34),
                e10b-t(1),
                fd10b-tx(2),
                e100b-tx(3),
                fd100b-tx(4),
                fd1000b-tx(6),
                power-down(255)
              }
              MAX-ACCESS read-only
              STATUS current
              DESCRIPTION "Connector"
              ::= {  staLanInteEntry 4 }

staLanInteNeg OBJECT-TYPE
              SYNTAX INTEGER{
                no(0),
                yes(1)
              }
              MAX-ACCESS read-only
              STATUS current
              DESCRIPTION "Negotiation-Done"
              ::= {  staLanInteEntry 5 }

staLanInteFlo OBJECT-TYPE
              SYNTAX INTEGER{
                no(0),
                yes(1)
              }
              MAX-ACCESS read-only
              STATUS current
              DESCRIPTION "Flow-Control"
              ::= {  staLanInteEntry 6 }

staLanInteMdi OBJECT-TYPE
              SYNTAX INTEGER{
                unknown(0),
                mdi(1),
                mdix(2)
              }
              MAX-ACCESS read-only
              STATUS current
              DESCRIPTION "MDI-Mode"
              ::= {  staLanInteEntry 7 }

staLanByteTable OBJECT-TYPE
                SYNTAX SEQUENCE OF StaLanByteEntry
                MAX-ACCESS not-accessible
                STATUS current
                DESCRIPTION "Byte-Transport"
                ::= {  staLan 52 }

staLanByteEntry OBJECT-TYPE
                SYNTAX StaLanByteEntry
                MAX-ACCESS not-accessible
                STATUS current
                DESCRIPTION "entry in table"
                INDEX { staLanByteIfc }
                ::= {  staLanByteTable 1 }

StaLanByteEntry ::= SEQUENCE {
                staLanByteIfc DisplayString,
                staLanByteTxbyte Counter64,
                staLanByteRxbyte Counter64,
                staLanByteThroug DisplayString,
                staLanByteMaxthr DisplayString,
                staLanByteBytest INTEGER,
                staLanByteBytesm INTEGER
               }

staLanByteIfc OBJECT-TYPE
                 SYNTAX DisplayString (SIZE(0..255))
                 MAX-ACCESS read-only
                 STATUS current
                 DESCRIPTION "Ifc"
                 ::= {  staLanByteEntry 1 }

staLanByteTxbyte OBJECT-TYPE
                 SYNTAX Counter64
                 MAX-ACCESS read-only
                 STATUS current
                 DESCRIPTION "Tx-Bytes"
                 ::= {  staLanByteEntry 2 }

staLanByteRxbyte OBJECT-TYPE
                 SYNTAX Counter64
                 MAX-ACCESS read-only
                 STATUS current
                 DESCRIPTION "Rx-Bytes"
                 ::= {  staLanByteEntry 3 }

staLanByteThroug OBJECT-TYPE
                 SYNTAX DisplayString (SIZE(0..255))
                 MAX-ACCESS read-only
                 STATUS current
                 DESCRIPTION "Throughput"
                 ::= {  staLanByteEntry 4 }

staLanByteMaxthr OBJECT-TYPE
                 SYNTAX DisplayString (SIZE(0..255))
                 MAX-ACCESS read-only
                 STATUS current
                 DESCRIPTION "Max.-Throughput"
                 ::= {  staLanByteEntry 5 }

staLanByteBytest OBJECT-TYPE
                 SYNTAX INTEGER (0..2147483647)
                 MAX-ACCESS read-only
                 STATUS current
                 DESCRIPTION "Bytes-Throughput"
                 ::= {  staLanByteEntry 6 }

staLanByteBytesm OBJECT-TYPE
                 SYNTAX INTEGER (0..2147483647)
                 MAX-ACCESS read-only
                 STATUS current
                 DESCRIPTION "Bytes-Max.-Throughput"
                 ::= {  staLanByteEntry 7 }

staLanPackTable OBJECT-TYPE
                SYNTAX SEQUENCE OF StaLanPackEntry
                MAX-ACCESS not-accessible
                STATUS current
                DESCRIPTION "Packet-Transport"
                ::= {  staLan 53 }

staLanPackEntry OBJECT-TYPE
                SYNTAX StaLanPackEntry
                MAX-ACCESS not-accessible
                STATUS current
                DESCRIPTION "entry in table"
                INDEX { staLanPackIfc }
                ::= {  staLanPackTable 1 }

StaLanPackEntry ::= SEQUENCE {
                staLanPackIfc DisplayString,
                staLanPackRxp Counter32,
                staLanPackTxp Counter32,
                staLanPackRxb Counter32,
                staLanPackRxm Counter32,
                staLanPackRxu Counter32,
                staLanPackTxb Counter32,
                staLanPackTxm Counter32,
                staLanPackTxu Counter32
               }

staLanPackIfc OBJECT-TYPE
              SYNTAX DisplayString (SIZE(0..255))
              MAX-ACCESS read-only
              STATUS current
              DESCRIPTION "Ifc"
              ::= {  staLanPackEntry 1 }

staLanPackRxp OBJECT-TYPE
              SYNTAX Counter32
              MAX-ACCESS read-only
              STATUS current
              DESCRIPTION "Rx-Packets"
              ::= {  staLanPackEntry 2 }

staLanPackTxp OBJECT-TYPE
              SYNTAX Counter32
              MAX-ACCESS read-only
              STATUS current
              DESCRIPTION "Tx-Packets"
              ::= {  staLanPackEntry 3 }

staLanPackRxb OBJECT-TYPE
              SYNTAX Counter32
              MAX-ACCESS read-only
              STATUS current
              DESCRIPTION "Rx-Broadcasts"
              ::= {  staLanPackEntry 4 }

staLanPackRxm OBJECT-TYPE
              SYNTAX Counter32
              MAX-ACCESS read-only
              STATUS current
              DESCRIPTION "Rx-Multicasts"
              ::= {  staLanPackEntry 5 }

staLanPackRxu OBJECT-TYPE
              SYNTAX Counter32
              MAX-ACCESS read-only
              STATUS current
              DESCRIPTION "Rx-Unicasts"
              ::= {  staLanPackEntry 6 }

staLanPackTxb OBJECT-TYPE
              SYNTAX Counter32
              MAX-ACCESS read-only
              STATUS current
              DESCRIPTION "Tx-Broadcasts"
              ::= {  staLanPackEntry 7 }

staLanPackTxm OBJECT-TYPE
              SYNTAX Counter32
              MAX-ACCESS read-only
              STATUS current
              DESCRIPTION "Tx-Multicasts"
              ::= {  staLanPackEntry 8 }

staLanPackTxu OBJECT-TYPE
              SYNTAX Counter32
              MAX-ACCESS read-only
              STATUS current
              DESCRIPTION "Tx-Unicasts"
              ::= {  staLanPackEntry 9 }

staLanErroTable OBJECT-TYPE
                SYNTAX SEQUENCE OF StaLanErroEntry
                MAX-ACCESS not-accessible
                STATUS current
                DESCRIPTION "Errors"
                ::= {  staLan 54 }

staLanErroEntry OBJECT-TYPE
                SYNTAX StaLanErroEntry
                MAX-ACCESS not-accessible
                STATUS current
                DESCRIPTION "entry in table"
                INDEX { staLanErroIfc }
                ::= {  staLanErroTable 1 }

StaLanErroEntry ::= SEQUENCE {
                staLanErroIfc DisplayString,
                staLanErroRxe Counter32,
                staLanErroTxe Counter32,
                staLanErroSta Counter32,
                staLanErroNic Counter32,
                staLanErroQue Counter32,
                staLanErroRxc Counter32,
                staLanErroCol Counter32
               }

staLanErroIfc OBJECT-TYPE
              SYNTAX DisplayString (SIZE(0..255))
              MAX-ACCESS read-only
              STATUS current
              DESCRIPTION "Ifc"
              ::= {  staLanErroEntry 1 }

staLanErroRxe OBJECT-TYPE
              SYNTAX Counter32
              MAX-ACCESS read-only
              STATUS current
              DESCRIPTION "Rx-Errors"
              ::= {  staLanErroEntry 2 }

staLanErroTxe OBJECT-TYPE
              SYNTAX Counter32
              MAX-ACCESS read-only
              STATUS current
              DESCRIPTION "Tx-Errors"
              ::= {  staLanErroEntry 3 }

staLanErroSta OBJECT-TYPE
              SYNTAX Counter32
              MAX-ACCESS read-only
              STATUS current
              DESCRIPTION "Stack-Errors"
              ::= {  staLanErroEntry 4 }

staLanErroNic OBJECT-TYPE
              SYNTAX Counter32
              MAX-ACCESS read-only
              STATUS current
              DESCRIPTION "NIC-Errors"
              ::= {  staLanErroEntry 5 }

staLanErroQue OBJECT-TYPE
              SYNTAX Counter32
              MAX-ACCESS read-only
              STATUS current
              DESCRIPTION "Queue-Errors"
              ::= {  staLanErroEntry 6 }

staLanErroRxc OBJECT-TYPE
              SYNTAX Counter32
              MAX-ACCESS read-only
              STATUS current
              DESCRIPTION "Rx-CRC-Errors"
              ::= {  staLanErroEntry 7 }

staLanErroCol OBJECT-TYPE
              SYNTAX Counter32
              MAX-ACCESS read-only
              STATUS current
              DESCRIPTION "Collisions"
              ::= {  staLanErroEntry 8 }

staPpp OBJECT IDENTIFIER ::= { sta 6}
staPppPppTable OBJECT-TYPE
               SYNTAX SEQUENCE OF StaPppPppEntry
               MAX-ACCESS not-accessible
               STATUS current
               DESCRIPTION "PPP-Phases"
               ::= {  staPpp 1 }

staPppPppEntry OBJECT-TYPE
               SYNTAX StaPppPppEntry
               MAX-ACCESS not-accessible
               STATUS current
               DESCRIPTION "entry in table"
               INDEX { staPppPppIfc }
               ::= {  staPppPppTable 1 }

StaPppPppEntry ::= SEQUENCE {
               staPppPppIfc INTEGER,
               staPppPppPha INTEGER,
               staPppPppLcp INTEGER,
               staPppPppIpc INTEGER,
               staPppPppCcp INTEGER
              }

staPppPppIfc OBJECT-TYPE
             SYNTAX INTEGER{
               dsl-ch-1(1),
               ext(2)
             }
             MAX-ACCESS read-only
             STATUS current
             DESCRIPTION "Ifc"
             ::= {  staPppPppEntry 1 }

staPppPppPha OBJECT-TYPE
             SYNTAX INTEGER{
               dead(1),
               establish(2),
               terminate(3),
               authenticate(4),
               callback(5),
               network(6)
             }
             MAX-ACCESS read-only
             STATUS current
             DESCRIPTION "Phase to"
             ::= {  staPppPppEntry 2 }

staPppPppLcp OBJECT-TYPE
             SYNTAX INTEGER{
               initial(1),
               startng(2),
               closed(3),
               stopped(4),
               closing(5),
               stoppng(6),
               reqsent(7),
               ackrcvd(8),
               acksent(9),
               opened(10)
             }
             MAX-ACCESS read-only
             STATUS current
             DESCRIPTION "LCP"
             ::= {  staPppPppEntry 3 }

staPppPppIpc OBJECT-TYPE
             SYNTAX INTEGER{
               initial(1),
               startng(2),
               closed(3),
               stopped(4),
               closing(5),
               stoppng(6),
               reqsent(7),
               ackrcvd(8),
               acksent(9),
               opened(10)
             }
             MAX-ACCESS read-only
             STATUS current
             DESCRIPTION "IPCP"
             ::= {  staPppPppEntry 4 }

staPppPppCcp OBJECT-TYPE
             SYNTAX INTEGER{
               initial(1),
               startng(2),
               closed(3),
               stopped(4),
               closing(5),
               stoppng(6),
               reqsent(7),
               ackrcvd(8),
               acksent(9),
               opened(10)
             }
             MAX-ACCESS read-only
             STATUS current
             DESCRIPTION "CCP"
             ::= {  staPppPppEntry 6 }

staPppLcp OBJECT IDENTIFIER ::= { staPpp 2}
staPppLcpRxerrors OBJECT-TYPE
                      SYNTAX Counter32
                      MAX-ACCESS read-only
                      STATUS current
                      DESCRIPTION "Rx-Errors"
                      ::= {  staPppLcp 1 }

staPppLcpRxdiscarded OBJECT-TYPE
                      SYNTAX Counter32
                      MAX-ACCESS read-only
                      STATUS current
                      DESCRIPTION "Rx-Discarded"
                      ::= {  staPppLcp 2 }

staPppLcpRxconfigrequ OBJECT-TYPE
                      SYNTAX Counter32
                      MAX-ACCESS read-only
                      STATUS current
                      DESCRIPTION "Rx-Config-Request"
                      ::= {  staPppLcp 3 }

staPppLcpRxconfigack OBJECT-TYPE
                      SYNTAX Counter32
                      MAX-ACCESS read-only
                      STATUS current
                      DESCRIPTION "Rx-Config-Ack."
                      ::= {  staPppLcp 4 }

staPppLcpRxconfignak OBJECT-TYPE
                      SYNTAX Counter32
                      MAX-ACCESS read-only
                      STATUS current
                      DESCRIPTION "Rx-Config-Nak."
                      ::= {  staPppLcp 5 }

staPppLcpRxconfigreje OBJECT-TYPE
                      SYNTAX Counter32
                      MAX-ACCESS read-only
                      STATUS current
                      DESCRIPTION "Rx-Config-Reject"
                      ::= {  staPppLcp 6 }

staPppLcpRxterminater OBJECT-TYPE
                      SYNTAX Counter32
                      MAX-ACCESS read-only
                      STATUS current
                      DESCRIPTION "Rx-Terminate-Request"
                      ::= {  staPppLcp 7 }

staPppLcpRxterminatea OBJECT-TYPE
                      SYNTAX Counter32
                      MAX-ACCESS read-only
                      STATUS current
                      DESCRIPTION "Rx-Terminate-Ack."
                      ::= {  staPppLcp 8 }

staPppLcpRxcodereject OBJECT-TYPE
                      SYNTAX Counter32
                      MAX-ACCESS read-only
                      STATUS current
                      DESCRIPTION "Rx-Code-Reject"
                      ::= {  staPppLcp 9 }

staPppLcpRxprotocolre OBJECT-TYPE
                      SYNTAX Counter32
                      MAX-ACCESS read-only
                      STATUS current
                      DESCRIPTION "Rx-Protocol-Reject"
                      ::= {  staPppLcp 10 }

staPppLcpRxechoreques OBJECT-TYPE
                      SYNTAX Counter32
                      MAX-ACCESS read-only
                      STATUS current
                      DESCRIPTION "Rx-Echo-Request"
                      ::= {  staPppLcp 11 }

staPppLcpRxechoreply OBJECT-TYPE
                      SYNTAX Counter32
                      MAX-ACCESS read-only
                      STATUS current
                      DESCRIPTION "Rx-Echo-Reply"
                      ::= {  staPppLcp 12 }

staPppLcpRxdiscardreq OBJECT-TYPE
                      SYNTAX Counter32
                      MAX-ACCESS read-only
                      STATUS current
                      DESCRIPTION "Rx-Discard-Request"
                      ::= {  staPppLcp 13 }

staPppLcpTxconfigrequ OBJECT-TYPE
                      SYNTAX Counter32
                      MAX-ACCESS read-only
                      STATUS current
                      DESCRIPTION "Tx-Config-Request"
                      ::= {  staPppLcp 14 }

staPppLcpTxconfigack OBJECT-TYPE
                      SYNTAX Counter32
                      MAX-ACCESS read-only
                      STATUS current
                      DESCRIPTION "Tx-Config-Ack."
                      ::= {  staPppLcp 15 }

staPppLcpTxconfignak OBJECT-TYPE
                      SYNTAX Counter32
                      MAX-ACCESS read-only
                      STATUS current
                      DESCRIPTION "Tx-Config-Nak."
                      ::= {  staPppLcp 16 }

staPppLcpTxconfigreje OBJECT-TYPE
                      SYNTAX Counter32
                      MAX-ACCESS read-only
                      STATUS current
                      DESCRIPTION "Tx-Config-Reject"
                      ::= {  staPppLcp 17 }

staPppLcpTxterminater OBJECT-TYPE
                      SYNTAX Counter32
                      MAX-ACCESS read-only
                      STATUS current
                      DESCRIPTION "Tx-Terminate-Request"
                      ::= {  staPppLcp 18 }

staPppLcpTxterminatea OBJECT-TYPE
                      SYNTAX Counter32
                      MAX-ACCESS read-only
                      STATUS current
                      DESCRIPTION "Tx-Terminate-Ack."
                      ::= {  staPppLcp 19 }

staPppLcpTxcodereject OBJECT-TYPE
                      SYNTAX Counter32
                      MAX-ACCESS read-only
                      STATUS current
                      DESCRIPTION "Tx-Code-Reject"
                      ::= {  staPppLcp 20 }

staPppLcpTxprotocolre OBJECT-TYPE
                      SYNTAX Counter32
                      MAX-ACCESS read-only
                      STATUS current
                      DESCRIPTION "Tx-Protocol-Reject"
                      ::= {  staPppLcp 21 }

staPppLcpTxechoreques OBJECT-TYPE
                      SYNTAX Counter32
                      MAX-ACCESS read-only
                      STATUS current
                      DESCRIPTION "Tx-Echo-Request"
                      ::= {  staPppLcp 22 }

staPppLcpTxechoreply OBJECT-TYPE
                      SYNTAX Counter32
                      MAX-ACCESS read-only
                      STATUS current
                      DESCRIPTION "Tx-Echo-Reply"
                      ::= {  staPppLcp 23 }

staPppLcpTxdiscardreq OBJECT-TYPE
                      SYNTAX Counter32
                      MAX-ACCESS read-only
                      STATUS current
                      DESCRIPTION "Tx-Discard-Request"
                      ::= {  staPppLcp 24 }

staPppLcpDeletevalues OBJECT-TYPE
                      SYNTAX DisplayString
                      MAX-ACCESS read-write
                      STATUS current
                      DESCRIPTION "Delete-Values"
                      ::= {  staPppLcp 25 }

staPppPap OBJECT IDENTIFIER ::= { staPpp 3}
staPppPapRxdis OBJECT-TYPE
               SYNTAX Counter32
               MAX-ACCESS read-only
               STATUS current
               DESCRIPTION "Rx-Discarded"
               ::= {  staPppPap 1 }

staPppPapRxreq OBJECT-TYPE
               SYNTAX Counter32
               MAX-ACCESS read-only
               STATUS current
               DESCRIPTION "Rx-Request"
               ::= {  staPppPap 2 }

staPppPapRxsuc OBJECT-TYPE
               SYNTAX Counter32
               MAX-ACCESS read-only
               STATUS current
               DESCRIPTION "Rx-Success"
               ::= {  staPppPap 3 }

staPppPapRxfai OBJECT-TYPE
               SYNTAX Counter32
               MAX-ACCESS read-only
               STATUS current
               DESCRIPTION "Rx-Failure"
               ::= {  staPppPap 4 }

staPppPapTxret OBJECT-TYPE
               SYNTAX Counter32
               MAX-ACCESS read-only
               STATUS current
               DESCRIPTION "Tx-Retry"
               ::= {  staPppPap 5 }

staPppPapTxreq OBJECT-TYPE
               SYNTAX Counter32
               MAX-ACCESS read-only
               STATUS current
               DESCRIPTION "Tx-Request"
               ::= {  staPppPap 6 }

staPppPapTxsuc OBJECT-TYPE
               SYNTAX Counter32
               MAX-ACCESS read-only
               STATUS current
               DESCRIPTION "Tx-Success"
               ::= {  staPppPap 7 }

staPppPapTxfai OBJECT-TYPE
               SYNTAX Counter32
               MAX-ACCESS read-only
               STATUS current
               DESCRIPTION "Tx-Failure"
               ::= {  staPppPap 8 }

staPppPapDelet OBJECT-TYPE
               SYNTAX DisplayString
               MAX-ACCESS read-write
               STATUS current
               DESCRIPTION "Delete-Values"
               ::= {  staPppPap 9 }

staPppCha OBJECT IDENTIFIER ::= { staPpp 4}
staPppChaRxdis OBJECT-TYPE
               SYNTAX Counter32
               MAX-ACCESS read-only
               STATUS current
               DESCRIPTION "Rx-Discarded"
               ::= {  staPppCha 1 }

staPppChaRxcha OBJECT-TYPE
               SYNTAX Counter32
               MAX-ACCESS read-only
               STATUS current
               DESCRIPTION "Rx-Challenge"
               ::= {  staPppCha 2 }

staPppChaRxres OBJECT-TYPE
               SYNTAX Counter32
               MAX-ACCESS read-only
               STATUS current
               DESCRIPTION "Rx-Response"
               ::= {  staPppCha 3 }

staPppChaRxsuc OBJECT-TYPE
               SYNTAX Counter32
               MAX-ACCESS read-only
               STATUS current
               DESCRIPTION "Rx-Success"
               ::= {  staPppCha 4 }

staPppChaRxfai OBJECT-TYPE
               SYNTAX Counter32
               MAX-ACCESS read-only
               STATUS current
               DESCRIPTION "Rx-Failure"
               ::= {  staPppCha 5 }

staPppChaTxret OBJECT-TYPE
               SYNTAX Counter32
               MAX-ACCESS read-only
               STATUS current
               DESCRIPTION "Tx-Retry"
               ::= {  staPppCha 6 }

staPppChaTxcha OBJECT-TYPE
               SYNTAX Counter32
               MAX-ACCESS read-only
               STATUS current
               DESCRIPTION "Tx-Challenge"
               ::= {  staPppCha 7 }

staPppChaTxres OBJECT-TYPE
               SYNTAX Counter32
               MAX-ACCESS read-only
               STATUS current
               DESCRIPTION "Tx-Response"
               ::= {  staPppCha 8 }

staPppChaTxsuc OBJECT-TYPE
               SYNTAX Counter32
               MAX-ACCESS read-only
               STATUS current
               DESCRIPTION "Tx-Success"
               ::= {  staPppCha 9 }

staPppChaTxfai OBJECT-TYPE
               SYNTAX Counter32
               MAX-ACCESS read-only
               STATUS current
               DESCRIPTION "Tx-Failure"
               ::= {  staPppCha 10 }

staPppChaDelet OBJECT-TYPE
               SYNTAX DisplayString
               MAX-ACCESS read-write
               STATUS current
               DESCRIPTION "Delete-Values"
               ::= {  staPppCha 11 }

staPppIpc OBJECT IDENTIFIER ::= { staPpp 6}
staPppIpcRxdiscarded OBJECT-TYPE
                      SYNTAX Counter32
                      MAX-ACCESS read-only
                      STATUS current
                      DESCRIPTION "Rx-Discarded"
                      ::= {  staPppIpc 1 }

staPppIpcRxconfigrequ OBJECT-TYPE
                      SYNTAX Counter32
                      MAX-ACCESS read-only
                      STATUS current
                      DESCRIPTION "Rx-Config-Request"
                      ::= {  staPppIpc 2 }

staPppIpcRxconfigack OBJECT-TYPE
                      SYNTAX Counter32
                      MAX-ACCESS read-only
                      STATUS current
                      DESCRIPTION "Rx-Config-Ack."
                      ::= {  staPppIpc 3 }

staPppIpcRxconfignak OBJECT-TYPE
                      SYNTAX Counter32
                      MAX-ACCESS read-only
                      STATUS current
                      DESCRIPTION "Rx-Config-Nak."
                      ::= {  staPppIpc 4 }

staPppIpcRxconfigreje OBJECT-TYPE
                      SYNTAX Counter32
                      MAX-ACCESS read-only
                      STATUS current
                      DESCRIPTION "Rx-Config-Reject"
                      ::= {  staPppIpc 5 }

staPppIpcRxterminater OBJECT-TYPE
                      SYNTAX Counter32
                      MAX-ACCESS read-only
                      STATUS current
                      DESCRIPTION "Rx-Terminate-Request"
                      ::= {  staPppIpc 6 }

staPppIpcRxterminatea OBJECT-TYPE
                      SYNTAX Counter32
                      MAX-ACCESS read-only
                      STATUS current
                      DESCRIPTION "Rx-Terminate-Ack."
                      ::= {  staPppIpc 7 }

staPppIpcRxcodereject OBJECT-TYPE
                      SYNTAX Counter32
                      MAX-ACCESS read-only
                      STATUS current
                      DESCRIPTION "Rx-Code-Reject"
                      ::= {  staPppIpc 8 }

staPppIpcTxconfigrequ OBJECT-TYPE
                      SYNTAX Counter32
                      MAX-ACCESS read-only
                      STATUS current
                      DESCRIPTION "Tx-Config-Request"
                      ::= {  staPppIpc 9 }

staPppIpcTxconfigack OBJECT-TYPE
                      SYNTAX Counter32
                      MAX-ACCESS read-only
                      STATUS current
                      DESCRIPTION "Tx-Config-Ack."
                      ::= {  staPppIpc 10 }

staPppIpcTxconfignak OBJECT-TYPE
                      SYNTAX Counter32
                      MAX-ACCESS read-only
                      STATUS current
                      DESCRIPTION "Tx-Config-Nak."
                      ::= {  staPppIpc 11 }

staPppIpcTxconfigreje OBJECT-TYPE
                      SYNTAX Counter32
                      MAX-ACCESS read-only
                      STATUS current
                      DESCRIPTION "Tx-Config-Reject"
                      ::= {  staPppIpc 12 }

staPppIpcTxterminater OBJECT-TYPE
                      SYNTAX Counter32
                      MAX-ACCESS read-only
                      STATUS current
                      DESCRIPTION "Tx-Terminate-Request"
                      ::= {  staPppIpc 13 }

staPppIpcTxterminatea OBJECT-TYPE
                      SYNTAX Counter32
                      MAX-ACCESS read-only
                      STATUS current
                      DESCRIPTION "Tx-Terminate-Ack."
                      ::= {  staPppIpc 14 }

staPppIpcTxcodereject OBJECT-TYPE
                      SYNTAX Counter32
                      MAX-ACCESS read-only
                      STATUS current
                      DESCRIPTION "Tx-Code-Reject"
                      ::= {  staPppIpc 15 }

staPppIpcDeletevalues OBJECT-TYPE
                      SYNTAX DisplayString
                      MAX-ACCESS read-write
                      STATUS current
                      DESCRIPTION "Delete-Values"
                      ::= {  staPppIpc 16 }

staPppCcp OBJECT IDENTIFIER ::= { staPpp 10}
staPppCcpRxdiscarded OBJECT-TYPE
                      SYNTAX Counter32
                      MAX-ACCESS read-only
                      STATUS current
                      DESCRIPTION "Rx-Discarded"
                      ::= {  staPppCcp 1 }

staPppCcpRxconfigrequ OBJECT-TYPE
                      SYNTAX Counter32
                      MAX-ACCESS read-only
                      STATUS current
                      DESCRIPTION "Rx-Config-Request"
                      ::= {  staPppCcp 2 }

staPppCcpRxconfigack OBJECT-TYPE
                      SYNTAX Counter32
                      MAX-ACCESS read-only
                      STATUS current
                      DESCRIPTION "Rx-Config-Ack."
                      ::= {  staPppCcp 3 }

staPppCcpRxconfignak OBJECT-TYPE
                      SYNTAX Counter32
                      MAX-ACCESS read-only
                      STATUS current
                      DESCRIPTION "Rx-Config-Nak."
                      ::= {  staPppCcp 4 }

staPppCcpRxconfigreje OBJECT-TYPE
                      SYNTAX Counter32
                      MAX-ACCESS read-only
                      STATUS current
                      DESCRIPTION "Rx-Config-Reject"
                      ::= {  staPppCcp 5 }

staPppCcpRxterminater OBJECT-TYPE
                      SYNTAX Counter32
                      MAX-ACCESS read-only
                      STATUS current
                      DESCRIPTION "Rx-Terminate-Request"
                      ::= {  staPppCcp 6 }

staPppCcpRxterminatea OBJECT-TYPE
                      SYNTAX Counter32
                      MAX-ACCESS read-only
                      STATUS current
                      DESCRIPTION "Rx-Terminate-Ack."
                      ::= {  staPppCcp 7 }

staPppCcpRxcodereject OBJECT-TYPE
                      SYNTAX Counter32
                      MAX-ACCESS read-only
                      STATUS current
                      DESCRIPTION "Rx-Code-Reject"
                      ::= {  staPppCcp 8 }

staPppCcpRxresetreque OBJECT-TYPE
                      SYNTAX Counter32
                      MAX-ACCESS read-only
                      STATUS current
                      DESCRIPTION "Rx-Reset-Request"
                      ::= {  staPppCcp 9 }

staPppCcpRxresetack OBJECT-TYPE
                      SYNTAX Counter32
                      MAX-ACCESS read-only
                      STATUS current
                      DESCRIPTION "Rx-Reset-Ack"
                      ::= {  staPppCcp 10 }

staPppCcpTxconfigrequ OBJECT-TYPE
                      SYNTAX Counter32
                      MAX-ACCESS read-only
                      STATUS current
                      DESCRIPTION "Tx-Config-Request"
                      ::= {  staPppCcp 11 }

staPppCcpTxconfigack OBJECT-TYPE
                      SYNTAX Counter32
                      MAX-ACCESS read-only
                      STATUS current
                      DESCRIPTION "Tx-Config-Ack."
                      ::= {  staPppCcp 12 }

staPppCcpTxconfignak OBJECT-TYPE
                      SYNTAX Counter32
                      MAX-ACCESS read-only
                      STATUS current
                      DESCRIPTION "Tx-Config-Nak."
                      ::= {  staPppCcp 13 }

staPppCcpTxconfigreje OBJECT-TYPE
                      SYNTAX Counter32
                      MAX-ACCESS read-only
                      STATUS current
                      DESCRIPTION "Tx-Config-Reject"
                      ::= {  staPppCcp 14 }

staPppCcpTxterminater OBJECT-TYPE
                      SYNTAX Counter32
                      MAX-ACCESS read-only
                      STATUS current
                      DESCRIPTION "Tx-Terminate-Request"
                      ::= {  staPppCcp 15 }

staPppCcpTxterminatea OBJECT-TYPE
                      SYNTAX Counter32
                      MAX-ACCESS read-only
                      STATUS current
                      DESCRIPTION "Tx-Terminate-Ack."
                      ::= {  staPppCcp 16 }

staPppCcpTxcodereject OBJECT-TYPE
                      SYNTAX Counter32
                      MAX-ACCESS read-only
                      STATUS current
                      DESCRIPTION "Tx-Code-Reject"
                      ::= {  staPppCcp 17 }

staPppCcpTxresetreque OBJECT-TYPE
                      SYNTAX Counter32
                      MAX-ACCESS read-only
                      STATUS current
                      DESCRIPTION "Tx-Reset-Request"
                      ::= {  staPppCcp 19 }

staPppCcpTxresetack OBJECT-TYPE
                      SYNTAX Counter32
                      MAX-ACCESS read-only
                      STATUS current
                      DESCRIPTION "Tx-Reset-Ack"
                      ::= {  staPppCcp 20 }

staPppCcpCompressione OBJECT-TYPE
                      SYNTAX Counter32
                      MAX-ACCESS read-only
                      STATUS current
                      DESCRIPTION "Compression-Errors"
                      ::= {  staPppCcp 22 }

staPppCcpDeletevalues OBJECT-TYPE
                      SYNTAX DisplayString
                      MAX-ACCESS read-write
                      STATUS current
                      DESCRIPTION "Delete-Values"
                      ::= {  staPppCcp 21 }

staPppRxo OBJECT IDENTIFIER ::= { staPpp 8}
staPppRxoLcpTable OBJECT-TYPE
                  SYNTAX SEQUENCE OF StaPppRxoLcpEntry
                  MAX-ACCESS not-accessible
                  STATUS current
                  DESCRIPTION "LCP"
                  ::= {  staPppRxo 1 }

staPppRxoLcpEntry OBJECT-TYPE
                  SYNTAX StaPppRxoLcpEntry
                  MAX-ACCESS not-accessible
                  STATUS current
                  DESCRIPTION "entry in table"
                  INDEX { staPppRxoLcpIfc }
                  ::= {  staPppRxoLcpTable 1 }

StaPppRxoLcpEntry ::= SEQUENCE {
                  staPppRxoLcpIfc INTEGER,
                  staPppRxoLcpMru INTEGER,
                  staPppRxoLcpAut INTEGER,
                  staPppRxoLcpMag DisplayString
                 }

staPppRxoLcpIfc OBJECT-TYPE
                SYNTAX INTEGER{
                  dsl-ch-1(1),
                  ext(2)
                }
                MAX-ACCESS read-only
                STATUS current
                DESCRIPTION "Ifc"
                ::= {  staPppRxoLcpEntry 1 }

staPppRxoLcpMru OBJECT-TYPE
                SYNTAX INTEGER (0..65535)
                MAX-ACCESS read-only
                STATUS current
                DESCRIPTION "MRU"
                ::= {  staPppRxoLcpEntry 2 }

staPppRxoLcpAut OBJECT-TYPE
                SYNTAX INTEGER{
                  none(0),
                  chap(8),
                  pap(4)
                }
                MAX-ACCESS read-only
                STATUS current
                DESCRIPTION "Authent."
                ::= {  staPppRxoLcpEntry 4 }

staPppRxoLcpMag OBJECT-TYPE
                SYNTAX DisplayString (SIZE(0..8))
                MAX-ACCESS read-only
                STATUS current
                DESCRIPTION "Magic-Num"
                ::= {  staPppRxoLcpEntry 6 }

staPppRxoIpcTable OBJECT-TYPE
                  SYNTAX SEQUENCE OF StaPppRxoIpcEntry
                  MAX-ACCESS not-accessible
                  STATUS current
                  DESCRIPTION "IPCP"
                  ::= {  staPppRxo 3 }

staPppRxoIpcEntry OBJECT-TYPE
                  SYNTAX StaPppRxoIpcEntry
                  MAX-ACCESS not-accessible
                  STATUS current
                  DESCRIPTION "entry in table"
                  INDEX { staPppRxoIpcIfc }
                  ::= {  staPppRxoIpcTable 1 }

StaPppRxoIpcEntry ::= SEQUENCE {
                  staPppRxoIpcIfc INTEGER,
                  staPppRxoIpcIpadd IpAddress,
                  staPppRxoIpcDnsde IpAddress,
                  staPppRxoIpcDnsba IpAddress,
                  staPppRxoIpcNbnsd IpAddress,
                  staPppRxoIpcNbnsb IpAddress
                 }

staPppRxoIpcIfc OBJECT-TYPE
                  SYNTAX INTEGER{
                    dsl-ch-1(1),
                    ext(2)
                  }
                  MAX-ACCESS read-only
                  STATUS current
                  DESCRIPTION "Ifc"
                  ::= {  staPppRxoIpcEntry 1 }

staPppRxoIpcIpadd OBJECT-TYPE
                  SYNTAX IpAddress
                  MAX-ACCESS read-only
                  STATUS current
                  DESCRIPTION "IP-Address"
                  ::= {  staPppRxoIpcEntry 2 }

staPppRxoIpcDnsde OBJECT-TYPE
                  SYNTAX IpAddress
                  MAX-ACCESS read-only
                  STATUS current
                  DESCRIPTION "DNS-Default"
                  ::= {  staPppRxoIpcEntry 3 }

staPppRxoIpcDnsba OBJECT-TYPE
                  SYNTAX IpAddress
                  MAX-ACCESS read-only
                  STATUS current
                  DESCRIPTION "DNS-Backup"
                  ::= {  staPppRxoIpcEntry 5 }

staPppRxoIpcNbnsd OBJECT-TYPE
                  SYNTAX IpAddress
                  MAX-ACCESS read-only
                  STATUS current
                  DESCRIPTION "NBNS-Default"
                  ::= {  staPppRxoIpcEntry 4 }

staPppRxoIpcNbnsb OBJECT-TYPE
                  SYNTAX IpAddress
                  MAX-ACCESS read-only
                  STATUS current
                  DESCRIPTION "NBNS-Backup"
                  ::= {  staPppRxoIpcEntry 6 }

staPppTxo OBJECT IDENTIFIER ::= { staPpp 9}
staPppTxoLcpTable OBJECT-TYPE
                  SYNTAX SEQUENCE OF StaPppTxoLcpEntry
                  MAX-ACCESS not-accessible
                  STATUS current
                  DESCRIPTION "LCP"
                  ::= {  staPppTxo 1 }

staPppTxoLcpEntry OBJECT-TYPE
                  SYNTAX StaPppTxoLcpEntry
                  MAX-ACCESS not-accessible
                  STATUS current
                  DESCRIPTION "entry in table"
                  INDEX { staPppTxoLcpIfc }
                  ::= {  staPppTxoLcpTable 1 }

StaPppTxoLcpEntry ::= SEQUENCE {
                  staPppTxoLcpIfc INTEGER,
                  staPppTxoLcpMru INTEGER,
                  staPppTxoLcpAut INTEGER,
                  staPppTxoLcpMag DisplayString
                 }

staPppTxoLcpIfc OBJECT-TYPE
                SYNTAX INTEGER{
                  dsl-ch-1(1),
                  ext(2)
                }
                MAX-ACCESS read-only
                STATUS current
                DESCRIPTION "Ifc"
                ::= {  staPppTxoLcpEntry 1 }

staPppTxoLcpMru OBJECT-TYPE
                SYNTAX INTEGER (0..65535)
                MAX-ACCESS read-only
                STATUS current
                DESCRIPTION "MRU"
                ::= {  staPppTxoLcpEntry 2 }

staPppTxoLcpAut OBJECT-TYPE
                SYNTAX INTEGER{
                  none(0),
                  chap(8),
                  pap(4)
                }
                MAX-ACCESS read-only
                STATUS current
                DESCRIPTION "Authent."
                ::= {  staPppTxoLcpEntry 4 }

staPppTxoLcpMag OBJECT-TYPE
                SYNTAX DisplayString (SIZE(0..8))
                MAX-ACCESS read-only
                STATUS current
                DESCRIPTION "Magic-Num"
                ::= {  staPppTxoLcpEntry 6 }

staPppTxoIpcTable OBJECT-TYPE
                  SYNTAX SEQUENCE OF StaPppTxoIpcEntry
                  MAX-ACCESS not-accessible
                  STATUS current
                  DESCRIPTION "IPCP"
                  ::= {  staPppTxo 3 }

staPppTxoIpcEntry OBJECT-TYPE
                  SYNTAX StaPppTxoIpcEntry
                  MAX-ACCESS not-accessible
                  STATUS current
                  DESCRIPTION "entry in table"
                  INDEX { staPppTxoIpcIfc }
                  ::= {  staPppTxoIpcTable 1 }

StaPppTxoIpcEntry ::= SEQUENCE {
                  staPppTxoIpcIfc INTEGER,
                  staPppTxoIpcIpadd IpAddress,
                  staPppTxoIpcDnsde IpAddress,
                  staPppTxoIpcDnsba IpAddress,
                  staPppTxoIpcNbnsd IpAddress,
                  staPppTxoIpcNbnsb IpAddress
                 }

staPppTxoIpcIfc OBJECT-TYPE
                  SYNTAX INTEGER{
                    dsl-ch-1(1),
                    ext(2)
                  }
                  MAX-ACCESS read-only
                  STATUS current
                  DESCRIPTION "Ifc"
                  ::= {  staPppTxoIpcEntry 1 }

staPppTxoIpcIpadd OBJECT-TYPE
                  SYNTAX IpAddress
                  MAX-ACCESS read-only
                  STATUS current
                  DESCRIPTION "IP-Address"
                  ::= {  staPppTxoIpcEntry 2 }

staPppTxoIpcDnsde OBJECT-TYPE
                  SYNTAX IpAddress
                  MAX-ACCESS read-only
                  STATUS current
                  DESCRIPTION "DNS-Default"
                  ::= {  staPppTxoIpcEntry 3 }

staPppTxoIpcDnsba OBJECT-TYPE
                  SYNTAX IpAddress
                  MAX-ACCESS read-only
                  STATUS current
                  DESCRIPTION "DNS-Backup"
                  ::= {  staPppTxoIpcEntry 5 }

staPppTxoIpcNbnsd OBJECT-TYPE
                  SYNTAX IpAddress
                  MAX-ACCESS read-only
                  STATUS current
                  DESCRIPTION "NBNS-Default"
                  ::= {  staPppTxoIpcEntry 4 }

staPppTxoIpcNbnsb OBJECT-TYPE
                  SYNTAX IpAddress
                  MAX-ACCESS read-only
                  STATUS current
                  DESCRIPTION "NBNS-Backup"
                  ::= {  staPppTxoIpcEntry 6 }

staPppDel OBJECT-TYPE
          SYNTAX DisplayString
          MAX-ACCESS read-write
          STATUS current
          DESCRIPTION "Delete-Values"
          ::= {  staPpp 13 }

staTcpip OBJECT IDENTIFIER ::= { sta 9}
staTcpipArp OBJECT IDENTIFIER ::= { staTcpip 1}
staTcpipArpLanr OBJECT-TYPE
                SYNTAX Counter32
                MAX-ACCESS read-only
                STATUS current
                DESCRIPTION "LAN-Rx"
                ::= {  staTcpipArp 1 }

staTcpipArpLant OBJECT-TYPE
                SYNTAX Counter32
                MAX-ACCESS read-only
                STATUS current
                DESCRIPTION "LAN-Tx"
                ::= {  staTcpipArp 2 }

staTcpipArpLane OBJECT-TYPE
                SYNTAX Counter32
                MAX-ACCESS read-only
                STATUS current
                DESCRIPTION "LAN-Errors"
                ::= {  staTcpipArp 3 }

staTcpipArpWanr OBJECT-TYPE
                SYNTAX Counter32
                MAX-ACCESS read-only
                STATUS current
                DESCRIPTION "WAN-Rx"
                ::= {  staTcpipArp 4 }

staTcpipArpWant OBJECT-TYPE
                SYNTAX Counter32
                MAX-ACCESS read-only
                STATUS current
                DESCRIPTION "WAN-Tx"
                ::= {  staTcpipArp 5 }

staTcpipArpWane OBJECT-TYPE
                SYNTAX Counter32
                MAX-ACCESS read-only
                STATUS current
                DESCRIPTION "WAN-Errors"
                ::= {  staTcpipArp 6 }

staTcpipArpTablTable OBJECT-TYPE
                     SYNTAX SEQUENCE OF StaTcpipArpTablEntry
                     MAX-ACCESS not-accessible
                     STATUS current
                     DESCRIPTION "Table-ARP"
                     ::= {  staTcpipArp 7 }

staTcpipArpTablEntry OBJECT-TYPE
                     SYNTAX StaTcpipArpTablEntry
                     MAX-ACCESS not-accessible
                     STATUS current
                     DESCRIPTION "entry in table"
                     INDEX { staTcpipArpTablIpa }
                     ::= {  staTcpipArpTablTable 1 }

StaTcpipArpTablEntry ::= SEQUENCE {
                     staTcpipArpTablIpa IpAddress,
                     staTcpipArpTablMac MacAddress,
                     staTcpipArpTablLas INTEGER,
                     staTcpipArpTablCon INTEGER,
                     staTcpipArpTablVla INTEGER,
                     staTcpipArpTablPee DisplayString
                    }

staTcpipArpTablIpa OBJECT-TYPE
                   SYNTAX IpAddress
                   MAX-ACCESS read-only
                   STATUS current
                   DESCRIPTION "IP-Address"
                   ::= {  staTcpipArpTablEntry 1 }

staTcpipArpTablMac OBJECT-TYPE
                   SYNTAX MacAddress
                   MAX-ACCESS read-only
                   STATUS current
                   DESCRIPTION "MAC-Address"
                   ::= {  staTcpipArpTablEntry 2 }

staTcpipArpTablLas OBJECT-TYPE
                   SYNTAX INTEGER (0..2147483647)
                   MAX-ACCESS read-only
                   STATUS current
                   DESCRIPTION "Last-access"
                   ::= {  staTcpipArpTablEntry 3 }

staTcpipArpTablCon OBJECT-TYPE
                   SYNTAX INTEGER{
                     lan-1(0),
                     wlan-1(1),
                     p2p-1-1(2),
                     p2p-1-2(3),
                     p2p-1-3(4),
                     p2p-1-4(5),
                     p2p-1-5(6),
                     p2p-1-6(7),
                     wlan-1-2(8),
                     wlan-1-3(9),
                     wlan-1-4(10),
                     wlan-1-5(11),
                     wlan-1-6(12),
                     wlan-1-7(13),
                     wlan-1-8(14),
                     wan(15)
                   }
                   MAX-ACCESS read-only
                   STATUS current
                   DESCRIPTION "Connect"
                   ::= {  staTcpipArpTablEntry 4 }

staTcpipArpTablVla OBJECT-TYPE
                   SYNTAX INTEGER (0..65535)
                   MAX-ACCESS read-only
                   STATUS current
                   DESCRIPTION "VLAN-ID"
                   ::= {  staTcpipArpTablEntry 7 }

staTcpipArpTablPee OBJECT-TYPE
                   SYNTAX DisplayString (SIZE(0..255))
                   MAX-ACCESS read-only
                   STATUS current
                   DESCRIPTION "Peer"
                   ::= {  staTcpipArpTablEntry 6 }

staTcpipArpDele OBJECT-TYPE
                SYNTAX DisplayString
                MAX-ACCESS read-write
                STATUS current
                DESCRIPTION "Delete-Values"
                ::= {  staTcpipArp 8 }

staTcpipIp OBJECT IDENTIFIER ::= { staTcpip 2}
staTcpipIpLanrx OBJECT-TYPE
                             SYNTAX Counter32
                             MAX-ACCESS read-only
                             STATUS current
                             DESCRIPTION "LAN-Rx"
                             ::= {  staTcpipIp 1 }

staTcpipIpLantx OBJECT-TYPE
                             SYNTAX Counter32
                             MAX-ACCESS read-only
                             STATUS current
                             DESCRIPTION "LAN-Tx"
                             ::= {  staTcpipIp 2 }

staTcpipIpLanchecksumerrors OBJECT-TYPE
                             SYNTAX Counter32
                             MAX-ACCESS read-only
                             STATUS current
                             DESCRIPTION "LAN-Checksum-Errors"
                             ::= {  staTcpipIp 3 }

staTcpipIpLanserviceerrors OBJECT-TYPE
                             SYNTAX Counter32
                             MAX-ACCESS read-only
                             STATUS current
                             DESCRIPTION "LAN-Service-Errors"
                             ::= {  staTcpipIp 4 }

staTcpipIpLanfragmentationer OBJECT-TYPE
                             SYNTAX Counter32
                             MAX-ACCESS read-only
                             STATUS current
                             DESCRIPTION "LAN-Fragmentation-Errors"
                             ::= {  staTcpipIp 10 }

staTcpipIpLanfragmentations OBJECT-TYPE
                             SYNTAX Counter32
                             MAX-ACCESS read-only
                             STATUS current
                             DESCRIPTION "LAN-Fragmentations"
                             ::= {  staTcpipIp 13 }

staTcpipIpLanfragmentationsf OBJECT-TYPE
                             SYNTAX Counter32
                             MAX-ACCESS read-only
                             STATUS current
                             DESCRIPTION "LAN-Fragmentations-Forced"
                             ::= {  staTcpipIp 14 }

staTcpipIpWanrx OBJECT-TYPE
                             SYNTAX Counter32
                             MAX-ACCESS read-only
                             STATUS current
                             DESCRIPTION "WAN-Rx"
                             ::= {  staTcpipIp 5 }

staTcpipIpWantx OBJECT-TYPE
                             SYNTAX Counter32
                             MAX-ACCESS read-only
                             STATUS current
                             DESCRIPTION "WAN-Tx"
                             ::= {  staTcpipIp 6 }

staTcpipIpWanchecksumerrors OBJECT-TYPE
                             SYNTAX Counter32
                             MAX-ACCESS read-only
                             STATUS current
                             DESCRIPTION "WAN-Checksum-Errors"
                             ::= {  staTcpipIp 7 }

staTcpipIpWanserviceerrors OBJECT-TYPE
                             SYNTAX Counter32
                             MAX-ACCESS read-only
                             STATUS current
                             DESCRIPTION "WAN-Service-Errors"
                             ::= {  staTcpipIp 8 }

staTcpipIpWanfragmentationer OBJECT-TYPE
                             SYNTAX Counter32
                             MAX-ACCESS read-only
                             STATUS current
                             DESCRIPTION "WAN-Fragmentation-Errors"
                             ::= {  staTcpipIp 11 }

staTcpipIpWanfragmentations OBJECT-TYPE
                             SYNTAX Counter32
                             MAX-ACCESS read-only
                             STATUS current
                             DESCRIPTION "WAN-Fragmentations"
                             ::= {  staTcpipIp 15 }

staTcpipIpWanfragmentationsf OBJECT-TYPE
                             SYNTAX Counter32
                             MAX-ACCESS read-only
                             STATUS current
                             DESCRIPTION "WAN-Fragmentations-Forced"
                             ::= {  staTcpipIp 16 }

staTcpipIpWanrxdisconnect OBJECT-TYPE
                             SYNTAX Counter32
                             MAX-ACCESS read-only
                             STATUS current
                             DESCRIPTION "WAN-Rx-Disconnect"
                             ::= {  staTcpipIp 9 }

staTcpipIpLooperror OBJECT-TYPE
                             SYNTAX Counter32
                             MAX-ACCESS read-only
                             STATUS current
                             DESCRIPTION "Loop-Error"
                             ::= {  staTcpipIp 17 }

staTcpipIpDeletevalues OBJECT-TYPE
                             SYNTAX DisplayString
                             MAX-ACCESS read-write
                             STATUS current
                             DESCRIPTION "Delete-Values"
                             ::= {  staTcpipIp 12 }

staTcpipIcmp OBJECT IDENTIFIER ::= { staTcpip 3}
staTcpipIcmpLanr OBJECT-TYPE
                 SYNTAX Counter32
                 MAX-ACCESS read-only
                 STATUS current
                 DESCRIPTION "LAN-Rx"
                 ::= {  staTcpipIcmp 1 }

staTcpipIcmpLant OBJECT-TYPE
                 SYNTAX Counter32
                 MAX-ACCESS read-only
                 STATUS current
                 DESCRIPTION "LAN-Tx"
                 ::= {  staTcpipIcmp 2 }

staTcpipIcmpLanc OBJECT-TYPE
                 SYNTAX Counter32
                 MAX-ACCESS read-only
                 STATUS current
                 DESCRIPTION "LAN-Checksum-Errors"
                 ::= {  staTcpipIcmp 3 }

staTcpipIcmpLans OBJECT-TYPE
                 SYNTAX Counter32
                 MAX-ACCESS read-only
                 STATUS current
                 DESCRIPTION "LAN-Service-Errors"
                 ::= {  staTcpipIcmp 4 }

staTcpipIcmpWanr OBJECT-TYPE
                 SYNTAX Counter32
                 MAX-ACCESS read-only
                 STATUS current
                 DESCRIPTION "WAN-Rx"
                 ::= {  staTcpipIcmp 5 }

staTcpipIcmpWant OBJECT-TYPE
                 SYNTAX Counter32
                 MAX-ACCESS read-only
                 STATUS current
                 DESCRIPTION "WAN-Tx"
                 ::= {  staTcpipIcmp 6 }

staTcpipIcmpWanc OBJECT-TYPE
                 SYNTAX Counter32
                 MAX-ACCESS read-only
                 STATUS current
                 DESCRIPTION "WAN-Checksum-Errors"
                 ::= {  staTcpipIcmp 7 }

staTcpipIcmpWans OBJECT-TYPE
                 SYNTAX Counter32
                 MAX-ACCESS read-only
                 STATUS current
                 DESCRIPTION "WAN-Service-Errors"
                 ::= {  staTcpipIcmp 8 }

staTcpipIcmpDele OBJECT-TYPE
                 SYNTAX DisplayString
                 MAX-ACCESS read-write
                 STATUS current
                 DESCRIPTION "Delete-Values"
                 ::= {  staTcpipIcmp 9 }

staTcpipTftp OBJECT IDENTIFIER ::= { staTcpip 4}
staTcpipTftpLanrx OBJECT-TYPE
                   SYNTAX Counter32
                   MAX-ACCESS read-only
                   STATUS current
                   DESCRIPTION "LAN-Rx"
                   ::= {  staTcpipTftp 1 }

staTcpipTftpLanrxr OBJECT-TYPE
                   SYNTAX Counter32
                   MAX-ACCESS read-only
                   STATUS current
                   DESCRIPTION "LAN-Rx-Read-Request"
                   ::= {  staTcpipTftp 2 }

staTcpipTftpLanrxw OBJECT-TYPE
                   SYNTAX Counter32
                   MAX-ACCESS read-only
                   STATUS current
                   DESCRIPTION "LAN-Rx-Write-Request"
                   ::= {  staTcpipTftp 3 }

staTcpipTftpLanrxd OBJECT-TYPE
                   SYNTAX Counter32
                   MAX-ACCESS read-only
                   STATUS current
                   DESCRIPTION "LAN-Rx-Data"
                   ::= {  staTcpipTftp 4 }

staTcpipTftpLanrxa OBJECT-TYPE
                   SYNTAX Counter32
                   MAX-ACCESS read-only
                   STATUS current
                   DESCRIPTION "LAN-Rx-Ack."
                   ::= {  staTcpipTftp 5 }

staTcpipTftpLanrxo OBJECT-TYPE
                   SYNTAX Counter32
                   MAX-ACCESS read-only
                   STATUS current
                   DESCRIPTION "LAN-Rx-Option-Ack."
                   ::= {  staTcpipTftp 6 }

staTcpipTftpLanrxe OBJECT-TYPE
                   SYNTAX Counter32
                   MAX-ACCESS read-only
                   STATUS current
                   DESCRIPTION "LAN-Rx-Errors"
                   ::= {  staTcpipTftp 7 }

staTcpipTftpLanrxb OBJECT-TYPE
                   SYNTAX Counter32
                   MAX-ACCESS read-only
                   STATUS current
                   DESCRIPTION "LAN-Rx-Bad-Packets"
                   ::= {  staTcpipTftp 8 }

staTcpipTftpLantx OBJECT-TYPE
                   SYNTAX Counter32
                   MAX-ACCESS read-only
                   STATUS current
                   DESCRIPTION "LAN-Tx"
                   ::= {  staTcpipTftp 9 }

staTcpipTftpLantxd OBJECT-TYPE
                   SYNTAX Counter32
                   MAX-ACCESS read-only
                   STATUS current
                   DESCRIPTION "LAN-Tx-Data"
                   ::= {  staTcpipTftp 10 }

staTcpipTftpLantxa OBJECT-TYPE
                   SYNTAX Counter32
                   MAX-ACCESS read-only
                   STATUS current
                   DESCRIPTION "LAN-Tx-Ack."
                   ::= {  staTcpipTftp 11 }

staTcpipTftpLantxo OBJECT-TYPE
                   SYNTAX Counter32
                   MAX-ACCESS read-only
                   STATUS current
                   DESCRIPTION "LAN-Tx-Option-Ack."
                   ::= {  staTcpipTftp 12 }

staTcpipTftpLantxe OBJECT-TYPE
                   SYNTAX Counter32
                   MAX-ACCESS read-only
                   STATUS current
                   DESCRIPTION "LAN-Tx-Errors"
                   ::= {  staTcpipTftp 13 }

staTcpipTftpLantxr OBJECT-TYPE
                   SYNTAX Counter32
                   MAX-ACCESS read-only
                   STATUS current
                   DESCRIPTION "LAN-Tx-Repeats"
                   ::= {  staTcpipTftp 14 }

staTcpipTftpLancon OBJECT-TYPE
                   SYNTAX Counter32
                   MAX-ACCESS read-only
                   STATUS current
                   DESCRIPTION "LAN-Connections"
                   ::= {  staTcpipTftp 15 }

staTcpipTftpWanrx OBJECT-TYPE
                   SYNTAX Counter32
                   MAX-ACCESS read-only
                   STATUS current
                   DESCRIPTION "WAN-Rx"
                   ::= {  staTcpipTftp 16 }

staTcpipTftpWanrxr OBJECT-TYPE
                   SYNTAX Counter32
                   MAX-ACCESS read-only
                   STATUS current
                   DESCRIPTION "WAN-Rx-Read-Request"
                   ::= {  staTcpipTftp 17 }

staTcpipTftpWanrxw OBJECT-TYPE
                   SYNTAX Counter32
                   MAX-ACCESS read-only
                   STATUS current
                   DESCRIPTION "WAN-Rx-Write-Request"
                   ::= {  staTcpipTftp 18 }

staTcpipTftpWanrxd OBJECT-TYPE
                   SYNTAX Counter32
                   MAX-ACCESS read-only
                   STATUS current
                   DESCRIPTION "WAN-Rx-Data"
                   ::= {  staTcpipTftp 19 }

staTcpipTftpWanrxa OBJECT-TYPE
                   SYNTAX Counter32
                   MAX-ACCESS read-only
                   STATUS current
                   DESCRIPTION "WAN-Rx-Ack."
                   ::= {  staTcpipTftp 20 }

staTcpipTftpWanrxo OBJECT-TYPE
                   SYNTAX Counter32
                   MAX-ACCESS read-only
                   STATUS current
                   DESCRIPTION "WAN-Rx-Option-Ack."
                   ::= {  staTcpipTftp 21 }

staTcpipTftpWanrxe OBJECT-TYPE
                   SYNTAX Counter32
                   MAX-ACCESS read-only
                   STATUS current
                   DESCRIPTION "WAN-Rx-Errors"
                   ::= {  staTcpipTftp 22 }

staTcpipTftpWanrxb OBJECT-TYPE
                   SYNTAX Counter32
                   MAX-ACCESS read-only
                   STATUS current
                   DESCRIPTION "WAN-Rx-Bad-Packets"
                   ::= {  staTcpipTftp 23 }

staTcpipTftpWantx OBJECT-TYPE
                   SYNTAX Counter32
                   MAX-ACCESS read-only
                   STATUS current
                   DESCRIPTION "WAN-Tx"
                   ::= {  staTcpipTftp 24 }

staTcpipTftpWantxd OBJECT-TYPE
                   SYNTAX Counter32
                   MAX-ACCESS read-only
                   STATUS current
                   DESCRIPTION "WAN-Tx-Data"
                   ::= {  staTcpipTftp 25 }

staTcpipTftpWantxa OBJECT-TYPE
                   SYNTAX Counter32
                   MAX-ACCESS read-only
                   STATUS current
                   DESCRIPTION "WAN-Tx-Ack."
                   ::= {  staTcpipTftp 26 }

staTcpipTftpWantxo OBJECT-TYPE
                   SYNTAX Counter32
                   MAX-ACCESS read-only
                   STATUS current
                   DESCRIPTION "WAN-Tx-Option-Ack."
                   ::= {  staTcpipTftp 27 }

staTcpipTftpWantxe OBJECT-TYPE
                   SYNTAX Counter32
                   MAX-ACCESS read-only
                   STATUS current
                   DESCRIPTION "WAN-Tx-Errors"
                   ::= {  staTcpipTftp 28 }

staTcpipTftpWantxr OBJECT-TYPE
                   SYNTAX Counter32
                   MAX-ACCESS read-only
                   STATUS current
                   DESCRIPTION "WAN-Tx-Repeats"
                   ::= {  staTcpipTftp 29 }

staTcpipTftpWancon OBJECT-TYPE
                   SYNTAX Counter32
                   MAX-ACCESS read-only
                   STATUS current
                   DESCRIPTION "WAN-Connections"
                   ::= {  staTcpipTftp 30 }

staTcpipTftpDelete OBJECT-TYPE
                   SYNTAX DisplayString
                   MAX-ACCESS read-write
                   STATUS current
                   DESCRIPTION "Delete-Values"
                   ::= {  staTcpipTftp 31 }

staTcpipTcp OBJECT IDENTIFIER ::= { staTcpip 5}
staTcpipTcpLanrx OBJECT-TYPE
                  SYNTAX Counter32
                  MAX-ACCESS read-only
                  STATUS current
                  DESCRIPTION "LAN-Rx"
                  ::= {  staTcpipTcp 1 }

staTcpipTcpLantx OBJECT-TYPE
                  SYNTAX Counter32
                  MAX-ACCESS read-only
                  STATUS current
                  DESCRIPTION "LAN-Tx"
                  ::= {  staTcpipTcp 2 }

staTcpipTcpLantxr OBJECT-TYPE
                  SYNTAX Counter32
                  MAX-ACCESS read-only
                  STATUS current
                  DESCRIPTION "LAN-Tx-Repeats"
                  ::= {  staTcpipTcp 3 }

staTcpipTcpLanche OBJECT-TYPE
                  SYNTAX Counter32
                  MAX-ACCESS read-only
                  STATUS current
                  DESCRIPTION "LAN-Checksum-Errors"
                  ::= {  staTcpipTcp 4 }

staTcpipTcpLanser OBJECT-TYPE
                  SYNTAX Counter32
                  MAX-ACCESS read-only
                  STATUS current
                  DESCRIPTION "LAN-Service-Errors"
                  ::= {  staTcpipTcp 5 }

staTcpipTcpLancon OBJECT-TYPE
                  SYNTAX INTEGER
                  MAX-ACCESS read-only
                  STATUS current
                  DESCRIPTION "LAN-Connections"
                  ::= {  staTcpipTcp 6 }

staTcpipTcpWanrx OBJECT-TYPE
                  SYNTAX Counter32
                  MAX-ACCESS read-only
                  STATUS current
                  DESCRIPTION "WAN-Rx"
                  ::= {  staTcpipTcp 7 }

staTcpipTcpWantx OBJECT-TYPE
                  SYNTAX Counter32
                  MAX-ACCESS read-only
                  STATUS current
                  DESCRIPTION "WAN-Tx"
                  ::= {  staTcpipTcp 8 }

staTcpipTcpWantxr OBJECT-TYPE
                  SYNTAX Counter32
                  MAX-ACCESS read-only
                  STATUS current
                  DESCRIPTION "WAN-Tx-Repeats"
                  ::= {  staTcpipTcp 9 }

staTcpipTcpWanche OBJECT-TYPE
                  SYNTAX Counter32
                  MAX-ACCESS read-only
                  STATUS current
                  DESCRIPTION "WAN-Checksum-Errors"
                  ::= {  staTcpipTcp 10 }

staTcpipTcpWanser OBJECT-TYPE
                  SYNTAX Counter32
                  MAX-ACCESS read-only
                  STATUS current
                  DESCRIPTION "WAN-Service-Errors"
                  ::= {  staTcpipTcp 11 }

staTcpipTcpWancon OBJECT-TYPE
                  SYNTAX INTEGER
                  MAX-ACCESS read-only
                  STATUS current
                  DESCRIPTION "WAN-Connections"
                  ::= {  staTcpipTcp 12 }

staTcpipTcpDelete OBJECT-TYPE
                  SYNTAX DisplayString
                  MAX-ACCESS read-write
                  STATUS current
                  DESCRIPTION "Delete-Values"
                  ::= {  staTcpipTcp 13 }

staTcpipDhcp OBJECT IDENTIFIER ::= { staTcpip 6}
staTcpipDhcpLanrx OBJECT-TYPE
                  SYNTAX Counter32
                  MAX-ACCESS read-only
                  STATUS current
                  DESCRIPTION "LAN-Rx"
                  ::= {  staTcpipDhcp 1 }

staTcpipDhcpLantx OBJECT-TYPE
                  SYNTAX Counter32
                  MAX-ACCESS read-only
                  STATUS current
                  DESCRIPTION "LAN-Tx"
                  ::= {  staTcpipDhcp 2 }

staTcpipDhcpWanrx OBJECT-TYPE
                  SYNTAX Counter32
                  MAX-ACCESS read-only
                  STATUS current
                  DESCRIPTION "WAN-Rx"
                  ::= {  staTcpipDhcp 3 }

staTcpipDhcpWantx OBJECT-TYPE
                  SYNTAX Counter32
                  MAX-ACCESS read-only
                  STATUS current
                  DESCRIPTION "WAN-Tx"
                  ::= {  staTcpipDhcp 19 }

staTcpipDhcpDisca OBJECT-TYPE
                  SYNTAX Counter32
                  MAX-ACCESS read-only
                  STATUS current
                  DESCRIPTION "Discard"
                  ::= {  staTcpipDhcp 4 }

staTcpipDhcpRxdis OBJECT-TYPE
                  SYNTAX Counter32
                  MAX-ACCESS read-only
                  STATUS current
                  DESCRIPTION "Rx-Discover"
                  ::= {  staTcpipDhcp 5 }

staTcpipDhcpRxreq OBJECT-TYPE
                  SYNTAX Counter32
                  MAX-ACCESS read-only
                  STATUS current
                  DESCRIPTION "Rx-Request"
                  ::= {  staTcpipDhcp 6 }

staTcpipDhcpRxdec OBJECT-TYPE
                  SYNTAX Counter32
                  MAX-ACCESS read-only
                  STATUS current
                  DESCRIPTION "Rx-Decline"
                  ::= {  staTcpipDhcp 7 }

staTcpipDhcpRxinf OBJECT-TYPE
                  SYNTAX Counter32
                  MAX-ACCESS read-only
                  STATUS current
                  DESCRIPTION "Rx-Inform"
                  ::= {  staTcpipDhcp 8 }

staTcpipDhcpRxrel OBJECT-TYPE
                  SYNTAX Counter32
                  MAX-ACCESS read-only
                  STATUS current
                  DESCRIPTION "Rx-Release"
                  ::= {  staTcpipDhcp 9 }

staTcpipDhcpTxoff OBJECT-TYPE
                  SYNTAX Counter32
                  MAX-ACCESS read-only
                  STATUS current
                  DESCRIPTION "Tx-Offer"
                  ::= {  staTcpipDhcp 10 }

staTcpipDhcpTxack OBJECT-TYPE
                  SYNTAX Counter32
                  MAX-ACCESS read-only
                  STATUS current
                  DESCRIPTION "Tx-Ack."
                  ::= {  staTcpipDhcp 11 }

staTcpipDhcpTxnak OBJECT-TYPE
                  SYNTAX Counter32
                  MAX-ACCESS read-only
                  STATUS current
                  DESCRIPTION "Tx-Nak."
                  ::= {  staTcpipDhcp 12 }

staTcpipDhcpServe OBJECT-TYPE
                  SYNTAX Counter32
                  MAX-ACCESS read-only
                  STATUS current
                  DESCRIPTION "Server-Error"
                  ::= {  staTcpipDhcp 13 }

staTcpipDhcpAssig OBJECT-TYPE
                  SYNTAX INTEGER
                  MAX-ACCESS read-only
                  STATUS current
                  DESCRIPTION "Assigned"
                  ::= {  staTcpipDhcp 14 }

staTcpipDhcpMacco OBJECT-TYPE
                  SYNTAX Counter32
                  MAX-ACCESS read-only
                  STATUS current
                  DESCRIPTION "MAC-Conflicts"
                  ::= {  staTcpipDhcp 15 }

staTcpipDhcpNetwoTable OBJECT-TYPE
                       SYNTAX SEQUENCE OF StaTcpipDhcpNetwoEntry
                       MAX-ACCESS not-accessible
                       STATUS current
                       DESCRIPTION "Network-list"
                       ::= {  staTcpipDhcp 20 }

staTcpipDhcpNetwoEntry OBJECT-TYPE
                       SYNTAX StaTcpipDhcpNetwoEntry
                       MAX-ACCESS not-accessible
                       STATUS current
                       DESCRIPTION "entry in table"
                       INDEX { staTcpipDhcpNetwoNetworknam }
                       ::= {  staTcpipDhcpNetwoTable 1 }

StaTcpipDhcpNetwoEntry ::= SEQUENCE {
                       staTcpipDhcpNetwoNetworknam DisplayString,
                       staTcpipDhcpNetwoStartaddre IpAddress,
                       staTcpipDhcpNetwoEndaddress IpAddress,
                       staTcpipDhcpNetwoNetmask IpAddress,
                       staTcpipDhcpNetwoBroadcasta IpAddress,
                       staTcpipDhcpNetwoGatewayadd IpAddress,
                       staTcpipDhcpNetwoDnsdefault IpAddress,
                       staTcpipDhcpNetwoDnsbackup IpAddress,
                       staTcpipDhcpNetwoNbnsdefaul IpAddress,
                       staTcpipDhcpNetwoNbnsbackup IpAddress,
                       staTcpipDhcpNetwoServerflag DisplayString,
                       staTcpipDhcpNetwoBroadcastb INTEGER,
                       staTcpipDhcpNetwoServerid IpAddress,
                       staTcpipDhcpNetwoLanifc INTEGER,
                       staTcpipDhcpNetwoVlanid INTEGER,
                       staTcpipDhcpNetwoMasterserv IpAddress,
                       staTcpipDhcpNetwoCache INTEGER,
                       staTcpipDhcpNetwoAdaption INTEGER
                      }

staTcpipDhcpNetwoNetworknam OBJECT-TYPE
                            SYNTAX DisplayString (SIZE(0..16))
                            MAX-ACCESS read-only
                            STATUS current
                            DESCRIPTION "Network-name"
                            ::= {  staTcpipDhcpNetwoEntry 1 }

staTcpipDhcpNetwoStartaddre OBJECT-TYPE
                            SYNTAX IpAddress
                            MAX-ACCESS read-only
                            STATUS current
                            DESCRIPTION "Start-Address-Pool"
                            ::= {  staTcpipDhcpNetwoEntry 2 }

staTcpipDhcpNetwoEndaddress OBJECT-TYPE
                            SYNTAX IpAddress
                            MAX-ACCESS read-only
                            STATUS current
                            DESCRIPTION "End-Address-Pool"
                            ::= {  staTcpipDhcpNetwoEntry 3 }

staTcpipDhcpNetwoNetmask OBJECT-TYPE
                            SYNTAX IpAddress
                            MAX-ACCESS read-only
                            STATUS current
                            DESCRIPTION "Netmask"
                            ::= {  staTcpipDhcpNetwoEntry 4 }

staTcpipDhcpNetwoBroadcasta OBJECT-TYPE
                            SYNTAX IpAddress
                            MAX-ACCESS read-only
                            STATUS current
                            DESCRIPTION "Broadcast-Address"
                            ::= {  staTcpipDhcpNetwoEntry 5 }

staTcpipDhcpNetwoGatewayadd OBJECT-TYPE
                            SYNTAX IpAddress
                            MAX-ACCESS read-only
                            STATUS current
                            DESCRIPTION "Gateway-Address"
                            ::= {  staTcpipDhcpNetwoEntry 6 }

staTcpipDhcpNetwoDnsdefault OBJECT-TYPE
                            SYNTAX IpAddress
                            MAX-ACCESS read-only
                            STATUS current
                            DESCRIPTION "DNS-Default"
                            ::= {  staTcpipDhcpNetwoEntry 7 }

staTcpipDhcpNetwoDnsbackup OBJECT-TYPE
                            SYNTAX IpAddress
                            MAX-ACCESS read-only
                            STATUS current
                            DESCRIPTION "DNS-Backup"
                            ::= {  staTcpipDhcpNetwoEntry 8 }

staTcpipDhcpNetwoNbnsdefaul OBJECT-TYPE
                            SYNTAX IpAddress
                            MAX-ACCESS read-only
                            STATUS current
                            DESCRIPTION "NBNS-Default"
                            ::= {  staTcpipDhcpNetwoEntry 9 }

staTcpipDhcpNetwoNbnsbackup OBJECT-TYPE
                            SYNTAX IpAddress
                            MAX-ACCESS read-only
                            STATUS current
                            DESCRIPTION "NBNS-Backup"
                            ::= {  staTcpipDhcpNetwoEntry 10 }

staTcpipDhcpNetwoServerflag OBJECT-TYPE
                            SYNTAX DisplayString (SIZE(0..255))
                            MAX-ACCESS read-only
                            STATUS current
                            DESCRIPTION "Server-Flags"
                            ::= {  staTcpipDhcpNetwoEntry 11 }

staTcpipDhcpNetwoBroadcastb OBJECT-TYPE
                            SYNTAX INTEGER{
                              no(0),
                              yes(1)
                            }
                            MAX-ACCESS read-only
                            STATUS current
                            DESCRIPTION "Broadcast-Bit"
                            ::= {  staTcpipDhcpNetwoEntry 13 }

staTcpipDhcpNetwoServerid OBJECT-TYPE
                            SYNTAX IpAddress
                            MAX-ACCESS read-only
                            STATUS current
                            DESCRIPTION "Server-ID"
                            ::= {  staTcpipDhcpNetwoEntry 14 }

staTcpipDhcpNetwoLanifc OBJECT-TYPE
                            SYNTAX INTEGER{
                              lan-1(0),
                              wlan-1(1),
                              p2p-1-1(2),
                              p2p-1-2(3),
                              p2p-1-3(4),
                              p2p-1-4(5),
                              p2p-1-5(6),
                              p2p-1-6(7),
                              wlan-1-2(8),
                              wlan-1-3(9),
                              wlan-1-4(10),
                              wlan-1-5(11),
                              wlan-1-6(12),
                              wlan-1-7(13),
                              wlan-1-8(14),
                              brg-1(15),
                              brg-2(16),
                              brg-3(17),
                              brg-4(18),
                              brg-5(19),
                              brg-6(20),
                              brg-7(21),
                              brg-8(22),
                              any(255)
                            }
                            MAX-ACCESS read-only
                            STATUS current
                            DESCRIPTION "LAN-Ifc"
                            ::= {  staTcpipDhcpNetwoEntry 15 }

staTcpipDhcpNetwoVlanid OBJECT-TYPE
                            SYNTAX INTEGER (0..65535)
                            MAX-ACCESS read-only
                            STATUS current
                            DESCRIPTION "VLAN-ID"
                            ::= {  staTcpipDhcpNetwoEntry 16 }

staTcpipDhcpNetwoMasterserv OBJECT-TYPE
                            SYNTAX IpAddress
                            MAX-ACCESS read-only
                            STATUS current
                            DESCRIPTION "Master-Server"
                            ::= {  staTcpipDhcpNetwoEntry 17 }

staTcpipDhcpNetwoCache OBJECT-TYPE
                            SYNTAX INTEGER{
                              no(0),
                              yes(1)
                            }
                            MAX-ACCESS read-only
                            STATUS current
                            DESCRIPTION "Cache"
                            ::= {  staTcpipDhcpNetwoEntry 18 }

staTcpipDhcpNetwoAdaption OBJECT-TYPE
                            SYNTAX INTEGER{
                              no(0),
                              yes(1)
                            }
                            MAX-ACCESS read-only
                            STATUS current
                            DESCRIPTION "Adaption"
                            ::= {  staTcpipDhcpNetwoEntry 19 }

staTcpipDhcpDhcptTable OBJECT-TYPE
                       SYNTAX SEQUENCE OF StaTcpipDhcpDhcptEntry
                       MAX-ACCESS not-accessible
                       STATUS current
                       DESCRIPTION "DHCP-Table"
                       ::= {  staTcpipDhcp 16 }

staTcpipDhcpDhcptEntry OBJECT-TYPE
                       SYNTAX StaTcpipDhcpDhcptEntry
                       MAX-ACCESS not-accessible
                       STATUS current
                       DESCRIPTION "entry in table"
                       INDEX { staTcpipDhcpDhcptIpa, staTcpipDhcpDhcptNet }
                       ::= {  staTcpipDhcpDhcptTable 1 }

StaTcpipDhcpDhcptEntry ::= SEQUENCE {
                       staTcpipDhcpDhcptIpa IpAddress,
                       staTcpipDhcpDhcptMac DisplayString,
                       staTcpipDhcpDhcptTim INTEGER,
                       staTcpipDhcpDhcptHos DisplayString,
                       staTcpipDhcpDhcptTyp BITS,
                       staTcpipDhcpDhcptLan INTEGER,
                       staTcpipDhcpDhcptVla INTEGER,
                       staTcpipDhcpDhcptNet DisplayString
                      }

staTcpipDhcpDhcptIpa OBJECT-TYPE
                     SYNTAX IpAddress
                     MAX-ACCESS read-only
                     STATUS current
                     DESCRIPTION "IP-Address"
                     ::= {  staTcpipDhcpDhcptEntry 1 }

staTcpipDhcpDhcptMac OBJECT-TYPE
                     SYNTAX DisplayString (SIZE(0..12))
                     MAX-ACCESS read-only
                     STATUS current
                     DESCRIPTION "MAC-Address"
                     ::= {  staTcpipDhcpDhcptEntry 2 }

staTcpipDhcpDhcptTim OBJECT-TYPE
                     SYNTAX INTEGER (0..2147483647)
                     MAX-ACCESS read-only
                     STATUS current
                     DESCRIPTION "Timeout"
                     ::= {  staTcpipDhcpDhcptEntry 3 }

staTcpipDhcpDhcptHos OBJECT-TYPE
                     SYNTAX DisplayString (SIZE(0..64))
                     MAX-ACCESS read-only
                     STATUS current
                     DESCRIPTION "Hostname"
                     ::= {  staTcpipDhcpDhcptEntry 4 }

staTcpipDhcpDhcptTyp OBJECT-TYPE
                     SYNTAX BITS{
                       new(1),
                       new(2),
                       dyn(16),
                       unkn(4),
                       stat(8),
                       bootp(32),
                       relay(2048)
                     }
                     MAX-ACCESS read-only
                     STATUS current
                     DESCRIPTION "Type"
                     ::= {  staTcpipDhcpDhcptEntry 5 }

staTcpipDhcpDhcptLan OBJECT-TYPE
                     SYNTAX INTEGER{
                       lan-1(0),
                       wlan-1(1),
                       p2p-1-1(2),
                       p2p-1-2(3),
                       p2p-1-3(4),
                       p2p-1-4(5),
                       p2p-1-5(6),
                       p2p-1-6(7),
                       wlan-1-2(8),
                       wlan-1-3(9),
                       wlan-1-4(10),
                       wlan-1-5(11),
                       wlan-1-6(12),
                       wlan-1-7(13),
                       wlan-1-8(14),
                       brg-1(15),
                       brg-2(16),
                       brg-3(17),
                       brg-4(18),
                       brg-5(19),
                       brg-6(20),
                       brg-7(21),
                       brg-8(22),
                       any(255)
                     }
                     MAX-ACCESS read-only
                     STATUS current
                     DESCRIPTION "LAN-Ifc"
                     ::= {  staTcpipDhcpDhcptEntry 6 }

staTcpipDhcpDhcptVla OBJECT-TYPE
                     SYNTAX INTEGER (0..65535)
                     MAX-ACCESS read-only
                     STATUS current
                     DESCRIPTION "VLAN-ID"
                     ::= {  staTcpipDhcpDhcptEntry 8 }

staTcpipDhcpDhcptNet OBJECT-TYPE
                     SYNTAX DisplayString (SIZE(0..17))
                     MAX-ACCESS read-only
                     STATUS current
                     DESCRIPTION "Network-name"
                     ::= {  staTcpipDhcpDhcptEntry 9 }

staTcpipDhcpDelet OBJECT-TYPE
                  SYNTAX DisplayString
                  MAX-ACCESS read-write
                  STATUS current
                  DESCRIPTION "Delete-Values"
                  ::= {  staTcpipDhcp 18 }

staTcpipDeletev OBJECT-TYPE
                SYNTAX DisplayString
                MAX-ACCESS read-write
                STATUS current
                DESCRIPTION "Delete-Values"
                ::= {  staTcpip 7 }

staTcpipNetbios OBJECT IDENTIFIER ::= { staTcpip 8}
staTcpipNetbiosLanr OBJECT-TYPE
                    SYNTAX Counter32
                    MAX-ACCESS read-only
                    STATUS current
                    DESCRIPTION "LAN-Rx"
                    ::= {  staTcpipNetbios 1 }

staTcpipNetbiosLant OBJECT-TYPE
                    SYNTAX Counter32
                    MAX-ACCESS read-only
                    STATUS current
                    DESCRIPTION "LAN-Tx"
                    ::= {  staTcpipNetbios 2 }

staTcpipNetbiosWanr OBJECT-TYPE
                    SYNTAX Counter32
                    MAX-ACCESS read-only
                    STATUS current
                    DESCRIPTION "WAN-Rx"
                    ::= {  staTcpipNetbios 3 }

staTcpipNetbiosWant OBJECT-TYPE
                    SYNTAX Counter32
                    MAX-ACCESS read-only
                    STATUS current
                    DESCRIPTION "WAN-Tx"
                    ::= {  staTcpipNetbios 4 }

staTcpipNetbiosRegi OBJECT-TYPE
                    SYNTAX Counter32
                    MAX-ACCESS read-only
                    STATUS current
                    DESCRIPTION "Registers"
                    ::= {  staTcpipNetbios 5 }

staTcpipNetbiosConf OBJECT-TYPE
                    SYNTAX Counter32
                    MAX-ACCESS read-only
                    STATUS current
                    DESCRIPTION "Conflicts"
                    ::= {  staTcpipNetbios 6 }

staTcpipNetbiosRele OBJECT-TYPE
                    SYNTAX Counter32
                    MAX-ACCESS read-only
                    STATUS current
                    DESCRIPTION "Releases"
                    ::= {  staTcpipNetbios 7 }

staTcpipNetbiosRefr OBJECT-TYPE
                    SYNTAX Counter32
                    MAX-ACCESS read-only
                    STATUS current
                    DESCRIPTION "Refreshs"
                    ::= {  staTcpipNetbios 8 }

staTcpipNetbiosTime OBJECT-TYPE
                    SYNTAX Counter32
                    MAX-ACCESS read-only
                    STATUS current
                    DESCRIPTION "Timeouts"
                    ::= {  staTcpipNetbios 9 }

staTcpipNetbiosHost OBJECT-TYPE
                    SYNTAX INTEGER
                    MAX-ACCESS read-only
                    STATUS current
                    DESCRIPTION "Hosts"
                    ::= {  staTcpipNetbios 10 }

staTcpipNetbiosGrou OBJECT-TYPE
                    SYNTAX INTEGER
                    MAX-ACCESS read-only
                    STATUS current
                    DESCRIPTION "Groups"
                    ::= {  staTcpipNetbios 11 }

staTcpipNetbiosBnod OBJECT-TYPE
                    SYNTAX INTEGER
                    MAX-ACCESS read-only
                    STATUS current
                    DESCRIPTION "B-Nodes"
                    ::= {  staTcpipNetbios 12 }

staTcpipNetbiosPnod OBJECT-TYPE
                    SYNTAX INTEGER
                    MAX-ACCESS read-only
                    STATUS current
                    DESCRIPTION "P-Nodes"
                    ::= {  staTcpipNetbios 13 }

staTcpipNetbiosMnod OBJECT-TYPE
                    SYNTAX INTEGER
                    MAX-ACCESS read-only
                    STATUS current
                    DESCRIPTION "M-Nodes"
                    ::= {  staTcpipNetbios 14 }

staTcpipNetbiosWnod OBJECT-TYPE
                    SYNTAX INTEGER
                    MAX-ACCESS read-only
                    STATUS current
                    DESCRIPTION "W-Nodes"
                    ::= {  staTcpipNetbios 15 }

staTcpipNetbiosPeerTable OBJECT-TYPE
                         SYNTAX SEQUENCE OF StaTcpipNetbiosPeerEntry
                         MAX-ACCESS not-accessible
                         STATUS current
                         DESCRIPTION "Peers"
                         ::= {  staTcpipNetbios 16 }

staTcpipNetbiosPeerEntry OBJECT-TYPE
                         SYNTAX StaTcpipNetbiosPeerEntry
                         MAX-ACCESS not-accessible
                         STATUS current
                         DESCRIPTION "entry in table"
                         INDEX { staTcpipNetbiosPeerNam }
                         ::= {  staTcpipNetbiosPeerTable 1 }

StaTcpipNetbiosPeerEntry ::= SEQUENCE {
                         staTcpipNetbiosPeerNam DisplayString,
                         staTcpipNetbiosPeerTyp INTEGER,
                         staTcpipNetbiosPeerBac INTEGER,
                         staTcpipNetbiosPeerTim INTEGER
                        }

staTcpipNetbiosPeerNam OBJECT-TYPE
                       SYNTAX DisplayString (SIZE(0..16))
                       MAX-ACCESS read-only
                       STATUS current
                       DESCRIPTION "Name"
                       ::= {  staTcpipNetbiosPeerEntry 1 }

staTcpipNetbiosPeerTyp OBJECT-TYPE
                       SYNTAX INTEGER{
                         workstation(1),
                         router(0)
                       }
                       MAX-ACCESS read-only
                       STATUS current
                       DESCRIPTION "Type"
                       ::= {  staTcpipNetbiosPeerEntry 2 }

staTcpipNetbiosPeerBac OBJECT-TYPE
                       SYNTAX INTEGER (0..255)
                       MAX-ACCESS read-only
                       STATUS current
                       DESCRIPTION "Backoff"
                       ::= {  staTcpipNetbiosPeerEntry 3 }

staTcpipNetbiosPeerTim OBJECT-TYPE
                       SYNTAX INTEGER (0..65535)
                       MAX-ACCESS read-only
                       STATUS current
                       DESCRIPTION "Time"
                       ::= {  staTcpipNetbiosPeerEntry 4 }

staTcpipNetbiosNetwTable OBJECT-TYPE
                         SYNTAX SEQUENCE OF StaTcpipNetbiosNetwEntry
                         MAX-ACCESS not-accessible
                         STATUS current
                         DESCRIPTION "Networks"
                         ::= {  staTcpipNetbios 18 }

staTcpipNetbiosNetwEntry OBJECT-TYPE
                         SYNTAX StaTcpipNetbiosNetwEntry
                         MAX-ACCESS not-accessible
                         STATUS current
                         DESCRIPTION "entry in table"
                         INDEX { staTcpipNetbiosNetwNet }
                         ::= {  staTcpipNetbiosNetwTable 1 }

StaTcpipNetbiosNetwEntry ::= SEQUENCE {
                         staTcpipNetbiosNetwNet DisplayString,
                         staTcpipNetbiosNetwNtd DisplayString,
                         staTcpipNetbiosNetwRtg INTEGER,
                         staTcpipNetbiosNetwInt INTEGER,
                         staTcpipNetbiosNetwVla INTEGER
                        }

staTcpipNetbiosNetwNet OBJECT-TYPE
                       SYNTAX DisplayString (SIZE(0..16))
                       MAX-ACCESS read-only
                       STATUS current
                       DESCRIPTION "Network-name"
                       ::= {  staTcpipNetbiosNetwEntry 1 }

staTcpipNetbiosNetwNtd OBJECT-TYPE
                       SYNTAX DisplayString (SIZE(0..15))
                       MAX-ACCESS read-only
                       STATUS current
                       DESCRIPTION "NT-Domain"
                       ::= {  staTcpipNetbiosNetwEntry 2 }

staTcpipNetbiosNetwRtg OBJECT-TYPE
                       SYNTAX INTEGER (0..65535)
                       MAX-ACCESS read-only
                       STATUS current
                       DESCRIPTION "Rtg-tag"
                       ::= {  staTcpipNetbiosNetwEntry 3 }

staTcpipNetbiosNetwInt OBJECT-TYPE
                       SYNTAX INTEGER{
                         lan-1(0),
                         wlan-1(1),
                         p2p-1-1(2),
                         p2p-1-2(3),
                         p2p-1-3(4),
                         p2p-1-4(5),
                         p2p-1-5(6),
                         p2p-1-6(7),
                         wlan-1-2(8),
                         wlan-1-3(9),
                         wlan-1-4(10),
                         wlan-1-5(11),
                         wlan-1-6(12),
                         wlan-1-7(13),
                         wlan-1-8(14),
                         brg-1(15),
                         brg-2(16),
                         brg-3(17),
                         brg-4(18),
                         brg-5(19),
                         brg-6(20),
                         brg-7(21),
                         brg-8(22),
                         any(255)
                       }
                       MAX-ACCESS read-only
                       STATUS current
                       DESCRIPTION "Interface"
                       ::= {  staTcpipNetbiosNetwEntry 4 }

staTcpipNetbiosNetwVla OBJECT-TYPE
                       SYNTAX INTEGER (0..65535)
                       MAX-ACCESS read-only
                       STATUS current
                       DESCRIPTION "VLAN-ID"
                       ::= {  staTcpipNetbiosNetwEntry 5 }

staTcpipNetbiosDele OBJECT-TYPE
                    SYNTAX DisplayString
                    MAX-ACCESS read-write
                    STATUS current
                    DESCRIPTION "Delete-Values"
                    ::= {  staTcpipNetbios 17 }

staTcpipDns OBJECT IDENTIFIER ::= { staTcpip 9}
staTcpipDnsLanr OBJECT-TYPE
                SYNTAX Counter32
                MAX-ACCESS read-only
                STATUS current
                DESCRIPTION "LAN-Rx"
                ::= {  staTcpipDns 1 }

staTcpipDnsLant OBJECT-TYPE
                SYNTAX Counter32
                MAX-ACCESS read-only
                STATUS current
                DESCRIPTION "LAN-Tx"
                ::= {  staTcpipDns 2 }

staTcpipDnsWanr OBJECT-TYPE
                SYNTAX Counter32
                MAX-ACCESS read-only
                STATUS current
                DESCRIPTION "WAN-Rx"
                ::= {  staTcpipDns 3 }

staTcpipDnsWant OBJECT-TYPE
                SYNTAX Counter32
                MAX-ACCESS read-only
                STATUS current
                DESCRIPTION "WAN-Tx"
                ::= {  staTcpipDns 4 }

staTcpipDnsForw OBJECT-TYPE
                SYNTAX Counter32
                MAX-ACCESS read-only
                STATUS current
                DESCRIPTION "Forwarded"
                ::= {  staTcpipDns 5 }

staTcpipDnsErro OBJECT-TYPE
                SYNTAX Counter32
                MAX-ACCESS read-only
                STATUS current
                DESCRIPTION "Errors"
                ::= {  staTcpipDns 6 }

staTcpipDnsDnsa OBJECT-TYPE
                SYNTAX Counter32
                MAX-ACCESS read-only
                STATUS current
                DESCRIPTION "DNS-Access"
                ::= {  staTcpipDns 7 }

staTcpipDnsDhcp OBJECT-TYPE
                SYNTAX Counter32
                MAX-ACCESS read-only
                STATUS current
                DESCRIPTION "DHCP-Access"
                ::= {  staTcpipDns 8 }

staTcpipDnsNetb OBJECT-TYPE
                SYNTAX Counter32
                MAX-ACCESS read-only
                STATUS current
                DESCRIPTION "NetBIOS-Access"
                ::= {  staTcpipDns 9 }

staTcpipDnsFilt OBJECT-TYPE
                SYNTAX Counter32
                MAX-ACCESS read-only
                STATUS current
                DESCRIPTION "Filter"
                ::= {  staTcpipDns 10 }

staTcpipDnsHitlTable OBJECT-TYPE
                     SYNTAX SEQUENCE OF StaTcpipDnsHitlEntry
                     MAX-ACCESS not-accessible
                     STATUS current
                     DESCRIPTION "Hit-List"
                     ::= {  staTcpipDns 11 }

staTcpipDnsHitlEntry OBJECT-TYPE
                     SYNTAX StaTcpipDnsHitlEntry
                     MAX-ACCESS not-accessible
                     STATUS current
                     DESCRIPTION "entry in table"
                     INDEX { staTcpipDnsHitlDom }
                     ::= {  staTcpipDnsHitlTable 1 }

StaTcpipDnsHitlEntry ::= SEQUENCE {
                     staTcpipDnsHitlDom DisplayString,
                     staTcpipDnsHitlReq INTEGER,
                     staTcpipDnsHitlTim DisplayString,
                     staTcpipDnsHitlIpa IpAddress
                    }

staTcpipDnsHitlDom OBJECT-TYPE
                   SYNTAX DisplayString (SIZE(0..64))
                   MAX-ACCESS read-only
                   STATUS current
                   DESCRIPTION "Domain"
                   ::= {  staTcpipDnsHitlEntry 1 }

staTcpipDnsHitlReq OBJECT-TYPE
                   SYNTAX INTEGER (0..2147483647)
                   MAX-ACCESS read-only
                   STATUS current
                   DESCRIPTION "Requests"
                   ::= {  staTcpipDnsHitlEntry 2 }

staTcpipDnsHitlTim OBJECT-TYPE
                   SYNTAX DisplayString (SIZE(0..20))
                   MAX-ACCESS read-only
                   STATUS current
                   DESCRIPTION "Time"
                   ::= {  staTcpipDnsHitlEntry 3 }

staTcpipDnsHitlIpa OBJECT-TYPE
                   SYNTAX IpAddress
                   MAX-ACCESS read-only
                   STATUS current
                   DESCRIPTION "IP-Address"
                   ::= {  staTcpipDnsHitlEntry 4 }

staTcpipDnsDele OBJECT-TYPE
                SYNTAX DisplayString
                MAX-ACCESS read-write
                STATUS current
                DESCRIPTION "Delete-Values"
                ::= {  staTcpipDns 12 }

staTcpipHttp OBJECT IDENTIFIER ::= { staTcpip 10}
staTcpipHttpHttpac OBJECT-TYPE
                   SYNTAX Counter32
                   MAX-ACCESS read-only
                   STATUS current
                   DESCRIPTION "HTTP-Accesses"
                   ::= {  staTcpipHttp 1 }

staTcpipHttpHttpsa OBJECT-TYPE
                   SYNTAX Counter32
                   MAX-ACCESS read-only
                   STATUS current
                   DESCRIPTION "HTTPS-Accesses"
                   ::= {  staTcpipHttp 6 }

staTcpipHttpHttpno OBJECT-TYPE
                   SYNTAX Counter32
                   MAX-ACCESS read-only
                   STATUS current
                   DESCRIPTION "HTTP-Notfound-Errors"
                   ::= {  staTcpipHttp 2 }

staTcpipHttpHttpau OBJECT-TYPE
                   SYNTAX Counter32
                   MAX-ACCESS read-only
                   STATUS current
                   DESCRIPTION "HTTP-Authentication-Errors"
                   ::= {  staTcpipHttp 3 }

staTcpipHttpHttppr OBJECT-TYPE
                   SYNTAX Counter32
                   MAX-ACCESS read-only
                   STATUS current
                   DESCRIPTION "HTTP-Protocol-Errors"
                   ::= {  staTcpipHttp 4 }

staTcpipHttpAgentlTable OBJECT-TYPE
                        SYNTAX SEQUENCE OF StaTcpipHttpAgentlEntry
                        MAX-ACCESS not-accessible
                        STATUS current
                        DESCRIPTION "Agent-List"
                        ::= {  staTcpipHttp 7 }

staTcpipHttpAgentlEntry OBJECT-TYPE
                        SYNTAX StaTcpipHttpAgentlEntry
                        MAX-ACCESS not-accessible
                        STATUS current
                        DESCRIPTION "entry in table"
                        INDEX { staTcpipHttpAgentlAge }
                        ::= {  staTcpipHttpAgentlTable 1 }

StaTcpipHttpAgentlEntry ::= SEQUENCE {
                        staTcpipHttpAgentlAge DisplayString,
                        staTcpipHttpAgentlAcc INTEGER
                       }

staTcpipHttpAgentlAge OBJECT-TYPE
                      SYNTAX DisplayString (SIZE(0..67))
                      MAX-ACCESS read-only
                      STATUS current
                      DESCRIPTION "Agent-Name"
                      ::= {  staTcpipHttpAgentlEntry 1 }

staTcpipHttpAgentlAcc OBJECT-TYPE
                      SYNTAX INTEGER (0..2147483647)
                      MAX-ACCESS read-only
                      STATUS current
                      DESCRIPTION "Accesses"
                      ::= {  staTcpipHttpAgentlEntry 2 }

staTcpipHttpDelete OBJECT-TYPE
                   SYNTAX DisplayString
                   MAX-ACCESS read-write
                   STATUS current
                   DESCRIPTION "Delete-Values"
                   ::= {  staTcpipHttp 5 }

staTcpipHttpActiveTable OBJECT-TYPE
                        SYNTAX SEQUENCE OF StaTcpipHttpActiveEntry
                        MAX-ACCESS not-accessible
                        STATUS current
                        DESCRIPTION "Active-Tunnels"
                        ::= {  staTcpipHttp 8 }

staTcpipHttpActiveEntry OBJECT-TYPE
                        SYNTAX StaTcpipHttpActiveEntry
                        MAX-ACCESS not-accessible
                        STATUS current
                        DESCRIPTION "entry in table"
                        INDEX { staTcpipHttpActiveIndex }
                        ::= {  staTcpipHttpActiveTable 1 }

StaTcpipHttpActiveEntry ::= SEQUENCE {
                        staTcpipHttpActiveIndex INTEGER,
                        staTcpipHttpActiveRemotea IpAddress,
                        staTcpipHttpActiveRemotep INTEGER,
                        staTcpipHttpActiveLocalho DisplayString,
                        staTcpipHttpActiveLocalpo INTEGER,
                        staTcpipHttpActiveLocalrt INTEGER,
                        staTcpipHttpActiveIdletim INTEGER,
                        staTcpipHttpActiveNumconn INTEGER
                       }

staTcpipHttpActiveIndex OBJECT-TYPE
                          SYNTAX INTEGER (0..2147483647)
                          MAX-ACCESS read-only
                          STATUS current
                          DESCRIPTION "Index"
                          ::= {  staTcpipHttpActiveEntry 1 }

staTcpipHttpActiveRemotea OBJECT-TYPE
                          SYNTAX IpAddress
                          MAX-ACCESS read-only
                          STATUS current
                          DESCRIPTION "Remote-Address"
                          ::= {  staTcpipHttpActiveEntry 2 }

staTcpipHttpActiveRemotep OBJECT-TYPE
                          SYNTAX INTEGER (0..65535)
                          MAX-ACCESS read-only
                          STATUS current
                          DESCRIPTION "Remote-Port"
                          ::= {  staTcpipHttpActiveEntry 3 }

staTcpipHttpActiveLocalho OBJECT-TYPE
                          SYNTAX DisplayString (SIZE(0..48))
                          MAX-ACCESS read-only
                          STATUS current
                          DESCRIPTION "Local-Host"
                          ::= {  staTcpipHttpActiveEntry 4 }

staTcpipHttpActiveLocalpo OBJECT-TYPE
                          SYNTAX INTEGER (0..65535)
                          MAX-ACCESS read-only
                          STATUS current
                          DESCRIPTION "Local-Port"
                          ::= {  staTcpipHttpActiveEntry 5 }

staTcpipHttpActiveLocalrt OBJECT-TYPE
                          SYNTAX INTEGER (0..65535)
                          MAX-ACCESS read-only
                          STATUS current
                          DESCRIPTION "Local-Rtg-Tag"
                          ::= {  staTcpipHttpActiveEntry 7 }

staTcpipHttpActiveIdletim OBJECT-TYPE
                          SYNTAX INTEGER (0..2147483647)
                          MAX-ACCESS read-only
                          STATUS current
                          DESCRIPTION "Idle-Time"
                          ::= {  staTcpipHttpActiveEntry 6 }

staTcpipHttpActiveNumconn OBJECT-TYPE
                          SYNTAX INTEGER (0..2147483647)
                          MAX-ACCESS read-only
                          STATUS current
                          DESCRIPTION "Num-Connections"
                          ::= {  staTcpipHttpActiveEntry 8 }

staTcpipNetworkTable OBJECT-TYPE
                     SYNTAX SEQUENCE OF StaTcpipNetworkEntry
                     MAX-ACCESS not-accessible
                     STATUS current
                     DESCRIPTION "Network-list"
                     ::= {  staTcpip 20 }

staTcpipNetworkEntry OBJECT-TYPE
                     SYNTAX StaTcpipNetworkEntry
                     MAX-ACCESS not-accessible
                     STATUS current
                     DESCRIPTION "entry in table"
                     INDEX { staTcpipNetworkNet }
                     ::= {  staTcpipNetworkTable 1 }

StaTcpipNetworkEntry ::= SEQUENCE {
                     staTcpipNetworkNet DisplayString,
                     staTcpipNetworkIpa IpAddress,
                     staTcpipNetworkIpn IpAddress,
                     staTcpipNetworkVla INTEGER,
                     staTcpipNetworkInt INTEGER,
                     staTcpipNetworkSrc INTEGER,
                     staTcpipNetworkTyp INTEGER,
                     staTcpipNetworkRtg INTEGER
                    }

staTcpipNetworkNet OBJECT-TYPE
                   SYNTAX DisplayString (SIZE(0..17))
                   MAX-ACCESS read-only
                   STATUS current
                   DESCRIPTION "Network-name"
                   ::= {  staTcpipNetworkEntry 1 }

staTcpipNetworkIpa OBJECT-TYPE
                   SYNTAX IpAddress
                   MAX-ACCESS read-only
                   STATUS current
                   DESCRIPTION "IP-Address"
                   ::= {  staTcpipNetworkEntry 2 }

staTcpipNetworkIpn OBJECT-TYPE
                   SYNTAX IpAddress
                   MAX-ACCESS read-only
                   STATUS current
                   DESCRIPTION "IP-Netmask"
                   ::= {  staTcpipNetworkEntry 3 }

staTcpipNetworkVla OBJECT-TYPE
                   SYNTAX INTEGER (0..65535)
                   MAX-ACCESS read-only
                   STATUS current
                   DESCRIPTION "VLAN-ID"
                   ::= {  staTcpipNetworkEntry 4 }

staTcpipNetworkInt OBJECT-TYPE
                   SYNTAX INTEGER{
                     lan-1(256),
                     wlan-1(512),
                     p2p-1-1(768),
                     p2p-1-2(769),
                     p2p-1-3(770),
                     p2p-1-4(771),
                     p2p-1-5(772),
                     p2p-1-6(773),
                     wlan-1-2(1024),
                     wlan-1-3(1025),
                     wlan-1-4(1026),
                     wlan-1-5(1027),
                     wlan-1-6(1028),
                     wlan-1-7(1029),
                     wlan-1-8(1030),
                     brg-1(1536),
                     brg-2(1537),
                     brg-3(1538),
                     brg-4(1539),
                     brg-5(1540),
                     brg-6(1541),
                     brg-7(1542),
                     brg-8(1543),
                     any(65535)
                   }
                   MAX-ACCESS read-only
                   STATUS current
                   DESCRIPTION "Interface"
                   ::= {  staTcpipNetworkEntry 5 }

staTcpipNetworkSrc OBJECT-TYPE
                   SYNTAX INTEGER{
                     strict(1),
                     loose(0)
                   }
                   MAX-ACCESS read-only
                   STATUS current
                   DESCRIPTION "Src-check"
                   ::= {  staTcpipNetworkEntry 6 }

staTcpipNetworkTyp OBJECT-TYPE
                   SYNTAX INTEGER{
                     disabled(0),
                     intranet(1),
                     dmz(2)
                   }
                   MAX-ACCESS read-only
                   STATUS current
                   DESCRIPTION "Type"
                   ::= {  staTcpipNetworkEntry 7 }

staTcpipNetworkRtg OBJECT-TYPE
                   SYNTAX INTEGER (0..65535)
                   MAX-ACCESS read-only
                   STATUS current
                   DESCRIPTION "Rtg-tag"
                   ::= {  staTcpipNetworkEntry 8 }

staTcpipSyslog OBJECT IDENTIFIER ::= { staTcpip 11}
staTcpipSyslogLasTable OBJECT-TYPE
                       SYNTAX SEQUENCE OF StaTcpipSyslogLasEntry
                       MAX-ACCESS not-accessible
                       STATUS current
                       DESCRIPTION "Last-Messages"
                       ::= {  staTcpipSyslog 11 }

staTcpipSyslogLasEntry OBJECT-TYPE
                       SYNTAX StaTcpipSyslogLasEntry
                       MAX-ACCESS not-accessible
                       STATUS current
                       DESCRIPTION "entry in table"
                       INDEX { staTcpipSyslogLasIdx }
                       ::= {  staTcpipSyslogLasTable 1 }

StaTcpipSyslogLasEntry ::= SEQUENCE {
                       staTcpipSyslogLasIdx INTEGER,
                       staTcpipSyslogLasTim DisplayString,
                       staTcpipSyslogLasSou INTEGER,
                       staTcpipSyslogLasLev INTEGER,
                       staTcpipSyslogLasMes DisplayString
                      }

staTcpipSyslogLasIdx OBJECT-TYPE
                     SYNTAX INTEGER (0..2147483647)
                     MAX-ACCESS read-only
                     STATUS current
                     DESCRIPTION "Idx."
                     ::= {  staTcpipSyslogLasEntry 1 }

staTcpipSyslogLasTim OBJECT-TYPE
                     SYNTAX DisplayString (SIZE(0..21))
                     MAX-ACCESS read-only
                     STATUS current
                     DESCRIPTION "Time"
                     ::= {  staTcpipSyslogLasEntry 2 }

staTcpipSyslogLasSou OBJECT-TYPE
                     SYNTAX INTEGER{
                       kern(0),
                       user(1),
                       mail(2),
                       daemon(3),
                       auth(4),
                       syslog(5),
                       lpr(6),
                       news(7),
                       uucp(8),
                       cron(9),
                       authpriv(10),
                       local0(16),
                       local1(17),
                       local2(18),
                       local3(19),
                       local4(20),
                       local5(21),
                       local6(22),
                       local7(23)
                     }
                     MAX-ACCESS read-only
                     STATUS current
                     DESCRIPTION "Source"
                     ::= {  staTcpipSyslogLasEntry 3 }

staTcpipSyslogLasLev OBJECT-TYPE
                     SYNTAX INTEGER{
                       emergency(0),
                       alarm(1),
                       critical(2),
                       error(3),
                       warning(4),
                       notice(5),
                       info(6),
                       debug(7)
                     }
                     MAX-ACCESS read-only
                     STATUS current
                     DESCRIPTION "Level"
                     ::= {  staTcpipSyslogLasEntry 4 }

staTcpipSyslogLasMes OBJECT-TYPE
                     SYNTAX DisplayString (SIZE(0..127))
                     MAX-ACCESS read-only
                     STATUS current
                     DESCRIPTION "Message"
                     ::= {  staTcpipSyslogLasEntry 5 }

staTcpipRadiusc OBJECT IDENTIFIER ::= { staTcpip 13}
staTcpipRadiuscInvalidau OBJECT-TYPE
                         SYNTAX Counter32
                         MAX-ACCESS read-only
                         STATUS current
                         DESCRIPTION "Invalid-Auth.-Address-Responses"
                         ::= {  staTcpipRadiusc 1 }

staTcpipRadiuscAuthenticTable OBJECT-TYPE
                              SYNTAX SEQUENCE OF StaTcpipRadiuscAuthenticEntry
                              MAX-ACCESS not-accessible
                              STATUS current
                              DESCRIPTION "Authentication-Servers"
                              ::= {  staTcpipRadiusc 2 }

staTcpipRadiuscAuthenticEntry OBJECT-TYPE
                              SYNTAX StaTcpipRadiuscAuthenticEntry
                              MAX-ACCESS not-accessible
                              STATUS current
                              DESCRIPTION "entry in table"
                              INDEX { staTcpipRadiuscAuthenticIpaddress, staTcpipRadiuscAuthenticPort }
                              ::= {  staTcpipRadiuscAuthenticTable 1 }

StaTcpipRadiuscAuthenticEntry ::= SEQUENCE {
                              staTcpipRadiuscAuthenticIpaddress IpAddress,
                              staTcpipRadiuscAuthenticPort INTEGER,
                              staTcpipRadiuscAuthenticLastreque INTEGER,
                              staTcpipRadiuscAuthenticRoundtrip Counter32,
                              staTcpipRadiuscAuthenticAccessreq Counter32,
                              staTcpipRadiuscAuthenticAccessret Counter32,
                              staTcpipRadiuscAuthenticAccessacc Counter32,
                              staTcpipRadiuscAuthenticAccessrej Counter32,
                              staTcpipRadiuscAuthenticAccesscha Counter32,
                              staTcpipRadiuscAuthenticMalformed Counter32,
                              staTcpipRadiuscAuthenticBadauthen Counter32,
                              staTcpipRadiuscAuthenticPendingre Counter32,
                              staTcpipRadiuscAuthenticTimeouts Counter32,
                              staTcpipRadiuscAuthenticUnknownty Counter32,
                              staTcpipRadiuscAuthenticDropped Counter32
                             }

staTcpipRadiuscAuthenticIpaddress OBJECT-TYPE
                                  SYNTAX IpAddress
                                  MAX-ACCESS read-only
                                  STATUS current
                                  DESCRIPTION "IP-Address"
                                  ::= {  staTcpipRadiuscAuthenticEntry 1 }

staTcpipRadiuscAuthenticPort OBJECT-TYPE
                                  SYNTAX INTEGER (0..65535)
                                  MAX-ACCESS read-only
                                  STATUS current
                                  DESCRIPTION "Port"
                                  ::= {  staTcpipRadiuscAuthenticEntry 2 }

staTcpipRadiuscAuthenticLastreque OBJECT-TYPE
                                  SYNTAX INTEGER (0..2147483647)
                                  MAX-ACCESS read-only
                                  STATUS current
                                  DESCRIPTION "Last-Request"
                                  ::= {  staTcpipRadiuscAuthenticEntry 3 }

staTcpipRadiuscAuthenticRoundtrip OBJECT-TYPE
                                  SYNTAX Counter32
                                  MAX-ACCESS read-only
                                  STATUS current
                                  DESCRIPTION "Round-Trip-Time"
                                  ::= {  staTcpipRadiuscAuthenticEntry 4 }

staTcpipRadiuscAuthenticAccessreq OBJECT-TYPE
                                  SYNTAX Counter32
                                  MAX-ACCESS read-only
                                  STATUS current
                                  DESCRIPTION "Access-Requests"
                                  ::= {  staTcpipRadiuscAuthenticEntry 5 }

staTcpipRadiuscAuthenticAccessret OBJECT-TYPE
                                  SYNTAX Counter32
                                  MAX-ACCESS read-only
                                  STATUS current
                                  DESCRIPTION "Access-Retransmits"
                                  ::= {  staTcpipRadiuscAuthenticEntry 6 }

staTcpipRadiuscAuthenticAccessacc OBJECT-TYPE
                                  SYNTAX Counter32
                                  MAX-ACCESS read-only
                                  STATUS current
                                  DESCRIPTION "Access-Accepts"
                                  ::= {  staTcpipRadiuscAuthenticEntry 7 }

staTcpipRadiuscAuthenticAccessrej OBJECT-TYPE
                                  SYNTAX Counter32
                                  MAX-ACCESS read-only
                                  STATUS current
                                  DESCRIPTION "Access-Rejects"
                                  ::= {  staTcpipRadiuscAuthenticEntry 8 }

staTcpipRadiuscAuthenticAccesscha OBJECT-TYPE
                                  SYNTAX Counter32
                                  MAX-ACCESS read-only
                                  STATUS current
                                  DESCRIPTION "Access-Challenges"
                                  ::= {  staTcpipRadiuscAuthenticEntry 9 }

staTcpipRadiuscAuthenticMalformed OBJECT-TYPE
                                  SYNTAX Counter32
                                  MAX-ACCESS read-only
                                  STATUS current
                                  DESCRIPTION "Malformed-Access-Responses"
                                  ::= {  staTcpipRadiuscAuthenticEntry 10 }

staTcpipRadiuscAuthenticBadauthen OBJECT-TYPE
                                  SYNTAX Counter32
                                  MAX-ACCESS read-only
                                  STATUS current
                                  DESCRIPTION "Bad-Authenticators"
                                  ::= {  staTcpipRadiuscAuthenticEntry 11 }

staTcpipRadiuscAuthenticPendingre OBJECT-TYPE
                                  SYNTAX Counter32
                                  MAX-ACCESS read-only
                                  STATUS current
                                  DESCRIPTION "Pending-Requests"
                                  ::= {  staTcpipRadiuscAuthenticEntry 12 }

staTcpipRadiuscAuthenticTimeouts OBJECT-TYPE
                                  SYNTAX Counter32
                                  MAX-ACCESS read-only
                                  STATUS current
                                  DESCRIPTION "Timeouts"
                                  ::= {  staTcpipRadiuscAuthenticEntry 13 }

staTcpipRadiuscAuthenticUnknownty OBJECT-TYPE
                                  SYNTAX Counter32
                                  MAX-ACCESS read-only
                                  STATUS current
                                  DESCRIPTION "Unknown-Types"
                                  ::= {  staTcpipRadiuscAuthenticEntry 14 }

staTcpipRadiuscAuthenticDropped OBJECT-TYPE
                                  SYNTAX Counter32
                                  MAX-ACCESS read-only
                                  STATUS current
                                  DESCRIPTION "Dropped"
                                  ::= {  staTcpipRadiuscAuthenticEntry 15 }

staTcpipRadiuscInvalidac OBJECT-TYPE
                         SYNTAX Counter32
                         MAX-ACCESS read-only
                         STATUS current
                         DESCRIPTION "Invalid-Accnt.-Address-Responses"
                         ::= {  staTcpipRadiusc 11 }

staTcpipRadiuscAccountinTable OBJECT-TYPE
                              SYNTAX SEQUENCE OF StaTcpipRadiuscAccountinEntry
                              MAX-ACCESS not-accessible
                              STATUS current
                              DESCRIPTION "Accounting-Servers"
                              ::= {  staTcpipRadiusc 12 }

staTcpipRadiuscAccountinEntry OBJECT-TYPE
                              SYNTAX StaTcpipRadiuscAccountinEntry
                              MAX-ACCESS not-accessible
                              STATUS current
                              DESCRIPTION "entry in table"
                              INDEX { staTcpipRadiuscAccountinIpaddress, staTcpipRadiuscAccountinPort }
                              ::= {  staTcpipRadiuscAccountinTable 1 }

StaTcpipRadiuscAccountinEntry ::= SEQUENCE {
                              staTcpipRadiuscAccountinIpaddress IpAddress,
                              staTcpipRadiuscAccountinPort INTEGER,
                              staTcpipRadiuscAccountinLastrequest INTEGER,
                              staTcpipRadiuscAccountinRoundtriptime Counter32,
                              staTcpipRadiuscAccountinAccountingreq Counter32,
                              staTcpipRadiuscAccountinAccountingret Counter32,
                              staTcpipRadiuscAccountinAccountingres Counter32,
                              staTcpipRadiuscAccountinMalformedacco Counter32,
                              staTcpipRadiuscAccountinBadauthentica Counter32,
                              staTcpipRadiuscAccountinPendingreques Counter32,
                              staTcpipRadiuscAccountinTimeouts Counter32,
                              staTcpipRadiuscAccountinUnknowntypes Counter32,
                              staTcpipRadiuscAccountinDropped Counter32
                             }

staTcpipRadiuscAccountinIpaddress OBJECT-TYPE
                                      SYNTAX IpAddress
                                      MAX-ACCESS read-only
                                      STATUS current
                                      DESCRIPTION "IP-Address"
                                      ::= {  staTcpipRadiuscAccountinEntry 1 }

staTcpipRadiuscAccountinPort OBJECT-TYPE
                                      SYNTAX INTEGER (0..65535)
                                      MAX-ACCESS read-only
                                      STATUS current
                                      DESCRIPTION "Port"
                                      ::= {  staTcpipRadiuscAccountinEntry 2 }

staTcpipRadiuscAccountinLastrequest OBJECT-TYPE
                                      SYNTAX INTEGER (0..2147483647)
                                      MAX-ACCESS read-only
                                      STATUS current
                                      DESCRIPTION "Last-Request"
                                      ::= {  staTcpipRadiuscAccountinEntry 3 }

staTcpipRadiuscAccountinRoundtriptime OBJECT-TYPE
                                      SYNTAX Counter32
                                      MAX-ACCESS read-only
                                      STATUS current
                                      DESCRIPTION "Round-Trip-Time"
                                      ::= {  staTcpipRadiuscAccountinEntry 4 }

staTcpipRadiuscAccountinAccountingreq OBJECT-TYPE
                                      SYNTAX Counter32
                                      MAX-ACCESS read-only
                                      STATUS current
                                      DESCRIPTION "Accounting-Requests"
                                      ::= {  staTcpipRadiuscAccountinEntry 5 }

staTcpipRadiuscAccountinAccountingret OBJECT-TYPE
                                      SYNTAX Counter32
                                      MAX-ACCESS read-only
                                      STATUS current
                                      DESCRIPTION "Accounting-Retransmits"
                                      ::= {  staTcpipRadiuscAccountinEntry 6 }

staTcpipRadiuscAccountinAccountingres OBJECT-TYPE
                                      SYNTAX Counter32
                                      MAX-ACCESS read-only
                                      STATUS current
                                      DESCRIPTION "Accounting-Responses"
                                      ::= {  staTcpipRadiuscAccountinEntry 7 }

staTcpipRadiuscAccountinMalformedacco OBJECT-TYPE
                                      SYNTAX Counter32
                                      MAX-ACCESS read-only
                                      STATUS current
                                      DESCRIPTION "Malformed-Accounting-Responses"
                                      ::= {  staTcpipRadiuscAccountinEntry 8 }

staTcpipRadiuscAccountinBadauthentica OBJECT-TYPE
                                      SYNTAX Counter32
                                      MAX-ACCESS read-only
                                      STATUS current
                                      DESCRIPTION "Bad-Authenticators"
                                      ::= {  staTcpipRadiuscAccountinEntry 9 }

staTcpipRadiuscAccountinPendingreques OBJECT-TYPE
                                      SYNTAX Counter32
                                      MAX-ACCESS read-only
                                      STATUS current
                                      DESCRIPTION "Pending-Requests"
                                      ::= {  staTcpipRadiuscAccountinEntry 10 }

staTcpipRadiuscAccountinTimeouts OBJECT-TYPE
                                      SYNTAX Counter32
                                      MAX-ACCESS read-only
                                      STATUS current
                                      DESCRIPTION "Timeouts"
                                      ::= {  staTcpipRadiuscAccountinEntry 11 }

staTcpipRadiuscAccountinUnknowntypes OBJECT-TYPE
                                      SYNTAX Counter32
                                      MAX-ACCESS read-only
                                      STATUS current
                                      DESCRIPTION "Unknown-Types"
                                      ::= {  staTcpipRadiuscAccountinEntry 12 }

staTcpipRadiuscAccountinDropped OBJECT-TYPE
                                      SYNTAX Counter32
                                      MAX-ACCESS read-only
                                      STATUS current
                                      DESCRIPTION "Dropped"
                                      ::= {  staTcpipRadiuscAccountinEntry 13 }

staTcpipRadiuss OBJECT IDENTIFIER ::= { staTcpip 12}
staTcpipRadiussAcce OBJECT IDENTIFIER ::= { staTcpipRadiuss 1}
staTcpipRadiussAcceDeletevalues OBJECT-TYPE
                                  SYNTAX DisplayString
                                  MAX-ACCESS read-write
                                  STATUS current
                                  DESCRIPTION "Delete-Values"
                                  ::= {  staTcpipRadiussAcce 100 }

staTcpipRadiussAcceClientsTable OBJECT-TYPE
                                       SYNTAX SEQUENCE OF StaTcpipRadiussAcceClientsEntry
                                       MAX-ACCESS not-accessible
                                       STATUS current
                                       DESCRIPTION "Clients"
                                       ::= {  staTcpipRadiussAcce 15 }

staTcpipRadiussAcceClientsEntry OBJECT-TYPE
                                       SYNTAX StaTcpipRadiussAcceClientsEntry
                                       MAX-ACCESS not-accessible
                                       STATUS current
                                       DESCRIPTION "entry in table"
                                       INDEX { staTcpipRadiussAcceClientsIpaddress }
                                       ::= {  staTcpipRadiussAcceClientsTable 1 }

StaTcpipRadiussAcceClientsEntry ::= SEQUENCE {
                                       staTcpipRadiussAcceClientsIpaddress IpAddress,
                                       staTcpipRadiussAcceClientsLastreque INTEGER,
                                       staTcpipRadiussAcceClientsNasident DisplayString,
                                       staTcpipRadiussAcceClientsAccessreq Counter32,
                                       staTcpipRadiussAcceClientsDuplicate Counter32,
                                       staTcpipRadiussAcceClientsAccessacc Counter32,
                                       staTcpipRadiussAcceClientsAccessrej Counter32,
                                       staTcpipRadiussAcceClientsAccesscha Counter32,
                                       staTcpipRadiussAcceClientsMalformed Counter32,
                                       staTcpipRadiussAcceClientsBadauthen Counter32,
                                       staTcpipRadiussAcceClientsDropped Counter32,
                                       staTcpipRadiussAcceClientsUnknownty Counter32
                                      }

staTcpipRadiussAcceClientsIpaddress OBJECT-TYPE
                                    SYNTAX IpAddress
                                    MAX-ACCESS read-only
                                    STATUS current
                                    DESCRIPTION "IP-Address"
                                    ::= {  staTcpipRadiussAcceClientsEntry 1 }

staTcpipRadiussAcceClientsLastreque OBJECT-TYPE
                                    SYNTAX INTEGER (0..2147483647)
                                    MAX-ACCESS read-only
                                    STATUS current
                                    DESCRIPTION "Last-Request"
                                    ::= {  staTcpipRadiussAcceClientsEntry 13 }

staTcpipRadiussAcceClientsNasident OBJECT-TYPE
                                    SYNTAX DisplayString (SIZE(0..64))
                                    MAX-ACCESS read-only
                                    STATUS current
                                    DESCRIPTION "NAS-Ident"
                                    ::= {  staTcpipRadiussAcceClientsEntry 14 }

staTcpipRadiussAcceClientsAccessreq OBJECT-TYPE
                                    SYNTAX Counter32
                                    MAX-ACCESS read-only
                                    STATUS current
                                    DESCRIPTION "Access-Requests"
                                    ::= {  staTcpipRadiussAcceClientsEntry 4 }

staTcpipRadiussAcceClientsDuplicate OBJECT-TYPE
                                    SYNTAX Counter32
                                    MAX-ACCESS read-only
                                    STATUS current
                                    DESCRIPTION "Duplicate-Requests"
                                    ::= {  staTcpipRadiussAcceClientsEntry 5 }

staTcpipRadiussAcceClientsAccessacc OBJECT-TYPE
                                    SYNTAX Counter32
                                    MAX-ACCESS read-only
                                    STATUS current
                                    DESCRIPTION "Access-Accepts"
                                    ::= {  staTcpipRadiussAcceClientsEntry 6 }

staTcpipRadiussAcceClientsAccessrej OBJECT-TYPE
                                    SYNTAX Counter32
                                    MAX-ACCESS read-only
                                    STATUS current
                                    DESCRIPTION "Access-Rejects"
                                    ::= {  staTcpipRadiussAcceClientsEntry 7 }

staTcpipRadiussAcceClientsAccesscha OBJECT-TYPE
                                    SYNTAX Counter32
                                    MAX-ACCESS read-only
                                    STATUS current
                                    DESCRIPTION "Access-Challenges"
                                    ::= {  staTcpipRadiussAcceClientsEntry 8 }

staTcpipRadiussAcceClientsMalformed OBJECT-TYPE
                                    SYNTAX Counter32
                                    MAX-ACCESS read-only
                                    STATUS current
                                    DESCRIPTION "Malformed-Access-Requests"
                                    ::= {  staTcpipRadiussAcceClientsEntry 9 }

staTcpipRadiussAcceClientsBadauthen OBJECT-TYPE
                                    SYNTAX Counter32
                                    MAX-ACCESS read-only
                                    STATUS current
                                    DESCRIPTION "Bad-Authenticator"
                                    ::= {  staTcpipRadiussAcceClientsEntry 10 }

staTcpipRadiussAcceClientsDropped OBJECT-TYPE
                                    SYNTAX Counter32
                                    MAX-ACCESS read-only
                                    STATUS current
                                    DESCRIPTION "Dropped"
                                    ::= {  staTcpipRadiussAcceClientsEntry 11 }

staTcpipRadiussAcceClientsUnknownty OBJECT-TYPE
                                    SYNTAX Counter32
                                    MAX-ACCESS read-only
                                    STATUS current
                                    DESCRIPTION "Unknown-Type"
                                    ::= {  staTcpipRadiussAcceClientsEntry 12 }

staTcpipRadiussAcceTotalaccessreq OBJECT-TYPE
                                  SYNTAX Counter32
                                  MAX-ACCESS read-only
                                  STATUS current
                                  DESCRIPTION "Total-Access-Requests"
                                  ::= {  staTcpipRadiussAcce 5 }

staTcpipRadiussAcceTotalinvalidac OBJECT-TYPE
                                  SYNTAX Counter32
                                  MAX-ACCESS read-only
                                  STATUS current
                                  DESCRIPTION "Total-Invalid-Access-Requests"
                                  ::= {  staTcpipRadiussAcce 6 }

staTcpipRadiussAcceTotalduplicate OBJECT-TYPE
                                  SYNTAX Counter32
                                  MAX-ACCESS read-only
                                  STATUS current
                                  DESCRIPTION "Total-Duplicate-Access-Requests"
                                  ::= {  staTcpipRadiussAcce 7 }

staTcpipRadiussAcceTotalaccessacc OBJECT-TYPE
                                  SYNTAX Counter32
                                  MAX-ACCESS read-only
                                  STATUS current
                                  DESCRIPTION "Total-Access-Accepts"
                                  ::= {  staTcpipRadiussAcce 8 }

staTcpipRadiussAcceTotalaccessrej OBJECT-TYPE
                                  SYNTAX Counter32
                                  MAX-ACCESS read-only
                                  STATUS current
                                  DESCRIPTION "Total-Access-Rejects"
                                  ::= {  staTcpipRadiussAcce 9 }

staTcpipRadiussAcceTotalaccesscha OBJECT-TYPE
                                  SYNTAX Counter32
                                  MAX-ACCESS read-only
                                  STATUS current
                                  DESCRIPTION "Total-Access-Challenges"
                                  ::= {  staTcpipRadiussAcce 10 }

staTcpipRadiussAcceTotalmalformed OBJECT-TYPE
                                  SYNTAX Counter32
                                  MAX-ACCESS read-only
                                  STATUS current
                                  DESCRIPTION "Total-Malformed-Access-Requests"
                                  ::= {  staTcpipRadiussAcce 11 }

staTcpipRadiussAcceTotalaccessbad OBJECT-TYPE
                                  SYNTAX Counter32
                                  MAX-ACCESS read-only
                                  STATUS current
                                  DESCRIPTION "Total-Access-Bad-Authenticator"
                                  ::= {  staTcpipRadiussAcce 12 }

staTcpipRadiussAcceTotalaccessdro OBJECT-TYPE
                                  SYNTAX Counter32
                                  MAX-ACCESS read-only
                                  STATUS current
                                  DESCRIPTION "Total-Access-Dropped"
                                  ::= {  staTcpipRadiussAcce 13 }

staTcpipRadiussAcceTotalaccessunk OBJECT-TYPE
                                  SYNTAX Counter32
                                  MAX-ACCESS read-only
                                  STATUS current
                                  DESCRIPTION "Total-Access-Unknown-Type"
                                  ::= {  staTcpipRadiussAcce 14 }

staTcpipRadiussAcco OBJECT IDENTIFIER ::= { staTcpipRadiuss 2}
staTcpipRadiussAccoDeletevalues OBJECT-TYPE
                                   SYNTAX DisplayString
                                   MAX-ACCESS read-write
                                   STATUS current
                                   DESCRIPTION "Delete-Values"
                                   ::= {  staTcpipRadiussAcco 100 }

staTcpipRadiussAccoClientsTable OBJECT-TYPE
                                        SYNTAX SEQUENCE OF StaTcpipRadiussAccoClientsEntry
                                        MAX-ACCESS not-accessible
                                        STATUS current
                                        DESCRIPTION "Clients"
                                        ::= {  staTcpipRadiussAcco 15 }

staTcpipRadiussAccoClientsEntry OBJECT-TYPE
                                        SYNTAX StaTcpipRadiussAccoClientsEntry
                                        MAX-ACCESS not-accessible
                                        STATUS current
                                        DESCRIPTION "entry in table"
                                        INDEX { staTcpipRadiussAccoClientsIpaddress }
                                        ::= {  staTcpipRadiussAccoClientsTable 1 }

StaTcpipRadiussAccoClientsEntry ::= SEQUENCE {
                                        staTcpipRadiussAccoClientsIpaddress IpAddress,
                                        staTcpipRadiussAccoClientsLastreques INTEGER,
                                        staTcpipRadiussAccoClientsNasident DisplayString,
                                        staTcpipRadiussAccoClientsAccountreq Counter32,
                                        staTcpipRadiussAccoClientsDuplicater Counter32,
                                        staTcpipRadiussAccoClientsAccountres Counter32,
                                        staTcpipRadiussAccoClientsAccountnor Counter32,
                                        staTcpipRadiussAccoClientsMalformeda Counter32,
                                        staTcpipRadiussAccoClientsBadauthent Counter32,
                                        staTcpipRadiussAccoClientsDropped Counter32,
                                        staTcpipRadiussAccoClientsUnknowntyp Counter32
                                       }

staTcpipRadiussAccoClientsIpaddress OBJECT-TYPE
                                     SYNTAX IpAddress
                                     MAX-ACCESS read-only
                                     STATUS current
                                     DESCRIPTION "IP-Address"
                                     ::= {  staTcpipRadiussAccoClientsEntry 1 }

staTcpipRadiussAccoClientsLastreques OBJECT-TYPE
                                     SYNTAX INTEGER (0..2147483647)
                                     MAX-ACCESS read-only
                                     STATUS current
                                     DESCRIPTION "Last-Request"
                                     ::= {  staTcpipRadiussAccoClientsEntry 13 }

staTcpipRadiussAccoClientsNasident OBJECT-TYPE
                                     SYNTAX DisplayString (SIZE(0..64))
                                     MAX-ACCESS read-only
                                     STATUS current
                                     DESCRIPTION "NAS-Ident"
                                     ::= {  staTcpipRadiussAccoClientsEntry 14 }

staTcpipRadiussAccoClientsAccountreq OBJECT-TYPE
                                     SYNTAX Counter32
                                     MAX-ACCESS read-only
                                     STATUS current
                                     DESCRIPTION "Account-Requests"
                                     ::= {  staTcpipRadiussAccoClientsEntry 4 }

staTcpipRadiussAccoClientsDuplicater OBJECT-TYPE
                                     SYNTAX Counter32
                                     MAX-ACCESS read-only
                                     STATUS current
                                     DESCRIPTION "Duplicate-Requests"
                                     ::= {  staTcpipRadiussAccoClientsEntry 5 }

staTcpipRadiussAccoClientsAccountres OBJECT-TYPE
                                     SYNTAX Counter32
                                     MAX-ACCESS read-only
                                     STATUS current
                                     DESCRIPTION "Account-Responses"
                                     ::= {  staTcpipRadiussAccoClientsEntry 6 }

staTcpipRadiussAccoClientsAccountnor OBJECT-TYPE
                                     SYNTAX Counter32
                                     MAX-ACCESS read-only
                                     STATUS current
                                     DESCRIPTION "Account-NoRecords"
                                     ::= {  staTcpipRadiussAccoClientsEntry 7 }

staTcpipRadiussAccoClientsMalformeda OBJECT-TYPE
                                     SYNTAX Counter32
                                     MAX-ACCESS read-only
                                     STATUS current
                                     DESCRIPTION "Malformed-Access-Requests"
                                     ::= {  staTcpipRadiussAccoClientsEntry 9 }

staTcpipRadiussAccoClientsBadauthent OBJECT-TYPE
                                     SYNTAX Counter32
                                     MAX-ACCESS read-only
                                     STATUS current
                                     DESCRIPTION "Bad-Authenticator"
                                     ::= {  staTcpipRadiussAccoClientsEntry 10 }

staTcpipRadiussAccoClientsDropped OBJECT-TYPE
                                     SYNTAX Counter32
                                     MAX-ACCESS read-only
                                     STATUS current
                                     DESCRIPTION "Dropped"
                                     ::= {  staTcpipRadiussAccoClientsEntry 11 }

staTcpipRadiussAccoClientsUnknowntyp OBJECT-TYPE
                                     SYNTAX Counter32
                                     MAX-ACCESS read-only
                                     STATUS current
                                     DESCRIPTION "Unknown-Type"
                                     ::= {  staTcpipRadiussAccoClientsEntry 12 }

staTcpipRadiussAccoActiveaccountinTable OBJECT-TYPE
                                        SYNTAX SEQUENCE OF StaTcpipRadiussAccoActiveaccountinEntry
                                        MAX-ACCESS not-accessible
                                        STATUS current
                                        DESCRIPTION "Active-Accounting-Sessions"
                                        ::= {  staTcpipRadiussAcco 16 }

staTcpipRadiussAccoActiveaccountinEntry OBJECT-TYPE
                                        SYNTAX StaTcpipRadiussAccoActiveaccountinEntry
                                        MAX-ACCESS not-accessible
                                        STATUS current
                                        DESCRIPTION "entry in table"
                                        INDEX { staTcpipRadiussAccoActiveaccountinIndex }
                                        ::= {  staTcpipRadiussAccoActiveaccountinTable 1 }

StaTcpipRadiussAccoActiveaccountinEntry ::= SEQUENCE {
                                        staTcpipRadiussAccoActiveaccountinIndex INTEGER,
                                        staTcpipRadiussAccoActiveaccountinStarttim DisplayString,
                                        staTcpipRadiussAccoActiveaccountinLastupda INTEGER,
                                        staTcpipRadiussAccoActiveaccountinUpdatede INTEGER,
                                        staTcpipRadiussAccoActiveaccountinNasipadd IpAddress,
                                        staTcpipRadiussAccoActiveaccountinNasident DisplayString,
                                        staTcpipRadiussAccoActiveaccountinNasportt INTEGER,
                                        staTcpipRadiussAccoActiveaccountinNasporti INTEGER,
                                        staTcpipRadiussAccoActiveaccountinSessioni DisplayString,
                                        staTcpipRadiussAccoActiveaccountinCalledst DisplayString,
                                        staTcpipRadiussAccoActiveaccountinCallings DisplayString,
                                        staTcpipRadiussAccoActiveaccountinUsername DisplayString,
                                        staTcpipRadiussAccoActiveaccountinSessiont INTEGER,
                                        staTcpipRadiussAccoActiveaccountinInputpac Counter32,
                                        staTcpipRadiussAccoActiveaccountinOutputpa Counter32,
                                        staTcpipRadiussAccoActiveaccountinInputoct Counter64,
                                        staTcpipRadiussAccoActiveaccountinOutputoc Counter64,
                                        staTcpipRadiussAccoActiveaccountinIpaddres IpAddress
                                       }

staTcpipRadiussAccoActiveaccountinIndex OBJECT-TYPE
                                           SYNTAX INTEGER (0..2147483647)
                                           MAX-ACCESS read-only
                                           STATUS current
                                           DESCRIPTION "Index"
                                           ::= {  staTcpipRadiussAccoActiveaccountinEntry 1 }

staTcpipRadiussAccoActiveaccountinStarttim OBJECT-TYPE
                                           SYNTAX DisplayString (SIZE(0..19))
                                           MAX-ACCESS read-only
                                           STATUS current
                                           DESCRIPTION "Start-Time"
                                           ::= {  staTcpipRadiussAccoActiveaccountinEntry 12 }

staTcpipRadiussAccoActiveaccountinLastupda OBJECT-TYPE
                                           SYNTAX INTEGER (0..2147483647)
                                           MAX-ACCESS read-only
                                           STATUS current
                                           DESCRIPTION "Last-Update"
                                           ::= {  staTcpipRadiussAccoActiveaccountinEntry 15 }

staTcpipRadiussAccoActiveaccountinUpdatede OBJECT-TYPE
                                           SYNTAX INTEGER (0..2147483647)
                                           MAX-ACCESS read-only
                                           STATUS current
                                           DESCRIPTION "Update-Delta"
                                           ::= {  staTcpipRadiussAccoActiveaccountinEntry 16 }

staTcpipRadiussAccoActiveaccountinNasipadd OBJECT-TYPE
                                           SYNTAX IpAddress
                                           MAX-ACCESS read-only
                                           STATUS current
                                           DESCRIPTION "NAS-IP-Address"
                                           ::= {  staTcpipRadiussAccoActiveaccountinEntry 2 }

staTcpipRadiussAccoActiveaccountinNasident OBJECT-TYPE
                                           SYNTAX DisplayString (SIZE(0..64))
                                           MAX-ACCESS read-only
                                           STATUS current
                                           DESCRIPTION "NAS-Ident"
                                           ::= {  staTcpipRadiussAccoActiveaccountinEntry 3 }

staTcpipRadiussAccoActiveaccountinNasportt OBJECT-TYPE
                                           SYNTAX INTEGER{
                                             async(0),
                                             sync(1),
                                             isdn-sync(2),
                                             v-120(3),
                                             v-110(4),
                                             virtual(5),
                                             piafs(6),
                                             hdlc-clear-channel(7),
                                             x-25(8),
                                             x-75(9),
                                             g-3-fax(10),
                                             sdsl(11),
                                             adsl-cap(12),
                                             adsl-dmt(13),
                                             idsl(14),
                                             ethernet(15),
                                             xdsl(16),
                                             cable(17),
                                             wireless-other(18),
                                             wireless-802-11(19),
                                             token-ring(20),
                                             fddi(21),
                                             wireless-cdma2000(22),
                                             wireless-umts(23),
                                             wireless-1x-ev(24),
                                             iapp(25),
                                             fttp(26),
                                             wireless-802-16(27),
                                             wireless-802-20(28),
                                             wireless-802-22(29),
                                             pppoa(30),
                                             pppoeoa(31),
                                             pppoeoe(32),
                                             pppoeovlan(33),
                                             pppoeoqinq(34),
                                             xpon(35),
                                             unknown(-1)
                                           }
                                           MAX-ACCESS read-only
                                           STATUS current
                                           DESCRIPTION "NAS-Port-Type"
                                           ::= {  staTcpipRadiussAccoActiveaccountinEntry 17 }

staTcpipRadiussAccoActiveaccountinNasporti OBJECT-TYPE
                                           SYNTAX INTEGER (0..2147483647)
                                           MAX-ACCESS read-only
                                           STATUS current
                                           DESCRIPTION "NAS-Port-Id"
                                           ::= {  staTcpipRadiussAccoActiveaccountinEntry 18 }

staTcpipRadiussAccoActiveaccountinSessioni OBJECT-TYPE
                                           SYNTAX DisplayString (SIZE(0..128))
                                           MAX-ACCESS read-only
                                           STATUS current
                                           DESCRIPTION "Session-ID"
                                           ::= {  staTcpipRadiussAccoActiveaccountinEntry 4 }

staTcpipRadiussAccoActiveaccountinCalledst OBJECT-TYPE
                                           SYNTAX DisplayString (SIZE(0..48))
                                           MAX-ACCESS read-only
                                           STATUS current
                                           DESCRIPTION "Called-Station-Id"
                                           ::= {  staTcpipRadiussAccoActiveaccountinEntry 19 }

staTcpipRadiussAccoActiveaccountinCallings OBJECT-TYPE
                                           SYNTAX DisplayString (SIZE(0..48))
                                           MAX-ACCESS read-only
                                           STATUS current
                                           DESCRIPTION "Calling-Station-Id"
                                           ::= {  staTcpipRadiussAccoActiveaccountinEntry 20 }

staTcpipRadiussAccoActiveaccountinUsername OBJECT-TYPE
                                           SYNTAX DisplayString (SIZE(0..48))
                                           MAX-ACCESS read-only
                                           STATUS current
                                           DESCRIPTION "User-Name"
                                           ::= {  staTcpipRadiussAccoActiveaccountinEntry 5 }

staTcpipRadiussAccoActiveaccountinSessiont OBJECT-TYPE
                                           SYNTAX INTEGER (0..2147483647)
                                           MAX-ACCESS read-only
                                           STATUS current
                                           DESCRIPTION "Session-Time"
                                           ::= {  staTcpipRadiussAccoActiveaccountinEntry 6 }

staTcpipRadiussAccoActiveaccountinInputpac OBJECT-TYPE
                                           SYNTAX Counter32
                                           MAX-ACCESS read-only
                                           STATUS current
                                           DESCRIPTION "Input-Packets"
                                           ::= {  staTcpipRadiussAccoActiveaccountinEntry 7 }

staTcpipRadiussAccoActiveaccountinOutputpa OBJECT-TYPE
                                           SYNTAX Counter32
                                           MAX-ACCESS read-only
                                           STATUS current
                                           DESCRIPTION "Output-Packets"
                                           ::= {  staTcpipRadiussAccoActiveaccountinEntry 8 }

staTcpipRadiussAccoActiveaccountinInputoct OBJECT-TYPE
                                           SYNTAX Counter64
                                           MAX-ACCESS read-only
                                           STATUS current
                                           DESCRIPTION "Input-Octets"
                                           ::= {  staTcpipRadiussAccoActiveaccountinEntry 9 }

staTcpipRadiussAccoActiveaccountinOutputoc OBJECT-TYPE
                                           SYNTAX Counter64
                                           MAX-ACCESS read-only
                                           STATUS current
                                           DESCRIPTION "Output-Octets"
                                           ::= {  staTcpipRadiussAccoActiveaccountinEntry 10 }

staTcpipRadiussAccoActiveaccountinIpaddres OBJECT-TYPE
                                           SYNTAX IpAddress
                                           MAX-ACCESS read-only
                                           STATUS current
                                           DESCRIPTION "IP-Address"
                                           ::= {  staTcpipRadiussAccoActiveaccountinEntry 11 }

staTcpipRadiussAccoCompletedaccounTable OBJECT-TYPE
                                        SYNTAX SEQUENCE OF StaTcpipRadiussAccoCompletedaccounEntry
                                        MAX-ACCESS not-accessible
                                        STATUS current
                                        DESCRIPTION "Completed-Accounting-Sessions"
                                        ::= {  staTcpipRadiussAcco 17 }

staTcpipRadiussAccoCompletedaccounEntry OBJECT-TYPE
                                        SYNTAX StaTcpipRadiussAccoCompletedaccounEntry
                                        MAX-ACCESS not-accessible
                                        STATUS current
                                        DESCRIPTION "entry in table"
                                        INDEX { staTcpipRadiussAccoCompletedaccounIndex }
                                        ::= {  staTcpipRadiussAccoCompletedaccounTable 1 }

StaTcpipRadiussAccoCompletedaccounEntry ::= SEQUENCE {
                                        staTcpipRadiussAccoCompletedaccounIndex INTEGER,
                                        staTcpipRadiussAccoCompletedaccounStarttim DisplayString,
                                        staTcpipRadiussAccoCompletedaccounStoptime DisplayString,
                                        staTcpipRadiussAccoCompletedaccounTerminat INTEGER,
                                        staTcpipRadiussAccoCompletedaccounNasipadd IpAddress,
                                        staTcpipRadiussAccoCompletedaccounNasident DisplayString,
                                        staTcpipRadiussAccoCompletedaccounNasportt INTEGER,
                                        staTcpipRadiussAccoCompletedaccounNasporti INTEGER,
                                        staTcpipRadiussAccoCompletedaccounSessioni DisplayString,
                                        staTcpipRadiussAccoCompletedaccounCalledst DisplayString,
                                        staTcpipRadiussAccoCompletedaccounCallings DisplayString,
                                        staTcpipRadiussAccoCompletedaccounUsername DisplayString,
                                        staTcpipRadiussAccoCompletedaccounSessiont INTEGER,
                                        staTcpipRadiussAccoCompletedaccounInputpac Counter32,
                                        staTcpipRadiussAccoCompletedaccounOutputpa Counter32,
                                        staTcpipRadiussAccoCompletedaccounInputoct Counter64,
                                        staTcpipRadiussAccoCompletedaccounOutputoc Counter64,
                                        staTcpipRadiussAccoCompletedaccounIpaddres IpAddress
                                       }

staTcpipRadiussAccoCompletedaccounIndex OBJECT-TYPE
                                           SYNTAX INTEGER (0..2147483647)
                                           MAX-ACCESS read-only
                                           STATUS current
                                           DESCRIPTION "Index"
                                           ::= {  staTcpipRadiussAccoCompletedaccounEntry 1 }

staTcpipRadiussAccoCompletedaccounStarttim OBJECT-TYPE
                                           SYNTAX DisplayString (SIZE(0..19))
                                           MAX-ACCESS read-only
                                           STATUS current
                                           DESCRIPTION "Start-Time"
                                           ::= {  staTcpipRadiussAccoCompletedaccounEntry 12 }

staTcpipRadiussAccoCompletedaccounStoptime OBJECT-TYPE
                                           SYNTAX DisplayString (SIZE(0..19))
                                           MAX-ACCESS read-only
                                           STATUS current
                                           DESCRIPTION "Stop-Time"
                                           ::= {  staTcpipRadiussAccoCompletedaccounEntry 13 }

staTcpipRadiussAccoCompletedaccounTerminat OBJECT-TYPE
                                           SYNTAX INTEGER{
                                             user-request(1),
                                             lost-carrier(2),
                                             lost-service(3),
                                             idle-timeout(4),
                                             session-timeout(5),
                                             admin-reset(6),
                                             admin-reboot(7),
                                             port-error(8),
                                             nas-error(9),
                                             nas-request(10),
                                             nas-reboot(11),
                                             port-unneeded(12),
                                             port-preempted(13),
                                             port-suspended(14),
                                             service-unavailable(15),
                                             callback(16),
                                             user-error(17),
                                             host-request(18),
                                             supplicant-restart(19),
                                             reauthentication-failure(20),
                                             port-reinit(21),
                                             port-admin-disabled(22)
                                           }
                                           MAX-ACCESS read-only
                                           STATUS current
                                           DESCRIPTION "Terminate-Cause"
                                           ::= {  staTcpipRadiussAccoCompletedaccounEntry 14 }

staTcpipRadiussAccoCompletedaccounNasipadd OBJECT-TYPE
                                           SYNTAX IpAddress
                                           MAX-ACCESS read-only
                                           STATUS current
                                           DESCRIPTION "NAS-IP-Address"
                                           ::= {  staTcpipRadiussAccoCompletedaccounEntry 2 }

staTcpipRadiussAccoCompletedaccounNasident OBJECT-TYPE
                                           SYNTAX DisplayString (SIZE(0..64))
                                           MAX-ACCESS read-only
                                           STATUS current
                                           DESCRIPTION "NAS-Ident"
                                           ::= {  staTcpipRadiussAccoCompletedaccounEntry 3 }

staTcpipRadiussAccoCompletedaccounNasportt OBJECT-TYPE
                                           SYNTAX INTEGER{
                                             async(0),
                                             sync(1),
                                             isdn-sync(2),
                                             v-120(3),
                                             v-110(4),
                                             virtual(5),
                                             piafs(6),
                                             hdlc-clear-channel(7),
                                             x-25(8),
                                             x-75(9),
                                             g-3-fax(10),
                                             sdsl(11),
                                             adsl-cap(12),
                                             adsl-dmt(13),
                                             idsl(14),
                                             ethernet(15),
                                             xdsl(16),
                                             cable(17),
                                             wireless-other(18),
                                             wireless-802-11(19),
                                             token-ring(20),
                                             fddi(21),
                                             wireless-cdma2000(22),
                                             wireless-umts(23),
                                             wireless-1x-ev(24),
                                             iapp(25),
                                             fttp(26),
                                             wireless-802-16(27),
                                             wireless-802-20(28),
                                             wireless-802-22(29),
                                             pppoa(30),
                                             pppoeoa(31),
                                             pppoeoe(32),
                                             pppoeovlan(33),
                                             pppoeoqinq(34),
                                             xpon(35),
                                             unknown(-1)
                                           }
                                           MAX-ACCESS read-only
                                           STATUS current
                                           DESCRIPTION "NAS-Port-Type"
                                           ::= {  staTcpipRadiussAccoCompletedaccounEntry 17 }

staTcpipRadiussAccoCompletedaccounNasporti OBJECT-TYPE
                                           SYNTAX INTEGER (0..2147483647)
                                           MAX-ACCESS read-only
                                           STATUS current
                                           DESCRIPTION "NAS-Port-Id"
                                           ::= {  staTcpipRadiussAccoCompletedaccounEntry 18 }

staTcpipRadiussAccoCompletedaccounSessioni OBJECT-TYPE
                                           SYNTAX DisplayString (SIZE(0..128))
                                           MAX-ACCESS read-only
                                           STATUS current
                                           DESCRIPTION "Session-ID"
                                           ::= {  staTcpipRadiussAccoCompletedaccounEntry 4 }

staTcpipRadiussAccoCompletedaccounCalledst OBJECT-TYPE
                                           SYNTAX DisplayString (SIZE(0..48))
                                           MAX-ACCESS read-only
                                           STATUS current
                                           DESCRIPTION "Called-Station-Id"
                                           ::= {  staTcpipRadiussAccoCompletedaccounEntry 19 }

staTcpipRadiussAccoCompletedaccounCallings OBJECT-TYPE
                                           SYNTAX DisplayString (SIZE(0..48))
                                           MAX-ACCESS read-only
                                           STATUS current
                                           DESCRIPTION "Calling-Station-Id"
                                           ::= {  staTcpipRadiussAccoCompletedaccounEntry 20 }

staTcpipRadiussAccoCompletedaccounUsername OBJECT-TYPE
                                           SYNTAX DisplayString (SIZE(0..48))
                                           MAX-ACCESS read-only
                                           STATUS current
                                           DESCRIPTION "User-Name"
                                           ::= {  staTcpipRadiussAccoCompletedaccounEntry 5 }

staTcpipRadiussAccoCompletedaccounSessiont OBJECT-TYPE
                                           SYNTAX INTEGER (0..2147483647)
                                           MAX-ACCESS read-only
                                           STATUS current
                                           DESCRIPTION "Session-Time"
                                           ::= {  staTcpipRadiussAccoCompletedaccounEntry 6 }

staTcpipRadiussAccoCompletedaccounInputpac OBJECT-TYPE
                                           SYNTAX Counter32
                                           MAX-ACCESS read-only
                                           STATUS current
                                           DESCRIPTION "Input-Packets"
                                           ::= {  staTcpipRadiussAccoCompletedaccounEntry 7 }

staTcpipRadiussAccoCompletedaccounOutputpa OBJECT-TYPE
                                           SYNTAX Counter32
                                           MAX-ACCESS read-only
                                           STATUS current
                                           DESCRIPTION "Output-Packets"
                                           ::= {  staTcpipRadiussAccoCompletedaccounEntry 8 }

staTcpipRadiussAccoCompletedaccounInputoct OBJECT-TYPE
                                           SYNTAX Counter64
                                           MAX-ACCESS read-only
                                           STATUS current
                                           DESCRIPTION "Input-Octets"
                                           ::= {  staTcpipRadiussAccoCompletedaccounEntry 9 }

staTcpipRadiussAccoCompletedaccounOutputoc OBJECT-TYPE
                                           SYNTAX Counter64
                                           MAX-ACCESS read-only
                                           STATUS current
                                           DESCRIPTION "Output-Octets"
                                           ::= {  staTcpipRadiussAccoCompletedaccounEntry 10 }

staTcpipRadiussAccoCompletedaccounIpaddres OBJECT-TYPE
                                           SYNTAX IpAddress
                                           MAX-ACCESS read-only
                                           STATUS current
                                           DESCRIPTION "IP-Address"
                                           ::= {  staTcpipRadiussAccoCompletedaccounEntry 11 }

staTcpipRadiussAccoTotalaccountreq OBJECT-TYPE
                                   SYNTAX Counter32
                                   MAX-ACCESS read-only
                                   STATUS current
                                   DESCRIPTION "Total-Account-Requests"
                                   ::= {  staTcpipRadiussAcco 5 }

staTcpipRadiussAccoTotalinvalidacc OBJECT-TYPE
                                   SYNTAX Counter32
                                   MAX-ACCESS read-only
                                   STATUS current
                                   DESCRIPTION "Total-Invalid-Account-Requests"
                                   ::= {  staTcpipRadiussAcco 6 }

staTcpipRadiussAccoTotalduplicatea OBJECT-TYPE
                                   SYNTAX Counter32
                                   MAX-ACCESS read-only
                                   STATUS current
                                   DESCRIPTION "Total-Duplicate-Account-Requests"
                                   ::= {  staTcpipRadiussAcco 7 }

staTcpipRadiussAccoTotalaccountres OBJECT-TYPE
                                   SYNTAX Counter32
                                   MAX-ACCESS read-only
                                   STATUS current
                                   DESCRIPTION "Total-Account-Responses"
                                   ::= {  staTcpipRadiussAcco 8 }

staTcpipRadiussAccoTotalmalformeda OBJECT-TYPE
                                   SYNTAX Counter32
                                   MAX-ACCESS read-only
                                   STATUS current
                                   DESCRIPTION "Total-Malformed-Account-Requests"
                                   ::= {  staTcpipRadiussAcco 9 }

staTcpipRadiussAccoTotalaccountbad OBJECT-TYPE
                                   SYNTAX Counter32
                                   MAX-ACCESS read-only
                                   STATUS current
                                   DESCRIPTION "Total-Account-Bad-Authenticator"
                                   ::= {  staTcpipRadiussAcco 10 }

staTcpipRadiussAccoTotalaccountdro OBJECT-TYPE
                                   SYNTAX Counter32
                                   MAX-ACCESS read-only
                                   STATUS current
                                   DESCRIPTION "Total-Account-Dropped"
                                   ::= {  staTcpipRadiussAcco 11 }

staTcpipRadiussAccoTotalaccountnor OBJECT-TYPE
                                   SYNTAX Counter32
                                   MAX-ACCESS read-only
                                   STATUS current
                                   DESCRIPTION "Total-Account-NoRecord"
                                   ::= {  staTcpipRadiussAcco 12 }

staTcpipRadiussAccoTotalaccountunk OBJECT-TYPE
                                   SYNTAX Counter32
                                   MAX-ACCESS read-only
                                   STATUS current
                                   DESCRIPTION "Total-Account-Unknown-Type"
                                   ::= {  staTcpipRadiussAcco 13 }

staTcpipRadiussLogtTable OBJECT-TYPE
                         SYNTAX SEQUENCE OF StaTcpipRadiussLogtEntry
                         MAX-ACCESS not-accessible
                         STATUS current
                         DESCRIPTION "Log-Table"
                         ::= {  staTcpipRadiuss 10 }

staTcpipRadiussLogtEntry OBJECT-TYPE
                         SYNTAX StaTcpipRadiussLogtEntry
                         MAX-ACCESS not-accessible
                         STATUS current
                         DESCRIPTION "entry in table"
                         INDEX { staTcpipRadiussLogtInd }
                         ::= {  staTcpipRadiussLogtTable 1 }

StaTcpipRadiussLogtEntry ::= SEQUENCE {
                         staTcpipRadiussLogtInd INTEGER,
                         staTcpipRadiussLogtTim DisplayString,
                         staTcpipRadiussLogtEve DisplayString
                        }

staTcpipRadiussLogtInd OBJECT-TYPE
                       SYNTAX INTEGER (0..2147483647)
                       MAX-ACCESS read-only
                       STATUS current
                       DESCRIPTION "Index"
                       ::= {  staTcpipRadiussLogtEntry 1 }

staTcpipRadiussLogtTim OBJECT-TYPE
                       SYNTAX DisplayString (SIZE(0..21))
                       MAX-ACCESS read-only
                       STATUS current
                       DESCRIPTION "Time"
                       ::= {  staTcpipRadiussLogtEntry 2 }

staTcpipRadiussLogtEve OBJECT-TYPE
                       SYNTAX DisplayString (SIZE(0..128))
                       MAX-ACCESS read-only
                       STATUS current
                       DESCRIPTION "Event"
                       ::= {  staTcpipRadiussLogtEntry 3 }

staTcpipRadiussDele OBJECT-TYPE
                    SYNTAX DisplayString
                    MAX-ACCESS read-write
                    STATUS current
                    DESCRIPTION "Delete-Values"
                    ::= {  staTcpipRadiuss 100 }

staIprou OBJECT IDENTIFIER ::= { sta 10}
staIprouLanrx OBJECT-TYPE
                SYNTAX Counter32
                MAX-ACCESS read-only
                STATUS current
                DESCRIPTION "LAN-Rx"
                ::= {  staIprou 1 }

staIprouLantx OBJECT-TYPE
                SYNTAX Counter32
                MAX-ACCESS read-only
                STATUS current
                DESCRIPTION "LAN-Tx"
                ::= {  staIprou 2 }

staIprouLanloca OBJECT-TYPE
                SYNTAX Counter32
                MAX-ACCESS read-only
                STATUS current
                DESCRIPTION "LAN-Local-Routings"
                ::= {  staIprou 3 }

staIprouLannetw OBJECT-TYPE
                SYNTAX Counter32
                MAX-ACCESS read-only
                STATUS current
                DESCRIPTION "LAN-Network-Errors"
                ::= {  staIprou 4 }

staIprouLanrout OBJECT-TYPE
                SYNTAX Counter32
                MAX-ACCESS read-only
                STATUS current
                DESCRIPTION "LAN-Routing-Errors"
                ::= {  staIprou 5 }

staIprouLanttle OBJECT-TYPE
                SYNTAX Counter32
                MAX-ACCESS read-only
                STATUS current
                DESCRIPTION "LAN-TTL-Errors"
                ::= {  staIprou 6 }

staIprouLanfilt OBJECT-TYPE
                SYNTAX Counter32
                MAX-ACCESS read-only
                STATUS current
                DESCRIPTION "LAN-Filters"
                ::= {  staIprou 7 }

staIprouLandisc OBJECT-TYPE
                SYNTAX Counter32
                MAX-ACCESS read-only
                STATUS current
                DESCRIPTION "LAN-Discards"
                ::= {  staIprou 8 }

staIprouWanrx OBJECT-TYPE
                SYNTAX Counter32
                MAX-ACCESS read-only
                STATUS current
                DESCRIPTION "WAN-Rx"
                ::= {  staIprou 9 }

staIprouWantx OBJECT-TYPE
                SYNTAX Counter32
                MAX-ACCESS read-only
                STATUS current
                DESCRIPTION "WAN-Tx"
                ::= {  staIprou 10 }

staIprouWannetw OBJECT-TYPE
                SYNTAX Counter32
                MAX-ACCESS read-only
                STATUS current
                DESCRIPTION "WAN-Network-Errors"
                ::= {  staIprou 11 }

staIprouWanttle OBJECT-TYPE
                SYNTAX Counter32
                MAX-ACCESS read-only
                STATUS current
                DESCRIPTION "WAN-TTL-Errors"
                ::= {  staIprou 12 }

staIprouWanfilt OBJECT-TYPE
                SYNTAX Counter32
                MAX-ACCESS read-only
                STATUS current
                DESCRIPTION "WAN-Filters"
                ::= {  staIprou 13 }

staIprouWandisc OBJECT-TYPE
                SYNTAX Counter32
                MAX-ACCESS read-only
                STATUS current
                DESCRIPTION "WAN-Discards"
                ::= {  staIprou 14 }

staIprouWantype OBJECT-TYPE
                SYNTAX Counter32
                MAX-ACCESS read-only
                STATUS current
                DESCRIPTION "WAN-Type-Errors"
                ::= {  staIprou 15 }

staIprouArperro OBJECT-TYPE
                SYNTAX Counter32
                MAX-ACCESS read-only
                STATUS current
                DESCRIPTION "ARP-Errors"
                ::= {  staIprou 16 }

staIprouEstabliTable OBJECT-TYPE
                     SYNTAX SEQUENCE OF StaIprouEstabliEntry
                     MAX-ACCESS not-accessible
                     STATUS current
                     DESCRIPTION "Establish-Table"
                     ::= {  staIprou 17 }

staIprouEstabliEntry OBJECT-TYPE
                     SYNTAX StaIprouEstabliEntry
                     MAX-ACCESS not-accessible
                     STATUS current
                     DESCRIPTION "entry in table"
                     INDEX { staIprouEstabliTim, staIprouEstabliCou }
                     ::= {  staIprouEstabliTable 1 }

StaIprouEstabliEntry ::= SEQUENCE {
                     staIprouEstabliTim DisplayString,
                     staIprouEstabliDes IpAddress,
                     staIprouEstabliSrc IpAddress,
                     staIprouEstabliPro INTEGER,
                     staIprouEstabliDpo INTEGER,
                     staIprouEstabliSou INTEGER,
                     staIprouEstabliCou INTEGER
                    }

staIprouEstabliTim OBJECT-TYPE
                   SYNTAX DisplayString (SIZE(0..19))
                   MAX-ACCESS read-only
                   STATUS current
                   DESCRIPTION "Time"
                   ::= {  staIprouEstabliEntry 1 }

staIprouEstabliDes OBJECT-TYPE
                   SYNTAX IpAddress
                   MAX-ACCESS read-only
                   STATUS current
                   DESCRIPTION "Dest.-Address"
                   ::= {  staIprouEstabliEntry 2 }

staIprouEstabliSrc OBJECT-TYPE
                   SYNTAX IpAddress
                   MAX-ACCESS read-only
                   STATUS current
                   DESCRIPTION "Src.-Address"
                   ::= {  staIprouEstabliEntry 3 }

staIprouEstabliPro OBJECT-TYPE
                   SYNTAX INTEGER{
                     icmp(1),
                     igmp(2),
                     ggt(3),
                     ipip(4),
                     tcp(6),
                     egp(8),
                     udp(17),
                     gre(47),
                     esp(50),
                     ah(51),
                     cftp(62),
                     ipcomp(108),
                     vrrp(112),
                     srp(119)
                   }
                   MAX-ACCESS read-only
                   STATUS current
                   DESCRIPTION "Prot."
                   ::= {  staIprouEstabliEntry 4 }

staIprouEstabliDpo OBJECT-TYPE
                   SYNTAX INTEGER (0..65535)
                   MAX-ACCESS read-only
                   STATUS current
                   DESCRIPTION "D-port-from"
                   ::= {  staIprouEstabliEntry 5 }

staIprouEstabliSou OBJECT-TYPE
                   SYNTAX INTEGER (0..65535)
                   MAX-ACCESS read-only
                   STATUS current
                   DESCRIPTION "Source-Port"
                   ::= {  staIprouEstabliEntry 6 }

staIprouEstabliCou OBJECT-TYPE
                   SYNTAX INTEGER (0..2147483647)
                   MAX-ACCESS read-only
                   STATUS current
                   DESCRIPTION "Counter"
                   ::= {  staIprouEstabliEntry 7 }

staIprouProtocoTable OBJECT-TYPE
                     SYNTAX SEQUENCE OF StaIprouProtocoEntry
                     MAX-ACCESS not-accessible
                     STATUS current
                     DESCRIPTION "Protocol-Table"
                     ::= {  staIprou 18 }

staIprouProtocoEntry OBJECT-TYPE
                     SYNTAX StaIprouProtocoEntry
                     MAX-ACCESS not-accessible
                     STATUS current
                     DESCRIPTION "entry in table"
                     INDEX { staIprouProtocoPro }
                     ::= {  staIprouProtocoTable 1 }

StaIprouProtocoEntry ::= SEQUENCE {
                     staIprouProtocoPro INTEGER,
                     staIprouProtocoLan Counter32,
                     staIprouProtocoWan Counter32
                    }

staIprouProtocoPro OBJECT-TYPE
                   SYNTAX INTEGER{
                     icmp(1),
                     igmp(2),
                     ggt(3),
                     ipip(4),
                     tcp(6),
                     egp(8),
                     udp(17),
                     gre(47),
                     esp(50),
                     ah(51),
                     cftp(62),
                     ipcomp(108),
                     vrrp(112),
                     srp(119)
                   }
                   MAX-ACCESS read-only
                   STATUS current
                   DESCRIPTION "Prot."
                   ::= {  staIprouProtocoEntry 1 }

staIprouProtocoLan OBJECT-TYPE
                   SYNTAX Counter32
                   MAX-ACCESS read-only
                   STATUS current
                   DESCRIPTION "LAN-Tx"
                   ::= {  staIprouProtocoEntry 2 }

staIprouProtocoWan OBJECT-TYPE
                   SYNTAX Counter32
                   MAX-ACCESS read-only
                   STATUS current
                   DESCRIPTION "WAN-Tx"
                   ::= {  staIprouProtocoEntry 3 }

staIprouRip OBJECT IDENTIFIER ::= { staIprou 19}
staIprouRipRx OBJECT-TYPE
                SYNTAX Counter32
                MAX-ACCESS read-only
                STATUS current
                DESCRIPTION "Rx"
                ::= {  staIprouRip 1 }

staIprouRipRequ OBJECT-TYPE
                SYNTAX Counter32
                MAX-ACCESS read-only
                STATUS current
                DESCRIPTION "Requests"
                ::= {  staIprouRip 2 }

staIprouRipResp OBJECT-TYPE
                SYNTAX Counter32
                MAX-ACCESS read-only
                STATUS current
                DESCRIPTION "Response"
                ::= {  staIprouRip 3 }

staIprouRipDisc OBJECT-TYPE
                SYNTAX Counter32
                MAX-ACCESS read-only
                STATUS current
                DESCRIPTION "Discards"
                ::= {  staIprouRip 4 }

staIprouRipErro OBJECT-TYPE
                SYNTAX Counter32
                MAX-ACCESS read-only
                STATUS current
                DESCRIPTION "Errors"
                ::= {  staIprouRip 5 }

staIprouRipEntr OBJECT-TYPE
                SYNTAX Counter32
                MAX-ACCESS read-only
                STATUS current
                DESCRIPTION "Entry-Errors"
                ::= {  staIprouRip 6 }

staIprouRipTx OBJECT-TYPE
                SYNTAX Counter32
                MAX-ACCESS read-only
                STATUS current
                DESCRIPTION "Tx"
                ::= {  staIprouRip 7 }

staIprouRipIpriTable OBJECT-TYPE
                     SYNTAX SEQUENCE OF StaIprouRipIpriEntry
                     MAX-ACCESS not-accessible
                     STATUS current
                     DESCRIPTION "IP-RIP-Table"
                     ::= {  staIprouRip 8 }

staIprouRipIpriEntry OBJECT-TYPE
                     SYNTAX StaIprouRipIpriEntry
                     MAX-ACCESS not-accessible
                     STATUS current
                     DESCRIPTION "entry in table"
                     INDEX { staIprouRipIpriIpa, staIprouRipIpriIpn, staIprouRipIpriRtg }
                     ::= {  staIprouRipIpriTable 1 }

StaIprouRipIpriEntry ::= SEQUENCE {
                     staIprouRipIpriIpa IpAddress,
                     staIprouRipIpriIpn IpAddress,
                     staIprouRipIpriRtg INTEGER,
                     staIprouRipIpriTim INTEGER,
                     staIprouRipIpriDis INTEGER,
                     staIprouRipIpriGat IpAddress,
                     staIprouRipIpriPee DisplayString,
                     staIprouRipIpriPor INTEGER,
                     staIprouRipIpriVla INTEGER,
                     staIprouRipIpriNet DisplayString
                    }

staIprouRipIpriIpa OBJECT-TYPE
                   SYNTAX IpAddress
                   MAX-ACCESS read-only
                   STATUS current
                   DESCRIPTION "IP-Address"
                   ::= {  staIprouRipIpriEntry 1 }

staIprouRipIpriIpn OBJECT-TYPE
                   SYNTAX IpAddress
                   MAX-ACCESS read-only
                   STATUS current
                   DESCRIPTION "IP-Netmask"
                   ::= {  staIprouRipIpriEntry 2 }

staIprouRipIpriRtg OBJECT-TYPE
                   SYNTAX INTEGER (0..65535)
                   MAX-ACCESS read-only
                   STATUS current
                   DESCRIPTION "Rtg-tag"
                   ::= {  staIprouRipIpriEntry 6 }

staIprouRipIpriTim OBJECT-TYPE
                   SYNTAX INTEGER (0..65535)
                   MAX-ACCESS read-only
                   STATUS current
                   DESCRIPTION "Time"
                   ::= {  staIprouRipIpriEntry 3 }

staIprouRipIpriDis OBJECT-TYPE
                   SYNTAX INTEGER (0..65535)
                   MAX-ACCESS read-only
                   STATUS current
                   DESCRIPTION "Distance"
                   ::= {  staIprouRipIpriEntry 4 }

staIprouRipIpriGat OBJECT-TYPE
                   SYNTAX IpAddress
                   MAX-ACCESS read-only
                   STATUS current
                   DESCRIPTION "Gateway"
                   ::= {  staIprouRipIpriEntry 5 }

staIprouRipIpriPee OBJECT-TYPE
                   SYNTAX DisplayString (SIZE(0..16))
                   MAX-ACCESS read-only
                   STATUS current
                   DESCRIPTION "Peer"
                   ::= {  staIprouRipIpriEntry 8 }

staIprouRipIpriPor OBJECT-TYPE
                   SYNTAX INTEGER{
                     lan-1(0),
                     wlan-1(1),
                     p2p-1-1(2),
                     p2p-1-2(3),
                     p2p-1-3(4),
                     p2p-1-4(5),
                     p2p-1-5(6),
                     p2p-1-6(7),
                     wlan-1-2(8),
                     wlan-1-3(9),
                     wlan-1-4(10),
                     wlan-1-5(11),
                     wlan-1-6(12),
                     wlan-1-7(13),
                     wlan-1-8(14),
                     brg-1(15),
                     brg-2(16),
                     brg-3(17),
                     brg-4(18),
                     brg-5(19),
                     brg-6(20),
                     brg-7(21),
                     brg-8(22),
                     any(255)
                   }
                   MAX-ACCESS read-only
                   STATUS current
                   DESCRIPTION "Port"
                   ::= {  staIprouRipIpriEntry 9 }

staIprouRipIpriVla OBJECT-TYPE
                   SYNTAX INTEGER (0..65535)
                   MAX-ACCESS read-only
                   STATUS current
                   DESCRIPTION "VLAN-ID"
                   ::= {  staIprouRipIpriEntry 10 }

staIprouRipIpriNet OBJECT-TYPE
                   SYNTAX DisplayString (SIZE(0..16))
                   MAX-ACCESS read-only
                   STATUS current
                   DESCRIPTION "Network-name"
                   ::= {  staIprouRipIpriEntry 11 }

staIprouRipDele OBJECT-TYPE
                SYNTAX DisplayString
                MAX-ACCESS read-write
                STATUS current
                DESCRIPTION "Delete-Values"
                ::= {  staIprouRip 9 }

staIprouRipLansTable OBJECT-TYPE
                     SYNTAX SEQUENCE OF StaIprouRipLansEntry
                     MAX-ACCESS not-accessible
                     STATUS current
                     DESCRIPTION "LAN-Sites"
                     ::= {  staIprouRip 10 }

staIprouRipLansEntry OBJECT-TYPE
                     SYNTAX StaIprouRipLansEntry
                     MAX-ACCESS not-accessible
                     STATUS current
                     DESCRIPTION "entry in table"
                     INDEX { staIprouRipLansNetw }
                     ::= {  staIprouRipLansTable 1 }

StaIprouRipLansEntry ::= SEQUENCE {
                     staIprouRipLansNetw DisplayString,
                     staIprouRipLansRipt INTEGER,
                     staIprouRipLansRipa INTEGER,
                     staIprouRipLansProp INTEGER,
                     staIprouRipLansPois INTEGER,
                     staIprouRipLansDftr INTEGER,
                     staIprouRipLansRtgt DisplayString,
                     staIprouRipLansRxfi DisplayString,
                     staIprouRipLansTxfi DisplayString,
                     staIprouRipLansPort INTEGER,
                     staIprouRipLansVlan INTEGER
                    }

staIprouRipLansNetw OBJECT-TYPE
                    SYNTAX DisplayString (SIZE(0..16))
                    MAX-ACCESS read-only
                    STATUS current
                    DESCRIPTION "Network-name"
                    ::= {  staIprouRipLansEntry 1 }

staIprouRipLansRipt OBJECT-TYPE
                    SYNTAX INTEGER{
                      off(0),
                      rip-1(1),
                      r1-comp(2),
                      rip-2(3)
                    }
                    MAX-ACCESS read-only
                    STATUS current
                    DESCRIPTION "RIP-Type"
                    ::= {  staIprouRipLansEntry 2 }

staIprouRipLansRipa OBJECT-TYPE
                    SYNTAX INTEGER{
                      no(0),
                      yes(1)
                    }
                    MAX-ACCESS read-only
                    STATUS current
                    DESCRIPTION "RIP-Accept"
                    ::= {  staIprouRipLansEntry 3 }

staIprouRipLansProp OBJECT-TYPE
                    SYNTAX INTEGER{
                      no(0),
                      yes(1)
                    }
                    MAX-ACCESS read-only
                    STATUS current
                    DESCRIPTION "Propagate"
                    ::= {  staIprouRipLansEntry 4 }

staIprouRipLansPois OBJECT-TYPE
                    SYNTAX INTEGER{
                      no(0),
                      yes(1)
                    }
                    MAX-ACCESS read-only
                    STATUS current
                    DESCRIPTION "Poisoned-Reverse"
                    ::= {  staIprouRipLansEntry 9 }

staIprouRipLansDftr OBJECT-TYPE
                    SYNTAX INTEGER (0..65535)
                    MAX-ACCESS read-only
                    STATUS current
                    DESCRIPTION "Dft-Rtg-Tag"
                    ::= {  staIprouRipLansEntry 5 }

staIprouRipLansRtgt OBJECT-TYPE
                    SYNTAX DisplayString (SIZE(0..33))
                    MAX-ACCESS read-only
                    STATUS current
                    DESCRIPTION "Rtg-Tag-List"
                    ::= {  staIprouRipLansEntry 6 }

staIprouRipLansRxfi OBJECT-TYPE
                    SYNTAX DisplayString (SIZE(0..16))
                    MAX-ACCESS read-only
                    STATUS current
                    DESCRIPTION "Rx-Filter"
                    ::= {  staIprouRipLansEntry 10 }

staIprouRipLansTxfi OBJECT-TYPE
                    SYNTAX DisplayString (SIZE(0..16))
                    MAX-ACCESS read-only
                    STATUS current
                    DESCRIPTION "Tx-Filter"
                    ::= {  staIprouRipLansEntry 11 }

staIprouRipLansPort OBJECT-TYPE
                    SYNTAX INTEGER{
                      lan-1(0),
                      wlan-1(1),
                      p2p-1-1(2),
                      p2p-1-2(3),
                      p2p-1-3(4),
                      p2p-1-4(5),
                      p2p-1-5(6),
                      p2p-1-6(7),
                      wlan-1-2(8),
                      wlan-1-3(9),
                      wlan-1-4(10),
                      wlan-1-5(11),
                      wlan-1-6(12),
                      wlan-1-7(13),
                      wlan-1-8(14),
                      brg-1(15),
                      brg-2(16),
                      brg-3(17),
                      brg-4(18),
                      brg-5(19),
                      brg-6(20),
                      brg-7(21),
                      brg-8(22),
                      any(255)
                    }
                    MAX-ACCESS read-only
                    STATUS current
                    DESCRIPTION "Port"
                    ::= {  staIprouRipLansEntry 7 }

staIprouRipLansVlan OBJECT-TYPE
                    SYNTAX INTEGER (0..65535)
                    MAX-ACCESS read-only
                    STATUS current
                    DESCRIPTION "VLAN-ID"
                    ::= {  staIprouRipLansEntry 8 }

staIprouRipVrrpTable OBJECT-TYPE
                     SYNTAX SEQUENCE OF StaIprouRipVrrpEntry
                     MAX-ACCESS not-accessible
                     STATUS current
                     DESCRIPTION "VRRP-Sites"
                     ::= {  staIprouRip 12 }

staIprouRipVrrpEntry OBJECT-TYPE
                     SYNTAX StaIprouRipVrrpEntry
                     MAX-ACCESS not-accessible
                     STATUS current
                     DESCRIPTION "entry in table"
                     INDEX { staIprouRipVrrpNet, staIprouRipVrrpRou }
                     ::= {  staIprouRipVrrpTable 1 }

StaIprouRipVrrpEntry ::= SEQUENCE {
                     staIprouRipVrrpNet DisplayString,
                     staIprouRipVrrpRip INTEGER,
                     staIprouRipVrrpRou INTEGER
                    }

staIprouRipVrrpNet OBJECT-TYPE
                   SYNTAX DisplayString (SIZE(0..16))
                   MAX-ACCESS read-only
                   STATUS current
                   DESCRIPTION "Network-name"
                   ::= {  staIprouRipVrrpEntry 1 }

staIprouRipVrrpRip OBJECT-TYPE
                   SYNTAX INTEGER{
                     off(0),
                     rip-1(1),
                     r1-comp(2),
                     rip-2(3)
                   }
                   MAX-ACCESS read-only
                   STATUS current
                   DESCRIPTION "RIP-Type"
                   ::= {  staIprouRipVrrpEntry 2 }

staIprouRipVrrpRou OBJECT-TYPE
                   SYNTAX INTEGER (0..255)
                   MAX-ACCESS read-only
                   STATUS current
                   DESCRIPTION "Router-ID"
                   ::= {  staIprouRipVrrpEntry 3 }

staIprouRipWansTable OBJECT-TYPE
                     SYNTAX SEQUENCE OF StaIprouRipWansEntry
                     MAX-ACCESS not-accessible
                     STATUS current
                     DESCRIPTION "WAN-Sites"
                     ::= {  staIprouRip 11 }

staIprouRipWansEntry OBJECT-TYPE
                     SYNTAX StaIprouRipWansEntry
                     MAX-ACCESS not-accessible
                     STATUS current
                     DESCRIPTION "entry in table"
                     INDEX { staIprouRipWansPeer }
                     ::= {  staIprouRipWansTable 1 }

StaIprouRipWansEntry ::= SEQUENCE {
                     staIprouRipWansPeer DisplayString,
                     staIprouRipWansRipt INTEGER,
                     staIprouRipWansRipa INTEGER,
                     staIprouRipWansMasq INTEGER,
                     staIprouRipWansPois INTEGER,
                     staIprouRipWansRfc2 INTEGER,
                     staIprouRipWansGate IpAddress,
                     staIprouRipWansDftr INTEGER,
                     staIprouRipWansRtgt DisplayString,
                     staIprouRipWansRxfi DisplayString,
                     staIprouRipWansTxfi DisplayString
                    }

staIprouRipWansPeer OBJECT-TYPE
                    SYNTAX DisplayString (SIZE(0..16))
                    MAX-ACCESS read-only
                    STATUS current
                    DESCRIPTION "Peer"
                    ::= {  staIprouRipWansEntry 1 }

staIprouRipWansRipt OBJECT-TYPE
                    SYNTAX INTEGER{
                      off(0),
                      rip-1(1),
                      r1-comp(2),
                      rip-2(3)
                    }
                    MAX-ACCESS read-only
                    STATUS current
                    DESCRIPTION "RIP-Type"
                    ::= {  staIprouRipWansEntry 2 }

staIprouRipWansRipa OBJECT-TYPE
                    SYNTAX INTEGER{
                      no(0),
                      yes(1)
                    }
                    MAX-ACCESS read-only
                    STATUS current
                    DESCRIPTION "RIP-Accept"
                    ::= {  staIprouRipWansEntry 3 }

staIprouRipWansMasq OBJECT-TYPE
                    SYNTAX INTEGER{
                      auto(0),
                      on(1),
                      intranet(2)
                    }
                    MAX-ACCESS read-only
                    STATUS current
                    DESCRIPTION "Masquerade"
                    ::= {  staIprouRipWansEntry 4 }

staIprouRipWansPois OBJECT-TYPE
                    SYNTAX INTEGER{
                      no(0),
                      yes(1)
                    }
                    MAX-ACCESS read-only
                    STATUS current
                    DESCRIPTION "Poisoned-Reverse"
                    ::= {  staIprouRipWansEntry 7 }

staIprouRipWansRfc2 OBJECT-TYPE
                    SYNTAX INTEGER{
                      no(0),
                      yes(1)
                    }
                    MAX-ACCESS read-only
                    STATUS current
                    DESCRIPTION "RFC2091"
                    ::= {  staIprouRipWansEntry 8 }

staIprouRipWansGate OBJECT-TYPE
                    SYNTAX IpAddress
                    MAX-ACCESS read-only
                    STATUS current
                    DESCRIPTION "Gateway"
                    ::= {  staIprouRipWansEntry 9 }

staIprouRipWansDftr OBJECT-TYPE
                    SYNTAX INTEGER (0..65535)
                    MAX-ACCESS read-only
                    STATUS current
                    DESCRIPTION "Dft-Rtg-Tag"
                    ::= {  staIprouRipWansEntry 5 }

staIprouRipWansRtgt OBJECT-TYPE
                    SYNTAX DisplayString (SIZE(0..33))
                    MAX-ACCESS read-only
                    STATUS current
                    DESCRIPTION "Rtg-Tag-List"
                    ::= {  staIprouRipWansEntry 6 }

staIprouRipWansRxfi OBJECT-TYPE
                    SYNTAX DisplayString (SIZE(0..16))
                    MAX-ACCESS read-only
                    STATUS current
                    DESCRIPTION "Rx-Filter"
                    ::= {  staIprouRipWansEntry 10 }

staIprouRipWansTxfi OBJECT-TYPE
                    SYNTAX DisplayString (SIZE(0..16))
                    MAX-ACCESS read-only
                    STATUS current
                    DESCRIPTION "Tx-Filter"
                    ::= {  staIprouRipWansEntry 11 }

staIprouRipDynlTable OBJECT-TYPE
                     SYNTAX SEQUENCE OF StaIprouRipDynlEntry
                     MAX-ACCESS not-accessible
                     STATUS current
                     DESCRIPTION "Dyn.-LAN-Sites"
                     ::= {  staIprouRip 13 }

staIprouRipDynlEntry OBJECT-TYPE
                     SYNTAX StaIprouRipDynlEntry
                     MAX-ACCESS not-accessible
                     STATUS current
                     DESCRIPTION "entry in table"
                     INDEX { staIprouRipDynlGate }
                     ::= {  staIprouRipDynlTable 1 }

StaIprouRipDynlEntry ::= SEQUENCE {
                     staIprouRipDynlGate DisplayString,
                     staIprouRipDynlRipt INTEGER,
                     staIprouRipDynlRipa INTEGER,
                     staIprouRipDynlPois INTEGER,
                     staIprouRipDynlDftr INTEGER,
                     staIprouRipDynlRtgt DisplayString,
                     staIprouRipDynlRxfi DisplayString,
                     staIprouRipDynlTxfi DisplayString,
                     staIprouRipDynlPort INTEGER,
                     staIprouRipDynlVlan INTEGER
                    }

staIprouRipDynlGate OBJECT-TYPE
                    SYNTAX DisplayString (SIZE(0..16))
                    MAX-ACCESS read-only
                    STATUS current
                    DESCRIPTION "Gateway"
                    ::= {  staIprouRipDynlEntry 1 }

staIprouRipDynlRipt OBJECT-TYPE
                    SYNTAX INTEGER{
                      off(0),
                      rip-1(1),
                      r1-comp(2),
                      rip-2(3)
                    }
                    MAX-ACCESS read-only
                    STATUS current
                    DESCRIPTION "RIP-Type"
                    ::= {  staIprouRipDynlEntry 2 }

staIprouRipDynlRipa OBJECT-TYPE
                    SYNTAX INTEGER{
                      no(0),
                      yes(1)
                    }
                    MAX-ACCESS read-only
                    STATUS current
                    DESCRIPTION "RIP-Accept"
                    ::= {  staIprouRipDynlEntry 3 }

staIprouRipDynlPois OBJECT-TYPE
                    SYNTAX INTEGER{
                      no(0),
                      yes(1)
                    }
                    MAX-ACCESS read-only
                    STATUS current
                    DESCRIPTION "Poisoned-Reverse"
                    ::= {  staIprouRipDynlEntry 4 }

staIprouRipDynlDftr OBJECT-TYPE
                    SYNTAX INTEGER (0..65535)
                    MAX-ACCESS read-only
                    STATUS current
                    DESCRIPTION "Dft-Rtg-Tag"
                    ::= {  staIprouRipDynlEntry 5 }

staIprouRipDynlRtgt OBJECT-TYPE
                    SYNTAX DisplayString (SIZE(0..33))
                    MAX-ACCESS read-only
                    STATUS current
                    DESCRIPTION "Rtg-Tag-List"
                    ::= {  staIprouRipDynlEntry 6 }

staIprouRipDynlRxfi OBJECT-TYPE
                    SYNTAX DisplayString (SIZE(0..16))
                    MAX-ACCESS read-only
                    STATUS current
                    DESCRIPTION "Rx-Filter"
                    ::= {  staIprouRipDynlEntry 10 }

staIprouRipDynlTxfi OBJECT-TYPE
                    SYNTAX DisplayString (SIZE(0..16))
                    MAX-ACCESS read-only
                    STATUS current
                    DESCRIPTION "Tx-Filter"
                    ::= {  staIprouRipDynlEntry 11 }

staIprouRipDynlPort OBJECT-TYPE
                    SYNTAX INTEGER{
                      lan-1(0),
                      wlan-1(1),
                      p2p-1-1(2),
                      p2p-1-2(3),
                      p2p-1-3(4),
                      p2p-1-4(5),
                      p2p-1-5(6),
                      p2p-1-6(7),
                      wlan-1-2(8),
                      wlan-1-3(9),
                      wlan-1-4(10),
                      wlan-1-5(11),
                      wlan-1-6(12),
                      wlan-1-7(13),
                      wlan-1-8(14),
                      brg-1(15),
                      brg-2(16),
                      brg-3(17),
                      brg-4(18),
                      brg-5(19),
                      brg-6(20),
                      brg-7(21),
                      brg-8(22),
                      any(255)
                    }
                    MAX-ACCESS read-only
                    STATUS current
                    DESCRIPTION "Port"
                    ::= {  staIprouRipDynlEntry 7 }

staIprouRipDynlVlan OBJECT-TYPE
                    SYNTAX INTEGER (0..65535)
                    MAX-ACCESS read-only
                    STATUS current
                    DESCRIPTION "VLAN-ID"
                    ::= {  staIprouRipDynlEntry 8 }

staIprouRipDynwTable OBJECT-TYPE
                     SYNTAX SEQUENCE OF StaIprouRipDynwEntry
                     MAX-ACCESS not-accessible
                     STATUS current
                     DESCRIPTION "Dyn.-WAN-Sites"
                     ::= {  staIprouRip 14 }

staIprouRipDynwEntry OBJECT-TYPE
                     SYNTAX StaIprouRipDynwEntry
                     MAX-ACCESS not-accessible
                     STATUS current
                     DESCRIPTION "entry in table"
                     INDEX { staIprouRipDynwPeer }
                     ::= {  staIprouRipDynwTable 1 }

StaIprouRipDynwEntry ::= SEQUENCE {
                     staIprouRipDynwPeer DisplayString,
                     staIprouRipDynwRipt INTEGER,
                     staIprouRipDynwRipa INTEGER,
                     staIprouRipDynwMasq INTEGER,
                     staIprouRipDynwPois INTEGER,
                     staIprouRipDynwRfc2 INTEGER,
                     staIprouRipDynwGate IpAddress,
                     staIprouRipDynwDftr INTEGER,
                     staIprouRipDynwRtgt DisplayString,
                     staIprouRipDynwRxfi DisplayString,
                     staIprouRipDynwTxfi DisplayString
                    }

staIprouRipDynwPeer OBJECT-TYPE
                    SYNTAX DisplayString (SIZE(0..16))
                    MAX-ACCESS read-only
                    STATUS current
                    DESCRIPTION "Peer"
                    ::= {  staIprouRipDynwEntry 1 }

staIprouRipDynwRipt OBJECT-TYPE
                    SYNTAX INTEGER{
                      off(0),
                      rip-1(1),
                      r1-comp(2),
                      rip-2(3)
                    }
                    MAX-ACCESS read-only
                    STATUS current
                    DESCRIPTION "RIP-Type"
                    ::= {  staIprouRipDynwEntry 2 }

staIprouRipDynwRipa OBJECT-TYPE
                    SYNTAX INTEGER{
                      no(0),
                      yes(1)
                    }
                    MAX-ACCESS read-only
                    STATUS current
                    DESCRIPTION "RIP-Accept"
                    ::= {  staIprouRipDynwEntry 3 }

staIprouRipDynwMasq OBJECT-TYPE
                    SYNTAX INTEGER{
                      auto(0),
                      on(1),
                      intranet(2)
                    }
                    MAX-ACCESS read-only
                    STATUS current
                    DESCRIPTION "Masquerade"
                    ::= {  staIprouRipDynwEntry 4 }

staIprouRipDynwPois OBJECT-TYPE
                    SYNTAX INTEGER{
                      no(0),
                      yes(1)
                    }
                    MAX-ACCESS read-only
                    STATUS current
                    DESCRIPTION "Poisoned-Reverse"
                    ::= {  staIprouRipDynwEntry 7 }

staIprouRipDynwRfc2 OBJECT-TYPE
                    SYNTAX INTEGER{
                      no(0),
                      yes(1)
                    }
                    MAX-ACCESS read-only
                    STATUS current
                    DESCRIPTION "RFC2091"
                    ::= {  staIprouRipDynwEntry 8 }

staIprouRipDynwGate OBJECT-TYPE
                    SYNTAX IpAddress
                    MAX-ACCESS read-only
                    STATUS current
                    DESCRIPTION "Gateway"
                    ::= {  staIprouRipDynwEntry 9 }

staIprouRipDynwDftr OBJECT-TYPE
                    SYNTAX INTEGER (0..65535)
                    MAX-ACCESS read-only
                    STATUS current
                    DESCRIPTION "Dft-Rtg-Tag"
                    ::= {  staIprouRipDynwEntry 5 }

staIprouRipDynwRtgt OBJECT-TYPE
                    SYNTAX DisplayString (SIZE(0..33))
                    MAX-ACCESS read-only
                    STATUS current
                    DESCRIPTION "Rtg-Tag-List"
                    ::= {  staIprouRipDynwEntry 6 }

staIprouRipDynwRxfi OBJECT-TYPE
                    SYNTAX DisplayString (SIZE(0..16))
                    MAX-ACCESS read-only
                    STATUS current
                    DESCRIPTION "Rx-Filter"
                    ::= {  staIprouRipDynwEntry 10 }

staIprouRipDynwTxfi OBJECT-TYPE
                    SYNTAX DisplayString (SIZE(0..16))
                    MAX-ACCESS read-only
                    STATUS current
                    DESCRIPTION "Tx-Filter"
                    ::= {  staIprouRipDynwEntry 11 }

staIprouRipFiltTable OBJECT-TYPE
                     SYNTAX SEQUENCE OF StaIprouRipFiltEntry
                     MAX-ACCESS not-accessible
                     STATUS current
                     DESCRIPTION "Filter"
                     ::= {  staIprouRip 15 }

staIprouRipFiltEntry OBJECT-TYPE
                     SYNTAX StaIprouRipFiltEntry
                     MAX-ACCESS not-accessible
                     STATUS current
                     DESCRIPTION "entry in table"
                     INDEX { staIprouRipFiltIdx }
                     ::= {  staIprouRipFiltTable 1 }

StaIprouRipFiltEntry ::= SEQUENCE {
                     staIprouRipFiltIdx INTEGER,
                     staIprouRipFiltNam DisplayString,
                     staIprouRipFiltIpa IpAddress,
                     staIprouRipFiltIpn IpAddress,
                     staIprouRipFiltTyp INTEGER
                    }

staIprouRipFiltIdx OBJECT-TYPE
                   SYNTAX INTEGER (0..65535)
                   MAX-ACCESS read-only
                   STATUS current
                   DESCRIPTION "Idx."
                   ::= {  staIprouRipFiltEntry 1 }

staIprouRipFiltNam OBJECT-TYPE
                   SYNTAX DisplayString (SIZE(0..255))
                   MAX-ACCESS read-only
                   STATUS current
                   DESCRIPTION "Name"
                   ::= {  staIprouRipFiltEntry 3 }

staIprouRipFiltIpa OBJECT-TYPE
                   SYNTAX IpAddress
                   MAX-ACCESS read-only
                   STATUS current
                   DESCRIPTION "IP-Address"
                   ::= {  staIprouRipFiltEntry 4 }

staIprouRipFiltIpn OBJECT-TYPE
                   SYNTAX IpAddress
                   MAX-ACCESS read-only
                   STATUS current
                   DESCRIPTION "IP-Netmask"
                   ::= {  staIprouRipFiltEntry 5 }

staIprouRipFiltTyp OBJECT-TYPE
                   SYNTAX INTEGER{
                     unknown(0),
                     positive(1),
                     negative(2)
                   }
                   MAX-ACCESS read-only
                   STATUS current
                   DESCRIPTION "Type"
                   ::= {  staIprouRipFiltEntry 2 }

staIprouDeletev OBJECT-TYPE
                SYNTAX DisplayString
                MAX-ACCESS read-write
                STATUS current
                DESCRIPTION "Delete-Values"
                ::= {  staIprou 20 }

staIprouServiceTable OBJECT-TYPE
                     SYNTAX SEQUENCE OF StaIprouServiceEntry
                     MAX-ACCESS not-accessible
                     STATUS current
                     DESCRIPTION "Service-Table"
                     ::= {  staIprou 21 }

staIprouServiceEntry OBJECT-TYPE
                     SYNTAX StaIprouServiceEntry
                     MAX-ACCESS not-accessible
                     STATUS current
                     DESCRIPTION "entry in table"
                     INDEX { staIprouServiceService }
                     ::= {  staIprouServiceTable 1 }

StaIprouServiceEntry ::= SEQUENCE {
                     staIprouServiceService INTEGER,
                     staIprouServicePacketrx Counter32,
                     staIprouServicePackettx Counter32,
                     staIprouServicePacketre DisplayString,
                     staIprouServiceKbytesrx Counter32,
                     staIprouServiceKbytestx Counter32,
                     staIprouServiceKbytesre DisplayString
                    }

staIprouServiceService OBJECT-TYPE
                        SYNTAX INTEGER{
                          icmp(1),
                          ftp(2),
                          http(3),
                          smtp(4),
                          dns(5),
                          telnet(6),
                          tftp(7),
                          dhcp(8),
                          pop3(9),
                          netbios(10),
                          imap2(11),
                          news(12),
                          irc(13),
                          snmp(14),
                          other(15),
                          total(16)
                        }
                        MAX-ACCESS read-only
                        STATUS current
                        DESCRIPTION "Service"
                        ::= {  staIprouServiceEntry 1 }

staIprouServicePacketrx OBJECT-TYPE
                        SYNTAX Counter32
                        MAX-ACCESS read-only
                        STATUS current
                        DESCRIPTION "Packet-Rx"
                        ::= {  staIprouServiceEntry 2 }

staIprouServicePackettx OBJECT-TYPE
                        SYNTAX Counter32
                        MAX-ACCESS read-only
                        STATUS current
                        DESCRIPTION "Packet-Tx"
                        ::= {  staIprouServiceEntry 3 }

staIprouServicePacketre OBJECT-TYPE
                        SYNTAX DisplayString (SIZE(0..255))
                        MAX-ACCESS read-only
                        STATUS current
                        DESCRIPTION "Packet-Rel"
                        ::= {  staIprouServiceEntry 4 }

staIprouServiceKbytesrx OBJECT-TYPE
                        SYNTAX Counter32
                        MAX-ACCESS read-only
                        STATUS current
                        DESCRIPTION "KBytes-Rx"
                        ::= {  staIprouServiceEntry 5 }

staIprouServiceKbytestx OBJECT-TYPE
                        SYNTAX Counter32
                        MAX-ACCESS read-only
                        STATUS current
                        DESCRIPTION "KBytes-Tx"
                        ::= {  staIprouServiceEntry 6 }

staIprouServiceKbytesre OBJECT-TYPE
                        SYNTAX DisplayString (SIZE(0..255))
                        MAX-ACCESS read-only
                        STATUS current
                        DESCRIPTION "KBytes-Rel"
                        ::= {  staIprouServiceEntry 7 }

staIprouFilterlTable OBJECT-TYPE
                     SYNTAX SEQUENCE OF StaIprouFilterlEntry
                     MAX-ACCESS not-accessible
                     STATUS current
                     DESCRIPTION "Filter-List"
                     ::= {  staIprou 22 }

staIprouFilterlEntry OBJECT-TYPE
                     SYNTAX StaIprouFilterlEntry
                     MAX-ACCESS not-accessible
                     STATUS current
                     DESCRIPTION "entry in table"
                     INDEX { staIprouFilterlIdx }
                     ::= {  staIprouFilterlTable 1 }

StaIprouFilterlEntry ::= SEQUENCE {
                     staIprouFilterlIdx INTEGER,
                     staIprouFilterlProt INTEGER,
                     staIprouFilterlSrcm DisplayString,
                     staIprouFilterlSrca IpAddress,
                     staIprouFilterlSrcn IpAddress,
                     staIprouFilterlSst INTEGER,
                     staIprouFilterlSend INTEGER,
                     staIprouFilterlDstm DisplayString,
                     staIprouFilterlDsta IpAddress,
                     staIprouFilterlDstn IpAddress,
                     staIprouFilterlDst INTEGER,
                     staIprouFilterlDend INTEGER,
                     staIprouFilterlActi DisplayString,
                     staIprouFilterlLink INTEGER,
                     staIprouFilterlPrio INTEGER,
                     staIprouFilterlRtgt INTEGER
                    }

staIprouFilterlIdx OBJECT-TYPE
                    SYNTAX INTEGER (0..65535)
                    MAX-ACCESS read-only
                    STATUS current
                    DESCRIPTION "Idx."
                    ::= {  staIprouFilterlEntry 1 }

staIprouFilterlProt OBJECT-TYPE
                    SYNTAX INTEGER (0..255)
                    MAX-ACCESS read-only
                    STATUS current
                    DESCRIPTION "Prot."
                    ::= {  staIprouFilterlEntry 2 }

staIprouFilterlSrcm OBJECT-TYPE
                    SYNTAX DisplayString (SIZE(0..12))
                    MAX-ACCESS read-only
                    STATUS current
                    DESCRIPTION "Src-MAC"
                    ::= {  staIprouFilterlEntry 13 }

staIprouFilterlSrca OBJECT-TYPE
                    SYNTAX IpAddress
                    MAX-ACCESS read-only
                    STATUS current
                    DESCRIPTION "Src-Address"
                    ::= {  staIprouFilterlEntry 3 }

staIprouFilterlSrcn OBJECT-TYPE
                    SYNTAX IpAddress
                    MAX-ACCESS read-only
                    STATUS current
                    DESCRIPTION "Src-Netmask"
                    ::= {  staIprouFilterlEntry 4 }

staIprouFilterlSst OBJECT-TYPE
                    SYNTAX INTEGER (0..65535)
                    MAX-ACCESS read-only
                    STATUS current
                    DESCRIPTION "S-St."
                    ::= {  staIprouFilterlEntry 5 }

staIprouFilterlSend OBJECT-TYPE
                    SYNTAX INTEGER (0..65535)
                    MAX-ACCESS read-only
                    STATUS current
                    DESCRIPTION "S-End"
                    ::= {  staIprouFilterlEntry 6 }

staIprouFilterlDstm OBJECT-TYPE
                    SYNTAX DisplayString (SIZE(0..12))
                    MAX-ACCESS read-only
                    STATUS current
                    DESCRIPTION "Dst-MAC"
                    ::= {  staIprouFilterlEntry 14 }

staIprouFilterlDsta OBJECT-TYPE
                    SYNTAX IpAddress
                    MAX-ACCESS read-only
                    STATUS current
                    DESCRIPTION "Dst-Address"
                    ::= {  staIprouFilterlEntry 7 }

staIprouFilterlDstn OBJECT-TYPE
                    SYNTAX IpAddress
                    MAX-ACCESS read-only
                    STATUS current
                    DESCRIPTION "Dst-Netmask"
                    ::= {  staIprouFilterlEntry 8 }

staIprouFilterlDst OBJECT-TYPE
                    SYNTAX INTEGER (0..65535)
                    MAX-ACCESS read-only
                    STATUS current
                    DESCRIPTION "D-St."
                    ::= {  staIprouFilterlEntry 9 }

staIprouFilterlDend OBJECT-TYPE
                    SYNTAX INTEGER (0..65535)
                    MAX-ACCESS read-only
                    STATUS current
                    DESCRIPTION "D-End"
                    ::= {  staIprouFilterlEntry 10 }

staIprouFilterlActi OBJECT-TYPE
                    SYNTAX DisplayString (SIZE(0..255))
                    MAX-ACCESS read-only
                    STATUS current
                    DESCRIPTION "Action"
                    ::= {  staIprouFilterlEntry 11 }

staIprouFilterlLink OBJECT-TYPE
                    SYNTAX INTEGER{
                      no(0),
                      yes(1)
                    }
                    MAX-ACCESS read-only
                    STATUS current
                    DESCRIPTION "Linked"
                    ::= {  staIprouFilterlEntry 15 }

staIprouFilterlPrio OBJECT-TYPE
                    SYNTAX INTEGER (0..65535)
                    MAX-ACCESS read-only
                    STATUS current
                    DESCRIPTION "Prio"
                    ::= {  staIprouFilterlEntry 16 }

staIprouFilterlRtgt OBJECT-TYPE
                    SYNTAX INTEGER (0..65535)
                    MAX-ACCESS read-only
                    STATUS current
                    DESCRIPTION "Rtg-tag"
                    ::= {  staIprouFilterlEntry 17 }

staIprouConnectTable OBJECT-TYPE
                     SYNTAX SEQUENCE OF StaIprouConnectEntry
                     MAX-ACCESS not-accessible
                     STATUS current
                     DESCRIPTION "Connection-List"
                     ::= {  staIprou 23 }

staIprouConnectEntry OBJECT-TYPE
                     SYNTAX StaIprouConnectEntry
                     MAX-ACCESS not-accessible
                     STATUS current
                     DESCRIPTION "entry in table"
                     INDEX { staIprouConnectSrca, staIprouConnectDsta, staIprouConnectProt, staIprouConnectSrcp, staIprouConnectDstp }
                     ::= {  staIprouConnectTable 1 }

StaIprouConnectEntry ::= SEQUENCE {
                     staIprouConnectSrca IpAddress,
                     staIprouConnectDsta IpAddress,
                     staIprouConnectProt INTEGER,
                     staIprouConnectSrcp INTEGER,
                     staIprouConnectDstp INTEGER,
                     staIprouConnectRtgt INTEGER,
                     staIprouConnectTime INTEGER,
                     staIprouConnectFlag INTEGER,
                     staIprouConnectFilt DisplayString,
                     staIprouConnectSrcr DisplayString,
                     staIprouConnectDest DisplayString
                    }

staIprouConnectSrca OBJECT-TYPE
                    SYNTAX IpAddress
                    MAX-ACCESS read-only
                    STATUS current
                    DESCRIPTION "Src-Address"
                    ::= {  staIprouConnectEntry 1 }

staIprouConnectDsta OBJECT-TYPE
                    SYNTAX IpAddress
                    MAX-ACCESS read-only
                    STATUS current
                    DESCRIPTION "Dst-Address"
                    ::= {  staIprouConnectEntry 2 }

staIprouConnectProt OBJECT-TYPE
                    SYNTAX INTEGER (0..255)
                    MAX-ACCESS read-only
                    STATUS current
                    DESCRIPTION "Prot."
                    ::= {  staIprouConnectEntry 3 }

staIprouConnectSrcp OBJECT-TYPE
                    SYNTAX INTEGER (0..65535)
                    MAX-ACCESS read-only
                    STATUS current
                    DESCRIPTION "Src-Port"
                    ::= {  staIprouConnectEntry 4 }

staIprouConnectDstp OBJECT-TYPE
                    SYNTAX INTEGER (0..65535)
                    MAX-ACCESS read-only
                    STATUS current
                    DESCRIPTION "Dst-Port"
                    ::= {  staIprouConnectEntry 5 }

staIprouConnectRtgt OBJECT-TYPE
                    SYNTAX INTEGER (0..65535)
                    MAX-ACCESS read-only
                    STATUS current
                    DESCRIPTION "Rtg-tag"
                    ::= {  staIprouConnectEntry 11 }

staIprouConnectTime OBJECT-TYPE
                    SYNTAX INTEGER (0..65535)
                    MAX-ACCESS read-only
                    STATUS current
                    DESCRIPTION "Timeout"
                    ::= {  staIprouConnectEntry 6 }

staIprouConnectFlag OBJECT-TYPE
                    SYNTAX INTEGER (0..2147483647)
                    MAX-ACCESS read-only
                    STATUS current
                    DESCRIPTION "Flags"
                    ::= {  staIprouConnectEntry 7 }

staIprouConnectFilt OBJECT-TYPE
                    SYNTAX DisplayString (SIZE(0..255))
                    MAX-ACCESS read-only
                    STATUS current
                    DESCRIPTION "Filter-Rule"
                    ::= {  staIprouConnectEntry 8 }

staIprouConnectSrcr OBJECT-TYPE
                    SYNTAX DisplayString (SIZE(0..255))
                    MAX-ACCESS read-only
                    STATUS current
                    DESCRIPTION "Src-Route"
                    ::= {  staIprouConnectEntry 9 }

staIprouConnectDest OBJECT-TYPE
                    SYNTAX DisplayString (SIZE(0..255))
                    MAX-ACCESS read-only
                    STATUS current
                    DESCRIPTION "Dest-Route"
                    ::= {  staIprouConnectEntry 10 }

staIprouOpenporTable OBJECT-TYPE
                     SYNTAX SEQUENCE OF StaIprouOpenporEntry
                     MAX-ACCESS not-accessible
                     STATUS current
                     DESCRIPTION "Open-Port-List"
                     ::= {  staIprou 29 }

staIprouOpenporEntry OBJECT-TYPE
                     SYNTAX StaIprouOpenporEntry
                     MAX-ACCESS not-accessible
                     STATUS current
                     DESCRIPTION "entry in table"
                     INDEX { staIprouOpenporSrca, staIprouOpenporDsta, staIprouOpenporProt, staIprouOpenporDstp }
                     ::= {  staIprouOpenporTable 1 }

StaIprouOpenporEntry ::= SEQUENCE {
                     staIprouOpenporSrca IpAddress,
                     staIprouOpenporDsta IpAddress,
                     staIprouOpenporProt INTEGER,
                     staIprouOpenporDstp INTEGER,
                     staIprouOpenporTime INTEGER,
                     staIprouOpenporFilt DisplayString,
                     staIprouOpenporSrcr DisplayString
                    }

staIprouOpenporSrca OBJECT-TYPE
                    SYNTAX IpAddress
                    MAX-ACCESS read-only
                    STATUS current
                    DESCRIPTION "Src-Address"
                    ::= {  staIprouOpenporEntry 1 }

staIprouOpenporDsta OBJECT-TYPE
                    SYNTAX IpAddress
                    MAX-ACCESS read-only
                    STATUS current
                    DESCRIPTION "Dst-Address"
                    ::= {  staIprouOpenporEntry 2 }

staIprouOpenporProt OBJECT-TYPE
                    SYNTAX INTEGER (0..255)
                    MAX-ACCESS read-only
                    STATUS current
                    DESCRIPTION "Prot."
                    ::= {  staIprouOpenporEntry 3 }

staIprouOpenporDstp OBJECT-TYPE
                    SYNTAX INTEGER (0..65535)
                    MAX-ACCESS read-only
                    STATUS current
                    DESCRIPTION "Dst-Port"
                    ::= {  staIprouOpenporEntry 5 }

staIprouOpenporTime OBJECT-TYPE
                    SYNTAX INTEGER (0..65535)
                    MAX-ACCESS read-only
                    STATUS current
                    DESCRIPTION "Timeout"
                    ::= {  staIprouOpenporEntry 6 }

staIprouOpenporFilt OBJECT-TYPE
                    SYNTAX DisplayString (SIZE(0..255))
                    MAX-ACCESS read-only
                    STATUS current
                    DESCRIPTION "Filter-Rule"
                    ::= {  staIprouOpenporEntry 8 }

staIprouOpenporSrcr OBJECT-TYPE
                    SYNTAX DisplayString (SIZE(0..255))
                    MAX-ACCESS read-only
                    STATUS current
                    DESCRIPTION "Src-Route"
                    ::= {  staIprouOpenporEntry 9 }

staIprouHostbloTable OBJECT-TYPE
                     SYNTAX SEQUENCE OF StaIprouHostbloEntry
                     MAX-ACCESS not-accessible
                     STATUS current
                     DESCRIPTION "Host-Block-List"
                     ::= {  staIprou 24 }

staIprouHostbloEntry OBJECT-TYPE
                     SYNTAX StaIprouHostbloEntry
                     MAX-ACCESS not-accessible
                     STATUS current
                     DESCRIPTION "entry in table"
                     INDEX { staIprouHostbloSrc }
                     ::= {  staIprouHostbloTable 1 }

StaIprouHostbloEntry ::= SEQUENCE {
                     staIprouHostbloSrc IpAddress,
                     staIprouHostbloTim INTEGER,
                     staIprouHostbloFil DisplayString
                    }

staIprouHostbloSrc OBJECT-TYPE
                   SYNTAX IpAddress
                   MAX-ACCESS read-only
                   STATUS current
                   DESCRIPTION "Src-Address"
                   ::= {  staIprouHostbloEntry 1 }

staIprouHostbloTim OBJECT-TYPE
                   SYNTAX INTEGER (0..2147483647)
                   MAX-ACCESS read-only
                   STATUS current
                   DESCRIPTION "Timeout"
                   ::= {  staIprouHostbloEntry 2 }

staIprouHostbloFil OBJECT-TYPE
                   SYNTAX DisplayString (SIZE(0..255))
                   MAX-ACCESS read-only
                   STATUS current
                   DESCRIPTION "Filter-Rule"
                   ::= {  staIprouHostbloEntry 3 }

staIprouPortbloTable OBJECT-TYPE
                     SYNTAX SEQUENCE OF StaIprouPortbloEntry
                     MAX-ACCESS not-accessible
                     STATUS current
                     DESCRIPTION "Port-Block-List"
                     ::= {  staIprou 25 }

staIprouPortbloEntry OBJECT-TYPE
                     SYNTAX StaIprouPortbloEntry
                     MAX-ACCESS not-accessible
                     STATUS current
                     DESCRIPTION "entry in table"
                     INDEX { staIprouPortbloDsta }
                     ::= {  staIprouPortbloTable 1 }

StaIprouPortbloEntry ::= SEQUENCE {
                     staIprouPortbloDsta IpAddress,
                     staIprouPortbloProt INTEGER,
                     staIprouPortbloDstp INTEGER,
                     staIprouPortbloTime INTEGER,
                     staIprouPortbloFilt DisplayString
                    }

staIprouPortbloDsta OBJECT-TYPE
                    SYNTAX IpAddress
                    MAX-ACCESS read-only
                    STATUS current
                    DESCRIPTION "Dst-Address"
                    ::= {  staIprouPortbloEntry 1 }

staIprouPortbloProt OBJECT-TYPE
                    SYNTAX INTEGER (0..65535)
                    MAX-ACCESS read-only
                    STATUS current
                    DESCRIPTION "Prot."
                    ::= {  staIprouPortbloEntry 2 }

staIprouPortbloDstp OBJECT-TYPE
                    SYNTAX INTEGER (0..65535)
                    MAX-ACCESS read-only
                    STATUS current
                    DESCRIPTION "Dst-Port"
                    ::= {  staIprouPortbloEntry 3 }

staIprouPortbloTime OBJECT-TYPE
                    SYNTAX INTEGER (0..2147483647)
                    MAX-ACCESS read-only
                    STATUS current
                    DESCRIPTION "Timeout"
                    ::= {  staIprouPortbloEntry 4 }

staIprouPortbloFilt OBJECT-TYPE
                    SYNTAX DisplayString (SIZE(0..255))
                    MAX-ACCESS read-only
                    STATUS current
                    DESCRIPTION "Filter-Rule"
                    ::= {  staIprouPortbloEntry 5 }

staIprouLogtablTable OBJECT-TYPE
                     SYNTAX SEQUENCE OF StaIprouLogtablEntry
                     MAX-ACCESS not-accessible
                     STATUS current
                     DESCRIPTION "Log-Table"
                     ::= {  staIprou 26 }

staIprouLogtablEntry OBJECT-TYPE
                     SYNTAX StaIprouLogtablEntry
                     MAX-ACCESS not-accessible
                     STATUS current
                     DESCRIPTION "entry in table"
                     INDEX { staIprouLogtablIdx }
                     ::= {  staIprouLogtablTable 1 }

StaIprouLogtablEntry ::= SEQUENCE {
                     staIprouLogtablIdx INTEGER,
                     staIprouLogtablSyst DisplayString,
                     staIprouLogtablSrca IpAddress,
                     staIprouLogtablDsta IpAddress,
                     staIprouLogtablProt INTEGER,
                     staIprouLogtablSrcp INTEGER,
                     staIprouLogtablDstp INTEGER,
                     staIprouLogtablFilt DisplayString,
                     staIprouLogtablLimi INTEGER,
                     staIprouLogtablThre INTEGER,
                     staIprouLogtablActi INTEGER
                    }

staIprouLogtablIdx OBJECT-TYPE
                    SYNTAX INTEGER (0..65535)
                    MAX-ACCESS read-only
                    STATUS current
                    DESCRIPTION "Idx."
                    ::= {  staIprouLogtablEntry 1 }

staIprouLogtablSyst OBJECT-TYPE
                    SYNTAX DisplayString (SIZE(0..19))
                    MAX-ACCESS read-only
                    STATUS current
                    DESCRIPTION "System-time"
                    ::= {  staIprouLogtablEntry 2 }

staIprouLogtablSrca OBJECT-TYPE
                    SYNTAX IpAddress
                    MAX-ACCESS read-only
                    STATUS current
                    DESCRIPTION "Src-Address"
                    ::= {  staIprouLogtablEntry 3 }

staIprouLogtablDsta OBJECT-TYPE
                    SYNTAX IpAddress
                    MAX-ACCESS read-only
                    STATUS current
                    DESCRIPTION "Dst-Address"
                    ::= {  staIprouLogtablEntry 4 }

staIprouLogtablProt OBJECT-TYPE
                    SYNTAX INTEGER (0..255)
                    MAX-ACCESS read-only
                    STATUS current
                    DESCRIPTION "Prot."
                    ::= {  staIprouLogtablEntry 5 }

staIprouLogtablSrcp OBJECT-TYPE
                    SYNTAX INTEGER (0..65535)
                    MAX-ACCESS read-only
                    STATUS current
                    DESCRIPTION "Src-Port"
                    ::= {  staIprouLogtablEntry 6 }

staIprouLogtablDstp OBJECT-TYPE
                    SYNTAX INTEGER (0..65535)
                    MAX-ACCESS read-only
                    STATUS current
                    DESCRIPTION "Dst-Port"
                    ::= {  staIprouLogtablEntry 7 }

staIprouLogtablFilt OBJECT-TYPE
                    SYNTAX DisplayString (SIZE(0..32))
                    MAX-ACCESS read-only
                    STATUS current
                    DESCRIPTION "Filter-Rule"
                    ::= {  staIprouLogtablEntry 8 }

staIprouLogtablLimi OBJECT-TYPE
                    SYNTAX INTEGER (0..2147483647)
                    MAX-ACCESS read-only
                    STATUS current
                    DESCRIPTION "Limit"
                    ::= {  staIprouLogtablEntry 9 }

staIprouLogtablThre OBJECT-TYPE
                    SYNTAX INTEGER (0..2147483647)
                    MAX-ACCESS read-only
                    STATUS current
                    DESCRIPTION "Threshold"
                    ::= {  staIprouLogtablEntry 10 }

staIprouLogtablActi OBJECT-TYPE
                    SYNTAX INTEGER (0..2147483647)
                    MAX-ACCESS read-only
                    STATUS current
                    DESCRIPTION "Action"
                    ::= {  staIprouLogtablEntry 11 }

staIprouHoconnlTable OBJECT-TYPE
                     SYNTAX SEQUENCE OF StaIprouHoconnlEntry
                     MAX-ACCESS not-accessible
                     STATUS current
                     DESCRIPTION "HO-Conn.-List"
                     ::= {  staIprou 27 }

staIprouHoconnlEntry OBJECT-TYPE
                     SYNTAX StaIprouHoconnlEntry
                     MAX-ACCESS not-accessible
                     STATUS current
                     DESCRIPTION "entry in table"
                     INDEX { staIprouHoconnlDst }
                     ::= {  staIprouHoconnlTable 1 }

StaIprouHoconnlEntry ::= SEQUENCE {
                     staIprouHoconnlDst IpAddress,
                     staIprouHoconnlNum INTEGER,
                     staIprouHoconnlTim INTEGER
                    }

staIprouHoconnlDst OBJECT-TYPE
                   SYNTAX IpAddress
                   MAX-ACCESS read-only
                   STATUS current
                   DESCRIPTION "Dst-Address"
                   ::= {  staIprouHoconnlEntry 1 }

staIprouHoconnlNum OBJECT-TYPE
                   SYNTAX INTEGER (0..2147483647)
                   MAX-ACCESS read-only
                   STATUS current
                   DESCRIPTION "Num-HO-Conn."
                   ::= {  staIprouHoconnlEntry 2 }

staIprouHoconnlTim OBJECT-TYPE
                   SYNTAX INTEGER (0..65535)
                   MAX-ACCESS read-only
                   STATUS current
                   DESCRIPTION "Timeout"
                   ::= {  staIprouHoconnlEntry 3 }

staIprouQosTable OBJECT-TYPE
                     SYNTAX SEQUENCE OF StaIprouQosEntry
                     MAX-ACCESS not-accessible
                     STATUS current
                     DESCRIPTION "QoS"
                     ::= {  staIprou 28 }

staIprouQosEntry OBJECT-TYPE
                     SYNTAX StaIprouQosEntry
                     MAX-ACCESS not-accessible
                     STATUS current
                     DESCRIPTION "entry in table"
                     INDEX { staIprouQosIfc }
                     ::= {  staIprouQosTable 1 }

StaIprouQosEntry ::= SEQUENCE {
                     staIprouQosIfc INTEGER,
                     staIprouQosPeer DisplayString,
                     staIprouQosUpstr INTEGER,
                     staIprouQosDowns INTEGER,
                     staIprouQosRxres INTEGER,
                     staIprouQosRxreq INTEGER,
                     staIprouQosRxblo INTEGER,
                     staIprouQosTxres INTEGER,
                     staIprouQosTxreq INTEGER,
                     staIprouQosTxfav INTEGER,
                     staIprouQosTxblo INTEGER,
                     staIprouQosFragm INTEGER,
                     staIprouQosPmtus INTEGER
                    }

staIprouQosIfc OBJECT-TYPE
                 SYNTAX INTEGER{
                   dsl-ch-1(1),
                   ext(2)
                 }
                 MAX-ACCESS read-only
                 STATUS current
                 DESCRIPTION "Ifc"
                 ::= {  staIprouQosEntry 1 }

staIprouQosPeer OBJECT-TYPE
                 SYNTAX DisplayString (SIZE(0..16))
                 MAX-ACCESS read-only
                 STATUS current
                 DESCRIPTION "Peer"
                 ::= {  staIprouQosEntry 2 }

staIprouQosUpstr OBJECT-TYPE
                 SYNTAX INTEGER (0..2147483647)
                 MAX-ACCESS read-only
                 STATUS current
                 DESCRIPTION "Upstream-Rate"
                 ::= {  staIprouQosEntry 8 }

staIprouQosDowns OBJECT-TYPE
                 SYNTAX INTEGER (0..2147483647)
                 MAX-ACCESS read-only
                 STATUS current
                 DESCRIPTION "Downstream-Rate"
                 ::= {  staIprouQosEntry 3 }

staIprouQosRxres OBJECT-TYPE
                 SYNTAX INTEGER (0..2147483647)
                 MAX-ACCESS read-only
                 STATUS current
                 DESCRIPTION "Rx-reserved"
                 ::= {  staIprouQosEntry 4 }

staIprouQosRxreq OBJECT-TYPE
                 SYNTAX INTEGER (0..2147483647)
                 MAX-ACCESS read-only
                 STATUS current
                 DESCRIPTION "Rx-requested"
                 ::= {  staIprouQosEntry 11 }

staIprouQosRxblo OBJECT-TYPE
                 SYNTAX INTEGER (0..65535)
                 MAX-ACCESS read-only
                 STATUS current
                 DESCRIPTION "Rx-blocks-pending"
                 ::= {  staIprouQosEntry 5 }

staIprouQosTxres OBJECT-TYPE
                 SYNTAX INTEGER (0..2147483647)
                 MAX-ACCESS read-only
                 STATUS current
                 DESCRIPTION "Tx-reserved"
                 ::= {  staIprouQosEntry 9 }

staIprouQosTxreq OBJECT-TYPE
                 SYNTAX INTEGER (0..2147483647)
                 MAX-ACCESS read-only
                 STATUS current
                 DESCRIPTION "Tx-requested"
                 ::= {  staIprouQosEntry 12 }

staIprouQosTxfav OBJECT-TYPE
                 SYNTAX INTEGER (0..2147483647)
                 MAX-ACCESS read-only
                 STATUS current
                 DESCRIPTION "Tx-favoured"
                 ::= {  staIprouQosEntry 13 }

staIprouQosTxblo OBJECT-TYPE
                 SYNTAX INTEGER (0..65535)
                 MAX-ACCESS read-only
                 STATUS current
                 DESCRIPTION "Tx-blocks-pending"
                 ::= {  staIprouQosEntry 10 }

staIprouQosFragm OBJECT-TYPE
                 SYNTAX INTEGER (0..65535)
                 MAX-ACCESS read-only
                 STATUS current
                 DESCRIPTION "Fragment-size"
                 ::= {  staIprouQosEntry 6 }

staIprouQosPmtus OBJECT-TYPE
                 SYNTAX INTEGER (0..65535)
                 MAX-ACCESS read-only
                 STATUS current
                 DESCRIPTION "PMTU-size"
                 ::= {  staIprouQosEntry 7 }

staIprouRules OBJECT-TYPE
                SYNTAX INTEGER
                MAX-ACCESS read-only
                STATUS current
                DESCRIPTION "Rules"
                ::= {  staIprou 34 }

staIprouFilter OBJECT-TYPE
                SYNTAX INTEGER
                MAX-ACCESS read-only
                STATUS current
                DESCRIPTION "Filter"
                ::= {  staIprou 35 }

staIprouL4error OBJECT-TYPE
                SYNTAX Counter32
                MAX-ACCESS read-only
                STATUS current
                DESCRIPTION "L4-Errors"
                ::= {  staIprou 31 }

staIprouVrrp OBJECT IDENTIFIER ::= { staIprou 33}
staIprouVrrpOpe OBJECT-TYPE
                SYNTAX INTEGER {
                  no(0),
                  yes(1)
                }
                MAX-ACCESS read-only
                STATUS current
                DESCRIPTION "Operating"
                ::= {  staIprouVrrp 5 }

staIprouVrrpRx OBJECT-TYPE
                SYNTAX Counter32
                MAX-ACCESS read-only
                STATUS current
                DESCRIPTION "Rx"
                ::= {  staIprouVrrp 1 }

staIprouVrrpTx OBJECT-TYPE
                SYNTAX Counter32
                MAX-ACCESS read-only
                STATUS current
                DESCRIPTION "Tx"
                ::= {  staIprouVrrp 2 }

staIprouVrrpErr OBJECT-TYPE
                SYNTAX Counter32
                MAX-ACCESS read-only
                STATUS current
                DESCRIPTION "Error"
                ::= {  staIprouVrrp 3 }

staIprouVrrpDro OBJECT-TYPE
                SYNTAX Counter32
                MAX-ACCESS read-only
                STATUS current
                DESCRIPTION "Drop"
                ::= {  staIprouVrrp 4 }

staIprouVrrpInt OBJECT-TYPE
                SYNTAX INTEGER {
                  no(0),
                  yes(1)
                }
                MAX-ACCESS read-only
                STATUS current
                DESCRIPTION "Internal-Services"
                ::= {  staIprouVrrp 6 }

staIprouVrrpVirTable OBJECT-TYPE
                     SYNTAX SEQUENCE OF StaIprouVrrpVirEntry
                     MAX-ACCESS not-accessible
                     STATUS current
                     DESCRIPTION "Virtual-Router"
                     ::= {  staIprouVrrp 10 }

staIprouVrrpVirEntry OBJECT-TYPE
                     SYNTAX StaIprouVrrpVirEntry
                     MAX-ACCESS not-accessible
                     STATUS current
                     DESCRIPTION "entry in table"
                     INDEX { staIprouVrrpVirRou }
                     ::= {  staIprouVrrpVirTable 1 }

StaIprouVrrpVirEntry ::= SEQUENCE {
                     staIprouVrrpVirRou INTEGER,
                     staIprouVrrpVirVir IpAddress,
                     staIprouVrrpVirPri INTEGER,
                     staIprouVrrpVirBpr INTEGER,
                     staIprouVrrpVirPee DisplayString,
                     staIprouVrrpVirSta INTEGER,
                     staIprouVrrpVirBac INTEGER,
                     staIprouVrrpVirMas IpAddress,
                     staIprouVrrpVirPor INTEGER,
                     staIprouVrrpVirVla INTEGER,
                     staIprouVrrpVirNet DisplayString
                    }

staIprouVrrpVirRou OBJECT-TYPE
                   SYNTAX INTEGER (0..255)
                   MAX-ACCESS read-only
                   STATUS current
                   DESCRIPTION "Router-ID"
                   ::= {  staIprouVrrpVirEntry 1 }

staIprouVrrpVirVir OBJECT-TYPE
                   SYNTAX IpAddress
                   MAX-ACCESS read-only
                   STATUS current
                   DESCRIPTION "virt.-Address"
                   ::= {  staIprouVrrpVirEntry 2 }

staIprouVrrpVirPri OBJECT-TYPE
                   SYNTAX INTEGER (0..255)
                   MAX-ACCESS read-only
                   STATUS current
                   DESCRIPTION "Prio"
                   ::= {  staIprouVrrpVirEntry 3 }

staIprouVrrpVirBpr OBJECT-TYPE
                   SYNTAX INTEGER (0..255)
                   MAX-ACCESS read-only
                   STATUS current
                   DESCRIPTION "B-Prio"
                   ::= {  staIprouVrrpVirEntry 4 }

staIprouVrrpVirPee OBJECT-TYPE
                   SYNTAX DisplayString (SIZE(0..16))
                   MAX-ACCESS read-only
                   STATUS current
                   DESCRIPTION "Peer"
                   ::= {  staIprouVrrpVirEntry 5 }

staIprouVrrpVirSta OBJECT-TYPE
                   SYNTAX INTEGER{
                     init(0),
                     listen(1),
                     standby(2),
                     master(3),
                     down(4),
                     reconnect(5)
                   }
                   MAX-ACCESS read-only
                   STATUS current
                   DESCRIPTION "State"
                   ::= {  staIprouVrrpVirEntry 6 }

staIprouVrrpVirBac OBJECT-TYPE
                   SYNTAX INTEGER{
                     no(0),
                     yes(1)
                   }
                   MAX-ACCESS read-only
                   STATUS current
                   DESCRIPTION "Backup"
                   ::= {  staIprouVrrpVirEntry 7 }

staIprouVrrpVirMas OBJECT-TYPE
                   SYNTAX IpAddress
                   MAX-ACCESS read-only
                   STATUS current
                   DESCRIPTION "Master"
                   ::= {  staIprouVrrpVirEntry 8 }

staIprouVrrpVirPor OBJECT-TYPE
                   SYNTAX INTEGER{
                     lan-1(0),
                     wlan-1(1),
                     p2p-1-1(2),
                     p2p-1-2(3),
                     p2p-1-3(4),
                     p2p-1-4(5),
                     p2p-1-5(6),
                     p2p-1-6(7),
                     wlan-1-2(8),
                     wlan-1-3(9),
                     wlan-1-4(10),
                     wlan-1-5(11),
                     wlan-1-6(12),
                     wlan-1-7(13),
                     wlan-1-8(14),
                     brg-1(15),
                     brg-2(16),
                     brg-3(17),
                     brg-4(18),
                     brg-5(19),
                     brg-6(20),
                     brg-7(21),
                     brg-8(22),
                     any(255)
                   }
                   MAX-ACCESS read-only
                   STATUS current
                   DESCRIPTION "Port"
                   ::= {  staIprouVrrpVirEntry 9 }

staIprouVrrpVirVla OBJECT-TYPE
                   SYNTAX INTEGER (0..65535)
                   MAX-ACCESS read-only
                   STATUS current
                   DESCRIPTION "VLAN-ID"
                   ::= {  staIprouVrrpVirEntry 10 }

staIprouVrrpVirNet OBJECT-TYPE
                   SYNTAX DisplayString (SIZE(0..16))
                   MAX-ACCESS read-only
                   STATUS current
                   DESCRIPTION "Network-name"
                   ::= {  staIprouVrrpVirEntry 11 }

staIprouVrrpMacTable OBJECT-TYPE
                     SYNTAX SEQUENCE OF StaIprouVrrpMacEntry
                     MAX-ACCESS not-accessible
                     STATUS current
                     DESCRIPTION "MAC-List"
                     ::= {  staIprouVrrp 11 }

staIprouVrrpMacEntry OBJECT-TYPE
                     SYNTAX StaIprouVrrpMacEntry
                     MAX-ACCESS not-accessible
                     STATUS current
                     DESCRIPTION "entry in table"
                     INDEX { staIprouVrrpMacVir }
                     ::= {  staIprouVrrpMacTable 1 }

StaIprouVrrpMacEntry ::= SEQUENCE {
                     staIprouVrrpMacVir IpAddress,
                     staIprouVrrpMacMac MacAddress,
                     staIprouVrrpMacRou INTEGER
                    }

staIprouVrrpMacVir OBJECT-TYPE
                   SYNTAX IpAddress
                   MAX-ACCESS read-only
                   STATUS current
                   DESCRIPTION "virt.-Address"
                   ::= {  staIprouVrrpMacEntry 1 }

staIprouVrrpMacMac OBJECT-TYPE
                   SYNTAX MacAddress
                   MAX-ACCESS read-only
                   STATUS current
                   DESCRIPTION "MAC-Address"
                   ::= {  staIprouVrrpMacEntry 2 }

staIprouVrrpMacRou OBJECT-TYPE
                   SYNTAX INTEGER (0..255)
                   MAX-ACCESS read-only
                   STATUS current
                   DESCRIPTION "Router-ID"
                   ::= {  staIprouVrrpMacEntry 3 }

staIprouVrrpEveTable OBJECT-TYPE
                     SYNTAX SEQUENCE OF StaIprouVrrpEveEntry
                     MAX-ACCESS not-accessible
                     STATUS current
                     DESCRIPTION "Event-Log"
                     ::= {  staIprouVrrp 12 }

staIprouVrrpEveEntry OBJECT-TYPE
                     SYNTAX StaIprouVrrpEveEntry
                     MAX-ACCESS not-accessible
                     STATUS current
                     DESCRIPTION "entry in table"
                     INDEX { staIprouVrrpEveIdx }
                     ::= {  staIprouVrrpEveTable 1 }

StaIprouVrrpEveEntry ::= SEQUENCE {
                     staIprouVrrpEveIdx INTEGER,
                     staIprouVrrpEveSys DisplayString,
                     staIprouVrrpEveSrc IpAddress,
                     staIprouVrrpEveVri INTEGER,
                     staIprouVrrpEveEve INTEGER,
                     staIprouVrrpEveInf DisplayString
                    }

staIprouVrrpEveIdx OBJECT-TYPE
                   SYNTAX INTEGER (0..65535)
                   MAX-ACCESS read-only
                   STATUS current
                   DESCRIPTION "Idx."
                   ::= {  staIprouVrrpEveEntry 1 }

staIprouVrrpEveSys OBJECT-TYPE
                   SYNTAX DisplayString (SIZE(0..19))
                   MAX-ACCESS read-only
                   STATUS current
                   DESCRIPTION "System-time"
                   ::= {  staIprouVrrpEveEntry 2 }

staIprouVrrpEveSrc OBJECT-TYPE
                   SYNTAX IpAddress
                   MAX-ACCESS read-only
                   STATUS current
                   DESCRIPTION "Src-Address"
                   ::= {  staIprouVrrpEveEntry 3 }

staIprouVrrpEveVri OBJECT-TYPE
                   SYNTAX INTEGER (0..255)
                   MAX-ACCESS read-only
                   STATUS current
                   DESCRIPTION "VRID"
                   ::= {  staIprouVrrpEveEntry 4 }

staIprouVrrpEveEve OBJECT-TYPE
                   SYNTAX INTEGER{
                     invalid-ttl(1),
                     invalid-version(2),
                     bad-number-of-virtual-addresses(3),
                     bad-authentication-type(4),
                     bad-advertisement-interval(5),
                     invalid-vrid(6),
                     invalid-router-address(7),
                     invalid-priority(8),
                     virtual-router-stopped(9),
                     virtual-router-started(10),
                     link-up(11),
                     link-down(12),
                     new-master(13),
                     backup-started(14),
                     backup-ended(15)
                   }
                   MAX-ACCESS read-only
                   STATUS current
                   DESCRIPTION "Event"
                   ::= {  staIprouVrrpEveEntry 5 }

staIprouVrrpEveInf OBJECT-TYPE
                   SYNTAX DisplayString (SIZE(0..255))
                   MAX-ACCESS read-only
                   STATUS current
                   DESCRIPTION "Info"
                   ::= {  staIprouVrrpEveEntry 6 }

staIprouVrrpDel OBJECT-TYPE
                SYNTAX DisplayString
                MAX-ACCESS read-write
                STATUS current
                DESCRIPTION "Delete-Values"
                ::= {  staIprouVrrp 20 }

staIprouActiproTable OBJECT-TYPE
                     SYNTAX SEQUENCE OF StaIprouActiproEntry
                     MAX-ACCESS not-accessible
                     STATUS current
                     DESCRIPTION "Act.-IP-Routing-Tab."
                     ::= {  staIprou 30 }

staIprouActiproEntry OBJECT-TYPE
                     SYNTAX StaIprouActiproEntry
                     MAX-ACCESS not-accessible
                     STATUS current
                     DESCRIPTION "entry in table"
                     INDEX { staIprouActiproIpa, staIprouActiproIpn, staIprouActiproRtg }
                     ::= {  staIprouActiproTable 1 }

StaIprouActiproEntry ::= SEQUENCE {
                     staIprouActiproIpa IpAddress,
                     staIprouActiproIpn IpAddress,
                     staIprouActiproRtg INTEGER,
                     staIprouActiproGat IpAddress,
                     staIprouActiproPee DisplayString,
                     staIprouActiproDis INTEGER,
                     staIprouActiproMas INTEGER,
                     staIprouActiproTyp INTEGER
                    }

staIprouActiproIpa OBJECT-TYPE
                   SYNTAX IpAddress
                   MAX-ACCESS read-only
                   STATUS current
                   DESCRIPTION "IP-Address"
                   ::= {  staIprouActiproEntry 1 }

staIprouActiproIpn OBJECT-TYPE
                   SYNTAX IpAddress
                   MAX-ACCESS read-only
                   STATUS current
                   DESCRIPTION "IP-Netmask"
                   ::= {  staIprouActiproEntry 2 }

staIprouActiproRtg OBJECT-TYPE
                   SYNTAX INTEGER (0..65535)
                   MAX-ACCESS read-only
                   STATUS current
                   DESCRIPTION "Rtg-tag"
                   ::= {  staIprouActiproEntry 3 }

staIprouActiproGat OBJECT-TYPE
                   SYNTAX IpAddress
                   MAX-ACCESS read-only
                   STATUS current
                   DESCRIPTION "Gateway"
                   ::= {  staIprouActiproEntry 4 }

staIprouActiproPee OBJECT-TYPE
                   SYNTAX DisplayString (SIZE(0..255))
                   MAX-ACCESS read-only
                   STATUS current
                   DESCRIPTION "Peer"
                   ::= {  staIprouActiproEntry 5 }

staIprouActiproDis OBJECT-TYPE
                   SYNTAX INTEGER (0..255)
                   MAX-ACCESS read-only
                   STATUS current
                   DESCRIPTION "Distance"
                   ::= {  staIprouActiproEntry 6 }

staIprouActiproMas OBJECT-TYPE
                   SYNTAX INTEGER{
                     no(0),
                     on(1),
                     intranet(2),
                     unknown(255)
                   }
                   MAX-ACCESS read-only
                   STATUS current
                   DESCRIPTION "Masquerade"
                   ::= {  staIprouActiproEntry 7 }

staIprouActiproTyp OBJECT-TYPE
                   SYNTAX INTEGER{
                     unknown(0),
                     static(1),
                     rip(2),
                     vpn(3),
                     capwap(4)
                   }
                   MAX-ACCESS read-only
                   STATUS current
                   DESCRIPTION "Type"
                   ::= {  staIprouActiproEntry 8 }

staConfi OBJECT IDENTIFIER ::= { sta 11}
staConfiLanactiv OBJECT-TYPE
                 SYNTAX INTEGER
                 MAX-ACCESS read-only
                 STATUS current
                 DESCRIPTION "LAN-Active-Connections"
                 ::= {  staConfi 1 }

staConfiLantotal OBJECT-TYPE
                 SYNTAX Counter32
                 MAX-ACCESS read-only
                 STATUS current
                 DESCRIPTION "LAN-Total-Connections"
                 ::= {  staConfi 2 }

staConfiWanactiv OBJECT-TYPE
                 SYNTAX INTEGER
                 MAX-ACCESS read-only
                 STATUS current
                 DESCRIPTION "WAN-Active-Connections"
                 ::= {  staConfi 3 }

staConfiWantotal OBJECT-TYPE
                 SYNTAX Counter32
                 MAX-ACCESS read-only
                 STATUS current
                 DESCRIPTION "WAN-Total-Connections"
                 ::= {  staConfi 4 }

staConfiOutbanda OBJECT-TYPE
                 SYNTAX INTEGER
                 MAX-ACCESS read-only
                 STATUS current
                 DESCRIPTION "Outband-Active-Connections"
                 ::= {  staConfi 5 }

staConfiOutbandt OBJECT-TYPE
                 SYNTAX Counter32
                 MAX-ACCESS read-only
                 STATUS current
                 DESCRIPTION "Outband-total-Connections"
                 ::= {  staConfi 6 }

staConfiOutbandb OBJECT-TYPE
                 SYNTAX INTEGER
                 MAX-ACCESS read-only
                 STATUS current
                 DESCRIPTION "Outband-Bitrate"
                 ::= {  staConfi 7 }

staConfiLoginerr OBJECT-TYPE
                 SYNTAX Counter32
                 MAX-ACCESS read-only
                 STATUS current
                 DESCRIPTION "Login-Errors"
                 ::= {  staConfi 8 }

staConfiLoginloc OBJECT-TYPE
                 SYNTAX Counter32
                 MAX-ACCESS read-only
                 STATUS current
                 DESCRIPTION "Login-Locks"
                 ::= {  staConfi 9 }

staConfiLoginrej OBJECT-TYPE
                 SYNTAX Counter32
                 MAX-ACCESS read-only
                 STATUS current
                 DESCRIPTION "Login-Rejects"
                 ::= {  staConfi 10 }

staConfiStartsca OBJECT-TYPE
                 SYNTAX DisplayString
                 MAX-ACCESS read-write
                 STATUS current
                 DESCRIPTION "Start-Scan"
                 ::= {  staConfi 13 }

staConfiScanresuTable OBJECT-TYPE
                      SYNTAX SEQUENCE OF StaConfiScanresuEntry
                      MAX-ACCESS not-accessible
                      STATUS current
                      DESCRIPTION "Scan-Results"
                      ::= {  staConfi 14 }

staConfiScanresuEntry OBJECT-TYPE
                      SYNTAX StaConfiScanresuEntry
                      MAX-ACCESS not-accessible
                      STATUS current
                      DESCRIPTION "entry in table"
                      INDEX { staConfiScanresuIpadd, staConfiScanresuRtgta }
                      ::= {  staConfiScanresuTable 1 }

StaConfiScanresuEntry ::= SEQUENCE {
                      staConfiScanresuIpadd IpAddress,
                      staConfiScanresuRtgta INTEGER,
                      staConfiScanresuName DisplayString,
                      staConfiScanresuDevic DisplayString,
                      staConfiScanresuVersi DisplayString,
                      staConfiScanresuCapip INTEGER,
                      staConfiScanresuHttpp INTEGER,
                      staConfiScanresuHttps INTEGER,
                      staConfiScanresuState INTEGER
                     }

staConfiScanresuIpadd OBJECT-TYPE
                      SYNTAX IpAddress
                      MAX-ACCESS read-only
                      STATUS current
                      DESCRIPTION "IP-Address"
                      ::= {  staConfiScanresuEntry 1 }

staConfiScanresuRtgta OBJECT-TYPE
                      SYNTAX INTEGER (0..65535)
                      MAX-ACCESS read-only
                      STATUS current
                      DESCRIPTION "Rtg-tag"
                      ::= {  staConfiScanresuEntry 9 }

staConfiScanresuName OBJECT-TYPE
                      SYNTAX DisplayString (SIZE(0..17))
                      MAX-ACCESS read-only
                      STATUS current
                      DESCRIPTION "Name"
                      ::= {  staConfiScanresuEntry 2 }

staConfiScanresuDevic OBJECT-TYPE
                      SYNTAX DisplayString (SIZE(0..64))
                      MAX-ACCESS read-only
                      STATUS current
                      DESCRIPTION "Device-Type"
                      ::= {  staConfiScanresuEntry 3 }

staConfiScanresuVersi OBJECT-TYPE
                      SYNTAX DisplayString (SIZE(0..30))
                      MAX-ACCESS read-only
                      STATUS current
                      DESCRIPTION "Version"
                      ::= {  staConfiScanresuEntry 4 }

staConfiScanresuCapip OBJECT-TYPE
                      SYNTAX INTEGER (0..65535)
                      MAX-ACCESS read-only
                      STATUS current
                      DESCRIPTION "CAPI-Port"
                      ::= {  staConfiScanresuEntry 6 }

staConfiScanresuHttpp OBJECT-TYPE
                      SYNTAX INTEGER (0..65535)
                      MAX-ACCESS read-only
                      STATUS current
                      DESCRIPTION "HTTP-Port"
                      ::= {  staConfiScanresuEntry 7 }

staConfiScanresuHttps OBJECT-TYPE
                      SYNTAX INTEGER (0..65535)
                      MAX-ACCESS read-only
                      STATUS current
                      DESCRIPTION "HTTPS-Port"
                      ::= {  staConfiScanresuEntry 8 }

staConfiScanresuState OBJECT-TYPE
                      SYNTAX INTEGER{
                        scanning(0),
                        ready(1),
                        error(2)
                      }
                      MAX-ACCESS read-only
                      STATUS current
                      DESCRIPTION "State"
                      ::= {  staConfiScanresuEntry 5 }

staConfiFeaturesTable OBJECT-TYPE
                      SYNTAX SEQUENCE OF StaConfiFeaturesEntry
                      MAX-ACCESS not-accessible
                      STATUS current
                      DESCRIPTION "Features"
                      ::= {  staConfi 16 }

staConfiFeaturesEntry OBJECT-TYPE
                      SYNTAX StaConfiFeaturesEntry
                      MAX-ACCESS not-accessible
                      STATUS current
                      DESCRIPTION "entry in table"
                      INDEX { staConfiFeaturesFea }
                      ::= {  staConfiFeaturesTable 1 }

StaConfiFeaturesEntry ::= SEQUENCE {
                      staConfiFeaturesFea INTEGER,
                      staConfiFeaturesExp DisplayString
                     }

staConfiFeaturesFea OBJECT-TYPE
                    SYNTAX INTEGER{
                      ipx(1),
                      lan-bridge(2),
                      lancapi(3),
                      leased-line(4),
                      switched-line(5),
                      dsl-interface(6),
                      fax(7),
                      modem(8),
                      vpn-5(9),
                      vpn-25(10),
                      vpn-25-old(11),
                      vpn-50-old(12),
                      vpn-100(13),
                      wlc-4025-100(14),
                      wlan-point-to-point(15),
                      public-spot(16),
                      vpn-200(17),
                      vpn-500(18),
                      vpn-1000(19),
                      hermes1-wpa(20),
                      vpn-3(21),
                      umts(22),
                      dynamic-vpn(23),
                      wlan-5ghz(24),
                      wlan-no-encryption(25),
                      voip-advanced-32(26),
                      voip-basic(27),
                      wlan-fcc-restrictions(28),
                      wlc-4025-50(29),
                      wlc-4006-12(30),
                      voip-advanced-8(31),
                      unused(32),
                      unused(33),
                      utm-antivirus-small(34),
                      utm-antispam-small(35),
                      utm-contentfilter-small(36),
                      wlc-public-spot(37)
                    }
                    MAX-ACCESS read-only
                    STATUS current
                    DESCRIPTION "Feature"
                    ::= {  staConfiFeaturesEntry 1 }

staConfiFeaturesExp OBJECT-TYPE
                    SYNTAX DisplayString (SIZE(0..255))
                    MAX-ACCESS read-only
                    STATUS current
                    DESCRIPTION "Expire"
                    ::= {  staConfiFeaturesEntry 2 }

staConfiDeleteva OBJECT-TYPE
                 SYNTAX DisplayString
                 MAX-ACCESS read-write
                 STATUS current
                 DESCRIPTION "Delete-Values"
                 ::= {  staConfi 11 }

staConfiEventlogTable OBJECT-TYPE
                      SYNTAX SEQUENCE OF StaConfiEventlogEntry
                      MAX-ACCESS not-accessible
                      STATUS current
                      DESCRIPTION "Event-Log"
                      ::= {  staConfi 12 }

staConfiEventlogEntry OBJECT-TYPE
                      SYNTAX StaConfiEventlogEntry
                      MAX-ACCESS not-accessible
                      STATUS current
                      DESCRIPTION "entry in table"
                      INDEX { staConfiEventlogIdx }
                      ::= {  staConfiEventlogTable 1 }

StaConfiEventlogEntry ::= SEQUENCE {
                      staConfiEventlogIdx INTEGER,
                      staConfiEventlogSyste DisplayString,
                      staConfiEventlogEvent INTEGER,
                      staConfiEventlogAcces INTEGER,
                      staConfiEventlogIpadd IpAddress,
                      staConfiEventlogInfo1 DisplayString,
                      staConfiEventlogInfo2 DisplayString
                     }

staConfiEventlogIdx OBJECT-TYPE
                      SYNTAX INTEGER (0..255)
                      MAX-ACCESS read-only
                      STATUS current
                      DESCRIPTION "Idx."
                      ::= {  staConfiEventlogEntry 1 }

staConfiEventlogSyste OBJECT-TYPE
                      SYNTAX DisplayString (SIZE(0..19))
                      MAX-ACCESS read-only
                      STATUS current
                      DESCRIPTION "System-time"
                      ::= {  staConfiEventlogEntry 7 }

staConfiEventlogEvent OBJECT-TYPE
                      SYNTAX INTEGER{
                        fwuplstart(4),
                        uplsucc(5),
                        uplfailto(6),
                        uplfailincl(7),
                        uplfailbaddev(8),
                        login(9),
                        logout(10),
                        cnfuplstart(11),
                        cnfdnlstart(12),
                        cnfdnlsucc(13),
                        errlogin(29)
                      }
                      MAX-ACCESS read-only
                      STATUS current
                      DESCRIPTION "Event"
                      ::= {  staConfiEventlogEntry 2 }

staConfiEventlogAcces OBJECT-TYPE
                      SYNTAX INTEGER{
                        outband(0),
                        telnet(1),
                        tftp(2),
                        http(3),
                        snmp(4),
                        https(5),
                        telnet-ssl(6),
                        ssh(7),
                        ppp(254),
                        unknown(255)
                      }
                      MAX-ACCESS read-only
                      STATUS current
                      DESCRIPTION "Access"
                      ::= {  staConfiEventlogEntry 3 }

staConfiEventlogIpadd OBJECT-TYPE
                      SYNTAX IpAddress
                      MAX-ACCESS read-only
                      STATUS current
                      DESCRIPTION "IP-Address"
                      ::= {  staConfiEventlogEntry 4 }

staConfiEventlogInfo1 OBJECT-TYPE
                      SYNTAX DisplayString (SIZE(0..32))
                      MAX-ACCESS read-only
                      STATUS current
                      DESCRIPTION "Info1"
                      ::= {  staConfiEventlogEntry 5 }

staConfiEventlogInfo2 OBJECT-TYPE
                      SYNTAX DisplayString (SIZE(0..64))
                      MAX-ACCESS read-only
                      STATUS current
                      DESCRIPTION "Info2"
                      ::= {  staConfiEventlogEntry 6 }

staQueue OBJECT IDENTIFIER ::= { sta 12}
staQueueLanheap OBJECT-TYPE
                SYNTAX INTEGER
                MAX-ACCESS read-only
                STATUS current
                DESCRIPTION "LAN-Heap-Packets"
                ::= {  staQueue 1 }

staQueueWanheap OBJECT-TYPE
                SYNTAX INTEGER
                MAX-ACCESS read-only
                STATUS current
                DESCRIPTION "WAN-Heap-Packets"
                ::= {  staQueue 3 }

staQueueWanqueu OBJECT-TYPE
                SYNTAX INTEGER
                MAX-ACCESS read-only
                STATUS current
                DESCRIPTION "WAN-Queue-Packets"
                ::= {  staQueue 4 }

staQueueArpquer OBJECT-TYPE
                SYNTAX INTEGER
                MAX-ACCESS read-only
                STATUS current
                DESCRIPTION "ARP-query-Queue-Packets"
                ::= {  staQueue 7 }

staQueueArpqueu OBJECT-TYPE
                SYNTAX INTEGER
                MAX-ACCESS read-only
                STATUS current
                DESCRIPTION "ARP-Queue-Packets"
                ::= {  staQueue 8 }

staQueueIpqueue OBJECT-TYPE
                SYNTAX INTEGER
                MAX-ACCESS read-only
                STATUS current
                DESCRIPTION "IP-Queue-Packets"
                ::= {  staQueue 9 }

staQueueIpurgen OBJECT-TYPE
                SYNTAX INTEGER
                MAX-ACCESS read-only
                STATUS current
                DESCRIPTION "IP-urgent-Queue-Packets"
                ::= {  staQueue 10 }

staQueueIcmpque OBJECT-TYPE
                SYNTAX INTEGER
                MAX-ACCESS read-only
                STATUS current
                DESCRIPTION "ICMP-Queue-Packets"
                ::= {  staQueue 11 }

staQueueTcpqueu OBJECT-TYPE
                SYNTAX INTEGER
                MAX-ACCESS read-only
                STATUS current
                DESCRIPTION "TCP-Queue-Packets"
                ::= {  staQueue 12 }

staQueueTftpser OBJECT-TYPE
                SYNTAX INTEGER
                MAX-ACCESS read-only
                STATUS current
                DESCRIPTION "TFTP-server-Queue-Packets"
                ::= {  staQueue 13 }

staQueueSnmpque OBJECT-TYPE
                SYNTAX INTEGER
                MAX-ACCESS read-only
                STATUS current
                DESCRIPTION "SNMP-Queue-Packets"
                ::= {  staQueue 14 }

staQueueProthea OBJECT-TYPE
                SYNTAX INTEGER
                MAX-ACCESS read-only
                STATUS current
                DESCRIPTION "PROT-Heap-Packets"
                ::= {  staQueue 22 }

staQueueDhcpser OBJECT-TYPE
                SYNTAX INTEGER
                MAX-ACCESS read-only
                STATUS current
                DESCRIPTION "DHCP-server-Queue-Packets"
                ::= {  staQueue 27 }

staQueueDhcpcli OBJECT-TYPE
                SYNTAX INTEGER
                MAX-ACCESS read-only
                STATUS current
                DESCRIPTION "DHCP-client-Queue-Packets"
                ::= {  staQueue 28 }

staQueueIprripq OBJECT-TYPE
                SYNTAX INTEGER
                MAX-ACCESS read-only
                STATUS current
                DESCRIPTION "IPR-RIP-Queue-Packets"
                ::= {  staQueue 29 }

staQueueDnstxqu OBJECT-TYPE
                SYNTAX INTEGER
                MAX-ACCESS read-only
                STATUS current
                DESCRIPTION "DNS-TX-Queue-Packets"
                ::= {  staQueue 30 }

staQueueDnsrxqu OBJECT-TYPE
                SYNTAX INTEGER
                MAX-ACCESS read-only
                STATUS current
                DESCRIPTION "DNS-RX-Queue-Packets"
                ::= {  staQueue 31 }

staQueueWlanman OBJECT-TYPE
                SYNTAX INTEGER
                MAX-ACCESS read-only
                STATUS current
                DESCRIPTION "WLAN-Management-Heap-Packets"
                ::= {  staQueue 40 }

staConneTable OBJECT-TYPE
              SYNTAX SEQUENCE OF StaConneEntry
              MAX-ACCESS not-accessible
              STATUS current
              DESCRIPTION "Connection"
              ::= {  sta 13 }

staConneEntry OBJECT-TYPE
              SYNTAX StaConneEntry
              MAX-ACCESS not-accessible
              STATUS current
              DESCRIPTION "entry in table"
              INDEX { staConneIfc }
              ::= {  staConneTable 1 }

StaConneEntry ::= SEQUENCE {
              staConneIfc INTEGER,
              staConneConn INTEGER,
              staConneActi INTEGER,
              staConnePass INTEGER,
              staConneErro INTEGER,
              staConneCont DisplayString,
              staConneChar INTEGER
             }

staConneIfc OBJECT-TYPE
             SYNTAX INTEGER{
               dsl-ch-1(1),
               ext(2)
             }
             MAX-ACCESS read-only
             STATUS current
             DESCRIPTION "Ifc"
             ::= {  staConneEntry 1 }

staConneConn OBJECT-TYPE
             SYNTAX INTEGER (0..2147483647)
             MAX-ACCESS read-only
             STATUS current
             DESCRIPTION "Connections"
             ::= {  staConneEntry 2 }

staConneActi OBJECT-TYPE
             SYNTAX INTEGER (0..2147483647)
             MAX-ACCESS read-only
             STATUS current
             DESCRIPTION "active"
             ::= {  staConneEntry 3 }

staConnePass OBJECT-TYPE
             SYNTAX INTEGER (0..2147483647)
             MAX-ACCESS read-only
             STATUS current
             DESCRIPTION "passive"
             ::= {  staConneEntry 4 }

staConneErro OBJECT-TYPE
             SYNTAX INTEGER (0..2147483647)
             MAX-ACCESS read-only
             STATUS current
             DESCRIPTION "Errors"
             ::= {  staConneEntry 5 }

staConneCont OBJECT-TYPE
             SYNTAX DisplayString (SIZE(0..255))
             MAX-ACCESS read-only
             STATUS current
             DESCRIPTION "Con.-Time"
             ::= {  staConneEntry 6 }

staConneChar OBJECT-TYPE
             SYNTAX INTEGER (0..2147483647)
             MAX-ACCESS read-only
             STATUS current
             DESCRIPTION "Charge"
             ::= {  staConneEntry 7 }

staInfocTable OBJECT-TYPE
              SYNTAX SEQUENCE OF StaInfocEntry
              MAX-ACCESS not-accessible
              STATUS current
              DESCRIPTION "Info-Connection"
              ::= {  sta 14 }

staInfocEntry OBJECT-TYPE
              SYNTAX StaInfocEntry
              MAX-ACCESS not-accessible
              STATUS current
              DESCRIPTION "entry in table"
              INDEX { staInfocIfc }
              ::= {  staInfocTable 1 }

StaInfocEntry ::= SEQUENCE {
              staInfocIfc INTEGER,
              staInfocSta DisplayString,
              staInfocMod INTEGER,
              staInfocDia DisplayString,
              staInfocPee DisplayString,
              staInfocB1d INTEGER,
              staInfocB2d INTEGER
             }

staInfocIfc OBJECT-TYPE
            SYNTAX INTEGER{
              dsl-ch-1(1),
              ext(2)
            }
            MAX-ACCESS read-only
            STATUS current
            DESCRIPTION "Ifc"
            ::= {  staInfocEntry 1 }

staInfocSta OBJECT-TYPE
            SYNTAX DisplayString (SIZE(0..16))
            MAX-ACCESS read-only
            STATUS current
            DESCRIPTION "Status"
            ::= {  staInfocEntry 2 }

staInfocMod OBJECT-TYPE
            SYNTAX INTEGER{
              unknown(0),
              active(4),
              passive(5),
              callback(9)
            }
            MAX-ACCESS read-only
            STATUS current
            DESCRIPTION "Mode"
            ::= {  staInfocEntry 3 }

staInfocDia OBJECT-TYPE
            SYNTAX DisplayString (SIZE(0..20))
            MAX-ACCESS read-only
            STATUS current
            DESCRIPTION "Dialup-remote"
            ::= {  staInfocEntry 4 }

staInfocPee OBJECT-TYPE
            SYNTAX DisplayString (SIZE(0..16))
            MAX-ACCESS read-only
            STATUS current
            DESCRIPTION "Peer"
            ::= {  staInfocEntry 5 }

staInfocB1d OBJECT-TYPE
            SYNTAX INTEGER (0..65535)
            MAX-ACCESS read-only
            STATUS current
            DESCRIPTION "B1-DT"
            ::= {  staInfocEntry 6 }

staInfocB2d OBJECT-TYPE
            SYNTAX INTEGER (0..65535)
            MAX-ACCESS read-only
            STATUS current
            DESCRIPTION "B2-DT"
            ::= {  staInfocEntry 7 }

staLayerTable OBJECT-TYPE
              SYNTAX SEQUENCE OF StaLayerEntry
              MAX-ACCESS not-accessible
              STATUS current
              DESCRIPTION "Layer-Connection"
              ::= {  sta 15 }

staLayerEntry OBJECT-TYPE
              SYNTAX StaLayerEntry
              MAX-ACCESS not-accessible
              STATUS current
              DESCRIPTION "entry in table"
              INDEX { staLayerIfc }
              ::= {  staLayerTable 1 }

StaLayerEntry ::= SEQUENCE {
              staLayerIfc INTEGER,
              staLayerWanl DisplayString,
              staLayerEnca INTEGER,
              staLayerLay3 INTEGER,
              staLayerLay2 INTEGER,
              staLayerL2op INTEGER,
              staLayerLay1 INTEGER,
              staLayerL1pa INTEGER
             }

staLayerIfc OBJECT-TYPE
             SYNTAX INTEGER{
               dsl-ch-1(1),
               ext(2)
             }
             MAX-ACCESS read-only
             STATUS current
             DESCRIPTION "Ifc"
             ::= {  staLayerEntry 1 }

staLayerWanl OBJECT-TYPE
             SYNTAX DisplayString (SIZE(0..9))
             MAX-ACCESS read-only
             STATUS current
             DESCRIPTION "WAN-layer"
             ::= {  staLayerEntry 2 }

staLayerEnca OBJECT-TYPE
             SYNTAX INTEGER{
               ether(0),
               trans(255)
             }
             MAX-ACCESS read-only
             STATUS current
             DESCRIPTION "Encaps."
             ::= {  staLayerEntry 3 }

staLayerLay3 OBJECT-TYPE
             SYNTAX INTEGER{
               trans(0),
               ppp(4),
               appp(5),
               scppp(6),
               scappp(7),
               sctrans(8),
               dhcp(9),
               trans(255)
             }
             MAX-ACCESS read-only
             STATUS current
             DESCRIPTION "Lay-3"
             ::= {  staLayerEntry 4 }

staLayerLay2 OBJECT-TYPE
             SYNTAX INTEGER{
               sscop(6),
               pppoe(5),
               x-75lapb(0),
               trans(1)
             }
             MAX-ACCESS read-only
             STATUS current
             DESCRIPTION "Lay-2"
             ::= {  staLayerEntry 5 }

staLayerL2op OBJECT-TYPE
             SYNTAX INTEGER{
               none(255),
               compr(0),
               bundle(1),
               bnd-plus-cmpr(2)
             }
             MAX-ACCESS read-only
             STATUS current
             DESCRIPTION "L2-Opt."
             ::= {  staLayerEntry 6 }

staLayerLay1 OBJECT-TYPE
             SYNTAX INTEGER{
               aal-5(2),
               eth(4),
               hdlc64k(0),
               hdlc56k(1),
               modem(5)
             }
             MAX-ACCESS read-only
             STATUS current
             DESCRIPTION "Lay-1"
             ::= {  staLayerEntry 7 }

staLayerL1pa OBJECT-TYPE
             SYNTAX INTEGER{
               none(0),
               v-21-300(1),
               v-23-600(2),
               v-23-1200(3),
               v-22-1200(4),
               v-22bis-2400(5),
               v-32qam-4800(6),
               v-32qam-9600(7),
               v-32bis-7200(8),
               v-32tcm-9600(9),
               v-32bis-12000(10),
               v-32bis-14400(11),
               v-34-2400(12),
               v-34-4800(13),
               v-34-7200(14),
               v-34-9600(15),
               v-34-12000(16),
               v-34-14400(17),
               v-34-16800(18),
               v-34-19200(19),
               v-34-21600(20),
               v-34-24000(21),
               v-34-26400(22),
               v-34-28800(23),
               v-34-31200(24),
               v-34-33600(25),
               v-90-28000(26),
               v-90-29333(27),
               v-90-30667(28),
               v-90-32000(29),
               v-90-33333(30),
               v-90-34667(31),
               v-90-36000(32),
               v-90-37333(33),
               v-90-38667(34),
               v-90-40000(35),
               v-90-41333(36),
               v-90-42667(37),
               v-90-44000(38),
               v-90-45333(39),
               v-90-46667(40),
               v-90-48000(41),
               v-90-49333(42),
               v-90-50667(43),
               v-90-52000(44),
               v-90-53333(45),
               v-90-54667(46),
               v-90-56000(47)
             }
             MAX-ACCESS read-only
             STATUS current
             DESCRIPTION "L1-Parameter"
             ::= {  staLayerEntry 8 }

staCalliTable OBJECT-TYPE
              SYNTAX SEQUENCE OF StaCalliEntry
              MAX-ACCESS not-accessible
              STATUS current
              DESCRIPTION "Call-Information"
              ::= {  sta 16 }

staCalliEntry OBJECT-TYPE
              SYNTAX StaCalliEntry
              MAX-ACCESS not-accessible
              STATUS current
              DESCRIPTION "entry in table"
              INDEX { staCalliSys, staCalliCou }
              ::= {  staCalliTable 1 }

StaCalliEntry ::= SEQUENCE {
              staCalliSys INTEGER,
              staCalliIfc INTEGER,
              staCalliCli DisplayString,
              staCalliDia DisplayString,
              staCalliCap INTEGER,
              staCalliBch INTEGER,
              staCalliCou INTEGER
             }

staCalliSys OBJECT-TYPE
            SYNTAX INTEGER (0..2147483647)
            MAX-ACCESS read-only
            STATUS current
            DESCRIPTION "System-time"
            ::= {  staCalliEntry 1 }

staCalliIfc OBJECT-TYPE
            SYNTAX INTEGER{
              dsl-1(1),
              ext(2)
            }
            MAX-ACCESS read-only
            STATUS current
            DESCRIPTION "Ifc"
            ::= {  staCalliEntry 2 }

staCalliCli OBJECT-TYPE
            SYNTAX DisplayString (SIZE(0..20))
            MAX-ACCESS read-only
            STATUS current
            DESCRIPTION "CLIP-Caller"
            ::= {  staCalliEntry 3 }

staCalliDia OBJECT-TYPE
            SYNTAX DisplayString (SIZE(0..20))
            MAX-ACCESS read-only
            STATUS current
            DESCRIPTION "Dial-Caller"
            ::= {  staCalliEntry 4 }

staCalliCap OBJECT-TYPE
            SYNTAX INTEGER{
              unknown(255),
              hdlc64k(0),
              hdlc56k(1),
              v110-9k6(3),
              v110-19k2(67),
              v110-38k4(131),
              modem(5),
              a-3-1khz(13),
              speech(14),
              fax-g2-3(15)
            }
            MAX-ACCESS read-only
            STATUS current
            DESCRIPTION "Capab."
            ::= {  staCalliEntry 5 }

staCalliBch OBJECT-TYPE
            SYNTAX INTEGER (0..65535)
            MAX-ACCESS read-only
            STATUS current
            DESCRIPTION "B-chan."
            ::= {  staCalliEntry 6 }

staCalliCou OBJECT-TYPE
            SYNTAX INTEGER (0..2147483647)
            MAX-ACCESS read-only
            STATUS current
            DESCRIPTION "Counter"
            ::= {  staCalliEntry 7 }

staRemotTable OBJECT-TYPE
              SYNTAX SEQUENCE OF StaRemotEntry
              MAX-ACCESS not-accessible
              STATUS current
              DESCRIPTION "Remote-Connections"
              ::= {  sta 17 }

staRemotEntry OBJECT-TYPE
              SYNTAX StaRemotEntry
              MAX-ACCESS not-accessible
              STATUS current
              DESCRIPTION "entry in table"
              INDEX { staRemotConns, staRemotCount }
              ::= {  staRemotTable 1 }

StaRemotEntry ::= SEQUENCE {
              staRemotConns DisplayString,
              staRemotRemot DisplayString,
              staRemotMode INTEGER,
              staRemotIfc INTEGER,
              staRemotConnt DisplayString,
              staRemotCharg INTEGER,
              staRemotCount INTEGER
             }

staRemotConns OBJECT-TYPE
              SYNTAX DisplayString (SIZE(0..19))
              MAX-ACCESS read-only
              STATUS current
              DESCRIPTION "Conn.-start"
              ::= {  staRemotEntry 1 }

staRemotRemot OBJECT-TYPE
              SYNTAX DisplayString (SIZE(0..16))
              MAX-ACCESS read-only
              STATUS current
              DESCRIPTION "Remote-ID"
              ::= {  staRemotEntry 2 }

staRemotMode OBJECT-TYPE
              SYNTAX INTEGER{
                unknown(0),
                active(4),
                passive(5),
                callback(9)
              }
              MAX-ACCESS read-only
              STATUS current
              DESCRIPTION "Mode"
              ::= {  staRemotEntry 3 }

staRemotIfc OBJECT-TYPE
              SYNTAX INTEGER{
                dsl-ch-1(1),
                ext(2)
              }
              MAX-ACCESS read-only
              STATUS current
              DESCRIPTION "Ifc"
              ::= {  staRemotEntry 4 }

staRemotConnt OBJECT-TYPE
              SYNTAX DisplayString (SIZE(0..255))
              MAX-ACCESS read-only
              STATUS current
              DESCRIPTION "Conn.-time"
              ::= {  staRemotEntry 5 }

staRemotCharg OBJECT-TYPE
              SYNTAX INTEGER (0..2147483647)
              MAX-ACCESS read-only
              STATUS current
              DESCRIPTION "Charge"
              ::= {  staRemotEntry 6 }

staRemotCount OBJECT-TYPE
              SYNTAX INTEGER (0..2147483647)
              MAX-ACCESS read-only
              STATUS current
              DESCRIPTION "Counter"
              ::= {  staRemotEntry 8 }

staCurre OBJECT-TYPE
         SYNTAX DisplayString
         MAX-ACCESS read-only
         STATUS current
         DESCRIPTION "Current-Time"
         ::= {  sta 18 }

staTime OBJECT IDENTIFIER ::= { sta 21}
staTimeCur OBJECT-TYPE
           SYNTAX DisplayString
           MAX-ACCESS read-only
           STATUS current
           DESCRIPTION "Current-Time"
           ::= {  staTime 1 }

staTimeSou OBJECT-TYPE
           SYNTAX INTEGER {
             manual(1),
             lan(3),
             ram(4),
             ntp(9),
             capwap(10),
             lanconfig(8),
             no(0)
           }
           MAX-ACCESS read-only
           STATUS current
           DESCRIPTION "Source"
           ::= {  staTime 2 }

staTimeSet OBJECT-TYPE
           SYNTAX INTEGER
           MAX-ACCESS read-only
           STATUS current
           DESCRIPTION "Set-Count"
           ::= {  staTime 3 }

staTimeTim OBJECT-TYPE
           SYNTAX INTEGER {
             e0(0),
             plus-1(1),
             plus-2(2),
             plus-3(3),
             plus-4(4),
             plus-5(5),
             plus-6(6),
             plus-7(7),
             plus-8(8),
             plus-9(9),
             plus-10(10),
             plus-11(11),
             plus-12(12),
             plus-13(13),
             plus-14(14),
             minus-1(255),
             minus-2(254),
             minus-3(253),
             minus-4(252),
             minus-5(251),
             minus-6(250),
             minus-7(249),
             minus-8(248),
             minus-9(247),
             minus-10(246),
             minus-11(245),
             minus-12(244)
           }
           MAX-ACCESS read-only
           STATUS current
           DESCRIPTION "Timezone"
           ::= {  staTime 10 }

staTimeDay OBJECT-TYPE
           SYNTAX INTEGER {
             no(0),
             yes(1),
             europe-eu(2),
             russia(3),
             usa(4),
             user-defined(255)
           }
           MAX-ACCESS read-only
           STATUS current
           DESCRIPTION "Daylight-saving-time"
           ::= {  staTime 11 }

staTimeDstTable OBJECT-TYPE
                SYNTAX SEQUENCE OF StaTimeDstEntry
                MAX-ACCESS not-accessible
                STATUS current
                DESCRIPTION "DST-clock-changes"
                ::= {  staTime 12 }

staTimeDstEntry OBJECT-TYPE
                SYNTAX StaTimeDstEntry
                MAX-ACCESS not-accessible
                STATUS current
                DESCRIPTION "entry in table"
                INDEX { staTimeDstEve }
                ::= {  staTimeDstTable 1 }

StaTimeDstEntry ::= SEQUENCE {
                staTimeDstEve INTEGER,
                staTimeDstInd INTEGER,
                staTimeDstDay INTEGER,
                staTimeDstMon INTEGER,
                staTimeDstHou INTEGER,
                staTimeDstMin INTEGER,
                staTimeDstTim INTEGER
               }

staTimeDstEve OBJECT-TYPE
              SYNTAX INTEGER{
                start(1),
                end(2)
              }
              MAX-ACCESS read-only
              STATUS current
              DESCRIPTION "Event"
              ::= {  staTimeDstEntry 1 }

staTimeDstInd OBJECT-TYPE
              SYNTAX INTEGER{
                e4-last(252),
                e3-last(253),
                e2-last(254),
                last(255),
                first(1),
                second(2),
                third(3),
                fourth(4)
              }
              MAX-ACCESS read-write
              STATUS current
              DESCRIPTION "Index"
              ::= {  staTimeDstEntry 2 }

staTimeDstDay OBJECT-TYPE
              SYNTAX INTEGER{
                monday(1),
                tuesday(2),
                wednesday(3),
                thursday(4),
                friday(5),
                saturday(6),
                sunday(0)
              }
              MAX-ACCESS read-write
              STATUS current
              DESCRIPTION "Day"
              ::= {  staTimeDstEntry 3 }

staTimeDstMon OBJECT-TYPE
              SYNTAX INTEGER{
                january(1),
                february(2),
                march(3),
                april(4),
                may(5),
                june(6),
                july(7),
                august(8),
                september(9),
                october(10),
                november(11),
                december(12)
              }
              MAX-ACCESS read-write
              STATUS current
              DESCRIPTION "Month"
              ::= {  staTimeDstEntry 4 }

staTimeDstHou OBJECT-TYPE
              SYNTAX INTEGER (0..255)
              MAX-ACCESS read-write
              STATUS current
              DESCRIPTION "Hour"
              ::= {  staTimeDstEntry 5 }

staTimeDstMin OBJECT-TYPE
              SYNTAX INTEGER (0..255)
              MAX-ACCESS read-write
              STATUS current
              DESCRIPTION "Minute"
              ::= {  staTimeDstEntry 6 }

staTimeDstTim OBJECT-TYPE
              SYNTAX INTEGER{
                utc(1),
                lst(0)
              }
              MAX-ACCESS read-write
              STATUS current
              DESCRIPTION "Time-type"
              ::= {  staTimeDstEntry 7 }

staLcr OBJECT IDENTIFIER ::= { sta 22}
staLcrTot OBJECT-TYPE
          SYNTAX Counter32
          MAX-ACCESS read-only
          STATUS current
          DESCRIPTION "Total-Calls"
          ::= {  staLcr 1 }

staLcrFou OBJECT-TYPE
          SYNTAX Counter32
          MAX-ACCESS read-only
          STATUS current
          DESCRIPTION "Found-Events"
          ::= {  staLcr 2 }

staLcrNot OBJECT-TYPE
          SYNTAX Counter32
          MAX-ACCESS read-only
          STATUS current
          DESCRIPTION "Notfound-Errors"
          ::= {  staLcr 3 }

staLcrMis OBJECT-TYPE
          SYNTAX Counter32
          MAX-ACCESS read-only
          STATUS current
          DESCRIPTION "Missingtime-Errors"
          ::= {  staLcr 4 }

staLcrProTable OBJECT-TYPE
               SYNTAX SEQUENCE OF StaLcrProEntry
               MAX-ACCESS not-accessible
               STATUS current
               DESCRIPTION "Provider"
               ::= {  staLcr 6 }

staLcrProEntry OBJECT-TYPE
               SYNTAX StaLcrProEntry
               MAX-ACCESS not-accessible
               STATUS current
               DESCRIPTION "entry in table"
               INDEX { staLcrProPro }
               ::= {  staLcrProTable 1 }

StaLcrProEntry ::= SEQUENCE {
               staLcrProPro DisplayString,
               staLcrProFai INTEGER,
               staLcrProSuc INTEGER
              }

staLcrProPro OBJECT-TYPE
             SYNTAX DisplayString (SIZE(0..5))
             MAX-ACCESS read-only
             STATUS current
             DESCRIPTION "Provider"
             ::= {  staLcrProEntry 1 }

staLcrProFai OBJECT-TYPE
             SYNTAX INTEGER (0..2147483647)
             MAX-ACCESS read-only
             STATUS current
             DESCRIPTION "Failures"
             ::= {  staLcrProEntry 2 }

staLcrProSuc OBJECT-TYPE
             SYNTAX INTEGER (0..2147483647)
             MAX-ACCESS read-only
             STATUS current
             DESCRIPTION "Successes"
             ::= {  staLcrProEntry 3 }

staLcrDel OBJECT-TYPE
          SYNTAX DisplayString
          MAX-ACCESS read-write
          STATUS current
          DESCRIPTION "Delete-Values"
          ::= {  staLcr 7 }

staCharg OBJECT IDENTIFIER ::= { sta 24}
staChargSpareda OBJECT-TYPE
                SYNTAX INTEGER
                MAX-ACCESS read-only
                STATUS current
                DESCRIPTION "Spare-Days-per-Period"
                ::= {  staCharg 6 }

staChargSpservere OBJECT-TYPE
                SYNTAX INTEGER
                MAX-ACCESS read-only
                STATUS current
                DESCRIPTION "Spare-Serial-Minutes"
                ::= {  staCharg 10 }

staChargRouters OBJECT-TYPE
                SYNTAX INTEGER
                MAX-ACCESS read-only
                STATUS current
                DESCRIPTION "Router-Serial-Minutes-Active"
                ::= {  staCharg 11 }

staChargSpareds OBJECT-TYPE
                SYNTAX INTEGER
                MAX-ACCESS read-only
                STATUS current
                DESCRIPTION "Spare-DSL-Broadband-Minutes"
                ::= {  staCharg 1 }

staChargRouterd OBJECT-TYPE
                SYNTAX INTEGER
                MAX-ACCESS read-only
                STATUS current
                DESCRIPTION "Router-DSL-Broadband-Minutes-Active"
                ::= {  staCharg 9 }

staChargTimetabTable OBJECT-TYPE
                     SYNTAX SEQUENCE OF StaChargTimetabEntry
                     MAX-ACCESS not-accessible
                     STATUS current
                     DESCRIPTION "Time-Table"
                     ::= {  staCharg 2 }

staChargTimetabEntry OBJECT-TYPE
                     SYNTAX StaChargTimetabEntry
                     MAX-ACCESS not-accessible
                     STATUS current
                     DESCRIPTION "entry in table"
                     INDEX { staChargTimetabIfc }
                     ::= {  staChargTimetabTable 1 }

StaChargTimetabEntry ::= SEQUENCE {
                     staChargTimetabIfc INTEGER,
                     staChargTimetabBudgetmi INTEGER,
                     staChargTimetabSparemin INTEGER,
                     staChargTimetabMinutesa INTEGER,
                     staChargTimetabMinutesp INTEGER
                    }

staChargTimetabIfc OBJECT-TYPE
                        SYNTAX INTEGER{
                          router-dsl-broadband(1),
                          router-serial(2),
                          lancapi(3),
                          ab-1(4),
                          ab-2(5),
                          ab-3(6),
                          ab-4(7),
                          time-modul(255)
                        }
                        MAX-ACCESS read-only
                        STATUS current
                        DESCRIPTION "Ifc"
                        ::= {  staChargTimetabEntry 1 }

staChargTimetabBudgetmi OBJECT-TYPE
                        SYNTAX INTEGER (0..2147483647)
                        MAX-ACCESS read-only
                        STATUS current
                        DESCRIPTION "Budget-minutes"
                        ::= {  staChargTimetabEntry 2 }

staChargTimetabSparemin OBJECT-TYPE
                        SYNTAX INTEGER (0..2147483647)
                        MAX-ACCESS read-only
                        STATUS current
                        DESCRIPTION "Spare-minutes"
                        ::= {  staChargTimetabEntry 3 }

staChargTimetabMinutesa OBJECT-TYPE
                        SYNTAX INTEGER (0..2147483647)
                        MAX-ACCESS read-only
                        STATUS current
                        DESCRIPTION "Minutes-active"
                        ::= {  staChargTimetabEntry 4 }

staChargTimetabMinutesp OBJECT-TYPE
                        SYNTAX INTEGER (0..2147483647)
                        MAX-ACCESS read-only
                        STATUS current
                        DESCRIPTION "Minutes-passive"
                        ::= {  staChargTimetabEntry 5 }

staChargDeletev OBJECT-TYPE
                SYNTAX DisplayString
                MAX-ACCESS read-write
                STATUS current
                DESCRIPTION "Delete-Values"
                ::= {  staCharg 3 }

staDsl OBJECT IDENTIFIER ::= { sta 25}
staDslRxpack OBJECT-TYPE
             SYNTAX Counter32
             MAX-ACCESS read-only
             STATUS current
             DESCRIPTION "Rx-Packets"
             ::= {  staDsl 1 }

staDslTxpack OBJECT-TYPE
             SYNTAX Counter32
             MAX-ACCESS read-only
             STATUS current
             DESCRIPTION "Tx-Packets"
             ::= {  staDsl 2 }

staDslRxerro OBJECT-TYPE
             SYNTAX Counter32
             MAX-ACCESS read-only
             STATUS current
             DESCRIPTION "Rx-Errors"
             ::= {  staDsl 3 }

staDslTxerro OBJECT-TYPE
             SYNTAX Counter32
             MAX-ACCESS read-only
             STATUS current
             DESCRIPTION "Tx-Errors"
             ::= {  staDsl 4 }

staDslRxnoco OBJECT-TYPE
             SYNTAX Counter32
             MAX-ACCESS read-only
             STATUS current
             DESCRIPTION "Rx-No-Connection"
             ::= {  staDsl 5 }

staDslNicerr OBJECT-TYPE
             SYNTAX Counter32
             MAX-ACCESS read-only
             STATUS current
             DESCRIPTION "NIC-Errors"
             ::= {  staDsl 6 }

staDslQueuep OBJECT-TYPE
             SYNTAX INTEGER
             MAX-ACCESS read-only
             STATUS current
             DESCRIPTION "Queue-Packets"
             ::= {  staDsl 7 }

staDslQueuee OBJECT-TYPE
             SYNTAX Counter32
             MAX-ACCESS read-only
             STATUS current
             DESCRIPTION "Queue-Errors"
             ::= {  staDsl 8 }

staDslRxbyte OBJECT-TYPE
             SYNTAX Counter64
             MAX-ACCESS read-only
             STATUS current
             DESCRIPTION "Rx-Bytes"
             ::= {  staDsl 9 }

staDslTxbyte OBJECT-TYPE
             SYNTAX Counter64
             MAX-ACCESS read-only
             STATUS current
             DESCRIPTION "Tx-Bytes"
             ::= {  staDsl 10 }

staDslRxunic OBJECT-TYPE
             SYNTAX Counter32
             MAX-ACCESS read-only
             STATUS current
             DESCRIPTION "Rx-Unicasts"
             ::= {  staDsl 11 }

staDslTxbroa OBJECT-TYPE
             SYNTAX Counter32
             MAX-ACCESS read-only
             STATUS current
             DESCRIPTION "Tx-Broadcasts"
             ::= {  staDsl 12 }

staDslTxunic OBJECT-TYPE
             SYNTAX Counter32
             MAX-ACCESS read-only
             STATUS current
             DESCRIPTION "Tx-Unicasts"
             ::= {  staDsl 13 }

staDslLinkac OBJECT-TYPE
             SYNTAX INTEGER {
               no(0),
               yes(1)
             }
             MAX-ACCESS read-only
             STATUS current
             DESCRIPTION "Link-Active"
             ::= {  staDsl 14 }

staDslPppoe OBJECT IDENTIFIER ::= { staDsl 23}
staDslPppoeTxpadi OBJECT-TYPE
                  SYNTAX INTEGER
                  MAX-ACCESS read-only
                  STATUS current
                  DESCRIPTION "Tx-PADI"
                  ::= {  staDslPppoe 1 }

staDslPppoeRxpado OBJECT-TYPE
                  SYNTAX INTEGER
                  MAX-ACCESS read-only
                  STATUS current
                  DESCRIPTION "Rx-PADO"
                  ::= {  staDslPppoe 2 }

staDslPppoeTxpadr OBJECT-TYPE
                  SYNTAX INTEGER
                  MAX-ACCESS read-only
                  STATUS current
                  DESCRIPTION "Tx-PADR"
                  ::= {  staDslPppoe 3 }

staDslPppoeRxpads OBJECT-TYPE
                  SYNTAX INTEGER
                  MAX-ACCESS read-only
                  STATUS current
                  DESCRIPTION "Rx-PADS"
                  ::= {  staDslPppoe 4 }

staDslPppoeTxpadt OBJECT-TYPE
                  SYNTAX INTEGER
                  MAX-ACCESS read-only
                  STATUS current
                  DESCRIPTION "Tx-PADT"
                  ::= {  staDslPppoe 5 }

staDslPppoeRxpadt OBJECT-TYPE
                  SYNTAX INTEGER
                  MAX-ACCESS read-only
                  STATUS current
                  DESCRIPTION "Rx-PADT"
                  ::= {  staDslPppoe 6 }

staDslPppoeTxprot OBJECT-TYPE
                  SYNTAX INTEGER
                  MAX-ACCESS read-only
                  STATUS current
                  DESCRIPTION "Tx-Protocol"
                  ::= {  staDslPppoe 7 }

staDslPppoeRxprot OBJECT-TYPE
                  SYNTAX INTEGER
                  MAX-ACCESS read-only
                  STATUS current
                  DESCRIPTION "Rx-Protocol"
                  ::= {  staDslPppoe 8 }

staDslPppoeTxdata OBJECT-TYPE
                  SYNTAX INTEGER
                  MAX-ACCESS read-only
                  STATUS current
                  DESCRIPTION "Tx-Data"
                  ::= {  staDslPppoe 9 }

staDslPppoeRxdata OBJECT-TYPE
                  SYNTAX INTEGER
                  MAX-ACCESS read-only
                  STATUS current
                  DESCRIPTION "Rx-Data"
                  ::= {  staDslPppoe 10 }

staDslPppoeRxbad OBJECT-TYPE
                  SYNTAX INTEGER
                  MAX-ACCESS read-only
                  STATUS current
                  DESCRIPTION "Rx-Bad"
                  ::= {  staDslPppoe 11 }

staDslPppoeAcname OBJECT-TYPE
                  SYNTAX DisplayString (SIZE(0..63))
                  MAX-ACCESS read-only
                  STATUS current
                  DESCRIPTION "AC-Name"
                  ::= {  staDslPppoe 12 }

staDslPppoeServic OBJECT-TYPE
                  SYNTAX DisplayString (SIZE(0..63))
                  MAX-ACCESS read-only
                  STATUS current
                  DESCRIPTION "Service"
                  ::= {  staDslPppoe 13 }

staDslPppoeDelete OBJECT-TYPE
                  SYNTAX DisplayString
                  MAX-ACCESS read-write
                  STATUS current
                  DESCRIPTION "Delete-Values"
                  ::= {  staDslPppoe 30 }

staDslDslol OBJECT IDENTIFIER ::= { staDsl 24}
staDslDslolIpconfig OBJECT-TYPE
                    SYNTAX INTEGER {
                      valid(1),
                      invalid(0)
                    }
                    MAX-ACCESS read-only
                    STATUS current
                    DESCRIPTION "IP-Configuration"
                    ::= {  staDslDslol 1 }

staDslDslolIpnetwor OBJECT-TYPE
                    SYNTAX IpAddress
                    MAX-ACCESS read-only
                    STATUS current
                    DESCRIPTION "IP-Network"
                    ::= {  staDslDslol 2 }

staDslDslolIpnetmas OBJECT-TYPE
                    SYNTAX IpAddress
                    MAX-ACCESS read-only
                    STATUS current
                    DESCRIPTION "IP-Netmask"
                    ::= {  staDslDslol 3 }

staDslDslolGatewayi OBJECT-TYPE
                    SYNTAX IpAddress
                    MAX-ACCESS read-only
                    STATUS current
                    DESCRIPTION "Gateway-IP"
                    ::= {  staDslDslol 4 }

staDslDslolGatewaym OBJECT-TYPE
                    SYNTAX DisplayString (SIZE(0..12))
                    MAX-ACCESS read-only
                    STATUS current
                    DESCRIPTION "Gateway-MAC"
                    ::= {  staDslDslol 5 }

staDslDslolCatchdhc OBJECT-TYPE
                    SYNTAX INTEGER {
                      yes(1),
                      no(0)
                    }
                    MAX-ACCESS read-only
                    STATUS current
                    DESCRIPTION "Catch-DHCP"
                    ::= {  staDslDslol 6 }

staDslDslolExclusiv OBJECT-TYPE
                    SYNTAX INTEGER {
                      yes(1),
                      no(0)
                    }
                    MAX-ACCESS read-only
                    STATUS current
                    DESCRIPTION "Exclusive-Mode"
                    ::= {  staDslDslol 7 }

staDslDelete OBJECT-TYPE
             SYNTAX DisplayString
             MAX-ACCESS read-write
             STATUS current
             DESCRIPTION "Delete-Values"
             ::= {  staDsl 30 }

staPptp OBJECT IDENTIFIER ::= { sta 27}
staPptpRxp OBJECT-TYPE
           SYNTAX Counter32
           MAX-ACCESS read-only
           STATUS current
           DESCRIPTION "Rx-Packets"
           ::= {  staPptp 1 }

staPptpTxp OBJECT-TYPE
           SYNTAX Counter32
           MAX-ACCESS read-only
           STATUS current
           DESCRIPTION "Tx-Packets"
           ::= {  staPptp 2 }

staPptpEch OBJECT-TYPE
           SYNTAX Counter32
           MAX-ACCESS read-only
           STATUS current
           DESCRIPTION "Echo-Retries"
           ::= {  staPptp 3 }

staPptpAck OBJECT-TYPE
           SYNTAX Counter32
           MAX-ACCESS read-only
           STATUS current
           DESCRIPTION "Ack-Timeouts"
           ::= {  staPptp 4 }

staPptpDro OBJECT-TYPE
           SYNTAX Counter32
           MAX-ACCESS read-only
           STATUS current
           DESCRIPTION "Dropped-Packets"
           ::= {  staPptp 5 }

staPptpRxe OBJECT-TYPE
           SYNTAX Counter32
           MAX-ACCESS read-only
           STATUS current
           DESCRIPTION "Rx-Errors"
           ::= {  staPptp 6 }

staPptpTcp OBJECT-TYPE
           SYNTAX Counter32
           MAX-ACCESS read-only
           STATUS current
           DESCRIPTION "Tcp-Errors"
           ::= {  staPptp 7 }

staPptpCal OBJECT-TYPE
           SYNTAX Counter32
           MAX-ACCESS read-only
           STATUS current
           DESCRIPTION "Call-Errors"
           ::= {  staPptp 8 }

staPptpConTable OBJECT-TYPE
                SYNTAX SEQUENCE OF StaPptpConEntry
                MAX-ACCESS not-accessible
                STATUS current
                DESCRIPTION "Connections"
                ::= {  staPptp 9 }

staPptpConEntry OBJECT-TYPE
                SYNTAX StaPptpConEntry
                MAX-ACCESS not-accessible
                STATUS current
                DESCRIPTION "entry in table"
                INDEX { staPptpConChann }
                ::= {  staPptpConTable 1 }

StaPptpConEntry ::= SEQUENCE {
                staPptpConChann DisplayString,
                staPptpConState INTEGER,
                staPptpConLaste INTEGER,
                staPptpConMode INTEGER,
                staPptpConShtim INTEGER,
                staPptpConPhysc DisplayString,
                staPptpConPeera IpAddress,
                staPptpConIpadd IpAddress,
                staPptpConDnsde IpAddress,
                staPptpConDnsba IpAddress,
                staPptpConNbnsd IpAddress,
                staPptpConNbnsb IpAddress,
                staPptpConConnt INTEGER
               }

staPptpConChann OBJECT-TYPE
                SYNTAX DisplayString (SIZE(0..16))
                MAX-ACCESS read-only
                STATUS current
                DESCRIPTION "Channel"
                ::= {  staPptpConEntry 1 }

staPptpConState OBJECT-TYPE
                SYNTAX INTEGER{
                  init(0),
                  setup-wan(1),
                  ready(2),
                  wait-for-cb(3),
                  dial(4),
                  incoming-call(5),
                  protocol(6),
                  connection(7),
                  disconnecting(8),
                  call-back(9),
                  bundle-connect(10),
                  protocol-2(11),
                  reserved(12),
                  bundle(13)
                }
                MAX-ACCESS read-only
                STATUS current
                DESCRIPTION "State"
                ::= {  staPptpConEntry 3 }

staPptpConLaste OBJECT-TYPE
                SYNTAX INTEGER{
                  none(0),
                  remote-disconnected(17153),
                  manual-disconnect(17154),
                  shorthold-expired(17155),
                  physical-disconnected(17156),
                  invalid-physical-channel(17157),
                  dynamic-vpn-reconnect(17158),
                  configuration-changed(17159),
                  removed-from-config(17160),
                  remote-doubled(267),
                  icmp-conn-error(275),
                  dhcp-timeout(277),
                  pptp-no-response(278),
                  vpn-no-response(279),
                  arp-no-response(280),
                  pptp-no-channel(513),
                  pptp-bad-format(514),
                  pptp-bad-value(515),
                  pptp-no-ressource(516),
                  pptp-bad-call-id(517),
                  pptp-gen-error(518),
                  lcp-rejected(32768),
                  auth-error(32769),
                  auth-rejected(32770),
                  lcp-conn-error(32771),
                  pap-rejected(32784),
                  pap-rx-timeout(32785),
                  pap-tx-timeout(32786),
                  wrong-pap-req(32787),
                  pap-nak-received(32788),
                  unkn-pap-peer(32789),
                  chap-rejected(32800),
                  chap-rx-timeout(32801),
                  chap-tx-timeout(32802),
                  wrong-chap-resp(32803),
                  chap-fail-recvd(32804),
                  unkn-chap-peer(32805),
                  ipxcp-rejected(32816),
                  wrong-ipxcp-net(32817),
                  ipxcp-net-reject(32818),
                  ipxcp-route-unkn(32819),
                  ipcp-rejected(32832),
                  ccp-rejected(32848),
                  no-ncp-available(33008)
                }
                MAX-ACCESS read-write
                STATUS current
                DESCRIPTION "Last-Error"
                ::= {  staPptpConEntry 11 }

staPptpConMode OBJECT-TYPE
                SYNTAX INTEGER{
                  active(128),
                  passive(0)
                }
                MAX-ACCESS read-only
                STATUS current
                DESCRIPTION "Mode"
                ::= {  staPptpConEntry 4 }

staPptpConShtim OBJECT-TYPE
                SYNTAX INTEGER (0..65535)
                MAX-ACCESS read-only
                STATUS current
                DESCRIPTION "SH-Time"
                ::= {  staPptpConEntry 5 }

staPptpConPhysc OBJECT-TYPE
                SYNTAX DisplayString (SIZE(0..16))
                MAX-ACCESS read-only
                STATUS current
                DESCRIPTION "Phys.-connection"
                ::= {  staPptpConEntry 6 }

staPptpConPeera OBJECT-TYPE
                SYNTAX IpAddress
                MAX-ACCESS read-only
                STATUS current
                DESCRIPTION "Peer-Address"
                ::= {  staPptpConEntry 7 }

staPptpConIpadd OBJECT-TYPE
                SYNTAX IpAddress
                MAX-ACCESS read-only
                STATUS current
                DESCRIPTION "IP-Address"
                ::= {  staPptpConEntry 8 }

staPptpConDnsde OBJECT-TYPE
                SYNTAX IpAddress
                MAX-ACCESS read-only
                STATUS current
                DESCRIPTION "DNS-Default"
                ::= {  staPptpConEntry 9 }

staPptpConDnsba OBJECT-TYPE
                SYNTAX IpAddress
                MAX-ACCESS read-only
                STATUS current
                DESCRIPTION "DNS-Backup"
                ::= {  staPptpConEntry 12 }

staPptpConNbnsd OBJECT-TYPE
                SYNTAX IpAddress
                MAX-ACCESS read-only
                STATUS current
                DESCRIPTION "NBNS-Default"
                ::= {  staPptpConEntry 10 }

staPptpConNbnsb OBJECT-TYPE
                SYNTAX IpAddress
                MAX-ACCESS read-only
                STATUS current
                DESCRIPTION "NBNS-Backup"
                ::= {  staPptpConEntry 13 }

staPptpConConnt OBJECT-TYPE
                SYNTAX INTEGER (0..2147483647)
                MAX-ACCESS read-only
                STATUS current
                DESCRIPTION "Conn.-time"
                ::= {  staPptpConEntry 14 }

staPptpTun OBJECT-TYPE
           SYNTAX INTEGER
           MAX-ACCESS read-only
           STATUS current
           DESCRIPTION "Tunnel"
           ::= {  staPptp 10 }

staPptpDel OBJECT-TYPE
           SYNTAX DisplayString
           MAX-ACCESS read-write
           STATUS current
           DESCRIPTION "Delete-Values"
           ::= {  staPptp 11 }

staPptpFlo OBJECT-TYPE
           SYNTAX INTEGER
           MAX-ACCESS read-only
           STATUS current
           DESCRIPTION "Flow-Control-Queue"
           ::= {  staPptp 12 }

staLanbr OBJECT IDENTIFIER ::= { sta 31}
staLanbrAddTable OBJECT-TYPE
                 SYNTAX SEQUENCE OF StaLanbrAddEntry
                 MAX-ACCESS not-accessible
                 STATUS current
                 DESCRIPTION "Address-Table"
                 ::= {  staLanbr 1 }

staLanbrAddEntry OBJECT-TYPE
                 SYNTAX StaLanbrAddEntry
                 MAX-ACCESS not-accessible
                 STATUS current
                 DESCRIPTION "entry in table"
                 INDEX { staLanbrAddInd }
                 ::= {  staLanbrAddTable 1 }

StaLanbrAddEntry ::= SEQUENCE {
                 staLanbrAddInd INTEGER,
                 staLanbrAddAge INTEGER,
                 staLanbrAddMac MacAddress,
                 staLanbrAddVla INTEGER,
                 staLanbrAddBri INTEGER,
                 staLanbrAddPor INTEGER,
                 staLanbrAddBrg MacAddress
                }

staLanbrAddInd OBJECT-TYPE
               SYNTAX INTEGER (0..2147483647)
               MAX-ACCESS read-only
               STATUS current
               DESCRIPTION "Index"
               ::= {  staLanbrAddEntry 1 }

staLanbrAddAge OBJECT-TYPE
               SYNTAX INTEGER (0..65535)
               MAX-ACCESS read-only
               STATUS current
               DESCRIPTION "Age"
               ::= {  staLanbrAddEntry 2 }

staLanbrAddMac OBJECT-TYPE
               SYNTAX MacAddress
               MAX-ACCESS read-only
               STATUS current
               DESCRIPTION "MAC-Address"
               ::= {  staLanbrAddEntry 3 }

staLanbrAddVla OBJECT-TYPE
               SYNTAX INTEGER (0..65535)
               MAX-ACCESS read-only
               STATUS current
               DESCRIPTION "VLAN-Id"
               ::= {  staLanbrAddEntry 7 }

staLanbrAddBri OBJECT-TYPE
               SYNTAX INTEGER{
                 brg-1(0),
                 brg-2(1),
                 brg-3(2),
                 brg-4(3),
                 brg-5(4),
                 brg-6(5),
                 brg-7(6),
                 brg-8(7),
                 none(255)
               }
               MAX-ACCESS read-only
               STATUS current
               DESCRIPTION "Bridge-Group"
               ::= {  staLanbrAddEntry 8 }

staLanbrAddPor OBJECT-TYPE
               SYNTAX INTEGER{
                 lan-1(0),
                 wlan-1(1),
                 p2p-1-1(2),
                 p2p-1-2(3),
                 p2p-1-3(4),
                 p2p-1-4(5),
                 p2p-1-5(6),
                 p2p-1-6(7),
                 wlan-1-2(8),
                 wlan-1-3(9),
                 wlan-1-4(10),
                 wlan-1-5(11),
                 wlan-1-6(12),
                 wlan-1-7(13),
                 wlan-1-8(14),
                 brg-1(15),
                 brg-2(16),
                 brg-3(17),
                 brg-4(18),
                 brg-5(19),
                 brg-6(20),
                 brg-7(21),
                 brg-8(22),
                 any(255)
               }
               MAX-ACCESS read-only
               STATUS current
               DESCRIPTION "Port"
               ::= {  staLanbrAddEntry 4 }

staLanbrAddBrg OBJECT-TYPE
               SYNTAX MacAddress
               MAX-ACCESS read-only
               STATUS current
               DESCRIPTION "Brg.-Addr."
               ::= {  staLanbrAddEntry 6 }

staLanbrPorTable OBJECT-TYPE
                 SYNTAX SEQUENCE OF StaLanbrPorEntry
                 MAX-ACCESS not-accessible
                 STATUS current
                 DESCRIPTION "Port-Data"
                 ::= {  staLanbr 11 }

staLanbrPorEntry OBJECT-TYPE
                 SYNTAX StaLanbrPorEntry
                 MAX-ACCESS not-accessible
                 STATUS current
                 DESCRIPTION "entry in table"
                 INDEX { staLanbrPorPor }
                 ::= {  staLanbrPorTable 1 }

StaLanbrPorEntry ::= SEQUENCE {
                 staLanbrPorPor DisplayString,
                 staLanbrPorOpe INTEGER,
                 staLanbrPorPoi INTEGER
                }

staLanbrPorPor OBJECT-TYPE
               SYNTAX DisplayString (SIZE(0..255))
               MAX-ACCESS read-only
               STATUS current
               DESCRIPTION "Port"
               ::= {  staLanbrPorEntry 1 }

staLanbrPorOpe OBJECT-TYPE
               SYNTAX INTEGER{
                 up(1),
                 down(2),
                 testing(3),
                 unknown(4),
                 dormant(5),
                 not-present(6),
                 lower-layer-down(7)
               }
               MAX-ACCESS read-only
               STATUS current
               DESCRIPTION "Operating-State"
               ::= {  staLanbrPorEntry 3 }

staLanbrPorPoi OBJECT-TYPE
               SYNTAX INTEGER{
                 no(0),
                 yes(1)
               }
               MAX-ACCESS read-only
               STATUS current
               DESCRIPTION "Point-To-Point-Port"
               ::= {  staLanbrPorEntry 2 }

staLanbrConTable OBJECT-TYPE
                 SYNTAX SEQUENCE OF StaLanbrConEntry
                 MAX-ACCESS not-accessible
                 STATUS current
                 DESCRIPTION "Connection-Table"
                 ::= {  staLanbr 9 }

staLanbrConEntry OBJECT-TYPE
                 SYNTAX StaLanbrConEntry
                 MAX-ACCESS not-accessible
                 STATUS current
                 DESCRIPTION "entry in table"
                 INDEX { staLanbrConIndex }
                 ::= {  staLanbrConTable 1 }

StaLanbrConEntry ::= SEQUENCE {
                 staLanbrConIndex INTEGER,
                 staLanbrConInterfa INTEGER,
                 staLanbrConProtoco DisplayString,
                 staLanbrConSubprot INTEGER,
                 staLanbrConSourcea IpAddress,
                 staLanbrConSourcep INTEGER,
                 staLanbrConDestpor INTEGER,
                 staLanbrConDestadd IpAddress,
                 staLanbrConDestmac DisplayString,
                 staLanbrConAge INTEGER
                }

staLanbrConIndex OBJECT-TYPE
                   SYNTAX INTEGER (0..2147483647)
                   MAX-ACCESS read-only
                   STATUS current
                   DESCRIPTION "Index"
                   ::= {  staLanbrConEntry 1 }

staLanbrConInterfa OBJECT-TYPE
                   SYNTAX INTEGER{
                     lan-1(0),
                     wlan-1(1),
                     p2p-1-1(2),
                     p2p-1-2(3),
                     p2p-1-3(4),
                     p2p-1-4(5),
                     p2p-1-5(6),
                     p2p-1-6(7),
                     wlan-1-2(8),
                     wlan-1-3(9),
                     wlan-1-4(10),
                     wlan-1-5(11),
                     wlan-1-6(12),
                     wlan-1-7(13),
                     wlan-1-8(14),
                     brg-1(15),
                     brg-2(16),
                     brg-3(17),
                     brg-4(18),
                     brg-5(19),
                     brg-6(20),
                     brg-7(21),
                     brg-8(22),
                     any(255)
                   }
                   MAX-ACCESS read-only
                   STATUS current
                   DESCRIPTION "Interface"
                   ::= {  staLanbrConEntry 2 }

staLanbrConProtoco OBJECT-TYPE
                   SYNTAX DisplayString (SIZE(0..4))
                   MAX-ACCESS read-only
                   STATUS current
                   DESCRIPTION "Protocol"
                   ::= {  staLanbrConEntry 3 }

staLanbrConSubprot OBJECT-TYPE
                   SYNTAX INTEGER (0..65535)
                   MAX-ACCESS read-only
                   STATUS current
                   DESCRIPTION "Sub-Protocol"
                   ::= {  staLanbrConEntry 4 }

staLanbrConSourcea OBJECT-TYPE
                   SYNTAX IpAddress
                   MAX-ACCESS read-only
                   STATUS current
                   DESCRIPTION "Source-Address"
                   ::= {  staLanbrConEntry 5 }

staLanbrConSourcep OBJECT-TYPE
                   SYNTAX INTEGER (0..65535)
                   MAX-ACCESS read-only
                   STATUS current
                   DESCRIPTION "Source-Port"
                   ::= {  staLanbrConEntry 6 }

staLanbrConDestpor OBJECT-TYPE
                   SYNTAX INTEGER (0..65535)
                   MAX-ACCESS read-only
                   STATUS current
                   DESCRIPTION "Dest-Port"
                   ::= {  staLanbrConEntry 7 }

staLanbrConDestadd OBJECT-TYPE
                   SYNTAX IpAddress
                   MAX-ACCESS read-only
                   STATUS current
                   DESCRIPTION "Dest-Address"
                   ::= {  staLanbrConEntry 8 }

staLanbrConDestmac OBJECT-TYPE
                   SYNTAX DisplayString (SIZE(0..12))
                   MAX-ACCESS read-only
                   STATUS current
                   DESCRIPTION "Dest-MAC"
                   ::= {  staLanbrConEntry 9 }

staLanbrConAge OBJECT-TYPE
                   SYNTAX INTEGER (0..2147483647)
                   MAX-ACCESS read-only
                   STATUS current
                   DESCRIPTION "Age"
                   ::= {  staLanbrConEntry 10 }

staLanbrDhcTable OBJECT-TYPE
                 SYNTAX SEQUENCE OF StaLanbrDhcEntry
                 MAX-ACCESS not-accessible
                 STATUS current
                 DESCRIPTION "DHCP-Table"
                 ::= {  staLanbr 10 }

staLanbrDhcEntry OBJECT-TYPE
                 SYNTAX StaLanbrDhcEntry
                 MAX-ACCESS not-accessible
                 STATUS current
                 DESCRIPTION "entry in table"
                 INDEX { staLanbrDhcMac }
                 ::= {  staLanbrDhcTable 1 }

StaLanbrDhcEntry ::= SEQUENCE {
                 staLanbrDhcMac MacAddress,
                 staLanbrDhcPor INTEGER,
                 staLanbrDhcSrc INTEGER,
                 staLanbrDhcIpa IpAddress
                }

staLanbrDhcMac OBJECT-TYPE
               SYNTAX MacAddress
               MAX-ACCESS read-only
               STATUS current
               DESCRIPTION "MAC-Address"
               ::= {  staLanbrDhcEntry 1 }

staLanbrDhcPor OBJECT-TYPE
               SYNTAX INTEGER{
                 lan-1(0),
                 wlan-1(1),
                 p2p-1-1(2),
                 p2p-1-2(3),
                 p2p-1-3(4),
                 p2p-1-4(5),
                 p2p-1-5(6),
                 p2p-1-6(7),
                 wlan-1-2(8),
                 wlan-1-3(9),
                 wlan-1-4(10),
                 wlan-1-5(11),
                 wlan-1-6(12),
                 wlan-1-7(13),
                 wlan-1-8(14),
                 brg-1(15),
                 brg-2(16),
                 brg-3(17),
                 brg-4(18),
                 brg-5(19),
                 brg-6(20),
                 brg-7(21),
                 brg-8(22),
                 any(255)
               }
               MAX-ACCESS read-only
               STATUS current
               DESCRIPTION "Port"
               ::= {  staLanbrDhcEntry 2 }

staLanbrDhcSrc OBJECT-TYPE
               SYNTAX INTEGER{
                 lan-1(0),
                 wlan-1(1),
                 p2p-1-1(2),
                 p2p-1-2(3),
                 p2p-1-3(4),
                 p2p-1-4(5),
                 p2p-1-5(6),
                 p2p-1-6(7),
                 wlan-1-2(8),
                 wlan-1-3(9),
                 wlan-1-4(10),
                 wlan-1-5(11),
                 wlan-1-6(12),
                 wlan-1-7(13),
                 wlan-1-8(14),
                 brg-1(15),
                 brg-2(16),
                 brg-3(17),
                 brg-4(18),
                 brg-5(19),
                 brg-6(20),
                 brg-7(21),
                 brg-8(22),
                 any(255)
               }
               MAX-ACCESS read-only
               STATUS current
               DESCRIPTION "Src-Port"
               ::= {  staLanbrDhcEntry 3 }

staLanbrDhcIpa OBJECT-TYPE
               SYNTAX IpAddress
               MAX-ACCESS read-only
               STATUS current
               DESCRIPTION "IP-Address"
               ::= {  staLanbrDhcEntry 4 }

staLanbrSpa OBJECT IDENTIFIER ::= { staLanbr 20}
staLanbrSpaOperati OBJECT-TYPE
                   SYNTAX INTEGER {
                     no(0),
                     yes(1)
                   }
                   MAX-ACCESS read-only
                   STATUS current
                   DESCRIPTION "Operating"
                   ::= {  staLanbrSpa 1 }

staLanbrSpaBridgei OBJECT-TYPE
                   SYNTAX DisplayString (SIZE(0..20))
                   MAX-ACCESS read-only
                   STATUS current
                   DESCRIPTION "Bridge-ID"
                   ::= {  staLanbrSpa 2 }

staLanbrSpaRootbri OBJECT-TYPE
                   SYNTAX DisplayString (SIZE(0..20))
                   MAX-ACCESS read-only
                   STATUS current
                   DESCRIPTION "Root-Bridge"
                   ::= {  staLanbrSpa 3 }

staLanbrSpaRootpor OBJECT-TYPE
                   SYNTAX INTEGER {
                     lan-1(0),
                     wlan-1(1),
                     p2p-1-1(2),
                     p2p-1-2(3),
                     p2p-1-3(4),
                     p2p-1-4(5),
                     p2p-1-5(6),
                     p2p-1-6(7),
                     wlan-1-2(8),
                     wlan-1-3(9),
                     wlan-1-4(10),
                     wlan-1-5(11),
                     wlan-1-6(12),
                     wlan-1-7(13),
                     wlan-1-8(14),
                     brg-1(15),
                     brg-2(16),
                     brg-3(17),
                     brg-4(18),
                     brg-5(19),
                     brg-6(20),
                     brg-7(21),
                     brg-8(22),
                     is-root-bridge(255)
                   }
                   MAX-ACCESS read-only
                   STATUS current
                   DESCRIPTION "Root-Port"
                   ::= {  staLanbrSpa 4 }

staLanbrSpaRootpat OBJECT-TYPE
                   SYNTAX INTEGER
                   MAX-ACCESS read-only
                   STATUS current
                   DESCRIPTION "Root-Path-Cost"
                   ::= {  staLanbrSpa 5 }

staLanbrSpaPorttabTable OBJECT-TYPE
                        SYNTAX SEQUENCE OF StaLanbrSpaPorttabEntry
                        MAX-ACCESS not-accessible
                        STATUS current
                        DESCRIPTION "Port-Table"
                        ::= {  staLanbrSpa 6 }

staLanbrSpaPorttabEntry OBJECT-TYPE
                        SYNTAX StaLanbrSpaPorttabEntry
                        MAX-ACCESS not-accessible
                        STATUS current
                        DESCRIPTION "entry in table"
                        INDEX { staLanbrSpaPorttabDes }
                        ::= {  staLanbrSpaPorttabTable 1 }

StaLanbrSpaPorttabEntry ::= SEQUENCE {
                        staLanbrSpaPorttabDes DisplayString,
                        staLanbrSpaPorttabPri INTEGER,
                        staLanbrSpaPorttabSta INTEGER,
                        staLanbrSpaPorttabRoo DisplayString,
                        staLanbrSpaPorttabBri DisplayString,
                        staLanbrSpaPorttabPat INTEGER
                       }

staLanbrSpaPorttabDes OBJECT-TYPE
                      SYNTAX DisplayString (SIZE(0..12))
                      MAX-ACCESS read-only
                      STATUS current
                      DESCRIPTION "Description"
                      ::= {  staLanbrSpaPorttabEntry 1 }

staLanbrSpaPorttabPri OBJECT-TYPE
                      SYNTAX INTEGER (0..255)
                      MAX-ACCESS read-only
                      STATUS current
                      DESCRIPTION "Priority"
                      ::= {  staLanbrSpaPorttabEntry 2 }

staLanbrSpaPorttabSta OBJECT-TYPE
                      SYNTAX INTEGER{
                        disabled(0),
                        listening(1),
                        learning(2),
                        forwarding(3),
                        blocking(4)
                      }
                      MAX-ACCESS read-only
                      STATUS current
                      DESCRIPTION "State"
                      ::= {  staLanbrSpaPorttabEntry 3 }

staLanbrSpaPorttabRoo OBJECT-TYPE
                      SYNTAX DisplayString (SIZE(0..16))
                      MAX-ACCESS read-only
                      STATUS current
                      DESCRIPTION "Root"
                      ::= {  staLanbrSpaPorttabEntry 4 }

staLanbrSpaPorttabBri OBJECT-TYPE
                      SYNTAX DisplayString (SIZE(0..16))
                      MAX-ACCESS read-only
                      STATUS current
                      DESCRIPTION "Bridge"
                      ::= {  staLanbrSpaPorttabEntry 5 }

staLanbrSpaPorttabPat OBJECT-TYPE
                      SYNTAX INTEGER (0..2147483647)
                      MAX-ACCESS read-only
                      STATUS current
                      DESCRIPTION "Path-Cost"
                      ::= {  staLanbrSpaPorttabEntry 6 }

staLanbrSpaProtoco OBJECT-TYPE
                   SYNTAX INTEGER {
                     classic(0),
                     rapid(1)
                   }
                   MAX-ACCESS read-only
                   STATUS current
                   DESCRIPTION "Protocol-Version"
                   ::= {  staLanbrSpa 7 }

staLanbrSpaPathcos OBJECT-TYPE
                   SYNTAX INTEGER {
                     classic(0),
                     rapid(1)
                   }
                   MAX-ACCESS read-only
                   STATUS current
                   DESCRIPTION "Path-Cost-Computation"
                   ::= {  staLanbrSpa 8 }

staLanbrSpaBridgep OBJECT-TYPE
                   SYNTAX INTEGER
                   MAX-ACCESS read-only
                   STATUS current
                   DESCRIPTION "Bridge-Priority"
                   ::= {  staLanbrSpa 9 }

staLanbrSpaRstpporTable OBJECT-TYPE
                        SYNTAX SEQUENCE OF StaLanbrSpaRstpporEntry
                        MAX-ACCESS not-accessible
                        STATUS current
                        DESCRIPTION "RSTP-Port-Table"
                        ::= {  staLanbrSpa 10 }

staLanbrSpaRstpporEntry OBJECT-TYPE
                        SYNTAX StaLanbrSpaRstpporEntry
                        MAX-ACCESS not-accessible
                        STATUS current
                        DESCRIPTION "entry in table"
                        INDEX { staLanbrSpaRstpporDes }
                        ::= {  staLanbrSpaRstpporTable 1 }

StaLanbrSpaRstpporEntry ::= SEQUENCE {
                        staLanbrSpaRstpporDes DisplayString,
                        staLanbrSpaRstpporRol INTEGER,
                        staLanbrSpaRstpporLea INTEGER,
                        staLanbrSpaRstpporFor INTEGER,
                        staLanbrSpaRstpporEdg INTEGER,
                        staLanbrSpaRstpporPro INTEGER,
                        staLanbrSpaRstpporPat INTEGER
                       }

staLanbrSpaRstpporDes OBJECT-TYPE
                      SYNTAX DisplayString (SIZE(0..255))
                      MAX-ACCESS read-only
                      STATUS current
                      DESCRIPTION "Description"
                      ::= {  staLanbrSpaRstpporEntry 1 }

staLanbrSpaRstpporRol OBJECT-TYPE
                      SYNTAX INTEGER{
                        root(0),
                        designated(1),
                        alternate(2),
                        backup(3),
                        disabled(4)
                      }
                      MAX-ACCESS read-only
                      STATUS current
                      DESCRIPTION "Role"
                      ::= {  staLanbrSpaRstpporEntry 2 }

staLanbrSpaRstpporLea OBJECT-TYPE
                      SYNTAX INTEGER{
                        no(0),
                        yes(1)
                      }
                      MAX-ACCESS read-only
                      STATUS current
                      DESCRIPTION "Learning"
                      ::= {  staLanbrSpaRstpporEntry 3 }

staLanbrSpaRstpporFor OBJECT-TYPE
                      SYNTAX INTEGER{
                        no(0),
                        yes(1)
                      }
                      MAX-ACCESS read-only
                      STATUS current
                      DESCRIPTION "Forwarding"
                      ::= {  staLanbrSpaRstpporEntry 4 }

staLanbrSpaRstpporEdg OBJECT-TYPE
                      SYNTAX INTEGER{
                        no(0),
                        yes(1)
                      }
                      MAX-ACCESS read-only
                      STATUS current
                      DESCRIPTION "Edge-Port"
                      ::= {  staLanbrSpaRstpporEntry 5 }

staLanbrSpaRstpporPro OBJECT-TYPE
                      SYNTAX INTEGER{
                        classic(0),
                        rapid(1)
                      }
                      MAX-ACCESS read-only
                      STATUS current
                      DESCRIPTION "Protocol-Version"
                      ::= {  staLanbrSpaRstpporEntry 6 }

staLanbrSpaRstpporPat OBJECT-TYPE
                      SYNTAX INTEGER (0..2147483647)
                      MAX-ACCESS read-only
                      STATUS current
                      DESCRIPTION "Path-Cost"
                      ::= {  staLanbrSpaRstpporEntry 7 }

staDhcpc OBJECT IDENTIFIER ::= { sta 32}
staDhcpcWanTable OBJECT-TYPE
                 SYNTAX SEQUENCE OF StaDhcpcWanEntry
                 MAX-ACCESS not-accessible
                 STATUS current
                 DESCRIPTION "WAN-IP-List"
                 ::= {  staDhcpc 20 }

staDhcpcWanEntry OBJECT-TYPE
                 SYNTAX StaDhcpcWanEntry
                 MAX-ACCESS not-accessible
                 STATUS current
                 DESCRIPTION "entry in table"
                 INDEX { staDhcpcWanIfc }
                 ::= {  staDhcpcWanTable 1 }

StaDhcpcWanEntry ::= SEQUENCE {
                 staDhcpcWanIfc INTEGER,
                 staDhcpcWanIpadd IpAddress,
                 staDhcpcWanIpnet IpAddress,
                 staDhcpcWanGatew IpAddress,
                 staDhcpcWanDnsde IpAddress,
                 staDhcpcWanDnsba IpAddress,
                 staDhcpcWanNbnsd IpAddress,
                 staDhcpcWanNbnsb IpAddress,
                 staDhcpcWanDomai DisplayString,
                 staDhcpcWanDhcps IpAddress
                }

staDhcpcWanIfc OBJECT-TYPE
                 SYNTAX INTEGER{
                   dsl-ch-1(1),
                   ext(2)
                 }
                 MAX-ACCESS read-only
                 STATUS current
                 DESCRIPTION "Ifc"
                 ::= {  staDhcpcWanEntry 1 }

staDhcpcWanIpadd OBJECT-TYPE
                 SYNTAX IpAddress
                 MAX-ACCESS read-only
                 STATUS current
                 DESCRIPTION "IP-Address"
                 ::= {  staDhcpcWanEntry 2 }

staDhcpcWanIpnet OBJECT-TYPE
                 SYNTAX IpAddress
                 MAX-ACCESS read-only
                 STATUS current
                 DESCRIPTION "IP-Netmask"
                 ::= {  staDhcpcWanEntry 3 }

staDhcpcWanGatew OBJECT-TYPE
                 SYNTAX IpAddress
                 MAX-ACCESS read-only
                 STATUS current
                 DESCRIPTION "Gateway"
                 ::= {  staDhcpcWanEntry 4 }

staDhcpcWanDnsde OBJECT-TYPE
                 SYNTAX IpAddress
                 MAX-ACCESS read-only
                 STATUS current
                 DESCRIPTION "DNS-Default"
                 ::= {  staDhcpcWanEntry 5 }

staDhcpcWanDnsba OBJECT-TYPE
                 SYNTAX IpAddress
                 MAX-ACCESS read-only
                 STATUS current
                 DESCRIPTION "DNS-Backup"
                 ::= {  staDhcpcWanEntry 6 }

staDhcpcWanNbnsd OBJECT-TYPE
                 SYNTAX IpAddress
                 MAX-ACCESS read-only
                 STATUS current
                 DESCRIPTION "NBNS-Default"
                 ::= {  staDhcpcWanEntry 7 }

staDhcpcWanNbnsb OBJECT-TYPE
                 SYNTAX IpAddress
                 MAX-ACCESS read-only
                 STATUS current
                 DESCRIPTION "NBNS-Backup"
                 ::= {  staDhcpcWanEntry 8 }

staDhcpcWanDomai OBJECT-TYPE
                 SYNTAX DisplayString (SIZE(0..255))
                 MAX-ACCESS read-only
                 STATUS current
                 DESCRIPTION "Domain"
                 ::= {  staDhcpcWanEntry 10 }

staDhcpcWanDhcps OBJECT-TYPE
                 SYNTAX IpAddress
                 MAX-ACCESS read-only
                 STATUS current
                 DESCRIPTION "DHCP-server"
                 ::= {  staDhcpcWanEntry 9 }

staDhcpcLanTable OBJECT-TYPE
                 SYNTAX SEQUENCE OF StaDhcpcLanEntry
                 MAX-ACCESS not-accessible
                 STATUS current
                 DESCRIPTION "LAN-IP-List"
                 ::= {  staDhcpc 21 }

staDhcpcLanEntry OBJECT-TYPE
                 SYNTAX StaDhcpcLanEntry
                 MAX-ACCESS not-accessible
                 STATUS current
                 DESCRIPTION "entry in table"
                 INDEX { staDhcpcLanIfc }
                 ::= {  staDhcpcLanTable 1 }

StaDhcpcLanEntry ::= SEQUENCE {
                 staDhcpcLanIfc DisplayString,
                 staDhcpcLanIpadd IpAddress,
                 staDhcpcLanIpnet IpAddress,
                 staDhcpcLanGatew IpAddress,
                 staDhcpcLanDnsde IpAddress,
                 staDhcpcLanDnsba IpAddress,
                 staDhcpcLanNbnsd IpAddress,
                 staDhcpcLanNbnsb IpAddress,
                 staDhcpcLanDomai DisplayString,
                 staDhcpcLanDhcps IpAddress
                }

staDhcpcLanIfc OBJECT-TYPE
                 SYNTAX DisplayString (SIZE(0..16))
                 MAX-ACCESS read-only
                 STATUS current
                 DESCRIPTION "Ifc"
                 ::= {  staDhcpcLanEntry 1 }

staDhcpcLanIpadd OBJECT-TYPE
                 SYNTAX IpAddress
                 MAX-ACCESS read-only
                 STATUS current
                 DESCRIPTION "IP-Address"
                 ::= {  staDhcpcLanEntry 2 }

staDhcpcLanIpnet OBJECT-TYPE
                 SYNTAX IpAddress
                 MAX-ACCESS read-only
                 STATUS current
                 DESCRIPTION "IP-Netmask"
                 ::= {  staDhcpcLanEntry 3 }

staDhcpcLanGatew OBJECT-TYPE
                 SYNTAX IpAddress
                 MAX-ACCESS read-only
                 STATUS current
                 DESCRIPTION "Gateway"
                 ::= {  staDhcpcLanEntry 4 }

staDhcpcLanDnsde OBJECT-TYPE
                 SYNTAX IpAddress
                 MAX-ACCESS read-only
                 STATUS current
                 DESCRIPTION "DNS-Default"
                 ::= {  staDhcpcLanEntry 5 }

staDhcpcLanDnsba OBJECT-TYPE
                 SYNTAX IpAddress
                 MAX-ACCESS read-only
                 STATUS current
                 DESCRIPTION "DNS-Backup"
                 ::= {  staDhcpcLanEntry 6 }

staDhcpcLanNbnsd OBJECT-TYPE
                 SYNTAX IpAddress
                 MAX-ACCESS read-only
                 STATUS current
                 DESCRIPTION "NBNS-Default"
                 ::= {  staDhcpcLanEntry 7 }

staDhcpcLanNbnsb OBJECT-TYPE
                 SYNTAX IpAddress
                 MAX-ACCESS read-only
                 STATUS current
                 DESCRIPTION "NBNS-Backup"
                 ::= {  staDhcpcLanEntry 8 }

staDhcpcLanDomai OBJECT-TYPE
                 SYNTAX DisplayString (SIZE(0..255))
                 MAX-ACCESS read-only
                 STATUS current
                 DESCRIPTION "Domain"
                 ::= {  staDhcpcLanEntry 10 }

staDhcpcLanDhcps OBJECT-TYPE
                 SYNTAX IpAddress
                 MAX-ACCESS read-only
                 STATUS current
                 DESCRIPTION "DHCP-server"
                 ::= {  staDhcpcLanEntry 9 }

staSnmp OBJECT IDENTIFIER ::= { sta 35}
staSnmpEveTable OBJECT-TYPE
                SYNTAX SEQUENCE OF StaSnmpEveEntry
                MAX-ACCESS not-accessible
                STATUS current
                DESCRIPTION "Event"
                ::= {  staSnmp 1 }

staSnmpEveEntry OBJECT-TYPE
                SYNTAX StaSnmpEveEntry
                MAX-ACCESS not-accessible
                STATUS current
                DESCRIPTION "entry in table"
                INDEX { staSnmpEveTra, staSnmpEveVen }
                ::= {  staSnmpEveTable 1 }

StaSnmpEveEntry ::= SEQUENCE {
                staSnmpEveTra INTEGER,
                staSnmpEveVen INTEGER,
                staSnmpEveCou INTEGER
               }

staSnmpEveTra OBJECT-TYPE
              SYNTAX INTEGER{
                coldstart(255),
                warmstart(1),
                linkdown(2),
                linkup(3),
                authfail(4),
                epgnloss(5),
                enterprise(6)
              }
              MAX-ACCESS read-only
              STATUS current
              DESCRIPTION "Trap-Name"
              ::= {  staSnmpEveEntry 1 }

staSnmpEveVen OBJECT-TYPE
              SYNTAX INTEGER{
                fwuplstart(4),
                uplsucc(5),
                uplfailto(6),
                uplfailincl(7),
                uplfailbaddev(8),
                login(9),
                logout(10),
                cnfuplstart(11),
                cnfdnlstart(12),
                cnfdnlsucc(13),
                errlogin(29),
                pptpconn(28),
                pppoesconn(39),
                http-tunnel-open(2000),
                http-tunnel-close(2001),
                ipfwflt(26),
                vrrp(41),
                bssscan(14),
                bssstart(15),
                bssjoin(16),
                assrej(22),
                cardhung(25),
                keyhandshake-timeout(33),
                cl-lostconn(55),
                cl-authfail(56),
                cl-assocfail(57),
                cl-802-1x-fail(59),
                cl-connected(58),
                exceirp(42),
                authstation(17),
                deauthstation(18),
                assstation(19),
                reassstation(20),
                disassstation(21),
                macchkfail(52),
                connected(54),
                roamed(53),
                idle-timeout(46),
                supervision(35),
                admin-deassoc(47),
                spgtree-portstatchg(1000),
                spgtree-rootportchg(1002),
                spgtree-rstpstatchg(1001),
                statchan(1)
              }
              MAX-ACCESS read-only
              STATUS current
              DESCRIPTION "Vendor-Name"
              ::= {  staSnmpEveEntry 2 }

staSnmpEveCou OBJECT-TYPE
              SYNTAX INTEGER (0..2147483647)
              MAX-ACCESS read-only
              STATUS current
              DESCRIPTION "Count"
              ::= {  staSnmpEveEntry 3 }

staMail OBJECT IDENTIFIER ::= { sta 43}
staMailBuf OBJECT-TYPE
           SYNTAX INTEGER
           MAX-ACCESS read-only
           STATUS current
           DESCRIPTION "Buffered-Mails"
           ::= {  staMail 1 }

staMailSen OBJECT-TYPE
           SYNTAX Counter32
           MAX-ACCESS read-only
           STATUS current
           DESCRIPTION "Sent-Mails"
           ::= {  staMail 2 }

staMailDis OBJECT-TYPE
           SYNTAX Counter32
           MAX-ACCESS read-only
           STATUS current
           DESCRIPTION "Discarded-Mails"
           ::= {  staMail 3 }

staMailCle OBJECT-TYPE
           SYNTAX DisplayString
           MAX-ACCESS read-write
           STATUS current
           DESCRIPTION "Clear-Buffer"
           ::= {  staMail 4 }

staMailDel OBJECT-TYPE
           SYNTAX DisplayString
           MAX-ACCESS read-write
           STATUS current
           DESCRIPTION "Delete-Statistics"
           ::= {  staMail 5 }

staIeee8 OBJECT IDENTIFIER ::= { sta 46}
staIeee8StaTable OBJECT-TYPE
                 SYNTAX SEQUENCE OF StaIeee8StaEntry
                 MAX-ACCESS not-accessible
                 STATUS current
                 DESCRIPTION "Station-Table"
                 ::= {  staIeee8 1 }

staIeee8StaEntry OBJECT-TYPE
                 SYNTAX StaIeee8StaEntry
                 MAX-ACCESS not-accessible
                 STATUS current
                 DESCRIPTION "entry in table"
                 INDEX { staIeee8StaMacad }
                 ::= {  staIeee8StaTable 1 }

StaIeee8StaEntry ::= SEQUENCE {
                 staIeee8StaMacad DisplayString,
                 staIeee8StaAuthi DisplayString,
                 staIeee8StaCommi DisplayString,
                 staIeee8StaSessi DisplayString,
                 staIeee8StaPortm INTEGER,
                 staIeee8StaPorts INTEGER,
                 staIeee8StaUsern DisplayString,
                 staIeee8StaReply DisplayString
                }

staIeee8StaMacad OBJECT-TYPE
                 SYNTAX DisplayString (SIZE(0..12))
                 MAX-ACCESS read-only
                 STATUS current
                 DESCRIPTION "MAC-Address"
                 ::= {  staIeee8StaEntry 1 }

staIeee8StaAuthi OBJECT-TYPE
                 SYNTAX DisplayString (SIZE(0..255))
                 MAX-ACCESS read-only
                 STATUS current
                 DESCRIPTION "Auth-Ifc"
                 ::= {  staIeee8StaEntry 2 }

staIeee8StaCommi OBJECT-TYPE
                 SYNTAX DisplayString (SIZE(0..255))
                 MAX-ACCESS read-only
                 STATUS current
                 DESCRIPTION "Comm-Ifc"
                 ::= {  staIeee8StaEntry 8 }

staIeee8StaSessi OBJECT-TYPE
                 SYNTAX DisplayString (SIZE(0..8))
                 MAX-ACCESS read-only
                 STATUS current
                 DESCRIPTION "Session-Id"
                 ::= {  staIeee8StaEntry 3 }

staIeee8StaPortm OBJECT-TYPE
                 SYNTAX INTEGER{
                   force-unauth(0),
                   force-auth(1),
                   auto(2)
                 }
                 MAX-ACCESS read-only
                 STATUS current
                 DESCRIPTION "Port-Mode"
                 ::= {  staIeee8StaEntry 4 }

staIeee8StaPorts OBJECT-TYPE
                 SYNTAX INTEGER{
                   unauthorized(0),
                   authorized(1)
                 }
                 MAX-ACCESS read-only
                 STATUS current
                 DESCRIPTION "Port-Status"
                 ::= {  staIeee8StaEntry 5 }

staIeee8StaUsern OBJECT-TYPE
                 SYNTAX DisplayString (SIZE(0..255))
                 MAX-ACCESS read-only
                 STATUS current
                 DESCRIPTION "User-Name"
                 ::= {  staIeee8StaEntry 6 }

staIeee8StaReply OBJECT-TYPE
                 SYNTAX DisplayString (SIZE(0..255))
                 MAX-ACCESS read-only
                 STATUS current
                 DESCRIPTION "Reply-Msg"
                 ::= {  staIeee8StaEntry 7 }

staHardw OBJECT IDENTIFIER ::= { sta 47}
staHardwMode OBJECT-TYPE
             SYNTAX DisplayString (SIZE(0..64))
             MAX-ACCESS read-only
             STATUS current
             DESCRIPTION "Model-Number"
             ::= {  staHardw 6 }

staHardwSeri OBJECT-TYPE
             SYNTAX DisplayString (SIZE(0..12))
             MAX-ACCESS read-only
             STATUS current
             DESCRIPTION "Serial-Number"
             ::= {  staHardw 7 }

staHardwBoar OBJECT-TYPE
             SYNTAX DisplayString (SIZE(0..1))
             MAX-ACCESS read-only
             STATUS current
             DESCRIPTION "Board-Revision"
             ::= {  staHardw 8 }

staHardwCput OBJECT-TYPE
             SYNTAX DisplayString (SIZE(0..39))
             MAX-ACCESS read-only
             STATUS current
             DESCRIPTION "CPU-Type"
             ::= {  staHardw 1 }

staHardwCpuc OBJECT-TYPE
             SYNTAX INTEGER
             MAX-ACCESS read-only
             STATUS current
             DESCRIPTION "CPU-Clock-MHz"
             ::= {  staHardw 2 }

staHardwCpul OBJECT-TYPE
             SYNTAX INTEGER
             MAX-ACCESS read-only
             STATUS current
             DESCRIPTION "CPU-Load-Percent"
             ::= {  staHardw 3 }

staHardwTota OBJECT-TYPE
             SYNTAX INTEGER
             MAX-ACCESS read-only
             STATUS current
             DESCRIPTION "Total-Memory-KBytes"
             ::= {  staHardw 4 }

staHardwFree OBJECT-TYPE
             SYNTAX INTEGER
             MAX-ACCESS read-only
             STATUS current
             DESCRIPTION "Free-Memory-KBytes"
             ::= {  staHardw 5 }

staHardwSwve OBJECT-TYPE
             SYNTAX DisplayString (SIZE(0..39))
             MAX-ACCESS read-only
             STATUS current
             DESCRIPTION "SW-Version"
             ::= {  staHardw 9 }

staHardwPcidTable OBJECT-TYPE
                  SYNTAX SEQUENCE OF StaHardwPcidEntry
                  MAX-ACCESS not-accessible
                  STATUS current
                  DESCRIPTION "PCI-Device-List"
                  ::= {  staHardw 30 }

staHardwPcidEntry OBJECT-TYPE
                  SYNTAX StaHardwPcidEntry
                  MAX-ACCESS not-accessible
                  STATUS current
                  DESCRIPTION "entry in table"
                  INDEX { staHardwPcidIndex }
                  ::= {  staHardwPcidTable 1 }

StaHardwPcidEntry ::= SEQUENCE {
                  staHardwPcidIndex INTEGER,
                  staHardwPcidBus INTEGER,
                  staHardwPcidDevice INTEGER,
                  staHardwPcidFunctio INTEGER,
                  staHardwPcidDevicei DisplayString,
                  staHardwPcidSubsyst DisplayString,
                  staHardwPcidClass INTEGER
                 }

staHardwPcidIndex OBJECT-TYPE
                    SYNTAX INTEGER (0..255)
                    MAX-ACCESS read-only
                    STATUS current
                    DESCRIPTION "Index"
                    ::= {  staHardwPcidEntry 1 }

staHardwPcidBus OBJECT-TYPE
                    SYNTAX INTEGER (0..2147483647)
                    MAX-ACCESS read-only
                    STATUS current
                    DESCRIPTION "Bus"
                    ::= {  staHardwPcidEntry 2 }

staHardwPcidDevice OBJECT-TYPE
                    SYNTAX INTEGER (0..2147483647)
                    MAX-ACCESS read-only
                    STATUS current
                    DESCRIPTION "Device"
                    ::= {  staHardwPcidEntry 3 }

staHardwPcidFunctio OBJECT-TYPE
                    SYNTAX INTEGER (0..2147483647)
                    MAX-ACCESS read-only
                    STATUS current
                    DESCRIPTION "Function"
                    ::= {  staHardwPcidEntry 4 }

staHardwPcidDevicei OBJECT-TYPE
                    SYNTAX DisplayString (SIZE(0..255))
                    MAX-ACCESS read-only
                    STATUS current
                    DESCRIPTION "Device-ID"
                    ::= {  staHardwPcidEntry 5 }

staHardwPcidSubsyst OBJECT-TYPE
                    SYNTAX DisplayString (SIZE(0..255))
                    MAX-ACCESS read-only
                    STATUS current
                    DESCRIPTION "Subsystem-ID"
                    ::= {  staHardwPcidEntry 6 }

staHardwPcidClass OBJECT-TYPE
                    SYNTAX INTEGER{
                      ethernet(131072),
                      token-ring(131328),
                      network(163840),
                      cardbus-bridge(395008),
                      isa-bridge(393472),
                      usb-uhci(787200),
                      usb-ohci(787216),
                      usb-ehci(787232),
                      ohci1394(786448)
                    }
                    MAX-ACCESS read-only
                    STATUS current
                    DESCRIPTION "Class"
                    ::= {  staHardwPcidEntry 7 }

staChannTable OBJECT-TYPE
              SYNTAX SEQUENCE OF StaChannEntry
              MAX-ACCESS not-accessible
              STATUS current
              DESCRIPTION "Channel"
              ::= {  sta 48 }

staChannEntry OBJECT-TYPE
              SYNTAX StaChannEntry
              MAX-ACCESS not-accessible
              STATUS current
              DESCRIPTION "entry in table"
              INDEX { staChannChan }
              ::= {  staChannTable 1 }

StaChannEntry ::= SEQUENCE {
              staChannChan INTEGER,
              staChannPhcha INTEGER,
              staChannPlci INTEGER,
              staChannBus INTEGER,
              staChannState INTEGER,
              staChannApp INTEGER,
              staChannMode INTEGER,
              staChannCause INTEGER,
              staChannNumbe DisplayString,
              staChannSubad INTEGER,
              staChannCharg INTEGER,
              staChannConns INTEGER,
              staChannConnt INTEGER,
              staChannExtra DisplayString,
              staChannIsdnd DisplayString,
              staChannPptpc INTEGER
             }

staChannChan OBJECT-TYPE
              SYNTAX INTEGER{
                dsl-err(1),
                dsl-line(2),
                ext-err(3),
                ext(4)
              }
              MAX-ACCESS read-only
              STATUS current
              DESCRIPTION "Chan."
              ::= {  staChannEntry 1 }

staChannPhcha OBJECT-TYPE
              SYNTAX INTEGER (0..2147483647)
              MAX-ACCESS read-only
              STATUS current
              DESCRIPTION "Ph.-Chan."
              ::= {  staChannEntry 15 }

staChannPlci OBJECT-TYPE
              SYNTAX INTEGER (0..2147483647)
              MAX-ACCESS read-only
              STATUS current
              DESCRIPTION "PLCI"
              ::= {  staChannEntry 2 }

staChannBus OBJECT-TYPE
              SYNTAX INTEGER (0..2147483647)
              MAX-ACCESS read-only
              STATUS current
              DESCRIPTION "Bus"
              ::= {  staChannEntry 3 }

staChannState OBJECT-TYPE
              SYNTAX INTEGER (0..2147483647)
              MAX-ACCESS read-only
              STATUS current
              DESCRIPTION "State"
              ::= {  staChannEntry 4 }

staChannApp OBJECT-TYPE
              SYNTAX INTEGER{
                none(0),
                router(1),
                capi(2),
                a-b(3),
                time-module(255)
              }
              MAX-ACCESS read-only
              STATUS current
              DESCRIPTION "App"
              ::= {  staChannEntry 5 }

staChannMode OBJECT-TYPE
              SYNTAX INTEGER{
                unk(0),
                act(1),
                pas(2),
                perm(3)
              }
              MAX-ACCESS read-only
              STATUS current
              DESCRIPTION "Mode"
              ::= {  staChannEntry 6 }

staChannCause OBJECT-TYPE
              SYNTAX INTEGER (0..65535)
              MAX-ACCESS read-write
              STATUS current
              DESCRIPTION "Cause"
              ::= {  staChannEntry 7 }

staChannNumbe OBJECT-TYPE
              SYNTAX DisplayString (SIZE(0..40))
              MAX-ACCESS read-only
              STATUS current
              DESCRIPTION "Number"
              ::= {  staChannEntry 8 }

staChannSubad OBJECT-TYPE
              SYNTAX INTEGER (0..2147483647)
              MAX-ACCESS read-only
              STATUS current
              DESCRIPTION "Subaddress"
              ::= {  staChannEntry 9 }

staChannCharg OBJECT-TYPE
              SYNTAX INTEGER (0..2147483647)
              MAX-ACCESS read-only
              STATUS current
              DESCRIPTION "Charge"
              ::= {  staChannEntry 10 }

staChannConns OBJECT-TYPE
              SYNTAX INTEGER (0..2147483647)
              MAX-ACCESS read-only
              STATUS current
              DESCRIPTION "Conn.-start"
              ::= {  staChannEntry 13 }

staChannConnt OBJECT-TYPE
              SYNTAX INTEGER (0..2147483647)
              MAX-ACCESS read-only
              STATUS current
              DESCRIPTION "Conn.-time"
              ::= {  staChannEntry 12 }

staChannExtra OBJECT-TYPE
              SYNTAX DisplayString (SIZE(0..16))
              MAX-ACCESS read-only
              STATUS current
              DESCRIPTION "Extra"
              ::= {  staChannEntry 11 }

staChannIsdnd OBJECT-TYPE
              SYNTAX DisplayString (SIZE(0..34))
              MAX-ACCESS read-only
              STATUS current
              DESCRIPTION "ISDN-display"
              ::= {  staChannEntry 14 }

staChannPptpc OBJECT-TYPE
              SYNTAX INTEGER (0..2147483647)
              MAX-ACCESS read-only
              STATUS current
              DESCRIPTION "PPTP-Conns."
              ::= {  staChannEntry 16 }

staUmtsm OBJECT IDENTIFIER ::= { sta 49}
staUmtsmOpe OBJECT-TYPE
            SYNTAX INTEGER {
              no(0),
              modem(1)
            }
            MAX-ACCESS read-only
            STATUS current
            DESCRIPTION "Operating"
            ::= {  staUmtsm 4 }

staUmtsmMod OBJECT-TYPE
            SYNTAX DisplayString (SIZE(0..255))
            MAX-ACCESS read-only
            STATUS current
            DESCRIPTION "Modem-Info"
            ::= {  staUmtsm 1 }

staUmtsmCon OBJECT-TYPE
            SYNTAX DisplayString (SIZE(0..63))
            MAX-ACCESS read-only
            STATUS current
            DESCRIPTION "Connect-Info"
            ::= {  staUmtsm 2 }

staUmtsmSta OBJECT-TYPE
            SYNTAX INTEGER {
              wait-for-device(15),
              deactivated(0),
              device-detection(1),
              reset(2),
              initializing(3),
              modem-id(4),
              ready(5),
              connecting(6),
              pass-connecting(7),
              data-mode(8)
            }
            MAX-ACCESS read-only
            STATUS current
            DESCRIPTION "State"
            ::= {  staUmtsm 3 }

staUmtsmDat OBJECT-TYPE
            SYNTAX INTEGER
            MAX-ACCESS read-only
            STATUS current
            DESCRIPTION "Data-Rate"
            ::= {  staUmtsm 5 }

staUmtsmDro OBJECT-TYPE
            SYNTAX INTEGER
            MAX-ACCESS read-only
            STATUS current
            DESCRIPTION "Dropped-Tx-packets"
            ::= {  staUmtsm 14 }

staUmtsmRxt OBJECT-TYPE
            SYNTAX INTEGER
            MAX-ACCESS read-only
            STATUS current
            DESCRIPTION "Rx-Timeouts"
            ::= {  staUmtsm 22 }

staFiles OBJECT IDENTIFIER ::= { sta 50}
staFilesConTable OBJECT-TYPE
                 SYNTAX SEQUENCE OF StaFilesConEntry
                 MAX-ACCESS not-accessible
                 STATUS current
                 DESCRIPTION "Contents"
                 ::= {  staFiles 1 }

staFilesConEntry OBJECT-TYPE
                 SYNTAX StaFilesConEntry
                 MAX-ACCESS not-accessible
                 STATUS current
                 DESCRIPTION "entry in table"
                 INDEX { staFilesConNam }
                 ::= {  staFilesConTable 1 }

StaFilesConEntry ::= SEQUENCE {
                 staFilesConNam DisplayString,
                 staFilesConSiz INTEGER
                }

staFilesConNam OBJECT-TYPE
               SYNTAX DisplayString (SIZE(0..255))
               MAX-ACCESS read-only
               STATUS current
               DESCRIPTION "Name"
               ::= {  staFilesConEntry 1 }

staFilesConSiz OBJECT-TYPE
               SYNTAX INTEGER (0..2147483647)
               MAX-ACCESS read-only
               STATUS current
               DESCRIPTION "Size"
               ::= {  staFilesConEntry 2 }

staPppoe OBJECT IDENTIFIER ::= { sta 52}
staPppoeRxp OBJECT-TYPE
            SYNTAX Counter32
            MAX-ACCESS read-only
            STATUS current
            DESCRIPTION "Rx-Packets"
            ::= {  staPppoe 1 }

staPppoeTxp OBJECT-TYPE
            SYNTAX Counter32
            MAX-ACCESS read-only
            STATUS current
            DESCRIPTION "Tx-Packets"
            ::= {  staPppoe 2 }

staPppoeDro OBJECT-TYPE
            SYNTAX Counter32
            MAX-ACCESS read-only
            STATUS current
            DESCRIPTION "Dropped-Packets"
            ::= {  staPppoe 5 }

staPppoeRxe OBJECT-TYPE
            SYNTAX Counter32
            MAX-ACCESS read-only
            STATUS current
            DESCRIPTION "Rx-Errors"
            ::= {  staPppoe 6 }

staPppoeSes OBJECT-TYPE
            SYNTAX Counter32
            MAX-ACCESS read-only
            STATUS current
            DESCRIPTION "Session-Errors"
            ::= {  staPppoe 8 }

staPppoeConTable OBJECT-TYPE
                 SYNTAX SEQUENCE OF StaPppoeConEntry
                 MAX-ACCESS not-accessible
                 STATUS current
                 DESCRIPTION "Connections"
                 ::= {  staPppoe 9 }

staPppoeConEntry OBJECT-TYPE
                 SYNTAX StaPppoeConEntry
                 MAX-ACCESS not-accessible
                 STATUS current
                 DESCRIPTION "entry in table"
                 INDEX { staPppoeConCha, staPppoeConMac }
                 ::= {  staPppoeConTable 1 }

StaPppoeConEntry ::= SEQUENCE {
                 staPppoeConCha DisplayString,
                 staPppoeConMac DisplayString,
                 staPppoeConSta INTEGER,
                 staPppoeConLas INTEGER,
                 staPppoeConSht INTEGER,
                 staPppoeConPee IpAddress,
                 staPppoeConCon INTEGER
                }

staPppoeConCha OBJECT-TYPE
               SYNTAX DisplayString (SIZE(0..16))
               MAX-ACCESS read-only
               STATUS current
               DESCRIPTION "Channel"
               ::= {  staPppoeConEntry 1 }

staPppoeConMac OBJECT-TYPE
               SYNTAX DisplayString (SIZE(0..12))
               MAX-ACCESS read-only
               STATUS current
               DESCRIPTION "MAC-Address"
               ::= {  staPppoeConEntry 2 }

staPppoeConSta OBJECT-TYPE
               SYNTAX INTEGER{
                 init(0),
                 setup-wan(1),
                 ready(2),
                 wait-for-cb(3),
                 dial(4),
                 incoming-call(5),
                 protocol(6),
                 connection(7),
                 disconnecting(8),
                 call-back(9),
                 bundle-connect(10),
                 protocol-2(11),
                 reserved(12),
                 bundle(13)
               }
               MAX-ACCESS read-only
               STATUS current
               DESCRIPTION "State"
               ::= {  staPppoeConEntry 3 }

staPppoeConLas OBJECT-TYPE
               SYNTAX INTEGER{
                 none(0),
                 remote-disconnected(17153),
                 manual-disconnect(17154),
                 shorthold-expired(17155),
                 physical-disconnected(17156),
                 invalid-physical-channel(17157),
                 dynamic-vpn-reconnect(17158),
                 configuration-changed(17159),
                 removed-from-config(17160),
                 remote-doubled(267),
                 icmp-conn-error(275),
                 dhcp-timeout(277),
                 pptp-no-response(278),
                 vpn-no-response(279),
                 arp-no-response(280),
                 pptp-no-channel(513),
                 pptp-bad-format(514),
                 pptp-bad-value(515),
                 pptp-no-ressource(516),
                 pptp-bad-call-id(517),
                 pptp-gen-error(518),
                 lcp-rejected(32768),
                 auth-error(32769),
                 auth-rejected(32770),
                 lcp-conn-error(32771),
                 pap-rejected(32784),
                 pap-rx-timeout(32785),
                 pap-tx-timeout(32786),
                 wrong-pap-req(32787),
                 pap-nak-received(32788),
                 unkn-pap-peer(32789),
                 chap-rejected(32800),
                 chap-rx-timeout(32801),
                 chap-tx-timeout(32802),
                 wrong-chap-resp(32803),
                 chap-fail-recvd(32804),
                 unkn-chap-peer(32805),
                 ipxcp-rejected(32816),
                 wrong-ipxcp-net(32817),
                 ipxcp-net-reject(32818),
                 ipxcp-route-unkn(32819),
                 ipcp-rejected(32832),
                 ccp-rejected(32848),
                 no-ncp-available(33008)
               }
               MAX-ACCESS read-write
               STATUS current
               DESCRIPTION "Last-Error"
               ::= {  staPppoeConEntry 4 }

staPppoeConSht OBJECT-TYPE
               SYNTAX INTEGER (0..65535)
               MAX-ACCESS read-only
               STATUS current
               DESCRIPTION "SH-Time"
               ::= {  staPppoeConEntry 5 }

staPppoeConPee OBJECT-TYPE
               SYNTAX IpAddress
               MAX-ACCESS read-only
               STATUS current
               DESCRIPTION "Peer-Address"
               ::= {  staPppoeConEntry 6 }

staPppoeConCon OBJECT-TYPE
               SYNTAX INTEGER (0..2147483647)
               MAX-ACCESS read-only
               STATUS current
               DESCRIPTION "Conn.-time"
               ::= {  staPppoeConEntry 7 }

staPppoeNum OBJECT-TYPE
            SYNTAX INTEGER
            MAX-ACCESS read-only
            STATUS current
            DESCRIPTION "Num.-Connections"
            ::= {  staPppoe 10 }

staPppoeDel OBJECT-TYPE
            SYNTAX DisplayString
            MAX-ACCESS read-write
            STATUS current
            DESCRIPTION "Delete-Values"
            ::= {  staPppoe 11 }

staAccou OBJECT IDENTIFIER ::= { sta 56}
staAccouCurTable OBJECT-TYPE
                 SYNTAX SEQUENCE OF StaAccouCurEntry
                 MAX-ACCESS not-accessible
                 STATUS current
                 DESCRIPTION "Current-User"
                 ::= {  staAccou 1 }

staAccouCurEntry OBJECT-TYPE
                 SYNTAX StaAccouCurEntry
                 MAX-ACCESS not-accessible
                 STATUS current
                 DESCRIPTION "entry in table"
                 INDEX { staAccouCurUsern, staAccouCurMacad, staAccouCurPeer, staAccouCurConnt }
                 ::= {  staAccouCurTable 1 }

StaAccouCurEntry ::= SEQUENCE {
                 staAccouCurUsern DisplayString,
                 staAccouCurMacad DisplayString,
                 staAccouCurPeer DisplayString,
                 staAccouCurConnt INTEGER,
                 staAccouCurRxkby INTEGER,
                 staAccouCurTxkby INTEGER,
                 staAccouCurTotal INTEGER,
                 staAccouCurConne INTEGER
                }

staAccouCurUsern OBJECT-TYPE
                 SYNTAX DisplayString (SIZE(0..28))
                 MAX-ACCESS read-only
                 STATUS current
                 DESCRIPTION "Username"
                 ::= {  staAccouCurEntry 1 }

staAccouCurMacad OBJECT-TYPE
                 SYNTAX DisplayString (SIZE(0..255))
                 MAX-ACCESS read-only
                 STATUS current
                 DESCRIPTION "MAC-Address"
                 ::= {  staAccouCurEntry 2 }

staAccouCurPeer OBJECT-TYPE
                 SYNTAX DisplayString (SIZE(0..31))
                 MAX-ACCESS read-only
                 STATUS current
                 DESCRIPTION "Peer"
                 ::= {  staAccouCurEntry 3 }

staAccouCurConnt OBJECT-TYPE
                 SYNTAX INTEGER{
                   unknown(0),
                   dial-up(1),
                   leased-line(2),
                   dsl-line(4),
                   vpn-conn(7),
                   pptp-conn(8)
                 }
                 MAX-ACCESS read-only
                 STATUS current
                 DESCRIPTION "Conn.-Type"
                 ::= {  staAccouCurEntry 4 }

staAccouCurRxkby OBJECT-TYPE
                 SYNTAX INTEGER (0..2147483647)
                 MAX-ACCESS read-only
                 STATUS current
                 DESCRIPTION "Rx-KBytes"
                 ::= {  staAccouCurEntry 5 }

staAccouCurTxkby OBJECT-TYPE
                 SYNTAX INTEGER (0..2147483647)
                 MAX-ACCESS read-only
                 STATUS current
                 DESCRIPTION "Tx-KBytes"
                 ::= {  staAccouCurEntry 6 }

staAccouCurTotal OBJECT-TYPE
                 SYNTAX INTEGER (0..2147483647)
                 MAX-ACCESS read-only
                 STATUS current
                 DESCRIPTION "Total-Time"
                 ::= {  staAccouCurEntry 8 }

staAccouCurConne OBJECT-TYPE
                 SYNTAX INTEGER (0..2147483647)
                 MAX-ACCESS read-only
                 STATUS current
                 DESCRIPTION "Connections"
                 ::= {  staAccouCurEntry 9 }

staAccouAccTable OBJECT-TYPE
                 SYNTAX SEQUENCE OF StaAccouAccEntry
                 MAX-ACCESS not-accessible
                 STATUS current
                 DESCRIPTION "Accounting-List"
                 ::= {  staAccou 2 }

staAccouAccEntry OBJECT-TYPE
                 SYNTAX StaAccouAccEntry
                 MAX-ACCESS not-accessible
                 STATUS current
                 DESCRIPTION "entry in table"
                 INDEX { staAccouAccUsern, staAccouAccMacad, staAccouAccPeer, staAccouAccConnt }
                 ::= {  staAccouAccTable 1 }

StaAccouAccEntry ::= SEQUENCE {
                 staAccouAccUsern DisplayString,
                 staAccouAccMacad DisplayString,
                 staAccouAccPeer DisplayString,
                 staAccouAccConnt INTEGER,
                 staAccouAccRxkby INTEGER,
                 staAccouAccTxkby INTEGER,
                 staAccouAccTotal INTEGER,
                 staAccouAccConne INTEGER
                }

staAccouAccUsern OBJECT-TYPE
                 SYNTAX DisplayString (SIZE(0..28))
                 MAX-ACCESS read-only
                 STATUS current
                 DESCRIPTION "Username"
                 ::= {  staAccouAccEntry 1 }

staAccouAccMacad OBJECT-TYPE
                 SYNTAX DisplayString (SIZE(0..255))
                 MAX-ACCESS read-only
                 STATUS current
                 DESCRIPTION "MAC-Address"
                 ::= {  staAccouAccEntry 2 }

staAccouAccPeer OBJECT-TYPE
                 SYNTAX DisplayString (SIZE(0..31))
                 MAX-ACCESS read-only
                 STATUS current
                 DESCRIPTION "Peer"
                 ::= {  staAccouAccEntry 3 }

staAccouAccConnt OBJECT-TYPE
                 SYNTAX INTEGER{
                   unknown(0),
                   dial-up(1),
                   leased-line(2),
                   dsl-line(4),
                   vpn-conn(7),
                   pptp-conn(8)
                 }
                 MAX-ACCESS read-only
                 STATUS current
                 DESCRIPTION "Conn.-Type"
                 ::= {  staAccouAccEntry 4 }

staAccouAccRxkby OBJECT-TYPE
                 SYNTAX INTEGER (0..2147483647)
                 MAX-ACCESS read-only
                 STATUS current
                 DESCRIPTION "Rx-KBytes"
                 ::= {  staAccouAccEntry 5 }

staAccouAccTxkby OBJECT-TYPE
                 SYNTAX INTEGER (0..2147483647)
                 MAX-ACCESS read-only
                 STATUS current
                 DESCRIPTION "Tx-KBytes"
                 ::= {  staAccouAccEntry 6 }

staAccouAccTotal OBJECT-TYPE
                 SYNTAX INTEGER (0..2147483647)
                 MAX-ACCESS read-only
                 STATUS current
                 DESCRIPTION "Total-Time"
                 ::= {  staAccouAccEntry 8 }

staAccouAccConne OBJECT-TYPE
                 SYNTAX INTEGER (0..2147483647)
                 MAX-ACCESS read-only
                 STATUS current
                 DESCRIPTION "Connections"
                 ::= {  staAccouAccEntry 9 }

staAccouLasTable OBJECT-TYPE
                 SYNTAX SEQUENCE OF StaAccouLasEntry
                 MAX-ACCESS not-accessible
                 STATUS current
                 DESCRIPTION "Last-Snapshot"
                 ::= {  staAccou 3 }

staAccouLasEntry OBJECT-TYPE
                 SYNTAX StaAccouLasEntry
                 MAX-ACCESS not-accessible
                 STATUS current
                 DESCRIPTION "entry in table"
                 INDEX { staAccouLasUsern, staAccouLasMacad, staAccouLasPeer, staAccouLasConnt }
                 ::= {  staAccouLasTable 1 }

StaAccouLasEntry ::= SEQUENCE {
                 staAccouLasUsern DisplayString,
                 staAccouLasMacad DisplayString,
                 staAccouLasPeer DisplayString,
                 staAccouLasConnt INTEGER,
                 staAccouLasRxkby INTEGER,
                 staAccouLasTxkby INTEGER,
                 staAccouLasTotal INTEGER,
                 staAccouLasConne INTEGER
                }

staAccouLasUsern OBJECT-TYPE
                 SYNTAX DisplayString (SIZE(0..28))
                 MAX-ACCESS read-only
                 STATUS current
                 DESCRIPTION "Username"
                 ::= {  staAccouLasEntry 1 }

staAccouLasMacad OBJECT-TYPE
                 SYNTAX DisplayString (SIZE(0..255))
                 MAX-ACCESS read-only
                 STATUS current
                 DESCRIPTION "MAC-Address"
                 ::= {  staAccouLasEntry 2 }

staAccouLasPeer OBJECT-TYPE
                 SYNTAX DisplayString (SIZE(0..31))
                 MAX-ACCESS read-only
                 STATUS current
                 DESCRIPTION "Peer"
                 ::= {  staAccouLasEntry 3 }

staAccouLasConnt OBJECT-TYPE
                 SYNTAX INTEGER{
                   unknown(0),
                   dial-up(1),
                   leased-line(2),
                   dsl-line(4),
                   vpn-conn(7),
                   pptp-conn(8)
                 }
                 MAX-ACCESS read-only
                 STATUS current
                 DESCRIPTION "Conn.-Type"
                 ::= {  staAccouLasEntry 4 }

staAccouLasRxkby OBJECT-TYPE
                 SYNTAX INTEGER (0..2147483647)
                 MAX-ACCESS read-only
                 STATUS current
                 DESCRIPTION "Rx-KBytes"
                 ::= {  staAccouLasEntry 5 }

staAccouLasTxkby OBJECT-TYPE
                 SYNTAX INTEGER (0..2147483647)
                 MAX-ACCESS read-only
                 STATUS current
                 DESCRIPTION "Tx-KBytes"
                 ::= {  staAccouLasEntry 6 }

staAccouLasTotal OBJECT-TYPE
                 SYNTAX INTEGER (0..2147483647)
                 MAX-ACCESS read-only
                 STATUS current
                 DESCRIPTION "Total-Time"
                 ::= {  staAccouLasEntry 8 }

staAccouLasConne OBJECT-TYPE
                 SYNTAX INTEGER (0..2147483647)
                 MAX-ACCESS read-only
                 STATUS current
                 DESCRIPTION "Connections"
                 ::= {  staAccouLasEntry 9 }

staAccouTimTable OBJECT-TYPE
                 SYNTAX SEQUENCE OF StaAccouTimEntry
                 MAX-ACCESS not-accessible
                 STATUS current
                 DESCRIPTION "Time-Last-Snapshot"
                 ::= {  staAccou 5 }

staAccouTimEntry OBJECT-TYPE
                 SYNTAX StaAccouTimEntry
                 MAX-ACCESS not-accessible
                 STATUS current
                 DESCRIPTION "entry in table"
                 INDEX { staAccouTimSys }
                 ::= {  staAccouTimTable 1 }

StaAccouTimEntry ::= SEQUENCE {
                 staAccouTimSys Counter32
                }

staAccouTimSys OBJECT-TYPE
               SYNTAX Counter32
               MAX-ACCESS read-only
               STATUS current
               DESCRIPTION "System-time"
               ::= {  staAccouTimEntry 1 }

staAccouDel OBJECT-TYPE
            SYNTAX DisplayString
            MAX-ACCESS read-write
            STATUS current
            DESCRIPTION "Delete-Values"
            ::= {  staAccou 4 }

staWlanm OBJECT IDENTIFIER ::= { sta 59}
staWlanmApconnTable OBJECT-TYPE
                    SYNTAX SEQUENCE OF StaWlanmApconnEntry
                    MAX-ACCESS not-accessible
                    STATUS current
                    DESCRIPTION "AP-Connections"
                    ::= {  staWlanm 1 }

staWlanmApconnEntry OBJECT-TYPE
                    SYNTAX StaWlanmApconnEntry
                    MAX-ACCESS not-accessible
                    STATUS current
                    DESCRIPTION "entry in table"
                    INDEX { staWlanmApconnId }
                    ::= {  staWlanmApconnTable 1 }

StaWlanmApconnEntry ::= SEQUENCE {
                    staWlanmApconnId INTEGER,
                    staWlanmApconnIpad IpAddress,
                    staWlanmApconnPort INTEGER,
                    staWlanmApconnPrio INTEGER,
                    staWlanmApconnResu INTEGER,
                    staWlanmApconnResp INTEGER,
                    staWlanmApconnUtil DisplayString,
                    staWlanmApconnName DisplayString,
                    staWlanmApconnStat INTEGER
                   }

staWlanmApconnId OBJECT-TYPE
                   SYNTAX INTEGER (0..2147483647)
                   MAX-ACCESS read-only
                   STATUS current
                   DESCRIPTION "ID"
                   ::= {  staWlanmApconnEntry 1 }

staWlanmApconnIpad OBJECT-TYPE
                   SYNTAX IpAddress
                   MAX-ACCESS read-only
                   STATUS current
                   DESCRIPTION "IP-Address"
                   ::= {  staWlanmApconnEntry 2 }

staWlanmApconnPort OBJECT-TYPE
                   SYNTAX INTEGER (0..65535)
                   MAX-ACCESS read-only
                   STATUS current
                   DESCRIPTION "Port"
                   ::= {  staWlanmApconnEntry 3 }

staWlanmApconnPrio OBJECT-TYPE
                   SYNTAX INTEGER{
                     unspec(0),
                     primary(1),
                     secondary(2)
                   }
                   MAX-ACCESS read-only
                   STATUS current
                   DESCRIPTION "Priority"
                   ::= {  staWlanmApconnEntry 8 }

staWlanmApconnResu OBJECT-TYPE
                   SYNTAX INTEGER{
                     success(0),
                     failure(1),
                     success-nat(2),
                     join-fail-unspecified(3),
                     join-fail-resource-depletion(4),
                     join-fail-unknwn-src(5),
                     join-fail-incorrect-data(6),
                     join-fail-session-id-in-use(7),
                     join-fail-wtp-not-supported(8),
                     join-fail-binding-not-supp(9),
                     reset-fail-unable-to-reset(10),
                     reset-fail-firmw-write-err(11),
                     fail-missing-mand-msg-elem(20),
                     fail-unrecognized-msg-elem(21),
                     unsupported-loader-version(300),
                     unsupported-firmware-version(301),
                     minus-minus(302)
                   }
                   MAX-ACCESS read-only
                   STATUS current
                   DESCRIPTION "Result"
                   ::= {  staWlanmApconnEntry 7 }

staWlanmApconnResp OBJECT-TYPE
                   SYNTAX INTEGER (0..2147483647)
                   MAX-ACCESS read-only
                   STATUS current
                   DESCRIPTION "RespTime"
                   ::= {  staWlanmApconnEntry 4 }

staWlanmApconnUtil OBJECT-TYPE
                   SYNTAX DisplayString (SIZE(0..6))
                   MAX-ACCESS read-only
                   STATUS current
                   DESCRIPTION "Utilisation"
                   ::= {  staWlanmApconnEntry 9 }

staWlanmApconnName OBJECT-TYPE
                   SYNTAX DisplayString (SIZE(0..31))
                   MAX-ACCESS read-only
                   STATUS current
                   DESCRIPTION "Name"
                   ::= {  staWlanmApconnEntry 5 }

staWlanmApconnStat OBJECT-TYPE
                   SYNTAX INTEGER{
                     unknown(0),
                     idle(5),
                     discovery(10),
                     dtls-setup(15),
                     join(20),
                     configure(25),
                     image-data(30),
                     reset(35),
                     dtls-teardown(40),
                     sulking(45),
                     run(100)
                   }
                   MAX-ACCESS read-only
                   STATUS current
                   DESCRIPTION "State"
                   ::= {  staWlanmApconnEntry 6 }

staWlanmGserverlTable OBJECT-TYPE
                    SYNTAX SEQUENCE OF StaWlanmGserverlEntry
                    MAX-ACCESS not-accessible
                    STATUS current
                    DESCRIPTION "GserverlConfig"
                    ::= {  staWlanm 99 }

staWlanmGserverlEntry OBJECT-TYPE
                    SYNTAX StaWlanmGserverlEntry
                    MAX-ACCESS not-accessible
                    STATUS current
                    DESCRIPTION "entry in table"
                    INDEX { staWlanmGserverlVersion }
                    ::= {  staWlanmGserverlTable 1 }

StaWlanmGserverlEntry ::= SEQUENCE {
                    staWlanmGserverlVersion INTEGER,
                    staWlanmGserverlIpaddress IpAddress,
                    staWlanmGserverlNetmask IpAddress,
                    staWlanmGserverlGateway IpAddress,
                    staWlanmGserverlDns1 IpAddress,
                    staWlanmGserverlDns2 IpAddress,
                    staWlanmGserverlMgmtvlani INTEGER,
                    staWlanmGserverlMgmtvlant INTEGER
                   }

staWlanmGserverlVersion OBJECT-TYPE
                        SYNTAX INTEGER (0..2147483647)
                        MAX-ACCESS read-only
                        STATUS current
                        DESCRIPTION "Version"
                        ::= {  staWlanmGserverlEntry 1 }

staWlanmGserverlIpaddress OBJECT-TYPE
                        SYNTAX IpAddress
                        MAX-ACCESS read-only
                        STATUS current
                        DESCRIPTION "IP-Address"
                        ::= {  staWlanmGserverlEntry 2 }

staWlanmGserverlNetmask OBJECT-TYPE
                        SYNTAX IpAddress
                        MAX-ACCESS read-only
                        STATUS current
                        DESCRIPTION "Net-Mask"
                        ::= {  staWlanmGserverlEntry 3 }

staWlanmGserverlGateway OBJECT-TYPE
                        SYNTAX IpAddress
                        MAX-ACCESS read-only
                        STATUS current
                        DESCRIPTION "Gateway"
                        ::= {  staWlanmGserverlEntry 4 }

staWlanmGserverlDns1 OBJECT-TYPE
                        SYNTAX IpAddress
                        MAX-ACCESS read-only
                        STATUS current
                        DESCRIPTION "DNS1"
                        ::= {  staWlanmGserverlEntry 5 }

staWlanmGserverlDns2 OBJECT-TYPE
                        SYNTAX IpAddress
                        MAX-ACCESS read-only
                        STATUS current
                        DESCRIPTION "DNS2"
                        ::= {  staWlanmGserverlEntry 6 }

staWlanmGserverlMgmtvlani OBJECT-TYPE
                        SYNTAX INTEGER (0..65535)
                        MAX-ACCESS read-only
                        STATUS current
                        DESCRIPTION "Mgmt-VLanId"
                        ::= {  staWlanmGserverlEntry 8 }

staWlanmGserverlMgmtvlant OBJECT-TYPE
                        SYNTAX INTEGER (0..65535)
                        MAX-ACCESS read-only
                        STATUS current
                        DESCRIPTION "Mgmt-VLanTrunk"
                        ::= {  staWlanmGserverlEntry 9 }

staWlanmLastwlTable OBJECT-TYPE
                    SYNTAX SEQUENCE OF StaWlanmLastwlEntry
                    MAX-ACCESS not-accessible
                    STATUS current
                    DESCRIPTION "Last-WLC"
                    ::= {  staWlanm 100 }

staWlanmLastwlEntry OBJECT-TYPE
                    SYNTAX StaWlanmLastwlEntry
                    MAX-ACCESS not-accessible
                    STATUS current
                    DESCRIPTION "entry in table"
                    INDEX { staWlanmLastwlIpa }
                    ::= {  staWlanmLastwlTable 1 }

StaWlanmLastwlEntry ::= SEQUENCE {
                    staWlanmLastwlIpa IpAddress,
                    staWlanmLastwlPor INTEGER,
                    staWlanmLastwlNam DisplayString,
                    staWlanmLastwlMgm INTEGER,
                    staWlanmLastwlRou INTEGER,
                    staWlanmLastwlTyp INTEGER
                   }

staWlanmLastwlIpa OBJECT-TYPE
                  SYNTAX IpAddress
                  MAX-ACCESS read-only
                  STATUS current
                  DESCRIPTION "IP-Address"
                  ::= {  staWlanmLastwlEntry 1 }

staWlanmLastwlPor OBJECT-TYPE
                  SYNTAX INTEGER (0..65535)
                  MAX-ACCESS read-only
                  STATUS current
                  DESCRIPTION "Port"
                  ::= {  staWlanmLastwlEntry 2 }

staWlanmLastwlNam OBJECT-TYPE
                  SYNTAX DisplayString (SIZE(0..31))
                  MAX-ACCESS read-only
                  STATUS current
                  DESCRIPTION "Name"
                  ::= {  staWlanmLastwlEntry 3 }

staWlanmLastwlMgm OBJECT-TYPE
                  SYNTAX INTEGER (0..65535)
                  MAX-ACCESS read-only
                  STATUS current
                  DESCRIPTION "Mgmt-VLAN-Id"
                  ::= {  staWlanmLastwlEntry 6 }

staWlanmLastwlRou OBJECT-TYPE
                  SYNTAX INTEGER (0..65535)
                  MAX-ACCESS read-only
                  STATUS current
                  DESCRIPTION "RouteTag"
                  ::= {  staWlanmLastwlEntry 4 }

staWlanmLastwlTyp OBJECT-TYPE
                  SYNTAX INTEGER (0..255)
                  MAX-ACCESS read-only
                  STATUS current
                  DESCRIPTION "Type"
                  ::= {  staWlanmLastwlEntry 5 }

staWlanmRadiopTable OBJECT-TYPE
                    SYNTAX SEQUENCE OF StaWlanmRadiopEntry
                    MAX-ACCESS not-accessible
                    STATUS current
                    DESCRIPTION "Radioprofiles"
                    ::= {  staWlanm 101 }

staWlanmRadiopEntry OBJECT-TYPE
                    SYNTAX StaWlanmRadiopEntry
                    MAX-ACCESS not-accessible
                    STATUS current
                    DESCRIPTION "entry in table"
                    INDEX { staWlanmRadiopName }
                    ::= {  staWlanmRadiopTable 1 }

StaWlanmRadiopEntry ::= SEQUENCE {
                    staWlanmRadiopName DisplayString,
                    staWlanmRadiopCountry INTEGER,
                    staWlanmRadiop24ghzmode INTEGER,
                    staWlanmRadiop5ghzmode INTEGER,
                    staWlanmRadiopSubbands INTEGER,
                    staWlanmRadiopQos INTEGER,
                    staWlanmRadiopDtimperio INTEGER,
                    staWlanmRadiopBackgroun INTEGER,
                    staWlanmRadiopAntennaga INTEGER,
                    staWlanmRadiopTxpowerre INTEGER,
                    staWlanmRadiopMgmtvlani INTEGER,
                    staWlanmRadiopMgmtvlant INTEGER,
                    staWlanmRadiopIndooronl INTEGER
                   }

staWlanmRadiopName OBJECT-TYPE
                        SYNTAX DisplayString (SIZE(0..31))
                        MAX-ACCESS read-only
                        STATUS current
                        DESCRIPTION "Name"
                        ::= {  staWlanmRadiopEntry 1 }

staWlanmRadiopCountry OBJECT-TYPE
                        SYNTAX INTEGER{
                          default(0),
                          albania(8),
                          argentina(32),
                          australia(36),
                          austria(40),
                          bahrain(48),
                          bangladesh(50),
                          belarus(112),
                          belgium(56),
                          bosnia-herzegovina(70),
                          brazil(76),
                          brunei-darussalam(96),
                          bulgaria(100),
                          canada(124),
                          chile(152),
                          china(156),
                          colombia(170),
                          costa-rica(188),
                          croatia(191),
                          cyprus(196),
                          czech(203),
                          denmark(208),
                          ecuador(218),
                          egalistan(999),
                          egypt(818),
                          estonia(233),
                          finland(246),
                          france(250),
                          germany(276),
                          ghana(288),
                          greece(300),
                          guatemala(320),
                          honduras(340),
                          hong-kong(344),
                          hungary(348),
                          iceland(352),
                          india(356),
                          indonesia(360),
                          ireland(372),
                          israel(376),
                          italy(380),
                          japan(392),
                          jordan(400),
                          south-korea(410),
                          kuwait(414),
                          latvia(428),
                          lebanon(422),
                          liechtenstein(438),
                          lithuania(440),
                          luxembourg(442),
                          macau(446),
                          macedonia(807),
                          malaysia(458),
                          malta(470),
                          mexico(484),
                          moldavia(498),
                          morocco(504),
                          netherlands(528),
                          new-zealand(554),
                          nicaragua(558),
                          norway(578),
                          oman(512),
                          pakistan(586),
                          panama(591),
                          paraguay(600),
                          peru(604),
                          philippines(608),
                          poland(616),
                          portugal(620),
                          puerto-rico(630),
                          qatar(634),
                          romania(642),
                          russia(643),
                          saudi-arabia(682),
                          singapore(702),
                          slovak(703),
                          slovenia(705),
                          south-africa(710),
                          spain(724),
                          sweden(752),
                          switzerland(756),
                          taiwan(158),
                          tanzania(834),
                          thailand(764),
                          tunisia(788),
                          turkey(792),
                          uganda(800),
                          ukraine(804),
                          united-arab-emirates(784),
                          united-kingdom(826),
                          united-states-fcc(840),
                          uruguay(858),
                          venezuela(862)
                        }
                        MAX-ACCESS read-only
                        STATUS current
                        DESCRIPTION "Country"
                        ::= {  staWlanmRadiopEntry 4 }

staWlanmRadiop24ghzmode OBJECT-TYPE
                        SYNTAX INTEGER{
                          e11bg-mixed(0),
                          e11b-only(2),
                          e11g-only(1),
                          e108mbps(3)
                        }
                        MAX-ACCESS read-only
                        STATUS current
                        DESCRIPTION "2.4GHz-Mode"
                        ::= {  staWlanmRadiopEntry 6 }

staWlanmRadiop5ghzmode OBJECT-TYPE
                        SYNTAX INTEGER{
                          normal(0),
                          e108mbps(3)
                        }
                        MAX-ACCESS read-only
                        STATUS current
                        DESCRIPTION "5GHz-Mode"
                        ::= {  staWlanmRadiopEntry 7 }

staWlanmRadiopSubbands OBJECT-TYPE
                        SYNTAX INTEGER{
                          band-1(1),
                          band-2(2),
                          band-3(3),
                          band-1-plus-2(4),
                          band-1-plus-3(5),
                          band-2-plus-3(6),
                          band-1-plus-2-plus-3(0)
                        }
                        MAX-ACCESS read-only
                        STATUS current
                        DESCRIPTION "Subbands"
                        ::= {  staWlanmRadiopEntry 8 }

staWlanmRadiopQos OBJECT-TYPE
                        SYNTAX INTEGER{
                          no(0),
                          yes(1)
                        }
                        MAX-ACCESS read-only
                        STATUS current
                        DESCRIPTION "QoS"
                        ::= {  staWlanmRadiopEntry 9 }

staWlanmRadiopDtimperio OBJECT-TYPE
                        SYNTAX INTEGER (0..255)
                        MAX-ACCESS read-only
                        STATUS current
                        DESCRIPTION "DTIM-Period"
                        ::= {  staWlanmRadiopEntry 10 }

staWlanmRadiopBackgroun OBJECT-TYPE
                        SYNTAX INTEGER (0..2147483647)
                        MAX-ACCESS read-only
                        STATUS current
                        DESCRIPTION "Background-Scan"
                        ::= {  staWlanmRadiopEntry 11 }

staWlanmRadiopAntennaga OBJECT-TYPE
                        SYNTAX INTEGER (0..255)
                        MAX-ACCESS read-only
                        STATUS current
                        DESCRIPTION "Antenna-Gain"
                        ::= {  staWlanmRadiopEntry 12 }

staWlanmRadiopTxpowerre OBJECT-TYPE
                        SYNTAX INTEGER (0..255)
                        MAX-ACCESS read-only
                        STATUS current
                        DESCRIPTION "Tx-Power-Reduction"
                        ::= {  staWlanmRadiopEntry 13 }

staWlanmRadiopMgmtvlani OBJECT-TYPE
                        SYNTAX INTEGER (0..65535)
                        MAX-ACCESS read-only
                        STATUS current
                        DESCRIPTION "Mgmt-VLAN-Id"
                        ::= {  staWlanmRadiopEntry 14 }

staWlanmRadiopMgmtvlant OBJECT-TYPE
                        SYNTAX INTEGER (0..65535)
                        MAX-ACCESS read-only
                        STATUS current
                        DESCRIPTION "Mgmt-VLAN-Trunk"
                        ::= {  staWlanmRadiopEntry 15 }

staWlanmRadiopIndooronl OBJECT-TYPE
                        SYNTAX INTEGER{
                          no(0),
                          yes(1)
                        }
                        MAX-ACCESS read-only
                        STATUS current
                        DESCRIPTION "Indoor-Only-Operation"
                        ::= {  staWlanmRadiopEntry 16 }

staWlanmRadiomTable OBJECT-TYPE
                    SYNTAX SEQUENCE OF StaWlanmRadiomEntry
                    MAX-ACCESS not-accessible
                    STATUS current
                    DESCRIPTION "Radio-Mode"
                    ::= {  staWlanm 102 }

staWlanmRadiomEntry OBJECT-TYPE
                    SYNTAX StaWlanmRadiomEntry
                    MAX-ACCESS not-accessible
                    STATUS current
                    DESCRIPTION "entry in table"
                    INDEX { staWlanmRadiomIndex }
                    ::= {  staWlanmRadiomTable 1 }

StaWlanmRadiomEntry ::= SEQUENCE {
                    staWlanmRadiomIndex INTEGER,
                    staWlanmRadiomRadiom INTEGER,
                    staWlanmRadiomOperat INTEGER,
                    staWlanmRadiomRadioc INTEGER,
                    staWlanmRadiomChanne DisplayString
                   }

staWlanmRadiomIndex OBJECT-TYPE
                     SYNTAX INTEGER (0..255)
                     MAX-ACCESS read-only
                     STATUS current
                     DESCRIPTION "Index"
                     ::= {  staWlanmRadiomEntry 1 }

staWlanmRadiomRadiom OBJECT-TYPE
                     SYNTAX INTEGER{
                       default(0),
                       e2-4ghz(1),
                       e5ghz(2),
                       off(3)
                     }
                     MAX-ACCESS read-only
                     STATUS current
                     DESCRIPTION "Radio-Mode"
                     ::= {  staWlanmRadiomEntry 2 }

staWlanmRadiomOperat OBJECT-TYPE
                     SYNTAX INTEGER{
                       yes(0),
                       no(1)
                     }
                     MAX-ACCESS read-only
                     STATUS current
                     DESCRIPTION "Operating"
                     ::= {  staWlanmRadiomEntry 3 }

staWlanmRadiomRadioc OBJECT-TYPE
                     SYNTAX INTEGER{
                       auto(0)
                     }
                     MAX-ACCESS read-only
                     STATUS current
                     DESCRIPTION "Radio-Channel"
                     ::= {  staWlanmRadiomEntry 5 }

staWlanmRadiomChanne OBJECT-TYPE
                     SYNTAX DisplayString (SIZE(0..48))
                     MAX-ACCESS read-only
                     STATUS current
                     DESCRIPTION "Channel-List"
                     ::= {  staWlanmRadiomEntry 4 }

staWlanmNetworTable OBJECT-TYPE
                    SYNTAX SEQUENCE OF StaWlanmNetworEntry
                    MAX-ACCESS not-accessible
                    STATUS current
                    DESCRIPTION "Networkprofiles"
                    ::= {  staWlanm 103 }

staWlanmNetworEntry OBJECT-TYPE
                    SYNTAX StaWlanmNetworEntry
                    MAX-ACCESS not-accessible
                    STATUS current
                    DESCRIPTION "entry in table"
                    INDEX { staWlanmNetworName }
                    ::= {  staWlanmNetworTable 1 }

StaWlanmNetworEntry ::= SEQUENCE {
                    staWlanmNetworName DisplayString,
                    staWlanmNetworSsid DisplayString,
                    staWlanmNetworOpera INTEGER,
                    staWlanmNetworVlani INTEGER,
                    staWlanmNetworEncry INTEGER,
                    staWlanmNetworWpa1s INTEGER,
                    staWlanmNetworWpa2s INTEGER,
                    staWlanmNetworWpave INTEGER,
                    staWlanmNetworKey DisplayString,
                    staWlanmNetworRadio INTEGER,
                    staWlanmNetworConti INTEGER,
                    staWlanmNetworMintx INTEGER,
                    staWlanmNetworMaxtx INTEGER,
                    staWlanmNetworBasic INTEGER,
                    staWlanmNetwor11bpr INTEGER,
                    staWlanmNetworMacfi INTEGER,
                    staWlanmNetworClbrg INTEGER,
                    staWlanmNetworMaxst INTEGER,
                    staWlanmNetworSsidb INTEGER,
                    staWlanmNetworVlant INTEGER
                   }

staWlanmNetworName OBJECT-TYPE
                    SYNTAX DisplayString (SIZE(0..31))
                    MAX-ACCESS read-only
                    STATUS current
                    DESCRIPTION "Name"
                    ::= {  staWlanmNetworEntry 1 }

staWlanmNetworSsid OBJECT-TYPE
                    SYNTAX DisplayString (SIZE(0..32))
                    MAX-ACCESS read-only
                    STATUS current
                    DESCRIPTION "SSID"
                    ::= {  staWlanmNetworEntry 21 }

staWlanmNetworOpera OBJECT-TYPE
                    SYNTAX INTEGER{
                      yes(0),
                      no(1)
                    }
                    MAX-ACCESS read-only
                    STATUS current
                    DESCRIPTION "Operating"
                    ::= {  staWlanmNetworEntry 4 }

staWlanmNetworVlani OBJECT-TYPE
                    SYNTAX INTEGER (0..65535)
                    MAX-ACCESS read-only
                    STATUS current
                    DESCRIPTION "VLAN-Id"
                    ::= {  staWlanmNetworEntry 5 }

staWlanmNetworEncry OBJECT-TYPE
                    SYNTAX INTEGER{
                      e802-11i-wpa-psk(0),
                      e802-11i-wpa-802-1x(1),
                      wep-104-bits(2),
                      wep-40-bits(3),
                      wep-104-bits-802-1x(4),
                      wep-40-bits-802-1x(5),
                      none(6)
                    }
                    MAX-ACCESS read-only
                    STATUS current
                    DESCRIPTION "Encryption"
                    ::= {  staWlanmNetworEntry 6 }

staWlanmNetworWpa1s OBJECT-TYPE
                    SYNTAX INTEGER{
                      tkip-aes(0),
                      aes(1),
                      tkip(2)
                    }
                    MAX-ACCESS read-only
                    STATUS current
                    DESCRIPTION "WPA1-Session-Keytypes"
                    ::= {  staWlanmNetworEntry 7 }

staWlanmNetworWpa2s OBJECT-TYPE
                    SYNTAX INTEGER{
                      tkip-aes(0),
                      aes(1),
                      tkip(2)
                    }
                    MAX-ACCESS read-only
                    STATUS current
                    DESCRIPTION "WPA2-Session-Keytypes"
                    ::= {  staWlanmNetworEntry 27 }

staWlanmNetworWpave OBJECT-TYPE
                    SYNTAX INTEGER{
                      wpa1-2(0),
                      wpa1(1),
                      wpa2(2)
                    }
                    MAX-ACCESS read-only
                    STATUS current
                    DESCRIPTION "WPA-Version"
                    ::= {  staWlanmNetworEntry 8 }

staWlanmNetworKey OBJECT-TYPE
                    SYNTAX DisplayString (SIZE(0..63))
                    MAX-ACCESS read-only
                    STATUS current
                    DESCRIPTION "Key"
                    ::= {  staWlanmNetworEntry 9 }

staWlanmNetworRadio OBJECT-TYPE
                    SYNTAX INTEGER{
                      e2-4ghz-5ghz(0),
                      e2-4ghz(1),
                      e5ghz(2)
                    }
                    MAX-ACCESS read-only
                    STATUS current
                    DESCRIPTION "Radio-Band"
                    ::= {  staWlanmNetworEntry 10 }

staWlanmNetworConti OBJECT-TYPE
                    SYNTAX INTEGER (0..65535)
                    MAX-ACCESS read-only
                    STATUS current
                    DESCRIPTION "Continuation"
                    ::= {  staWlanmNetworEntry 11 }

staWlanmNetworMintx OBJECT-TYPE
                    SYNTAX INTEGER{
                      auto(0),
                      e1m(1),
                      e2m(2),
                      e5-5m(3),
                      e11m(4),
                      e6m(5),
                      e9m(6),
                      e12m(7),
                      e18m(8),
                      e24m(9),
                      e36m(10),
                      e48m(11),
                      e54m(12),
                      t-72m(13),
                      t-96m(14),
                      t-108m(15)
                    }
                    MAX-ACCESS read-only
                    STATUS current
                    DESCRIPTION "Min-Tx-Rate"
                    ::= {  staWlanmNetworEntry 12 }

staWlanmNetworMaxtx OBJECT-TYPE
                    SYNTAX INTEGER{
                      auto(0),
                      e1m(1),
                      e2m(2),
                      e5-5m(3),
                      e11m(4),
                      e6m(5),
                      e9m(6),
                      e12m(7),
                      e18m(8),
                      e24m(9),
                      e36m(10),
                      e48m(11),
                      e54m(12),
                      t-72m(13),
                      t-96m(14),
                      t-108m(15)
                    }
                    MAX-ACCESS read-only
                    STATUS current
                    DESCRIPTION "Max-Tx-Rate"
                    ::= {  staWlanmNetworEntry 13 }

staWlanmNetworBasic OBJECT-TYPE
                    SYNTAX INTEGER{
                      e1m(1),
                      e2m(0),
                      e5-5m(3),
                      e11m(4),
                      e6m(5),
                      e9m(6),
                      e12m(7),
                      e18m(8),
                      e24m(9),
                      e36m(10),
                      e48m(11),
                      e54m(12),
                      t-72m(13),
                      t-96m(14),
                      t-108m(15)
                    }
                    MAX-ACCESS read-only
                    STATUS current
                    DESCRIPTION "Basic-Rate"
                    ::= {  staWlanmNetworEntry 14 }

staWlanmNetwor11bpr OBJECT-TYPE
                    SYNTAX INTEGER{
                      auto(0),
                      long(1)
                    }
                    MAX-ACCESS read-only
                    STATUS current
                    DESCRIPTION "11b-Preamble"
                    ::= {  staWlanmNetworEntry 15 }

staWlanmNetworMacfi OBJECT-TYPE
                    SYNTAX INTEGER{
                      yes(1),
                      no(0)
                    }
                    MAX-ACCESS read-only
                    STATUS current
                    DESCRIPTION "MAC-Filter"
                    ::= {  staWlanmNetworEntry 16 }

staWlanmNetworClbrg OBJECT-TYPE
                    SYNTAX INTEGER{
                      no(0),
                      yes(1),
                      exclusive(2)
                    }
                    MAX-ACCESS read-only
                    STATUS current
                    DESCRIPTION "Cl.-Brg.-Support"
                    ::= {  staWlanmNetworEntry 17 }

staWlanmNetworMaxst OBJECT-TYPE
                    SYNTAX INTEGER (0..65535)
                    MAX-ACCESS read-only
                    STATUS current
                    DESCRIPTION "Max-Stations"
                    ::= {  staWlanmNetworEntry 18 }

staWlanmNetworSsidb OBJECT-TYPE
                    SYNTAX INTEGER{
                      yes(0),
                      no(1)
                    }
                    MAX-ACCESS read-only
                    STATUS current
                    DESCRIPTION "SSID-Broadcast"
                    ::= {  staWlanmNetworEntry 19 }

staWlanmNetworVlant OBJECT-TYPE
                    SYNTAX INTEGER (0..65535)
                    MAX-ACCESS read-only
                    STATUS current
                    DESCRIPTION "VLAN-Trunk"
                    ::= {  staWlanmNetworEntry 20 }

staWlanmLogtabTable OBJECT-TYPE
                    SYNTAX SEQUENCE OF StaWlanmLogtabEntry
                    MAX-ACCESS not-accessible
                    STATUS current
                    DESCRIPTION "Log-Table"
                    ::= {  staWlanm 120 }

staWlanmLogtabEntry OBJECT-TYPE
                    SYNTAX StaWlanmLogtabEntry
                    MAX-ACCESS not-accessible
                    STATUS current
                    DESCRIPTION "entry in table"
                    INDEX { staWlanmLogtabInd }
                    ::= {  staWlanmLogtabTable 1 }

StaWlanmLogtabEntry ::= SEQUENCE {
                    staWlanmLogtabInd INTEGER,
                    staWlanmLogtabTim DisplayString,
                    staWlanmLogtabEve DisplayString
                   }

staWlanmLogtabInd OBJECT-TYPE
                  SYNTAX INTEGER (0..2147483647)
                  MAX-ACCESS read-only
                  STATUS current
                  DESCRIPTION "Index"
                  ::= {  staWlanmLogtabEntry 1 }

staWlanmLogtabTim OBJECT-TYPE
                  SYNTAX DisplayString (SIZE(0..19))
                  MAX-ACCESS read-only
                  STATUS current
                  DESCRIPTION "Time"
                  ::= {  staWlanmLogtabEntry 2 }

staWlanmLogtabEve OBJECT-TYPE
                  SYNTAX DisplayString (SIZE(0..80))
                  MAX-ACCESS read-only
                  STATUS current
                  DESCRIPTION "Event"
                  ::= {  staWlanmLogtabEntry 6 }

staCerti OBJECT IDENTIFIER ::= { sta 61}
staCertiSce OBJECT IDENTIFIER ::= { staCerti 1}
staCertiSceNumca OBJECT-TYPE
                 SYNTAX INTEGER
                 MAX-ACCESS read-only
                 STATUS current
                 DESCRIPTION "NumCAs"
                 ::= {  staCertiSce 1 }

staCertiSceNumra OBJECT-TYPE
                 SYNTAX INTEGER
                 MAX-ACCESS read-only
                 STATUS current
                 DESCRIPTION "NumRAs"
                 ::= {  staCertiSce 2 }

staCertiSceNumce OBJECT-TYPE
                 SYNTAX INTEGER
                 MAX-ACCESS read-only
                 STATUS current
                 DESCRIPTION "NumCerts"
                 ::= {  staCertiSce 3 }

staCertiSceCasTable OBJECT-TYPE
                      SYNTAX SEQUENCE OF StaCertiSceCasEntry
                      MAX-ACCESS not-accessible
                      STATUS current
                      DESCRIPTION "CAs"
                      ::= {  staCertiSce 4 }

staCertiSceCasEntry OBJECT-TYPE
                      SYNTAX StaCertiSceCasEntry
                      MAX-ACCESS not-accessible
                      STATUS current
                      DESCRIPTION "entry in table"
                      INDEX { staCertiSceCasIdx }
                      ::= {  staCertiSceCasTable 1 }

StaCertiSceCasEntry ::= SEQUENCE {
                      staCertiSceCasIdx INTEGER,
                      staCertiSceCasName DisplayString,
                      staCertiSceCasExpire DisplayString,
                      staCertiSceCasIssued DisplayString,
                      staCertiSceCasKeyusa DisplayString,
                      staCertiSceCasIssuer DisplayString,
                      staCertiSceCasSubjec DisplayString,
                      staCertiSceCasStatus INTEGER,
                      staCertiSceCasMd5fin DisplayString,
                      staCertiSceCasSha1fi DisplayString,
                      staCertiSceCasExpsnm INTEGER,
                      staCertiSceCasIsssnm INTEGER
                     }

staCertiSceCasIdx OBJECT-TYPE
                     SYNTAX INTEGER (0..2147483647)
                     MAX-ACCESS read-only
                     STATUS current
                     DESCRIPTION "Idx."
                     ::= {  staCertiSceCasEntry 1 }

staCertiSceCasName OBJECT-TYPE
                     SYNTAX DisplayString (SIZE(0..15))
                     MAX-ACCESS read-only
                     STATUS current
                     DESCRIPTION "Name"
                     ::= {  staCertiSceCasEntry 2 }

staCertiSceCasExpire OBJECT-TYPE
                     SYNTAX DisplayString (SIZE(0..19))
                     MAX-ACCESS read-only
                     STATUS current
                     DESCRIPTION "Expires"
                     ::= {  staCertiSceCasEntry 3 }

staCertiSceCasIssued OBJECT-TYPE
                     SYNTAX DisplayString (SIZE(0..19))
                     MAX-ACCESS read-only
                     STATUS current
                     DESCRIPTION "Issued"
                     ::= {  staCertiSceCasEntry 4 }

staCertiSceCasKeyusa OBJECT-TYPE
                     SYNTAX DisplayString (SIZE(0..251))
                     MAX-ACCESS read-only
                     STATUS current
                     DESCRIPTION "Key-Usage"
                     ::= {  staCertiSceCasEntry 5 }

staCertiSceCasIssuer OBJECT-TYPE
                     SYNTAX DisplayString (SIZE(0..251))
                     MAX-ACCESS read-only
                     STATUS current
                     DESCRIPTION "Issuer"
                     ::= {  staCertiSceCasEntry 6 }

staCertiSceCasSubjec OBJECT-TYPE
                     SYNTAX DisplayString (SIZE(0..251))
                     MAX-ACCESS read-only
                     STATUS current
                     DESCRIPTION "Subject"
                     ::= {  staCertiSceCasEntry 7 }

staCertiSceCasStatus OBJECT-TYPE
                     SYNTAX INTEGER{
                       status-unknown(0),
                       enroll-requested(1),
                       enroll-received(2),
                       enroll-ok(3),
                       enroll-bad(4),
                       enroll-bad-config(5),
                       enroll-pending(6),
                       enroll-rejected(7),
                       enroll-rejected-badalg(8),
                       enroll-rejected-badmsgchk(9),
                       enroll-rejected-badreq(10),
                       enroll-rejected-badtime(11),
                       enroll-rejected-badcertid(12),
                       enroll-ca-missing(13),
                       enroll-exp-unknown(14),
                       enroll-key-missing(15),
                       enroll-req-missing(16),
                       enroll-bad-reply(17),
                       ca-ra-requested(18),
                       ca-ra-received(19),
                       ca-ra-ok(20),
                       ca-ra-need-update(21),
                       ca-ra-bad(22),
                       ca-ra-bad-config(23),
                       not-a-ca-cert(24),
                       fingerprint-check-failed(25),
                       job-busy(26),
                       job-timeout(27),
                       job-scep-not-free(28),
                       job-no-url(29),
                       job-no-scep-msg(30),
                       utc-err(31),
                       mem-err(32),
                       msg-len-err(33),
                       selfsigned-err(34),
                       pkcs7-wrap-err(35),
                       pkcs7-unwrap-err(36),
                       gen-err(37),
                       job-httpc-err(38),
                       job-httpc-con-err(39),
                       job-httpc-dns-err(40),
                       job-httpc-prot-err(41),
                       job-httpc-mem-err(42),
                       job-wdog-err(43),
                       ok(44),
                       dn-normalization-failed(45),
                       io-err(46),
                       disabled(47)
                     }
                     MAX-ACCESS read-only
                     STATUS current
                     DESCRIPTION "Status"
                     ::= {  staCertiSceCasEntry 8 }

staCertiSceCasMd5fin OBJECT-TYPE
                     SYNTAX DisplayString (SIZE(0..46))
                     MAX-ACCESS read-only
                     STATUS current
                     DESCRIPTION "md5-Fingerprint"
                     ::= {  staCertiSceCasEntry 10 }

staCertiSceCasSha1fi OBJECT-TYPE
                     SYNTAX DisplayString (SIZE(0..58))
                     MAX-ACCESS read-only
                     STATUS current
                     DESCRIPTION "sha1-Fingerprint"
                     ::= {  staCertiSceCasEntry 11 }

staCertiSceCasExpsnm OBJECT-TYPE
                     SYNTAX INTEGER (0..2147483647)
                     MAX-ACCESS read-only
                     STATUS current
                     DESCRIPTION "Exp-SNMP"
                     ::= {  staCertiSceCasEntry 12 }

staCertiSceCasIsssnm OBJECT-TYPE
                     SYNTAX INTEGER (0..2147483647)
                     MAX-ACCESS read-only
                     STATUS current
                     DESCRIPTION "Iss-SNMP"
                     ::= {  staCertiSceCasEntry 13 }

staCertiSceRasTable OBJECT-TYPE
                      SYNTAX SEQUENCE OF StaCertiSceRasEntry
                      MAX-ACCESS not-accessible
                      STATUS current
                      DESCRIPTION "RAs"
                      ::= {  staCertiSce 5 }

staCertiSceRasEntry OBJECT-TYPE
                      SYNTAX StaCertiSceRasEntry
                      MAX-ACCESS not-accessible
                      STATUS current
                      DESCRIPTION "entry in table"
                      INDEX { staCertiSceRasIdx }
                      ::= {  staCertiSceRasTable 1 }

StaCertiSceRasEntry ::= SEQUENCE {
                      staCertiSceRasIdx INTEGER,
                      staCertiSceRasName DisplayString,
                      staCertiSceRasExpire DisplayString,
                      staCertiSceRasIssued DisplayString,
                      staCertiSceRasKeyusa DisplayString,
                      staCertiSceRasIssuer DisplayString,
                      staCertiSceRasSubjec DisplayString,
                      staCertiSceRasStatus INTEGER,
                      staCertiSceRasExpsnm INTEGER,
                      staCertiSceRasIsssnm INTEGER
                     }

staCertiSceRasIdx OBJECT-TYPE
                     SYNTAX INTEGER (0..2147483647)
                     MAX-ACCESS read-only
                     STATUS current
                     DESCRIPTION "Idx."
                     ::= {  staCertiSceRasEntry 1 }

staCertiSceRasName OBJECT-TYPE
                     SYNTAX DisplayString (SIZE(0..15))
                     MAX-ACCESS read-only
                     STATUS current
                     DESCRIPTION "Name"
                     ::= {  staCertiSceRasEntry 2 }

staCertiSceRasExpire OBJECT-TYPE
                     SYNTAX DisplayString (SIZE(0..19))
                     MAX-ACCESS read-only
                     STATUS current
                     DESCRIPTION "Expires"
                     ::= {  staCertiSceRasEntry 3 }

staCertiSceRasIssued OBJECT-TYPE
                     SYNTAX DisplayString (SIZE(0..19))
                     MAX-ACCESS read-only
                     STATUS current
                     DESCRIPTION "Issued"
                     ::= {  staCertiSceRasEntry 4 }

staCertiSceRasKeyusa OBJECT-TYPE
                     SYNTAX DisplayString (SIZE(0..251))
                     MAX-ACCESS read-only
                     STATUS current
                     DESCRIPTION "Key-Usage"
                     ::= {  staCertiSceRasEntry 5 }

staCertiSceRasIssuer OBJECT-TYPE
                     SYNTAX DisplayString (SIZE(0..251))
                     MAX-ACCESS read-only
                     STATUS current
                     DESCRIPTION "Issuer"
                     ::= {  staCertiSceRasEntry 6 }

staCertiSceRasSubjec OBJECT-TYPE
                     SYNTAX DisplayString (SIZE(0..251))
                     MAX-ACCESS read-only
                     STATUS current
                     DESCRIPTION "Subject"
                     ::= {  staCertiSceRasEntry 7 }

staCertiSceRasStatus OBJECT-TYPE
                     SYNTAX INTEGER{
                       status-unknown(0),
                       enroll-requested(1),
                       enroll-received(2),
                       enroll-ok(3),
                       enroll-bad(4),
                       enroll-bad-config(5),
                       enroll-pending(6),
                       enroll-rejected(7),
                       enroll-rejected-badalg(8),
                       enroll-rejected-badmsgchk(9),
                       enroll-rejected-badreq(10),
                       enroll-rejected-badtime(11),
                       enroll-rejected-badcertid(12),
                       enroll-ca-missing(13),
                       enroll-exp-unknown(14),
                       enroll-key-missing(15),
                       enroll-req-missing(16),
                       enroll-bad-reply(17),
                       ca-ra-requested(18),
                       ca-ra-received(19),
                       ca-ra-ok(20),
                       ca-ra-need-update(21),
                       ca-ra-bad(22),
                       ca-ra-bad-config(23),
                       not-a-ca-cert(24),
                       fingerprint-check-failed(25),
                       job-busy(26),
                       job-timeout(27),
                       job-scep-not-free(28),
                       job-no-url(29),
                       job-no-scep-msg(30),
                       utc-err(31),
                       mem-err(32),
                       msg-len-err(33),
                       selfsigned-err(34),
                       pkcs7-wrap-err(35),
                       pkcs7-unwrap-err(36),
                       gen-err(37),
                       job-httpc-err(38),
                       job-httpc-con-err(39),
                       job-httpc-dns-err(40),
                       job-httpc-prot-err(41),
                       job-httpc-mem-err(42),
                       job-wdog-err(43),
                       ok(44),
                       dn-normalization-failed(45),
                       io-err(46),
                       disabled(47)
                     }
                     MAX-ACCESS read-only
                     STATUS current
                     DESCRIPTION "Status"
                     ::= {  staCertiSceRasEntry 8 }

staCertiSceRasExpsnm OBJECT-TYPE
                     SYNTAX INTEGER (0..2147483647)
                     MAX-ACCESS read-only
                     STATUS current
                     DESCRIPTION "Exp-SNMP"
                     ::= {  staCertiSceRasEntry 9 }

staCertiSceRasIsssnm OBJECT-TYPE
                     SYNTAX INTEGER (0..2147483647)
                     MAX-ACCESS read-only
                     STATUS current
                     DESCRIPTION "Iss-SNMP"
                     ::= {  staCertiSceRasEntry 10 }

staCertiSceCertsTable OBJECT-TYPE
                      SYNTAX SEQUENCE OF StaCertiSceCertsEntry
                      MAX-ACCESS not-accessible
                      STATUS current
                      DESCRIPTION "Certs"
                      ::= {  staCertiSce 6 }

staCertiSceCertsEntry OBJECT-TYPE
                      SYNTAX StaCertiSceCertsEntry
                      MAX-ACCESS not-accessible
                      STATUS current
                      DESCRIPTION "entry in table"
                      INDEX { staCertiSceCertsIdx }
                      ::= {  staCertiSceCertsTable 1 }

StaCertiSceCertsEntry ::= SEQUENCE {
                      staCertiSceCertsIdx INTEGER,
                      staCertiSceCertsName DisplayString,
                      staCertiSceCertsExpires DisplayString,
                      staCertiSceCertsIssued DisplayString,
                      staCertiSceCertsKeyusage DisplayString,
                      staCertiSceCertsExtended DisplayString,
                      staCertiSceCertsSubjecta DisplayString,
                      staCertiSceCertsIssuer DisplayString,
                      staCertiSceCertsSubject DisplayString,
                      staCertiSceCertsStatus INTEGER,
                      staCertiSceCertsExpsnmp INTEGER,
                      staCertiSceCertsIsssnmp INTEGER
                     }

staCertiSceCertsIdx OBJECT-TYPE
                         SYNTAX INTEGER (0..2147483647)
                         MAX-ACCESS read-only
                         STATUS current
                         DESCRIPTION "Idx."
                         ::= {  staCertiSceCertsEntry 1 }

staCertiSceCertsName OBJECT-TYPE
                         SYNTAX DisplayString (SIZE(0..15))
                         MAX-ACCESS read-only
                         STATUS current
                         DESCRIPTION "Name"
                         ::= {  staCertiSceCertsEntry 2 }

staCertiSceCertsExpires OBJECT-TYPE
                         SYNTAX DisplayString (SIZE(0..19))
                         MAX-ACCESS read-only
                         STATUS current
                         DESCRIPTION "Expires"
                         ::= {  staCertiSceCertsEntry 3 }

staCertiSceCertsIssued OBJECT-TYPE
                         SYNTAX DisplayString (SIZE(0..19))
                         MAX-ACCESS read-only
                         STATUS current
                         DESCRIPTION "Issued"
                         ::= {  staCertiSceCertsEntry 4 }

staCertiSceCertsKeyusage OBJECT-TYPE
                         SYNTAX DisplayString (SIZE(0..251))
                         MAX-ACCESS read-only
                         STATUS current
                         DESCRIPTION "Key-Usage"
                         ::= {  staCertiSceCertsEntry 5 }

staCertiSceCertsExtended OBJECT-TYPE
                         SYNTAX DisplayString (SIZE(0..251))
                         MAX-ACCESS read-only
                         STATUS current
                         DESCRIPTION "Extended-KeyUsage"
                         ::= {  staCertiSceCertsEntry 12 }

staCertiSceCertsSubjecta OBJECT-TYPE
                         SYNTAX DisplayString (SIZE(0..251))
                         MAX-ACCESS read-only
                         STATUS current
                         DESCRIPTION "SubjectAltName"
                         ::= {  staCertiSceCertsEntry 6 }

staCertiSceCertsIssuer OBJECT-TYPE
                         SYNTAX DisplayString (SIZE(0..251))
                         MAX-ACCESS read-only
                         STATUS current
                         DESCRIPTION "Issuer"
                         ::= {  staCertiSceCertsEntry 7 }

staCertiSceCertsSubject OBJECT-TYPE
                         SYNTAX DisplayString (SIZE(0..251))
                         MAX-ACCESS read-only
                         STATUS current
                         DESCRIPTION "Subject"
                         ::= {  staCertiSceCertsEntry 8 }

staCertiSceCertsStatus OBJECT-TYPE
                         SYNTAX INTEGER{
                           status-unknown(0),
                           enroll-requested(1),
                           enroll-received(2),
                           enroll-ok(3),
                           enroll-bad(4),
                           enroll-bad-config(5),
                           enroll-pending(6),
                           enroll-rejected(7),
                           enroll-rejected-badalg(8),
                           enroll-rejected-badmsgchk(9),
                           enroll-rejected-badreq(10),
                           enroll-rejected-badtime(11),
                           enroll-rejected-badcertid(12),
                           enroll-ca-missing(13),
                           enroll-exp-unknown(14),
                           enroll-key-missing(15),
                           enroll-req-missing(16),
                           enroll-bad-reply(17),
                           ca-ra-requested(18),
                           ca-ra-received(19),
                           ca-ra-ok(20),
                           ca-ra-need-update(21),
                           ca-ra-bad(22),
                           ca-ra-bad-config(23),
                           not-a-ca-cert(24),
                           fingerprint-check-failed(25),
                           job-busy(26),
                           job-timeout(27),
                           job-scep-not-free(28),
                           job-no-url(29),
                           job-no-scep-msg(30),
                           utc-err(31),
                           mem-err(32),
                           msg-len-err(33),
                           selfsigned-err(34),
                           pkcs7-wrap-err(35),
                           pkcs7-unwrap-err(36),
                           gen-err(37),
                           job-httpc-err(38),
                           job-httpc-con-err(39),
                           job-httpc-dns-err(40),
                           job-httpc-prot-err(41),
                           job-httpc-mem-err(42),
                           job-wdog-err(43),
                           ok(44),
                           dn-normalization-failed(45),
                           io-err(46),
                           disabled(47)
                         }
                         MAX-ACCESS read-only
                         STATUS current
                         DESCRIPTION "Status"
                         ::= {  staCertiSceCertsEntry 9 }

staCertiSceCertsExpsnmp OBJECT-TYPE
                         SYNTAX INTEGER (0..2147483647)
                         MAX-ACCESS read-only
                         STATUS current
                         DESCRIPTION "Exp-SNMP"
                         ::= {  staCertiSceCertsEntry 10 }

staCertiSceCertsIsssnmp OBJECT-TYPE
                         SYNTAX INTEGER (0..2147483647)
                         MAX-ACCESS read-only
                         STATUS current
                         DESCRIPTION "Iss-SNMP"
                         ::= {  staCertiSceCertsEntry 11 }

staCertiSceDelet OBJECT-TYPE
                 SYNTAX DisplayString
                 MAX-ACCESS read-write
                 STATUS current
                 DESCRIPTION "Delete-Values"
                 ::= {  staCertiSce 7 }

staVlan OBJECT IDENTIFIER ::= { sta 62}
staVlanOpe OBJECT-TYPE
           SYNTAX INTEGER {
             no(0),
             yes(1)
           }
           MAX-ACCESS read-only
           STATUS current
           DESCRIPTION "Operating"
           ::= {  staVlan 4 }

staVlanNetTable OBJECT-TYPE
                SYNTAX SEQUENCE OF StaVlanNetEntry
                MAX-ACCESS not-accessible
                STATUS current
                DESCRIPTION "Networks"
                ::= {  staVlan 1 }

staVlanNetEntry OBJECT-TYPE
                SYNTAX StaVlanNetEntry
                MAX-ACCESS not-accessible
                STATUS current
                DESCRIPTION "entry in table"
                INDEX { staVlanNetVla }
                ::= {  staVlanNetTable 1 }

StaVlanNetEntry ::= SEQUENCE {
                staVlanNetVla INTEGER,
                staVlanNetPor DisplayString
               }

staVlanNetVla OBJECT-TYPE
              SYNTAX INTEGER (0..65535)
              MAX-ACCESS read-only
              STATUS current
              DESCRIPTION "VLAN-ID"
              ::= {  staVlanNetEntry 1 }

staVlanNetPor OBJECT-TYPE
              SYNTAX DisplayString (SIZE(0..255))
              MAX-ACCESS read-only
              STATUS current
              DESCRIPTION "Ports"
              ::= {  staVlanNetEntry 4 }

staVlanPorTable OBJECT-TYPE
                SYNTAX SEQUENCE OF StaVlanPorEntry
                MAX-ACCESS not-accessible
                STATUS current
                DESCRIPTION "Port-Table"
                ::= {  staVlan 2 }

staVlanPorEntry OBJECT-TYPE
                SYNTAX StaVlanPorEntry
                MAX-ACCESS not-accessible
                STATUS current
                DESCRIPTION "entry in table"
                INDEX { staVlanPorPor }
                ::= {  staVlanPorTable 1 }

StaVlanPorEntry ::= SEQUENCE {
                staVlanPorPor DisplayString,
                staVlanPorTag INTEGER
               }

staVlanPorPor OBJECT-TYPE
              SYNTAX DisplayString (SIZE(0..8))
              MAX-ACCESS read-only
              STATUS current
              DESCRIPTION "Port"
              ::= {  staVlanPorEntry 1 }

staVlanPorTag OBJECT-TYPE
              SYNTAX INTEGER{
                ingress-mixed(0),
                never(1),
                mixed(2),
                always(3)
              }
              MAX-ACCESS read-only
              STATUS current
              DESCRIPTION "Tagging-Mode"
              ::= {  staVlanPorEntry 6 }

staDelet OBJECT-TYPE
         SYNTAX DisplayString
         MAX-ACCESS read-write
         STATUS current
         DESCRIPTION "Delete-Values"
         ::= {  sta 100 }

setName OBJECT-TYPE
         SYNTAX DisplayString (SIZE(0..16))
         MAX-ACCESS read-write
         STATUS current
         DESCRIPTION "Name"
         ::= {  set 1 }

setWan OBJECT IDENTIFIER ::= { set 2}
setWanDialuppTable OBJECT-TYPE
                   SYNTAX SEQUENCE OF SetWanDialuppEntry
                   MAX-ACCESS not-accessible
                   STATUS current
                   DESCRIPTION "Dialup-Peers"
                   ::= {  setWan 2 }

setWanDialuppEntry OBJECT-TYPE
                   SYNTAX SetWanDialuppEntry
                   MAX-ACCESS not-accessible
                   STATUS current
                   DESCRIPTION "entry in table"
                   INDEX { setWanDialuppPee }
                   ::= {  setWanDialuppTable 1 }

SetWanDialuppEntry ::= SEQUENCE {
                   setWanDialuppPee DisplayString,
                   setWanDialuppDia DisplayString,
                   setWanDialuppB1d INTEGER,
                   setWanDialuppB2d INTEGER,
                   setWanDialuppWan DisplayString,
                   setWanDialuppCal INTEGER
                  }

setWanDialuppPee OBJECT-TYPE
                 SYNTAX DisplayString (SIZE(0..16))
                 MAX-ACCESS read-write
                 STATUS current
                 DESCRIPTION "Peer"
                 ::= {  setWanDialuppEntry 1 }

setWanDialuppDia OBJECT-TYPE
                 SYNTAX DisplayString (SIZE(0..31))
                 MAX-ACCESS read-write
                 STATUS current
                 DESCRIPTION "Dialup-remote"
                 ::= {  setWanDialuppEntry 2 }

setWanDialuppB1d OBJECT-TYPE
                 SYNTAX INTEGER (0..65535)
                 MAX-ACCESS read-write
                 STATUS current
                 DESCRIPTION "B1-DT"
                 ::= {  setWanDialuppEntry 3 }

setWanDialuppB2d OBJECT-TYPE
                 SYNTAX INTEGER (0..65535)
                 MAX-ACCESS read-write
                 STATUS current
                 DESCRIPTION "B2-DT"
                 ::= {  setWanDialuppEntry 4 }

setWanDialuppWan OBJECT-TYPE
                 SYNTAX DisplayString (SIZE(0..9))
                 MAX-ACCESS read-write
                 STATUS current
                 DESCRIPTION "WAN-layer"
                 ::= {  setWanDialuppEntry 5 }

setWanDialuppCal OBJECT-TYPE
                 SYNTAX INTEGER{
                   no(0),
                   auto(1),
                   name(5),
                   fast(9),
                   looser(2)
                 }
                 MAX-ACCESS read-write
                 STATUS current
                 DESCRIPTION "Callback"
                 ::= {  setWanDialuppEntry 6 }

setWanRoundroTable OBJECT-TYPE
                   SYNTAX SEQUENCE OF SetWanRoundroEntry
                   MAX-ACCESS not-accessible
                   STATUS current
                   DESCRIPTION "RoundRobin"
                   ::= {  setWan 3 }

setWanRoundroEntry OBJECT-TYPE
                   SYNTAX SetWanRoundroEntry
                   MAX-ACCESS not-accessible
                   STATUS current
                   DESCRIPTION "entry in table"
                   INDEX { setWanRoundroPee }
                   ::= {  setWanRoundroTable 1 }

SetWanRoundroEntry ::= SEQUENCE {
                   setWanRoundroPee DisplayString,
                   setWanRoundroRou DisplayString,
                   setWanRoundroHea INTEGER
                  }

setWanRoundroPee OBJECT-TYPE
                 SYNTAX DisplayString (SIZE(0..18))
                 MAX-ACCESS read-write
                 STATUS current
                 DESCRIPTION "Peer"
                 ::= {  setWanRoundroEntry 1 }

setWanRoundroRou OBJECT-TYPE
                 SYNTAX DisplayString (SIZE(0..53))
                 MAX-ACCESS read-write
                 STATUS current
                 DESCRIPTION "Round-Robin"
                 ::= {  setWanRoundroEntry 2 }

setWanRoundroHea OBJECT-TYPE
                 SYNTAX INTEGER{
                   last(0),
                   first(1)
                 }
                 MAX-ACCESS read-write
                 STATUS current
                 DESCRIPTION "Head"
                 ::= {  setWanRoundroEntry 3 }

setWanLayerTable OBJECT-TYPE
                   SYNTAX SEQUENCE OF SetWanLayerEntry
                   MAX-ACCESS not-accessible
                   STATUS current
                   DESCRIPTION "Layer"
                   ::= {  setWan 4 }

setWanLayerEntry OBJECT-TYPE
                   SYNTAX SetWanLayerEntry
                   MAX-ACCESS not-accessible
                   STATUS current
                   DESCRIPTION "entry in table"
                   INDEX { setWanLayerWanl }
                   ::= {  setWanLayerTable 1 }

SetWanLayerEntry ::= SEQUENCE {
                   setWanLayerWanl DisplayString,
                   setWanLayerEnca INTEGER,
                   setWanLayerLay3 INTEGER,
                   setWanLayerLay2 INTEGER,
                   setWanLayerL2op INTEGER,
                   setWanLayerLay1 INTEGER
                  }

setWanLayerWanl OBJECT-TYPE
                SYNTAX DisplayString (SIZE(0..9))
                MAX-ACCESS read-write
                STATUS current
                DESCRIPTION "WAN-layer"
                ::= {  setWanLayerEntry 1 }

setWanLayerEnca OBJECT-TYPE
                SYNTAX INTEGER{
                  ether(0),
                  trans(255)
                }
                MAX-ACCESS read-write
                STATUS current
                DESCRIPTION "Encaps."
                ::= {  setWanLayerEntry 2 }

setWanLayerLay3 OBJECT-TYPE
                SYNTAX INTEGER{
                  ppp(4),
                  appp(5),
                  scppp(6),
                  scappp(7),
                  sctrans(8),
                  dhcp(9),
                  trans(255)
                }
                MAX-ACCESS read-write
                STATUS current
                DESCRIPTION "Lay-3"
                ::= {  setWanLayerEntry 3 }

setWanLayerLay2 OBJECT-TYPE
                SYNTAX INTEGER{
                  pppoe(5),
                  trans(1)
                }
                MAX-ACCESS read-write
                STATUS current
                DESCRIPTION "Lay-2"
                ::= {  setWanLayerEntry 4 }

setWanLayerL2op OBJECT-TYPE
                SYNTAX INTEGER{
                  none(255),
                  compr(0)
                }
                MAX-ACCESS read-write
                STATUS current
                DESCRIPTION "L2-Opt."
                ::= {  setWanLayerEntry 5 }

setWanLayerLay1 OBJECT-TYPE
                SYNTAX INTEGER{
                  eth(4),
                  serial(6)
                }
                MAX-ACCESS read-write
                STATUS current
                DESCRIPTION "Lay-1"
                ::= {  setWanLayerEntry 6 }

setWanPppTable OBJECT-TYPE
                   SYNTAX SEQUENCE OF SetWanPppEntry
                   MAX-ACCESS not-accessible
                   STATUS current
                   DESCRIPTION "PPP"
                   ::= {  setWan 5 }

setWanPppEntry OBJECT-TYPE
                   SYNTAX SetWanPppEntry
                   MAX-ACCESS not-accessible
                   STATUS current
                   DESCRIPTION "entry in table"
                   INDEX { setWanPppPee }
                   ::= {  setWanPppTable 1 }

SetWanPppEntry ::= SEQUENCE {
                   setWanPppPee DisplayString,
                   setWanPppAut INTEGER,
                   setWanPppKey DisplayString,
                   setWanPppTim INTEGER,
                   setWanPppTry INTEGER,
                   setWanPppCon INTEGER,
                   setWanPppFai INTEGER,
                   setWanPppTer INTEGER,
                   setWanPppUse DisplayString,
                   setWanPppRig INTEGER
                  }

setWanPppPee OBJECT-TYPE
             SYNTAX DisplayString (SIZE(0..16))
             MAX-ACCESS read-write
             STATUS current
             DESCRIPTION "Peer"
             ::= {  setWanPppEntry 1 }

setWanPppAut OBJECT-TYPE
             SYNTAX INTEGER{
               none(0),
               chap(8),
               pap(4)
             }
             MAX-ACCESS read-write
             STATUS current
             DESCRIPTION "Authent."
             ::= {  setWanPppEntry 2 }

setWanPppKey OBJECT-TYPE
             SYNTAX DisplayString (SIZE(0..32))
             MAX-ACCESS read-write
             STATUS current
             DESCRIPTION "Key"
             ::= {  setWanPppEntry 3 }

setWanPppTim OBJECT-TYPE
             SYNTAX INTEGER (0..255)
             MAX-ACCESS read-write
             STATUS current
             DESCRIPTION "Time"
             ::= {  setWanPppEntry 4 }

setWanPppTry OBJECT-TYPE
             SYNTAX INTEGER (0..255)
             MAX-ACCESS read-write
             STATUS current
             DESCRIPTION "Try"
             ::= {  setWanPppEntry 5 }

setWanPppCon OBJECT-TYPE
             SYNTAX INTEGER (0..255)
             MAX-ACCESS read-write
             STATUS current
             DESCRIPTION "Conf"
             ::= {  setWanPppEntry 7 }

setWanPppFai OBJECT-TYPE
             SYNTAX INTEGER (0..255)
             MAX-ACCESS read-write
             STATUS current
             DESCRIPTION "Fail"
             ::= {  setWanPppEntry 8 }

setWanPppTer OBJECT-TYPE
             SYNTAX INTEGER (0..255)
             MAX-ACCESS read-write
             STATUS current
             DESCRIPTION "Term"
             ::= {  setWanPppEntry 9 }

setWanPppUse OBJECT-TYPE
             SYNTAX DisplayString (SIZE(0..64))
             MAX-ACCESS read-write
             STATUS current
             DESCRIPTION "Username"
             ::= {  setWanPppEntry 6 }

setWanPppRig OBJECT-TYPE
             SYNTAX INTEGER{
               none(0),
               ip(1),
               ip-plus-nbt(3)
             }
             MAX-ACCESS read-write
             STATUS current
             DESCRIPTION "Rights"
             ::= {  setWanPppEntry 10 }

setWanDslbroaTable OBJECT-TYPE
                   SYNTAX SEQUENCE OF SetWanDslbroaEntry
                   MAX-ACCESS not-accessible
                   STATUS current
                   DESCRIPTION "DSL-Broadband-Peers"
                   ::= {  setWan 19 }

setWanDslbroaEntry OBJECT-TYPE
                   SYNTAX SetWanDslbroaEntry
                   MAX-ACCESS not-accessible
                   STATUS current
                   DESCRIPTION "entry in table"
                   INDEX { setWanDslbroaPee }
                   ::= {  setWanDslbroaTable 1 }

SetWanDslbroaEntry ::= SEQUENCE {
                   setWanDslbroaPee DisplayString,
                   setWanDslbroaSht INTEGER,
                   setWanDslbroaAcn DisplayString,
                   setWanDslbroaSer DisplayString,
                   setWanDslbroaWan DisplayString,
                   setWanDslbroaMac INTEGER,
                   setWanDslbroaUse MacAddress,
                   setWanDslbroaVla INTEGER
                  }

setWanDslbroaPee OBJECT-TYPE
                 SYNTAX DisplayString (SIZE(0..16))
                 MAX-ACCESS read-write
                 STATUS current
                 DESCRIPTION "Peer"
                 ::= {  setWanDslbroaEntry 1 }

setWanDslbroaSht OBJECT-TYPE
                 SYNTAX INTEGER (0..65535)
                 MAX-ACCESS read-write
                 STATUS current
                 DESCRIPTION "SH-Time"
                 ::= {  setWanDslbroaEntry 3 }

setWanDslbroaAcn OBJECT-TYPE
                 SYNTAX DisplayString (SIZE(0..64))
                 MAX-ACCESS read-write
                 STATUS current
                 DESCRIPTION "AC-name"
                 ::= {  setWanDslbroaEntry 9 }

setWanDslbroaSer OBJECT-TYPE
                 SYNTAX DisplayString (SIZE(0..32))
                 MAX-ACCESS read-write
                 STATUS current
                 DESCRIPTION "Servicename"
                 ::= {  setWanDslbroaEntry 10 }

setWanDslbroaWan OBJECT-TYPE
                 SYNTAX DisplayString (SIZE(0..9))
                 MAX-ACCESS read-write
                 STATUS current
                 DESCRIPTION "WAN-layer"
                 ::= {  setWanDslbroaEntry 5 }

setWanDslbroaMac OBJECT-TYPE
                 SYNTAX INTEGER{
                   gserverl(1),
                   local(0),
                   user-def(2)
                 }
                 MAX-ACCESS read-write
                 STATUS current
                 DESCRIPTION "MAC-Type"
                 ::= {  setWanDslbroaEntry 15 }

setWanDslbroaUse OBJECT-TYPE
                 SYNTAX MacAddress
                 MAX-ACCESS read-write
                 STATUS current
                 DESCRIPTION "user-def.-MAC"
                 ::= {  setWanDslbroaEntry 13 }

setWanDslbroaVla OBJECT-TYPE
                 SYNTAX INTEGER (0..65535)
                 MAX-ACCESS read-write
                 STATUS current
                 DESCRIPTION "VLAN-ID"
                 ::= {  setWanDslbroaEntry 16 }

setWanMtulistTable OBJECT-TYPE
                   SYNTAX SEQUENCE OF SetWanMtulistEntry
                   MAX-ACCESS not-accessible
                   STATUS current
                   DESCRIPTION "MTU-List"
                   ::= {  setWan 26 }

setWanMtulistEntry OBJECT-TYPE
                   SYNTAX SetWanMtulistEntry
                   MAX-ACCESS not-accessible
                   STATUS current
                   DESCRIPTION "entry in table"
                   INDEX { setWanMtulistPee }
                   ::= {  setWanMtulistTable 1 }

SetWanMtulistEntry ::= SEQUENCE {
                   setWanMtulistPee DisplayString,
                   setWanMtulistMtu INTEGER
                  }

setWanMtulistPee OBJECT-TYPE
                 SYNTAX DisplayString (SIZE(0..16))
                 MAX-ACCESS read-write
                 STATUS current
                 DESCRIPTION "Peer"
                 ::= {  setWanMtulistEntry 1 }

setWanMtulistMtu OBJECT-TYPE
                 SYNTAX INTEGER (0..65535)
                 MAX-ACCESS read-write
                 STATUS current
                 DESCRIPTION "MTU"
                 ::= {  setWanMtulistEntry 2 }

setWanIplistTable OBJECT-TYPE
                   SYNTAX SEQUENCE OF SetWanIplistEntry
                   MAX-ACCESS not-accessible
                   STATUS current
                   DESCRIPTION "IP-List"
                   ::= {  setWan 20 }

setWanIplistEntry OBJECT-TYPE
                   SYNTAX SetWanIplistEntry
                   MAX-ACCESS not-accessible
                   STATUS current
                   DESCRIPTION "entry in table"
                   INDEX { setWanIplistPeer }
                   ::= {  setWanIplistTable 1 }

SetWanIplistEntry ::= SEQUENCE {
                   setWanIplistPeer DisplayString,
                   setWanIplistIpadd IpAddress,
                   setWanIplistIpnet IpAddress,
                   setWanIplistMasqi IpAddress,
                   setWanIplistGatew IpAddress,
                   setWanIplistDnsde IpAddress,
                   setWanIplistDnsba IpAddress,
                   setWanIplistNbnsd IpAddress,
                   setWanIplistNbnsb IpAddress
                  }

setWanIplistPeer OBJECT-TYPE
                  SYNTAX DisplayString (SIZE(0..17))
                  MAX-ACCESS read-write
                  STATUS current
                  DESCRIPTION "Peer"
                  ::= {  setWanIplistEntry 1 }

setWanIplistIpadd OBJECT-TYPE
                  SYNTAX IpAddress
                  MAX-ACCESS read-write
                  STATUS current
                  DESCRIPTION "IP-Address"
                  ::= {  setWanIplistEntry 2 }

setWanIplistIpnet OBJECT-TYPE
                  SYNTAX IpAddress
                  MAX-ACCESS read-write
                  STATUS current
                  DESCRIPTION "IP-Netmask"
                  ::= {  setWanIplistEntry 3 }

setWanIplistMasqi OBJECT-TYPE
                  SYNTAX IpAddress
                  MAX-ACCESS read-write
                  STATUS current
                  DESCRIPTION "Masq.-IP-Addr."
                  ::= {  setWanIplistEntry 9 }

setWanIplistGatew OBJECT-TYPE
                  SYNTAX IpAddress
                  MAX-ACCESS read-write
                  STATUS current
                  DESCRIPTION "Gateway"
                  ::= {  setWanIplistEntry 4 }

setWanIplistDnsde OBJECT-TYPE
                  SYNTAX IpAddress
                  MAX-ACCESS read-write
                  STATUS current
                  DESCRIPTION "DNS-Default"
                  ::= {  setWanIplistEntry 5 }

setWanIplistDnsba OBJECT-TYPE
                  SYNTAX IpAddress
                  MAX-ACCESS read-write
                  STATUS current
                  DESCRIPTION "DNS-Backup"
                  ::= {  setWanIplistEntry 6 }

setWanIplistNbnsd OBJECT-TYPE
                  SYNTAX IpAddress
                  MAX-ACCESS read-write
                  STATUS current
                  DESCRIPTION "NBNS-Default"
                  ::= {  setWanIplistEntry 7 }

setWanIplistNbnsb OBJECT-TYPE
                  SYNTAX IpAddress
                  MAX-ACCESS read-write
                  STATUS current
                  DESCRIPTION "NBNS-Backup"
                  ::= {  setWanIplistEntry 8 }

setWanPptppeeTable OBJECT-TYPE
                   SYNTAX SEQUENCE OF SetWanPptppeeEntry
                   MAX-ACCESS not-accessible
                   STATUS current
                   DESCRIPTION "PPTP-Peers"
                   ::= {  setWan 21 }

setWanPptppeeEntry OBJECT-TYPE
                   SYNTAX SetWanPptppeeEntry
                   MAX-ACCESS not-accessible
                   STATUS current
                   DESCRIPTION "entry in table"
                   INDEX { setWanPptppeePee }
                   ::= {  setWanPptppeeTable 1 }

SetWanPptppeeEntry ::= SEQUENCE {
                   setWanPptppeePee DisplayString,
                   setWanPptppeeIpa IpAddress,
                   setWanPptppeeRtg INTEGER,
                   setWanPptppeePor INTEGER,
                   setWanPptppeeSht INTEGER
                  }

setWanPptppeePee OBJECT-TYPE
                 SYNTAX DisplayString (SIZE(0..16))
                 MAX-ACCESS read-write
                 STATUS current
                 DESCRIPTION "Peer"
                 ::= {  setWanPptppeeEntry 1 }

setWanPptppeeIpa OBJECT-TYPE
                 SYNTAX IpAddress
                 MAX-ACCESS read-write
                 STATUS current
                 DESCRIPTION "IP-Address"
                 ::= {  setWanPptppeeEntry 2 }

setWanPptppeeRtg OBJECT-TYPE
                 SYNTAX INTEGER (0..65535)
                 MAX-ACCESS read-write
                 STATUS current
                 DESCRIPTION "Rtg-tag"
                 ::= {  setWanPptppeeEntry 5 }

setWanPptppeePor OBJECT-TYPE
                 SYNTAX INTEGER (0..65535)
                 MAX-ACCESS read-write
                 STATUS current
                 DESCRIPTION "Port"
                 ::= {  setWanPptppeeEntry 3 }

setWanPptppeeSht OBJECT-TYPE
                 SYNTAX INTEGER (0..65535)
                 MAX-ACCESS read-write
                 STATUS current
                 DESCRIPTION "SH-Time"
                 ::= {  setWanPptppeeEntry 4 }

setWanRadius OBJECT IDENTIFIER ::= { setWan 22}
setWanRadiusOpera OBJECT-TYPE
                  SYNTAX INTEGER {
                    no(0),
                    yes(1),
                    exclusive(2)
                  }
                  MAX-ACCESS read-write
                  STATUS current
                  DESCRIPTION "Operating"
                  ::= {  setWanRadius 1 }

setWanRadiusServe OBJECT-TYPE
                  SYNTAX IpAddress
                  MAX-ACCESS read-write
                  STATUS current
                  DESCRIPTION "Server-Address"
                  ::= {  setWanRadius 2 }

setWanRadiusAuthp OBJECT-TYPE
                  SYNTAX INTEGER
                  MAX-ACCESS read-write
                  STATUS current
                  DESCRIPTION "Auth.-Port"
                  ::= {  setWanRadius 3 }

setWanRadiusLoopb OBJECT-TYPE
                  SYNTAX DisplayString (SIZE(0..16))
                  MAX-ACCESS read-write
                  STATUS current
                  DESCRIPTION "Loopback-Addr."
                  ::= {  setWanRadius 8 }

setWanRadiusProto OBJECT-TYPE
                  SYNTAX INTEGER {
                    radius(0),
                    radsec(1)
                  }
                  MAX-ACCESS read-write
                  STATUS current
                  DESCRIPTION "Protocol"
                  ::= {  setWanRadius 9 }

setWanRadiusSecre OBJECT-TYPE
                  SYNTAX DisplayString (SIZE(0..31))
                  MAX-ACCESS read-write
                  STATUS current
                  DESCRIPTION "Secret"
                  ::= {  setWanRadius 4 }

setWanRadiusPppop OBJECT-TYPE
                  SYNTAX INTEGER {
                    no(0),
                    yes(1),
                    exclusive(2)
                  }
                  MAX-ACCESS read-write
                  STATUS current
                  DESCRIPTION "PPP-Operation"
                  ::= {  setWanRadius 5 }

setWanRadiusClipo OBJECT-TYPE
                  SYNTAX INTEGER {
                    no(0),
                    yes(1),
                    exclusive(2)
                  }
                  MAX-ACCESS read-write
                  STATUS current
                  DESCRIPTION "CLIP-Operation"
                  ::= {  setWanRadius 6 }

setWanRadiusClipp OBJECT-TYPE
                  SYNTAX DisplayString (SIZE(0..31))
                  MAX-ACCESS read-write
                  STATUS current
                  DESCRIPTION "CLIP-Password"
                  ::= {  setWanRadius 7 }

setWanPollingTable OBJECT-TYPE
                   SYNTAX SEQUENCE OF SetWanPollingEntry
                   MAX-ACCESS not-accessible
                   STATUS current
                   DESCRIPTION "Polling-Table"
                   ::= {  setWan 23 }

setWanPollingEntry OBJECT-TYPE
                   SYNTAX SetWanPollingEntry
                   MAX-ACCESS not-accessible
                   STATUS current
                   DESCRIPTION "entry in table"
                   INDEX { setWanPollingPeer }
                   ::= {  setWanPollingTable 1 }

SetWanPollingEntry ::= SEQUENCE {
                   setWanPollingPeer DisplayString,
                   setWanPollingIpaddress1 IpAddress,
                   setWanPollingIpaddress2 IpAddress,
                   setWanPollingIpaddress3 IpAddress,
                   setWanPollingIpaddress4 IpAddress,
                   setWanPollingTime INTEGER,
                   setWanPollingTry INTEGER,
                   setWanPollingLoopbackad DisplayString
                  }

setWanPollingPeer OBJECT-TYPE
                        SYNTAX DisplayString (SIZE(0..16))
                        MAX-ACCESS read-write
                        STATUS current
                        DESCRIPTION "Peer"
                        ::= {  setWanPollingEntry 1 }

setWanPollingIpaddress1 OBJECT-TYPE
                        SYNTAX IpAddress
                        MAX-ACCESS read-write
                        STATUS current
                        DESCRIPTION "IP-Address-1"
                        ::= {  setWanPollingEntry 2 }

setWanPollingIpaddress2 OBJECT-TYPE
                        SYNTAX IpAddress
                        MAX-ACCESS read-write
                        STATUS current
                        DESCRIPTION "IP-Address-2"
                        ::= {  setWanPollingEntry 5 }

setWanPollingIpaddress3 OBJECT-TYPE
                        SYNTAX IpAddress
                        MAX-ACCESS read-write
                        STATUS current
                        DESCRIPTION "IP-Address-3"
                        ::= {  setWanPollingEntry 6 }

setWanPollingIpaddress4 OBJECT-TYPE
                        SYNTAX IpAddress
                        MAX-ACCESS read-write
                        STATUS current
                        DESCRIPTION "IP-Address-4"
                        ::= {  setWanPollingEntry 7 }

setWanPollingTime OBJECT-TYPE
                        SYNTAX INTEGER (0..65535)
                        MAX-ACCESS read-write
                        STATUS current
                        DESCRIPTION "Time"
                        ::= {  setWanPollingEntry 3 }

setWanPollingTry OBJECT-TYPE
                        SYNTAX INTEGER (0..255)
                        MAX-ACCESS read-write
                        STATUS current
                        DESCRIPTION "Try"
                        ::= {  setWanPollingEntry 4 }

setWanPollingLoopbackad OBJECT-TYPE
                        SYNTAX DisplayString (SIZE(0..16))
                        MAX-ACCESS read-write
                        STATUS current
                        DESCRIPTION "Loopback-Addr."
                        ::= {  setWanPollingEntry 8 }

setWanBackuppTable OBJECT-TYPE
                   SYNTAX SEQUENCE OF SetWanBackuppEntry
                   MAX-ACCESS not-accessible
                   STATUS current
                   DESCRIPTION "Backup-Peers"
                   ::= {  setWan 24 }

setWanBackuppEntry OBJECT-TYPE
                   SYNTAX SetWanBackuppEntry
                   MAX-ACCESS not-accessible
                   STATUS current
                   DESCRIPTION "entry in table"
                   INDEX { setWanBackuppPee }
                   ::= {  setWanBackuppTable 1 }

SetWanBackuppEntry ::= SEQUENCE {
                   setWanBackuppPee DisplayString,
                   setWanBackuppAlt DisplayString,
                   setWanBackuppHea INTEGER
                  }

setWanBackuppPee OBJECT-TYPE
                 SYNTAX DisplayString (SIZE(0..18))
                 MAX-ACCESS read-write
                 STATUS current
                 DESCRIPTION "Peer"
                 ::= {  setWanBackuppEntry 1 }

setWanBackuppAlt OBJECT-TYPE
                 SYNTAX DisplayString (SIZE(0..53))
                 MAX-ACCESS read-write
                 STATUS current
                 DESCRIPTION "Alternative-Peers"
                 ::= {  setWanBackuppEntry 2 }

setWanBackuppHea OBJECT-TYPE
                 SYNTAX INTEGER{
                   last(0),
                   first(1)
                 }
                 MAX-ACCESS read-write
                 STATUS current
                 DESCRIPTION "Head"
                 ::= {  setWanBackuppEntry 3 }

setWanActiontTable OBJECT-TYPE
                   SYNTAX SEQUENCE OF SetWanActiontEntry
                   MAX-ACCESS not-accessible
                   STATUS current
                   DESCRIPTION "Action-Table"
                   ::= {  setWan 25 }

setWanActiontEntry OBJECT-TYPE
                   SYNTAX SetWanActiontEntry
                   MAX-ACCESS not-accessible
                   STATUS current
                   DESCRIPTION "entry in table"
                   INDEX { setWanActiontIndex }
                   ::= {  setWanActiontTable 1 }

SetWanActiontEntry ::= SEQUENCE {
                   setWanActiontIndex INTEGER,
                   setWanActiontActiv INTEGER,
                   setWanActiontHostn DisplayString,
                   setWanActiontPeer DisplayString,
                   setWanActiontLockt INTEGER,
                   setWanActiontCondi INTEGER,
                   setWanActiontActio DisplayString,
                   setWanActiontCheck DisplayString,
                   setWanActiontOwner DisplayString
                  }

setWanActiontIndex OBJECT-TYPE
                   SYNTAX INTEGER (0..65535)
                   MAX-ACCESS read-write
                   STATUS current
                   DESCRIPTION "Index"
                   ::= {  setWanActiontEntry 1 }

setWanActiontActiv OBJECT-TYPE
                   SYNTAX INTEGER{
                     yes(0),
                     no(1)
                   }
                   MAX-ACCESS read-write
                   STATUS current
                   DESCRIPTION "Active"
                   ::= {  setWanActiontEntry 8 }

setWanActiontHostn OBJECT-TYPE
                   SYNTAX DisplayString (SIZE(0..64))
                   MAX-ACCESS read-write
                   STATUS current
                   DESCRIPTION "Host-Name"
                   ::= {  setWanActiontEntry 2 }

setWanActiontPeer OBJECT-TYPE
                   SYNTAX DisplayString (SIZE(0..16))
                   MAX-ACCESS read-write
                   STATUS current
                   DESCRIPTION "Peer"
                   ::= {  setWanActiontEntry 3 }

setWanActiontLockt OBJECT-TYPE
                   SYNTAX INTEGER (0..2147483647)
                   MAX-ACCESS read-write
                   STATUS current
                   DESCRIPTION "Lock-Time"
                   ::= {  setWanActiontEntry 4 }

setWanActiontCondi OBJECT-TYPE
                   SYNTAX INTEGER{
                     establish(0),
                     disconnect(1),
                     broken(2)
                   }
                   MAX-ACCESS read-write
                   STATUS current
                   DESCRIPTION "Condition"
                   ::= {  setWanActiontEntry 5 }

setWanActiontActio OBJECT-TYPE
                   SYNTAX DisplayString (SIZE(0..250))
                   MAX-ACCESS read-write
                   STATUS current
                   DESCRIPTION "Action"
                   ::= {  setWanActiontEntry 6 }

setWanActiontCheck OBJECT-TYPE
                   SYNTAX DisplayString (SIZE(0..50))
                   MAX-ACCESS read-write
                   STATUS current
                   DESCRIPTION "Check-For"
                   ::= {  setWanActiontEntry 7 }

setWanActiontOwner OBJECT-TYPE
                   SYNTAX DisplayString (SIZE(0..16))
                   MAX-ACCESS read-write
                   STATUS current
                   DESCRIPTION "Owner"
                   ::= {  setWanActiontEntry 9 }

setWanBackupd OBJECT-TYPE
              SYNTAX INTEGER
              MAX-ACCESS read-write
              STATUS current
              DESCRIPTION "Backup-Delay-Seconds"
              ::= {  setWan 18 }

setWanIncominTable OBJECT-TYPE
                   SYNTAX SEQUENCE OF SetWanIncominEntry
                   MAX-ACCESS not-accessible
                   STATUS current
                   DESCRIPTION "Incoming-Calling-Numbers"
                   ::= {  setWan 6 }

setWanIncominEntry OBJECT-TYPE
                   SYNTAX SetWanIncominEntry
                   MAX-ACCESS not-accessible
                   STATUS current
                   DESCRIPTION "entry in table"
                   INDEX { setWanIncominDia }
                   ::= {  setWanIncominTable 1 }

SetWanIncominEntry ::= SEQUENCE {
                   setWanIncominDia DisplayString,
                   setWanIncominPee DisplayString
                  }

setWanIncominDia OBJECT-TYPE
                 SYNTAX DisplayString (SIZE(0..31))
                 MAX-ACCESS read-write
                 STATUS current
                 DESCRIPTION "Dialup-remote"
                 ::= {  setWanIncominEntry 1 }

setWanIncominPee OBJECT-TYPE
                 SYNTAX DisplayString (SIZE(0..16))
                 MAX-ACCESS read-write
                 STATUS current
                 DESCRIPTION "Peer"
                 ::= {  setWanIncominEntry 2 }

setWanScriptsTable OBJECT-TYPE
                   SYNTAX SEQUENCE OF SetWanScriptsEntry
                   MAX-ACCESS not-accessible
                   STATUS current
                   DESCRIPTION "Scripts"
                   ::= {  setWan 8 }

setWanScriptsEntry OBJECT-TYPE
                   SYNTAX SetWanScriptsEntry
                   MAX-ACCESS not-accessible
                   STATUS current
                   DESCRIPTION "entry in table"
                   INDEX { setWanScriptsPee }
                   ::= {  setWanScriptsTable 1 }

SetWanScriptsEntry ::= SEQUENCE {
                   setWanScriptsPee DisplayString,
                   setWanScriptsScr DisplayString
                  }

setWanScriptsPee OBJECT-TYPE
                 SYNTAX DisplayString (SIZE(0..18))
                 MAX-ACCESS read-write
                 STATUS current
                 DESCRIPTION "Peer"
                 ::= {  setWanScriptsEntry 1 }

setWanScriptsScr OBJECT-TYPE
                 SYNTAX DisplayString (SIZE(0..58))
                 MAX-ACCESS read-write
                 STATUS current
                 DESCRIPTION "Script"
                 ::= {  setWanScriptsEntry 2 }

setWanProtect OBJECT-TYPE
              SYNTAX INTEGER {
                none(0),
                number(2),
                screened(4)
              }
              MAX-ACCESS read-write
              STATUS current
              DESCRIPTION "Protect"
              ::= {  setWan 9 }

setWanCallbac OBJECT-TYPE
              SYNTAX INTEGER
              MAX-ACCESS read-write
              STATUS current
              DESCRIPTION "Callback-Attempts"
              ::= {  setWan 10 }

setWanManuald OBJECT IDENTIFIER ::= { setWan 13}
setWanManualdCon OBJECT-TYPE
                 SYNTAX DisplayString
                 MAX-ACCESS read-write
                 STATUS current
                 DESCRIPTION "Connect"
                 ::= {  setWanManuald 1 }

setWanManualdDis OBJECT-TYPE
                 SYNTAX DisplayString
                 MAX-ACCESS read-write
                 STATUS current
                 DESCRIPTION "Disconnect"
                 ::= {  setWanManuald 2 }

setWanRouteriTable OBJECT-TYPE
                   SYNTAX SEQUENCE OF SetWanRouteriEntry
                   MAX-ACCESS not-accessible
                   STATUS current
                   DESCRIPTION "Router-Interface"
                   ::= {  setWan 11 }

setWanRouteriEntry OBJECT-TYPE
                   SYNTAX SetWanRouteriEntry
                   MAX-ACCESS not-accessible
                   STATUS current
                   DESCRIPTION "entry in table"
                   INDEX { setWanRouteriIfc }
                   ::= {  setWanRouteriTable 1 }

SetWanRouteriEntry ::= SEQUENCE {
                   setWanRouteriIfc INTEGER,
                   setWanRouteriMsn DisplayString,
                   setWanRouteriYc INTEGER,
                   setWanRouteriCli INTEGER,
                   setWanRouteriAcc INTEGER,
                   setWanRouteriTyp INTEGER
                  }

setWanRouteriIfc OBJECT-TYPE
                 SYNTAX INTEGER{
                   dsl-1(1),
                   ext(2)
                 }
                 MAX-ACCESS read-only
                 STATUS current
                 DESCRIPTION "Ifc"
                 ::= {  setWanRouteriEntry 1 }

setWanRouteriMsn OBJECT-TYPE
                 SYNTAX DisplayString (SIZE(0..30))
                 MAX-ACCESS read-write
                 STATUS current
                 DESCRIPTION "MSN/EAZ"
                 ::= {  setWanRouteriEntry 2 }

setWanRouteriYc OBJECT-TYPE
                 SYNTAX INTEGER{
                   yes(0),
                   no(1)
                 }
                 MAX-ACCESS read-write
                 STATUS current
                 DESCRIPTION "YC."
                 ::= {  setWanRouteriEntry 8 }

setWanRouteriCli OBJECT-TYPE
                 SYNTAX INTEGER{
                   yes(0),
                   no(1)
                 }
                 MAX-ACCESS read-write
                 STATUS current
                 DESCRIPTION "CLIP"
                 ::= {  setWanRouteriEntry 3 }

setWanRouteriAcc OBJECT-TYPE
                 SYNTAX INTEGER{
                   all(0),
                   none(128)
                 }
                 MAX-ACCESS read-write
                 STATUS current
                 DESCRIPTION "Accept-calls"
                 ::= {  setWanRouteriEntry 9 }

setWanRouteriTyp OBJECT-TYPE
                 SYNTAX INTEGER (0..2147483647)
                 MAX-ACCESS read-only
                 STATUS current
                 DESCRIPTION "Type-of-interface"
                 ::= {  setWanRouteriEntry 10 }

setWanDialpre OBJECT-TYPE
              SYNTAX DisplayString (SIZE(0..8))
              MAX-ACCESS not-accessible
              STATUS current
              DESCRIPTION "Dial-Prefix"
              ::= {  setWan 7 }

setAccou OBJECT IDENTIFIER ::= { set 18}
setAccouOpe OBJECT-TYPE
            SYNTAX INTEGER {
              no(0),
              yes(1)
            }
            MAX-ACCESS read-write
            STATUS current
            DESCRIPTION "Operating"
            ::= {  setAccou 1 }

setAccouSav OBJECT-TYPE
            SYNTAX INTEGER {
              no(0),
              yes(1)
            }
            MAX-ACCESS read-write
            STATUS current
            DESCRIPTION "Save-to-Flashrom"
            ::= {  setAccou 2 }

setAccouDis OBJECT-TYPE
            SYNTAX INTEGER {
              mac-address(0),
              ip-address(1)
            }
            MAX-ACCESS read-write
            STATUS current
            DESCRIPTION "Discriminator"
            ::= {  setAccou 10 }

setAccouSor OBJECT-TYPE
            SYNTAX INTEGER {
              time(0),
              data(1)
            }
            MAX-ACCESS read-write
            STATUS current
            DESCRIPTION "Sort-by"
            ::= {  setAccou 3 }

setAccouCurTable OBJECT-TYPE
                 SYNTAX SEQUENCE OF SetAccouCurEntry
                 MAX-ACCESS not-accessible
                 STATUS current
                 DESCRIPTION "Current-User"
                 ::= {  setAccou 4 }

setAccouCurEntry OBJECT-TYPE
                 SYNTAX SetAccouCurEntry
                 MAX-ACCESS not-accessible
                 STATUS current
                 DESCRIPTION "entry in table"
                 INDEX { setAccouCurUsern, setAccouCurMacad, setAccouCurPeer, setAccouCurConnt }
                 ::= {  setAccouCurTable 1 }

SetAccouCurEntry ::= SEQUENCE {
                 setAccouCurUsern DisplayString,
                 setAccouCurMacad DisplayString,
                 setAccouCurPeer DisplayString,
                 setAccouCurConnt INTEGER,
                 setAccouCurRxkby INTEGER,
                 setAccouCurTxkby INTEGER,
                 setAccouCurTotal INTEGER,
                 setAccouCurConne INTEGER
                }

setAccouCurUsern OBJECT-TYPE
                 SYNTAX DisplayString (SIZE(0..28))
                 MAX-ACCESS read-only
                 STATUS current
                 DESCRIPTION "Username"
                 ::= {  setAccouCurEntry 1 }

setAccouCurMacad OBJECT-TYPE
                 SYNTAX DisplayString (SIZE(0..255))
                 MAX-ACCESS read-only
                 STATUS current
                 DESCRIPTION "MAC-Address"
                 ::= {  setAccouCurEntry 2 }

setAccouCurPeer OBJECT-TYPE
                 SYNTAX DisplayString (SIZE(0..31))
                 MAX-ACCESS read-only
                 STATUS current
                 DESCRIPTION "Peer"
                 ::= {  setAccouCurEntry 3 }

setAccouCurConnt OBJECT-TYPE
                 SYNTAX INTEGER{
                   unknown(0),
                   dial-up(1),
                   leased-line(2),
                   dsl-line(4),
                   vpn-conn(7),
                   pptp-conn(8)
                 }
                 MAX-ACCESS read-only
                 STATUS current
                 DESCRIPTION "Conn.-Type"
                 ::= {  setAccouCurEntry 4 }

setAccouCurRxkby OBJECT-TYPE
                 SYNTAX INTEGER (0..2147483647)
                 MAX-ACCESS read-only
                 STATUS current
                 DESCRIPTION "Rx-KBytes"
                 ::= {  setAccouCurEntry 5 }

setAccouCurTxkby OBJECT-TYPE
                 SYNTAX INTEGER (0..2147483647)
                 MAX-ACCESS read-only
                 STATUS current
                 DESCRIPTION "Tx-KBytes"
                 ::= {  setAccouCurEntry 6 }

setAccouCurTotal OBJECT-TYPE
                 SYNTAX INTEGER (0..2147483647)
                 MAX-ACCESS read-only
                 STATUS current
                 DESCRIPTION "Total-Time"
                 ::= {  setAccouCurEntry 8 }

setAccouCurConne OBJECT-TYPE
                 SYNTAX INTEGER (0..2147483647)
                 MAX-ACCESS read-only
                 STATUS current
                 DESCRIPTION "Connections"
                 ::= {  setAccouCurEntry 9 }

setAccouAccTable OBJECT-TYPE
                 SYNTAX SEQUENCE OF SetAccouAccEntry
                 MAX-ACCESS not-accessible
                 STATUS current
                 DESCRIPTION "Accounting-List"
                 ::= {  setAccou 5 }

setAccouAccEntry OBJECT-TYPE
                 SYNTAX SetAccouAccEntry
                 MAX-ACCESS not-accessible
                 STATUS current
                 DESCRIPTION "entry in table"
                 INDEX { setAccouAccUsern, setAccouAccMacad, setAccouAccPeer, setAccouAccConnt }
                 ::= {  setAccouAccTable 1 }

SetAccouAccEntry ::= SEQUENCE {
                 setAccouAccUsern DisplayString,
                 setAccouAccMacad DisplayString,
                 setAccouAccPeer DisplayString,
                 setAccouAccConnt INTEGER,
                 setAccouAccRxkby INTEGER,
                 setAccouAccTxkby INTEGER,
                 setAccouAccTotal INTEGER,
                 setAccouAccConne INTEGER
                }

setAccouAccUsern OBJECT-TYPE
                 SYNTAX DisplayString (SIZE(0..28))
                 MAX-ACCESS read-only
                 STATUS current
                 DESCRIPTION "Username"
                 ::= {  setAccouAccEntry 1 }

setAccouAccMacad OBJECT-TYPE
                 SYNTAX DisplayString (SIZE(0..255))
                 MAX-ACCESS read-only
                 STATUS current
                 DESCRIPTION "MAC-Address"
                 ::= {  setAccouAccEntry 2 }

setAccouAccPeer OBJECT-TYPE
                 SYNTAX DisplayString (SIZE(0..31))
                 MAX-ACCESS read-only
                 STATUS current
                 DESCRIPTION "Peer"
                 ::= {  setAccouAccEntry 3 }

setAccouAccConnt OBJECT-TYPE
                 SYNTAX INTEGER{
                   unknown(0),
                   dial-up(1),
                   leased-line(2),
                   dsl-line(4),
                   vpn-conn(7),
                   pptp-conn(8)
                 }
                 MAX-ACCESS read-only
                 STATUS current
                 DESCRIPTION "Conn.-Type"
                 ::= {  setAccouAccEntry 4 }

setAccouAccRxkby OBJECT-TYPE
                 SYNTAX INTEGER (0..2147483647)
                 MAX-ACCESS read-only
                 STATUS current
                 DESCRIPTION "Rx-KBytes"
                 ::= {  setAccouAccEntry 5 }

setAccouAccTxkby OBJECT-TYPE
                 SYNTAX INTEGER (0..2147483647)
                 MAX-ACCESS read-only
                 STATUS current
                 DESCRIPTION "Tx-KBytes"
                 ::= {  setAccouAccEntry 6 }

setAccouAccTotal OBJECT-TYPE
                 SYNTAX INTEGER (0..2147483647)
                 MAX-ACCESS read-only
                 STATUS current
                 DESCRIPTION "Total-Time"
                 ::= {  setAccouAccEntry 8 }

setAccouAccConne OBJECT-TYPE
                 SYNTAX INTEGER (0..2147483647)
                 MAX-ACCESS read-only
                 STATUS current
                 DESCRIPTION "Connections"
                 ::= {  setAccouAccEntry 9 }

setAccouDel OBJECT-TYPE
            SYNTAX DisplayString
            MAX-ACCESS read-write
            STATUS current
            DESCRIPTION "Delete-Accounting-List"
            ::= {  setAccou 6 }

setAccouTimTable OBJECT-TYPE
                 SYNTAX SEQUENCE OF SetAccouTimEntry
                 MAX-ACCESS not-accessible
                 STATUS current
                 DESCRIPTION "Time-Snapshot"
                 ::= {  setAccou 8 }

setAccouTimEntry OBJECT-TYPE
                 SYNTAX SetAccouTimEntry
                 MAX-ACCESS not-accessible
                 STATUS current
                 DESCRIPTION "entry in table"
                 INDEX { setAccouTimInde }
                 ::= {  setAccouTimTable 1 }

SetAccouTimEntry ::= SEQUENCE {
                 setAccouTimInde INTEGER,
                 setAccouTimActi INTEGER,
                 setAccouTimType INTEGER,
                 setAccouTimDay INTEGER,
                 setAccouTimDayo INTEGER,
                 setAccouTimHour INTEGER,
                 setAccouTimMinu INTEGER
                }

setAccouTimInde OBJECT-TYPE
                SYNTAX INTEGER (0..255)
                MAX-ACCESS read-only
                STATUS current
                DESCRIPTION "Index"
                ::= {  setAccouTimEntry 1 }

setAccouTimActi OBJECT-TYPE
                SYNTAX INTEGER{
                  yes(1),
                  no(0)
                }
                MAX-ACCESS read-write
                STATUS current
                DESCRIPTION "Active"
                ::= {  setAccouTimEntry 2 }

setAccouTimType OBJECT-TYPE
                SYNTAX INTEGER{
                  monthly(0),
                  weekly(1),
                  daily(2)
                }
                MAX-ACCESS read-write
                STATUS current
                DESCRIPTION "Type"
                ::= {  setAccouTimEntry 3 }

setAccouTimDay OBJECT-TYPE
                SYNTAX INTEGER (0..255)
                MAX-ACCESS read-write
                STATUS current
                DESCRIPTION "Day"
                ::= {  setAccouTimEntry 4 }

setAccouTimDayo OBJECT-TYPE
                SYNTAX INTEGER{
                  unknown(0),
                  sunday(1),
                  monday(2),
                  tuesday(3),
                  wednesday(4),
                  thursday(5),
                  friday(6),
                  saturday(7)
                }
                MAX-ACCESS read-write
                STATUS current
                DESCRIPTION "DayOfWeek"
                ::= {  setAccouTimEntry 5 }

setAccouTimHour OBJECT-TYPE
                SYNTAX INTEGER (0..255)
                MAX-ACCESS read-write
                STATUS current
                DESCRIPTION "Hour"
                ::= {  setAccouTimEntry 6 }

setAccouTimMinu OBJECT-TYPE
                SYNTAX INTEGER (0..255)
                MAX-ACCESS read-write
                STATUS current
                DESCRIPTION "Minute"
                ::= {  setAccouTimEntry 7 }

setAccouLasTable OBJECT-TYPE
                 SYNTAX SEQUENCE OF SetAccouLasEntry
                 MAX-ACCESS not-accessible
                 STATUS current
                 DESCRIPTION "Last-Snapshot"
                 ::= {  setAccou 9 }

setAccouLasEntry OBJECT-TYPE
                 SYNTAX SetAccouLasEntry
                 MAX-ACCESS not-accessible
                 STATUS current
                 DESCRIPTION "entry in table"
                 INDEX { setAccouLasUsern, setAccouLasMacad, setAccouLasPeer, setAccouLasConnt }
                 ::= {  setAccouLasTable 1 }

SetAccouLasEntry ::= SEQUENCE {
                 setAccouLasUsern DisplayString,
                 setAccouLasMacad DisplayString,
                 setAccouLasPeer DisplayString,
                 setAccouLasConnt INTEGER,
                 setAccouLasRxkby INTEGER,
                 setAccouLasTxkby INTEGER,
                 setAccouLasTotal INTEGER,
                 setAccouLasConne INTEGER
                }

setAccouLasUsern OBJECT-TYPE
                 SYNTAX DisplayString (SIZE(0..28))
                 MAX-ACCESS read-only
                 STATUS current
                 DESCRIPTION "Username"
                 ::= {  setAccouLasEntry 1 }

setAccouLasMacad OBJECT-TYPE
                 SYNTAX DisplayString (SIZE(0..255))
                 MAX-ACCESS read-only
                 STATUS current
                 DESCRIPTION "MAC-Address"
                 ::= {  setAccouLasEntry 2 }

setAccouLasPeer OBJECT-TYPE
                 SYNTAX DisplayString (SIZE(0..31))
                 MAX-ACCESS read-only
                 STATUS current
                 DESCRIPTION "Peer"
                 ::= {  setAccouLasEntry 3 }

setAccouLasConnt OBJECT-TYPE
                 SYNTAX INTEGER{
                   unknown(0),
                   dial-up(1),
                   leased-line(2),
                   dsl-line(4),
                   vpn-conn(7),
                   pptp-conn(8)
                 }
                 MAX-ACCESS read-only
                 STATUS current
                 DESCRIPTION "Conn.-Type"
                 ::= {  setAccouLasEntry 4 }

setAccouLasRxkby OBJECT-TYPE
                 SYNTAX INTEGER (0..2147483647)
                 MAX-ACCESS read-only
                 STATUS current
                 DESCRIPTION "Rx-KBytes"
                 ::= {  setAccouLasEntry 5 }

setAccouLasTxkby OBJECT-TYPE
                 SYNTAX INTEGER (0..2147483647)
                 MAX-ACCESS read-only
                 STATUS current
                 DESCRIPTION "Tx-KBytes"
                 ::= {  setAccouLasEntry 6 }

setAccouLasTotal OBJECT-TYPE
                 SYNTAX INTEGER (0..2147483647)
                 MAX-ACCESS read-only
                 STATUS current
                 DESCRIPTION "Total-Time"
                 ::= {  setAccouLasEntry 8 }

setAccouLasConne OBJECT-TYPE
                 SYNTAX INTEGER (0..2147483647)
                 MAX-ACCESS read-only
                 STATUS current
                 DESCRIPTION "Connections"
                 ::= {  setAccouLasEntry 9 }

setCharg OBJECT IDENTIFIER ::= { set 3}
setChargDaysper OBJECT-TYPE
                SYNTAX INTEGER
                MAX-ACCESS read-write
                STATUS current
                DESCRIPTION "Days-per-Period"
                ::= {  setCharg 2 }

setChargSerialm OBJECT-TYPE
                SYNTAX INTEGER
                MAX-ACCESS read-write
                STATUS current
                DESCRIPTION "Serial-minutes-Budget"
                ::= {  setCharg 13 }

setChargSpservere OBJECT-TYPE
                SYNTAX INTEGER
                MAX-ACCESS read-only
                STATUS current
                DESCRIPTION "Spare-Serial-Minutes"
                ::= {  setCharg 14 }

setChargRouters OBJECT-TYPE
                SYNTAX INTEGER
                MAX-ACCESS read-only
                STATUS current
                DESCRIPTION "Router-Serial-Minutes-Active"
                ::= {  setCharg 15 }

setChargTimetabTable OBJECT-TYPE
                     SYNTAX SEQUENCE OF SetChargTimetabEntry
                     MAX-ACCESS not-accessible
                     STATUS current
                     DESCRIPTION "Time-Table"
                     ::= {  setCharg 7 }

setChargTimetabEntry OBJECT-TYPE
                     SYNTAX SetChargTimetabEntry
                     MAX-ACCESS not-accessible
                     STATUS current
                     DESCRIPTION "entry in table"
                     INDEX { setChargTimetabIfc }
                     ::= {  setChargTimetabTable 1 }

SetChargTimetabEntry ::= SEQUENCE {
                     setChargTimetabIfc INTEGER,
                     setChargTimetabBudgetmi INTEGER,
                     setChargTimetabSparemin INTEGER,
                     setChargTimetabMinutesa INTEGER,
                     setChargTimetabMinutesp INTEGER
                    }

setChargTimetabIfc OBJECT-TYPE
                        SYNTAX INTEGER{
                          router-dsl-broadband(1),
                          router-serial(2),
                          lancapi(3),
                          ab-1(4),
                          ab-2(5),
                          ab-3(6),
                          ab-4(7),
                          time-modul(255)
                        }
                        MAX-ACCESS read-only
                        STATUS current
                        DESCRIPTION "Ifc"
                        ::= {  setChargTimetabEntry 1 }

setChargTimetabBudgetmi OBJECT-TYPE
                        SYNTAX INTEGER (0..2147483647)
                        MAX-ACCESS read-only
                        STATUS current
                        DESCRIPTION "Budget-minutes"
                        ::= {  setChargTimetabEntry 2 }

setChargTimetabSparemin OBJECT-TYPE
                        SYNTAX INTEGER (0..2147483647)
                        MAX-ACCESS read-only
                        STATUS current
                        DESCRIPTION "Spare-minutes"
                        ::= {  setChargTimetabEntry 3 }

setChargTimetabMinutesa OBJECT-TYPE
                        SYNTAX INTEGER (0..2147483647)
                        MAX-ACCESS read-only
                        STATUS current
                        DESCRIPTION "Minutes-active"
                        ::= {  setChargTimetabEntry 4 }

setChargTimetabMinutesp OBJECT-TYPE
                        SYNTAX INTEGER (0..2147483647)
                        MAX-ACCESS read-only
                        STATUS current
                        DESCRIPTION "Minutes-passive"
                        ::= {  setChargTimetabEntry 5 }

setChargDslbroa OBJECT-TYPE
                SYNTAX INTEGER
                MAX-ACCESS read-write
                STATUS current
                DESCRIPTION "DSL-Broadband-Minutes-Budget"
                ::= {  setCharg 8 }

setChargAdditio OBJECT-TYPE
                SYNTAX INTEGER
                MAX-ACCESS read-write
                STATUS current
                DESCRIPTION "Additional-DSL-Broadband-Budget"
                ::= {  setCharg 11 }

setChargSpareds OBJECT-TYPE
                SYNTAX INTEGER
                MAX-ACCESS read-only
                STATUS current
                DESCRIPTION "Spare-DSL-Broadband-Minutes"
                ::= {  setCharg 9 }

setChargRouterd OBJECT-TYPE
                SYNTAX INTEGER
                MAX-ACCESS read-only
                STATUS current
                DESCRIPTION "Router-DSL-Broadband-Minutes-Active"
                ::= {  setCharg 10 }

setChargActivat OBJECT-TYPE
                SYNTAX DisplayString
                MAX-ACCESS read-write
                STATUS current
                DESCRIPTION "Activate-Additional-Budget"
                ::= {  setCharg 12 }

setChargResetbu OBJECT-TYPE
                SYNTAX DisplayString
                MAX-ACCESS read-write
                STATUS current
                DESCRIPTION "Reset-Budgets"
                ::= {  setCharg 16 }

setLan OBJECT IDENTIFIER ::= { set 4}
setLanMacadd OBJECT-TYPE
             SYNTAX MacAddress
             MAX-ACCESS read-only
             STATUS current
             DESCRIPTION "MAC-Address"
             ::= {  setLan 2 }

setLanSpareh OBJECT-TYPE
             SYNTAX INTEGER
             MAX-ACCESS read-write
             STATUS current
             DESCRIPTION "Spare-Heap"
             ::= {  setLan 3 }

setLanTracem OBJECT-TYPE
             SYNTAX MacAddress
             MAX-ACCESS read-write
             STATUS current
             DESCRIPTION "Trace-MAC"
             ::= {  setLan 8 }

setLanTracel OBJECT-TYPE
             SYNTAX INTEGER
             MAX-ACCESS read-write
             STATUS current
             DESCRIPTION "Trace-Level"
             ::= {  setLan 9 }

setLanIeee80 OBJECT IDENTIFIER ::= { setLan 10}
setLanIeee80SupTable OBJECT-TYPE
                     SYNTAX SEQUENCE OF SetLanIeee80SupEntry
                     MAX-ACCESS not-accessible
                     STATUS current
                     DESCRIPTION "Supplicant-Ifc-Setup"
                     ::= {  setLanIeee80 1 }

setLanIeee80SupEntry OBJECT-TYPE
                     SYNTAX SetLanIeee80SupEntry
                     MAX-ACCESS not-accessible
                     STATUS current
                     DESCRIPTION "entry in table"
                     INDEX { setLanIeee80SupIfc }
                     ::= {  setLanIeee80SupTable 1 }

SetLanIeee80SupEntry ::= SEQUENCE {
                     setLanIeee80SupIfc INTEGER,
                     setLanIeee80SupMet INTEGER,
                     setLanIeee80SupCre DisplayString
                    }

setLanIeee80SupIfc OBJECT-TYPE
                   SYNTAX INTEGER{
                     lan-1(1)
                   }
                   MAX-ACCESS read-only
                   STATUS current
                   DESCRIPTION "Ifc"
                   ::= {  setLanIeee80SupEntry 1 }

setLanIeee80SupMet OBJECT-TYPE
                   SYNTAX INTEGER{
                     none(0),
                     md5(1024),
                     tls(3328),
                     ttls-pap(5383),
                     ttls-chap(5384),
                     ttls-mschap(5567),
                     ttls-mschapv2(5402),
                     ttls-md5(5380),
                     peap-mschapv2(6426),
                     peap-gtc(6406)
                   }
                   MAX-ACCESS read-write
                   STATUS current
                   DESCRIPTION "Method"
                   ::= {  setLanIeee80SupEntry 2 }

setLanIeee80SupCre OBJECT-TYPE
                   SYNTAX DisplayString (SIZE(0..64))
                   MAX-ACCESS read-write
                   STATUS current
                   DESCRIPTION "Credentials"
                   ::= {  setLanIeee80SupEntry 3 }

setTcpip OBJECT IDENTIFIER ::= { set 7}
setTcpipOpera OBJECT-TYPE
              SYNTAX INTEGER {
                no(0),
                yes(1)
              }
              MAX-ACCESS read-write
              STATUS current
              DESCRIPTION "Operating"
              ::= {  setTcpip 1 }

setTcpipNetwoTable OBJECT-TYPE
                   SYNTAX SEQUENCE OF SetTcpipNetwoEntry
                   MAX-ACCESS not-accessible
                   STATUS current
                   DESCRIPTION "Network-list"
                   ::= {  setTcpip 30 }

setTcpipNetwoEntry OBJECT-TYPE
                   SYNTAX SetTcpipNetwoEntry
                   MAX-ACCESS not-accessible
                   STATUS current
                   DESCRIPTION "entry in table"
                   INDEX { setTcpipNetwoNet }
                   ::= {  setTcpipNetwoTable 1 }

SetTcpipNetwoEntry ::= SEQUENCE {
                   setTcpipNetwoNet DisplayString,
                   setTcpipNetwoIpa IpAddress,
                   setTcpipNetwoIpn IpAddress,
                   setTcpipNetwoVla INTEGER,
                   setTcpipNetwoInt INTEGER,
                   setTcpipNetwoSrc INTEGER,
                   setTcpipNetwoTyp INTEGER,
                   setTcpipNetwoRtg INTEGER,
                   setTcpipNetwoCom DisplayString
                  }

setTcpipNetwoNet OBJECT-TYPE
                 SYNTAX DisplayString (SIZE(0..17))
                 MAX-ACCESS read-write
                 STATUS current
                 DESCRIPTION "Network-name"
                 ::= {  setTcpipNetwoEntry 1 }

setTcpipNetwoIpa OBJECT-TYPE
                 SYNTAX IpAddress
                 MAX-ACCESS read-write
                 STATUS current
                 DESCRIPTION "IP-Address"
                 ::= {  setTcpipNetwoEntry 2 }

setTcpipNetwoIpn OBJECT-TYPE
                 SYNTAX IpAddress
                 MAX-ACCESS read-write
                 STATUS current
                 DESCRIPTION "IP-Netmask"
                 ::= {  setTcpipNetwoEntry 3 }

setTcpipNetwoVla OBJECT-TYPE
                 SYNTAX INTEGER (0..65535)
                 MAX-ACCESS read-write
                 STATUS current
                 DESCRIPTION "VLAN-ID"
                 ::= {  setTcpipNetwoEntry 4 }

setTcpipNetwoInt OBJECT-TYPE
                 SYNTAX INTEGER{
                   lan-1(256),
                   wlan-1(512),
                   p2p-1-1(768),
                   p2p-1-2(769),
                   p2p-1-3(770),
                   p2p-1-4(771),
                   p2p-1-5(772),
                   p2p-1-6(773),
                   wlan-1-2(1024),
                   wlan-1-3(1025),
                   wlan-1-4(1026),
                   wlan-1-5(1027),
                   wlan-1-6(1028),
                   wlan-1-7(1029),
                   wlan-1-8(1030),
                   brg-1(1536),
                   brg-2(1537),
                   brg-3(1538),
                   brg-4(1539),
                   brg-5(1540),
                   brg-6(1541),
                   brg-7(1542),
                   brg-8(1543),
                   any(65535)
                 }
                 MAX-ACCESS read-write
                 STATUS current
                 DESCRIPTION "Interface"
                 ::= {  setTcpipNetwoEntry 5 }

setTcpipNetwoSrc OBJECT-TYPE
                 SYNTAX INTEGER{
                   strict(1),
                   loose(0)
                 }
                 MAX-ACCESS read-write
                 STATUS current
                 DESCRIPTION "Src-check"
                 ::= {  setTcpipNetwoEntry 6 }

setTcpipNetwoTyp OBJECT-TYPE
                 SYNTAX INTEGER{
                   disabled(0),
                   intranet(1),
                   dmz(2)
                 }
                 MAX-ACCESS read-write
                 STATUS current
                 DESCRIPTION "Type"
                 ::= {  setTcpipNetwoEntry 7 }

setTcpipNetwoRtg OBJECT-TYPE
                 SYNTAX INTEGER (0..65535)
                 MAX-ACCESS read-write
                 STATUS current
                 DESCRIPTION "Rtg-tag"
                 ::= {  setTcpipNetwoEntry 8 }

setTcpipNetwoCom OBJECT-TYPE
                 SYNTAX DisplayString (SIZE(0..64))
                 MAX-ACCESS read-write
                 STATUS current
                 DESCRIPTION "Comment"
                 ::= {  setTcpipNetwoEntry 9 }

setTcpipLoopbTable OBJECT-TYPE
                   SYNTAX SEQUENCE OF SetTcpipLoopbEntry
                   MAX-ACCESS not-accessible
                   STATUS current
                   DESCRIPTION "Loopback-List"
                   ::= {  setTcpip 17 }

setTcpipLoopbEntry OBJECT-TYPE
                   SYNTAX SetTcpipLoopbEntry
                   MAX-ACCESS not-accessible
                   STATUS current
                   DESCRIPTION "entry in table"
                   INDEX { setTcpipLoopbNam }
                   ::= {  setTcpipLoopbTable 1 }

SetTcpipLoopbEntry ::= SEQUENCE {
                   setTcpipLoopbNam DisplayString,
                   setTcpipLoopbLoo IpAddress,
                   setTcpipLoopbRtg INTEGER
                  }

setTcpipLoopbNam OBJECT-TYPE
                 SYNTAX DisplayString (SIZE(0..16))
                 MAX-ACCESS read-write
                 STATUS current
                 DESCRIPTION "Name"
                 ::= {  setTcpipLoopbEntry 2 }

setTcpipLoopbLoo OBJECT-TYPE
                 SYNTAX IpAddress
                 MAX-ACCESS read-write
                 STATUS current
                 DESCRIPTION "Loopback-Addr."
                 ::= {  setTcpipLoopbEntry 1 }

setTcpipLoopbRtg OBJECT-TYPE
                 SYNTAX INTEGER (0..65535)
                 MAX-ACCESS read-write
                 STATUS current
                 DESCRIPTION "Rtg-tag"
                 ::= {  setTcpipLoopbEntry 3 }

setTcpipAccesTable OBJECT-TYPE
                   SYNTAX SEQUENCE OF SetTcpipAccesEntry
                   MAX-ACCESS not-accessible
                   STATUS current
                   DESCRIPTION "Access-List"
                   ::= {  setTcpip 6 }

setTcpipAccesEntry OBJECT-TYPE
                   SYNTAX SetTcpipAccesEntry
                   MAX-ACCESS not-accessible
                   STATUS current
                   DESCRIPTION "entry in table"
                   INDEX { setTcpipAccesIpa }
                   ::= {  setTcpipAccesTable 1 }

SetTcpipAccesEntry ::= SEQUENCE {
                   setTcpipAccesIpa IpAddress,
                   setTcpipAccesIpn IpAddress
                  }

setTcpipAccesIpa OBJECT-TYPE
                 SYNTAX IpAddress
                 MAX-ACCESS read-write
                 STATUS current
                 DESCRIPTION "IP-Address"
                 ::= {  setTcpipAccesEntry 1 }

setTcpipAccesIpn OBJECT-TYPE
                 SYNTAX IpAddress
                 MAX-ACCESS read-write
                 STATUS current
                 DESCRIPTION "IP-Netmask"
                 ::= {  setTcpipAccesEntry 2 }

setTcpipDnsde OBJECT-TYPE
              SYNTAX IpAddress
              MAX-ACCESS read-write
              STATUS current
              DESCRIPTION "DNS-Default"
              ::= {  setTcpip 7 }

setTcpipDnsba OBJECT-TYPE
              SYNTAX IpAddress
              MAX-ACCESS read-write
              STATUS current
              DESCRIPTION "DNS-Backup"
              ::= {  setTcpip 8 }

setTcpipNbnsd OBJECT-TYPE
              SYNTAX IpAddress
              MAX-ACCESS read-write
              STATUS current
              DESCRIPTION "NBNS-Default"
              ::= {  setTcpip 9 }

setTcpipNbnsb OBJECT-TYPE
              SYNTAX IpAddress
              MAX-ACCESS read-write
              STATUS current
              DESCRIPTION "NBNS-Backup"
              ::= {  setTcpip 10 }

setTcpipArptaTable OBJECT-TYPE
                   SYNTAX SEQUENCE OF SetTcpipArptaEntry
                   MAX-ACCESS not-accessible
                   STATUS current
                   DESCRIPTION "ARP-Table"
                   ::= {  setTcpip 16 }

setTcpipArptaEntry OBJECT-TYPE
                   SYNTAX SetTcpipArptaEntry
                   MAX-ACCESS not-accessible
                   STATUS current
                   DESCRIPTION "entry in table"
                   INDEX { setTcpipArptaIpa }
                   ::= {  setTcpipArptaTable 1 }

SetTcpipArptaEntry ::= SEQUENCE {
                   setTcpipArptaIpa IpAddress,
                   setTcpipArptaMac MacAddress,
                   setTcpipArptaLas INTEGER,
                   setTcpipArptaCon INTEGER,
                   setTcpipArptaVla INTEGER,
                   setTcpipArptaPee DisplayString
                  }

setTcpipArptaIpa OBJECT-TYPE
                 SYNTAX IpAddress
                 MAX-ACCESS read-only
                 STATUS current
                 DESCRIPTION "IP-Address"
                 ::= {  setTcpipArptaEntry 1 }

setTcpipArptaMac OBJECT-TYPE
                 SYNTAX MacAddress
                 MAX-ACCESS read-only
                 STATUS current
                 DESCRIPTION "MAC-Address"
                 ::= {  setTcpipArptaEntry 2 }

setTcpipArptaLas OBJECT-TYPE
                 SYNTAX INTEGER (0..2147483647)
                 MAX-ACCESS read-only
                 STATUS current
                 DESCRIPTION "Last-access"
                 ::= {  setTcpipArptaEntry 3 }

setTcpipArptaCon OBJECT-TYPE
                 SYNTAX INTEGER{
                   lan-1(0),
                   wlan-1(1),
                   p2p-1-1(2),
                   p2p-1-2(3),
                   p2p-1-3(4),
                   p2p-1-4(5),
                   p2p-1-5(6),
                   p2p-1-6(7),
                   wlan-1-2(8),
                   wlan-1-3(9),
                   wlan-1-4(10),
                   wlan-1-5(11),
                   wlan-1-6(12),
                   wlan-1-7(13),
                   wlan-1-8(14),
                   wan(15)
                 }
                 MAX-ACCESS read-only
                 STATUS current
                 DESCRIPTION "Connect"
                 ::= {  setTcpipArptaEntry 4 }

setTcpipArptaVla OBJECT-TYPE
                 SYNTAX INTEGER (0..65535)
                 MAX-ACCESS read-only
                 STATUS current
                 DESCRIPTION "VLAN-ID"
                 ::= {  setTcpipArptaEntry 7 }

setTcpipArptaPee OBJECT-TYPE
                 SYNTAX DisplayString (SIZE(0..255))
                 MAX-ACCESS read-only
                 STATUS current
                 DESCRIPTION "Peer"
                 ::= {  setTcpipArptaEntry 6 }

setTcpipNonlo OBJECT-TYPE
              SYNTAX INTEGER {
                no(0),
                yes(1)
              }
              MAX-ACCESS read-write
              STATUS current
              DESCRIPTION "Non-Loc.-ARP-Replies"
              ::= {  setTcpip 20 }

setTcpipIcmpo OBJECT-TYPE
              SYNTAX INTEGER {
                no(0),
                yes(1)
              }
              MAX-ACCESS read-write
              STATUS current
              DESCRIPTION "ICMP-On-ARP-Timeout"
              ::= {  setTcpip 22 }

setTcpipArpag OBJECT-TYPE
              SYNTAX INTEGER
              MAX-ACCESS read-write
              STATUS current
              DESCRIPTION "ARP-Aging-Minutes"
              ::= {  setTcpip 11 }

setTcpipAlive OBJECT IDENTIFIER ::= { setTcpip 21}
setTcpipAliveTarget OBJECT-TYPE
                    SYNTAX IpAddress
                    MAX-ACCESS read-write
                    STATUS current
                    DESCRIPTION "Target-Address"
                    ::= {  setTcpipAlive 1 }

setTcpipAliveTestin OBJECT-TYPE
                    SYNTAX INTEGER
                    MAX-ACCESS read-write
                    STATUS current
                    DESCRIPTION "Test-Interval"
                    ::= {  setTcpipAlive 2 }

setTcpipAliveRetryc OBJECT-TYPE
                    SYNTAX INTEGER
                    MAX-ACCESS read-write
                    STATUS current
                    DESCRIPTION "Retry-Count"
                    ::= {  setTcpipAlive 3 }

setTcpipAliveRetryi OBJECT-TYPE
                    SYNTAX INTEGER
                    MAX-ACCESS read-write
                    STATUS current
                    DESCRIPTION "Retry-Interval"
                    ::= {  setTcpipAlive 4 }

setTcpipAliveFailli OBJECT-TYPE
                    SYNTAX INTEGER
                    MAX-ACCESS read-write
                    STATUS current
                    DESCRIPTION "Fail-Limit"
                    ::= {  setTcpipAlive 5 }

setTcpipAliveBootty OBJECT-TYPE
                    SYNTAX INTEGER {
                      warm-boot(0),
                      cold-boot(1)
                    }
                    MAX-ACCESS read-write
                    STATUS current
                    DESCRIPTION "Boot-Type"
                    ::= {  setTcpipAlive 6 }

setIprou OBJECT IDENTIFIER ::= { set 8}
setIprouOpe OBJECT-TYPE
            SYNTAX INTEGER {
              no(0),
              yes(1)
            }
            MAX-ACCESS read-write
            STATUS current
            DESCRIPTION "Operating"
            ::= {  setIprou 1 }

setIprouIprTable OBJECT-TYPE
                 SYNTAX SEQUENCE OF SetIprouIprEntry
                 MAX-ACCESS not-accessible
                 STATUS current
                 DESCRIPTION "IP-Routing-Table"
                 ::= {  setIprou 2 }

setIprouIprEntry OBJECT-TYPE
                 SYNTAX SetIprouIprEntry
                 MAX-ACCESS not-accessible
                 STATUS current
                 DESCRIPTION "entry in table"
                 INDEX { setIprouIprIpa, setIprouIprIpn, setIprouIprRtg }
                 ::= {  setIprouIprTable 1 }

SetIprouIprEntry ::= SEQUENCE {
                 setIprouIprIpa IpAddress,
                 setIprouIprIpn IpAddress,
                 setIprouIprRtg INTEGER,
                 setIprouIprPee DisplayString,
                 setIprouIprDis INTEGER,
                 setIprouIprMas INTEGER,
                 setIprouIprAct INTEGER,
                 setIprouIprCom DisplayString
                }

setIprouIprIpa OBJECT-TYPE
               SYNTAX IpAddress
               MAX-ACCESS read-write
               STATUS current
               DESCRIPTION "IP-Address"
               ::= {  setIprouIprEntry 1 }

setIprouIprIpn OBJECT-TYPE
               SYNTAX IpAddress
               MAX-ACCESS read-write
               STATUS current
               DESCRIPTION "IP-Netmask"
               ::= {  setIprouIprEntry 2 }

setIprouIprRtg OBJECT-TYPE
               SYNTAX INTEGER (0..65535)
               MAX-ACCESS read-write
               STATUS current
               DESCRIPTION "Rtg-tag"
               ::= {  setIprouIprEntry 8 }

setIprouIprPee OBJECT-TYPE
               SYNTAX DisplayString (SIZE(0..16))
               MAX-ACCESS read-write
               STATUS current
               DESCRIPTION "Peer-or-IP"
               ::= {  setIprouIprEntry 3 }

setIprouIprDis OBJECT-TYPE
               SYNTAX INTEGER (0..255)
               MAX-ACCESS read-write
               STATUS current
               DESCRIPTION "Distance"
               ::= {  setIprouIprEntry 4 }

setIprouIprMas OBJECT-TYPE
               SYNTAX INTEGER{
                 no(0),
                 on(1),
                 intranet(2)
               }
               MAX-ACCESS read-write
               STATUS current
               DESCRIPTION "Masquerade"
               ::= {  setIprouIprEntry 5 }

setIprouIprAct OBJECT-TYPE
               SYNTAX INTEGER{
                 no(1),
                 yes(0),
                 semi(2)
               }
               MAX-ACCESS read-write
               STATUS current
               DESCRIPTION "Active"
               ::= {  setIprouIprEntry 6 }

setIprouIprCom OBJECT-TYPE
               SYNTAX DisplayString (SIZE(0..64))
               MAX-ACCESS read-write
               STATUS current
               DESCRIPTION "Comment"
               ::= {  setIprouIprEntry 7 }

setIprouDefTable OBJECT-TYPE
                 SYNTAX SEQUENCE OF SetIprouDefEntry
                 MAX-ACCESS not-accessible
                 STATUS current
                 DESCRIPTION "Default-Time-List"
                 ::= {  setIprou 13 }

setIprouDefEntry OBJECT-TYPE
                 SYNTAX SetIprouDefEntry
                 MAX-ACCESS not-accessible
                 STATUS current
                 DESCRIPTION "entry in table"
                 INDEX { setIprouDefInd }
                 ::= {  setIprouDefTable 1 }

SetIprouDefEntry ::= SEQUENCE {
                 setIprouDefInd INTEGER,
                 setIprouDefDay BITS,
                 setIprouDefSta DisplayString,
                 setIprouDefSto DisplayString,
                 setIprouDefPee DisplayString
                }

setIprouDefInd OBJECT-TYPE
               SYNTAX INTEGER (0..65535)
               MAX-ACCESS read-write
               STATUS current
               DESCRIPTION "Index"
               ::= {  setIprouDefEntry 1 }

setIprouDefDay OBJECT-TYPE
               SYNTAX BITS{
                 monday(1),
                 tuesday(2),
                 wednesday(4),
                 thursday(8),
                 friday(16),
                 saturday(32),
                 sunday(64),
                 holiday(128)
               }
               MAX-ACCESS read-write
               STATUS current
               DESCRIPTION "Days"
               ::= {  setIprouDefEntry 2 }

setIprouDefSta OBJECT-TYPE
               SYNTAX DisplayString (SIZE(0..5))
               MAX-ACCESS read-write
               STATUS current
               DESCRIPTION "Start"
               ::= {  setIprouDefEntry 3 }

setIprouDefSto OBJECT-TYPE
               SYNTAX DisplayString (SIZE(0..5))
               MAX-ACCESS read-write
               STATUS current
               DESCRIPTION "Stop"
               ::= {  setIprouDefEntry 4 }

setIprouDefPee OBJECT-TYPE
               SYNTAX DisplayString (SIZE(0..16))
               MAX-ACCESS read-write
               STATUS current
               DESCRIPTION "Peer"
               ::= {  setIprouDefEntry 5 }

setIprouUsa OBJECT-TYPE
            SYNTAX INTEGER {
              no(0),
              yes(1)
            }
            MAX-ACCESS read-write
            STATUS current
            DESCRIPTION "Usage-Default-Timetable"
            ::= {  setIprou 14 }

setIprouPro OBJECT-TYPE
            SYNTAX INTEGER {
              no(0),
              yes(1)
            }
            MAX-ACCESS read-write
            STATUS current
            DESCRIPTION "Proxy-ARP"
            ::= {  setIprou 5 }

setIprouSen OBJECT-TYPE
            SYNTAX INTEGER {
              no(1),
              yes(0)
            }
            MAX-ACCESS read-write
            STATUS current
            DESCRIPTION "Send-ICMP-Redirect"
            ::= {  setIprou 6 }

setIprouSta OBJECT-TYPE
            SYNTAX IpAddress
            MAX-ACCESS read-write
            STATUS current
            DESCRIPTION "Start-WAN-Pool"
            ::= {  setIprou 11 }

setIprouEnd OBJECT-TYPE
            SYNTAX IpAddress
            MAX-ACCESS read-write
            STATUS current
            DESCRIPTION "End-WAN-Pool"
            ::= {  setIprou 12 }

setIprouRou OBJECT IDENTIFIER ::= { setIprou 7}
setIprouRouRou OBJECT-TYPE
               SYNTAX INTEGER {
                 normal(0),
                 type-of-service(1),
                 diffserv(2)
               }
               MAX-ACCESS read-write
               STATUS current
               DESCRIPTION "Routing-Method"
               ::= {  setIprouRou 1 }

setIprouRouIcm OBJECT-TYPE
               SYNTAX INTEGER {
                 normal(0),
                 reliable(1)
               }
               MAX-ACCESS read-write
               STATUS current
               DESCRIPTION "ICMP-Routing-Method"
               ::= {  setIprouRou 2 }

setIprouRouSyn OBJECT-TYPE
               SYNTAX INTEGER {
                 no(0),
                 yes(1)
               }
               MAX-ACCESS read-write
               STATUS current
               DESCRIPTION "SYN/ACK-Speedup"
               ::= {  setIprouRou 3 }

setIprouRouL2l OBJECT-TYPE
               SYNTAX INTEGER {
                 no(0),
                 yes(1),
                 auto(2)
               }
               MAX-ACCESS read-write
               STATUS current
               DESCRIPTION "L2-L3-Tagging"
               ::= {  setIprouRou 4 }

setIprouRouL3l OBJECT-TYPE
               SYNTAX INTEGER {
                 no(0),
                 yes(1)
               }
               MAX-ACCESS read-write
               STATUS current
               DESCRIPTION "L3-L2-Tagging"
               ::= {  setIprouRou 5 }

setIprouRip OBJECT IDENTIFIER ::= { setIprou 8}
setIprouRipLanTable OBJECT-TYPE
                    SYNTAX SEQUENCE OF SetIprouRipLanEntry
                    MAX-ACCESS not-accessible
                    STATUS current
                    DESCRIPTION "LAN-Sites"
                    ::= {  setIprouRip 5 }

setIprouRipLanEntry OBJECT-TYPE
                    SYNTAX SetIprouRipLanEntry
                    MAX-ACCESS not-accessible
                    STATUS current
                    DESCRIPTION "entry in table"
                    INDEX { setIprouRipLanNetw }
                    ::= {  setIprouRipLanTable 1 }

SetIprouRipLanEntry ::= SEQUENCE {
                    setIprouRipLanNetw DisplayString,
                    setIprouRipLanRipt INTEGER,
                    setIprouRipLanRipa INTEGER,
                    setIprouRipLanProp INTEGER,
                    setIprouRipLanPois INTEGER,
                    setIprouRipLanDftr INTEGER,
                    setIprouRipLanRtgt DisplayString,
                    setIprouRipLanRxfi DisplayString,
                    setIprouRipLanTxfi DisplayString
                   }

setIprouRipLanNetw OBJECT-TYPE
                   SYNTAX DisplayString (SIZE(0..16))
                   MAX-ACCESS read-write
                   STATUS current
                   DESCRIPTION "Network-name"
                   ::= {  setIprouRipLanEntry 1 }

setIprouRipLanRipt OBJECT-TYPE
                   SYNTAX INTEGER{
                     off(0),
                     rip-1(1),
                     r1-comp(2),
                     rip-2(3)
                   }
                   MAX-ACCESS read-write
                   STATUS current
                   DESCRIPTION "RIP-Type"
                   ::= {  setIprouRipLanEntry 2 }

setIprouRipLanRipa OBJECT-TYPE
                   SYNTAX INTEGER{
                     no(0),
                     yes(1)
                   }
                   MAX-ACCESS read-write
                   STATUS current
                   DESCRIPTION "RIP-Accept"
                   ::= {  setIprouRipLanEntry 3 }

setIprouRipLanProp OBJECT-TYPE
                   SYNTAX INTEGER{
                     no(0),
                     yes(1)
                   }
                   MAX-ACCESS read-write
                   STATUS current
                   DESCRIPTION "Propagate"
                   ::= {  setIprouRipLanEntry 4 }

setIprouRipLanPois OBJECT-TYPE
                   SYNTAX INTEGER{
                     no(0),
                     yes(1)
                   }
                   MAX-ACCESS read-write
                   STATUS current
                   DESCRIPTION "Poisoned-Reverse"
                   ::= {  setIprouRipLanEntry 7 }

setIprouRipLanDftr OBJECT-TYPE
                   SYNTAX INTEGER (0..65535)
                   MAX-ACCESS read-write
                   STATUS current
                   DESCRIPTION "Dft-Rtg-Tag"
                   ::= {  setIprouRipLanEntry 5 }

setIprouRipLanRtgt OBJECT-TYPE
                   SYNTAX DisplayString (SIZE(0..33))
                   MAX-ACCESS read-write
                   STATUS current
                   DESCRIPTION "Rtg-Tag-List"
                   ::= {  setIprouRipLanEntry 6 }

setIprouRipLanRxfi OBJECT-TYPE
                   SYNTAX DisplayString (SIZE(0..16))
                   MAX-ACCESS read-write
                   STATUS current
                   DESCRIPTION "Rx-Filter"
                   ::= {  setIprouRipLanEntry 10 }

setIprouRipLanTxfi OBJECT-TYPE
                   SYNTAX DisplayString (SIZE(0..16))
                   MAX-ACCESS read-write
                   STATUS current
                   DESCRIPTION "Tx-Filter"
                   ::= {  setIprouRipLanEntry 11 }

setIprouRipR1m OBJECT-TYPE
               SYNTAX INTEGER {
                 class(0),
                 address(1),
                 cl-plus-addr(2)
               }
               MAX-ACCESS read-write
               STATUS current
               DESCRIPTION "R1-Mask"
               ::= {  setIprouRip 2 }

setIprouRipIprTable OBJECT-TYPE
                    SYNTAX SEQUENCE OF SetIprouRipIprEntry
                    MAX-ACCESS not-accessible
                    STATUS current
                    DESCRIPTION "IP-RIP-Table"
                    ::= {  setIprouRip 3 }

setIprouRipIprEntry OBJECT-TYPE
                    SYNTAX SetIprouRipIprEntry
                    MAX-ACCESS not-accessible
                    STATUS current
                    DESCRIPTION "entry in table"
                    INDEX { setIprouRipIprIpa, setIprouRipIprIpn, setIprouRipIprRtg }
                    ::= {  setIprouRipIprTable 1 }

SetIprouRipIprEntry ::= SEQUENCE {
                    setIprouRipIprIpa IpAddress,
                    setIprouRipIprIpn IpAddress,
                    setIprouRipIprRtg INTEGER,
                    setIprouRipIprTim INTEGER,
                    setIprouRipIprDis INTEGER,
                    setIprouRipIprGat IpAddress,
                    setIprouRipIprPee DisplayString,
                    setIprouRipIprPor INTEGER,
                    setIprouRipIprVla INTEGER,
                    setIprouRipIprNet DisplayString
                   }

setIprouRipIprIpa OBJECT-TYPE
                  SYNTAX IpAddress
                  MAX-ACCESS read-only
                  STATUS current
                  DESCRIPTION "IP-Address"
                  ::= {  setIprouRipIprEntry 1 }

setIprouRipIprIpn OBJECT-TYPE
                  SYNTAX IpAddress
                  MAX-ACCESS read-only
                  STATUS current
                  DESCRIPTION "IP-Netmask"
                  ::= {  setIprouRipIprEntry 2 }

setIprouRipIprRtg OBJECT-TYPE
                  SYNTAX INTEGER (0..65535)
                  MAX-ACCESS read-only
                  STATUS current
                  DESCRIPTION "Rtg-tag"
                  ::= {  setIprouRipIprEntry 6 }

setIprouRipIprTim OBJECT-TYPE
                  SYNTAX INTEGER (0..65535)
                  MAX-ACCESS read-only
                  STATUS current
                  DESCRIPTION "Time"
                  ::= {  setIprouRipIprEntry 3 }

setIprouRipIprDis OBJECT-TYPE
                  SYNTAX INTEGER (0..65535)
                  MAX-ACCESS read-only
                  STATUS current
                  DESCRIPTION "Distance"
                  ::= {  setIprouRipIprEntry 4 }

setIprouRipIprGat OBJECT-TYPE
                  SYNTAX IpAddress
                  MAX-ACCESS read-only
                  STATUS current
                  DESCRIPTION "Gateway"
                  ::= {  setIprouRipIprEntry 5 }

setIprouRipIprPee OBJECT-TYPE
                  SYNTAX DisplayString (SIZE(0..16))
                  MAX-ACCESS read-only
                  STATUS current
                  DESCRIPTION "Peer"
                  ::= {  setIprouRipIprEntry 8 }

setIprouRipIprPor OBJECT-TYPE
                  SYNTAX INTEGER{
                    lan-1(0),
                    wlan-1(1),
                    p2p-1-1(2),
                    p2p-1-2(3),
                    p2p-1-3(4),
                    p2p-1-4(5),
                    p2p-1-5(6),
                    p2p-1-6(7),
                    wlan-1-2(8),
                    wlan-1-3(9),
                    wlan-1-4(10),
                    wlan-1-5(11),
                    wlan-1-6(12),
                    wlan-1-7(13),
                    wlan-1-8(14),
                    brg-1(15),
                    brg-2(16),
                    brg-3(17),
                    brg-4(18),
                    brg-5(19),
                    brg-6(20),
                    brg-7(21),
                    brg-8(22),
                    any(255)
                  }
                  MAX-ACCESS read-only
                  STATUS current
                  DESCRIPTION "Port"
                  ::= {  setIprouRipIprEntry 9 }

setIprouRipIprVla OBJECT-TYPE
                  SYNTAX INTEGER (0..65535)
                  MAX-ACCESS read-only
                  STATUS current
                  DESCRIPTION "VLAN-ID"
                  ::= {  setIprouRipIprEntry 10 }

setIprouRipIprNet OBJECT-TYPE
                  SYNTAX DisplayString (SIZE(0..16))
                  MAX-ACCESS read-only
                  STATUS current
                  DESCRIPTION "Network-name"
                  ::= {  setIprouRipIprEntry 11 }

setIprouRipWanTable OBJECT-TYPE
                    SYNTAX SEQUENCE OF SetIprouRipWanEntry
                    MAX-ACCESS not-accessible
                    STATUS current
                    DESCRIPTION "WAN-Sites"
                    ::= {  setIprouRip 4 }

setIprouRipWanEntry OBJECT-TYPE
                    SYNTAX SetIprouRipWanEntry
                    MAX-ACCESS not-accessible
                    STATUS current
                    DESCRIPTION "entry in table"
                    INDEX { setIprouRipWanPeer }
                    ::= {  setIprouRipWanTable 1 }

SetIprouRipWanEntry ::= SEQUENCE {
                    setIprouRipWanPeer DisplayString,
                    setIprouRipWanRipt INTEGER,
                    setIprouRipWanRipa INTEGER,
                    setIprouRipWanMasq INTEGER,
                    setIprouRipWanPois INTEGER,
                    setIprouRipWanRfc2 INTEGER,
                    setIprouRipWanGate IpAddress,
                    setIprouRipWanDftr INTEGER,
                    setIprouRipWanRtgt DisplayString,
                    setIprouRipWanRxfi DisplayString,
                    setIprouRipWanTxfi DisplayString
                   }

setIprouRipWanPeer OBJECT-TYPE
                   SYNTAX DisplayString (SIZE(0..16))
                   MAX-ACCESS read-write
                   STATUS current
                   DESCRIPTION "Peer"
                   ::= {  setIprouRipWanEntry 1 }

setIprouRipWanRipt OBJECT-TYPE
                   SYNTAX INTEGER{
                     off(0),
                     rip-1(1),
                     r1-comp(2),
                     rip-2(3)
                   }
                   MAX-ACCESS read-write
                   STATUS current
                   DESCRIPTION "RIP-Type"
                   ::= {  setIprouRipWanEntry 2 }

setIprouRipWanRipa OBJECT-TYPE
                   SYNTAX INTEGER{
                     no(0),
                     yes(1)
                   }
                   MAX-ACCESS read-write
                   STATUS current
                   DESCRIPTION "RIP-Accept"
                   ::= {  setIprouRipWanEntry 3 }

setIprouRipWanMasq OBJECT-TYPE
                   SYNTAX INTEGER{
                     auto(0),
                     on(1),
                     intranet(2)
                   }
                   MAX-ACCESS read-write
                   STATUS current
                   DESCRIPTION "Masquerade"
                   ::= {  setIprouRipWanEntry 4 }

setIprouRipWanPois OBJECT-TYPE
                   SYNTAX INTEGER{
                     no(0),
                     yes(1)
                   }
                   MAX-ACCESS read-write
                   STATUS current
                   DESCRIPTION "Poisoned-Reverse"
                   ::= {  setIprouRipWanEntry 7 }

setIprouRipWanRfc2 OBJECT-TYPE
                   SYNTAX INTEGER{
                     no(0),
                     yes(1)
                   }
                   MAX-ACCESS read-write
                   STATUS current
                   DESCRIPTION "RFC2091"
                   ::= {  setIprouRipWanEntry 8 }

setIprouRipWanGate OBJECT-TYPE
                   SYNTAX IpAddress
                   MAX-ACCESS read-write
                   STATUS current
                   DESCRIPTION "Gateway"
                   ::= {  setIprouRipWanEntry 9 }

setIprouRipWanDftr OBJECT-TYPE
                   SYNTAX INTEGER (0..65535)
                   MAX-ACCESS read-write
                   STATUS current
                   DESCRIPTION "Dft-Rtg-Tag"
                   ::= {  setIprouRipWanEntry 5 }

setIprouRipWanRtgt OBJECT-TYPE
                   SYNTAX DisplayString (SIZE(0..33))
                   MAX-ACCESS read-write
                   STATUS current
                   DESCRIPTION "Rtg-Tag-List"
                   ::= {  setIprouRipWanEntry 6 }

setIprouRipWanRxfi OBJECT-TYPE
                   SYNTAX DisplayString (SIZE(0..16))
                   MAX-ACCESS read-write
                   STATUS current
                   DESCRIPTION "Rx-Filter"
                   ::= {  setIprouRipWanEntry 10 }

setIprouRipWanTxfi OBJECT-TYPE
                   SYNTAX DisplayString (SIZE(0..16))
                   MAX-ACCESS read-write
                   STATUS current
                   DESCRIPTION "Tx-Filter"
                   ::= {  setIprouRipWanEntry 11 }

setIprouRipFilTable OBJECT-TYPE
                    SYNTAX SEQUENCE OF SetIprouRipFilEntry
                    MAX-ACCESS not-accessible
                    STATUS current
                    DESCRIPTION "Filter"
                    ::= {  setIprouRip 7 }

setIprouRipFilEntry OBJECT-TYPE
                    SYNTAX SetIprouRipFilEntry
                    MAX-ACCESS not-accessible
                    STATUS current
                    DESCRIPTION "entry in table"
                    INDEX { setIprouRipFilNam }
                    ::= {  setIprouRipFilTable 1 }

SetIprouRipFilEntry ::= SEQUENCE {
                    setIprouRipFilNam DisplayString,
                    setIprouRipFilFil DisplayString
                   }

setIprouRipFilNam OBJECT-TYPE
                  SYNTAX DisplayString (SIZE(0..18))
                  MAX-ACCESS read-write
                  STATUS current
                  DESCRIPTION "Name"
                  ::= {  setIprouRipFilEntry 1 }

setIprouRipFilFil OBJECT-TYPE
                  SYNTAX DisplayString (SIZE(0..64))
                  MAX-ACCESS read-write
                  STATUS current
                  DESCRIPTION "Filter"
                  ::= {  setIprouRipFilEntry 2 }

setIprouRipPar OBJECT IDENTIFIER ::= { setIprouRip 6}
setIprouRipParUpda OBJECT-TYPE
                   SYNTAX INTEGER
                   MAX-ACCESS read-write
                   STATUS current
                   DESCRIPTION "Update"
                   ::= {  setIprouRipPar 1 }

setIprouRipParHold OBJECT-TYPE
                   SYNTAX INTEGER
                   MAX-ACCESS read-write
                   STATUS current
                   DESCRIPTION "Holddown"
                   ::= {  setIprouRipPar 2 }

setIprouRipParInva OBJECT-TYPE
                   SYNTAX INTEGER
                   MAX-ACCESS read-write
                   STATUS current
                   DESCRIPTION "Invalidate"
                   ::= {  setIprouRipPar 3 }

setIprouRipParFlus OBJECT-TYPE
                   SYNTAX INTEGER
                   MAX-ACCESS read-write
                   STATUS current
                   DESCRIPTION "Flush"
                   ::= {  setIprouRipPar 4 }

setIprouRipParUpdd OBJECT-TYPE
                   SYNTAX INTEGER
                   MAX-ACCESS read-write
                   STATUS current
                   DESCRIPTION "Upd-Delay"
                   ::= {  setIprouRipPar 5 }

setIprouRipParMaxh OBJECT-TYPE
                   SYNTAX INTEGER
                   MAX-ACCESS read-write
                   STATUS current
                   DESCRIPTION "Max-Hopcount"
                   ::= {  setIprouRipPar 6 }

setIprouRipParRout OBJECT-TYPE
                   SYNTAX INTEGER
                   MAX-ACCESS read-write
                   STATUS current
                   DESCRIPTION "Routes-per-Frame"
                   ::= {  setIprouRipPar 7 }

setIprou1nn OBJECT IDENTIFIER ::= { setIprou 9}
setIprou1nnTcpagings OBJECT-TYPE
                     SYNTAX INTEGER
                     MAX-ACCESS read-write
                     STATUS current
                     DESCRIPTION "TCP-Aging-Seconds"
                     ::= {  setIprou1nn 1 }

setIprou1nnUdpagings OBJECT-TYPE
                     SYNTAX INTEGER
                     MAX-ACCESS read-write
                     STATUS current
                     DESCRIPTION "UDP-Aging-Seconds"
                     ::= {  setIprou1nn 2 }

setIprou1nnIcmpaging OBJECT-TYPE
                     SYNTAX INTEGER
                     MAX-ACCESS read-write
                     STATUS current
                     DESCRIPTION "ICMP-Aging-Seconds"
                     ::= {  setIprou1nn 3 }

setIprou1nnServicetaTable OBJECT-TYPE
                          SYNTAX SEQUENCE OF SetIprou1nnServicetaEntry
                          MAX-ACCESS not-accessible
                          STATUS current
                          DESCRIPTION "Service-Table"
                          ::= {  setIprou1nn 4 }

setIprou1nnServicetaEntry OBJECT-TYPE
                          SYNTAX SetIprou1nnServicetaEntry
                          MAX-ACCESS not-accessible
                          STATUS current
                          DESCRIPTION "entry in table"
                          INDEX { setIprou1nnServicetaDportf, setIprou1nnServicetaDportt, setIprou1nnServicetaProtoc, setIprou1nnServicetaPeer, setIprou1nnServicetaWanadd }
                          ::= {  setIprou1nnServicetaTable 1 }

SetIprou1nnServicetaEntry ::= SEQUENCE {
                          setIprou1nnServicetaDportf INTEGER,
                          setIprou1nnServicetaDportt INTEGER,
                          setIprou1nnServicetaProtoc INTEGER,
                          setIprou1nnServicetaPeer DisplayString,
                          setIprou1nnServicetaWanadd IpAddress,
                          setIprou1nnServicetaIntran IpAddress,
                          setIprou1nnServicetaMappor INTEGER,
                          setIprou1nnServicetaActive INTEGER,
                          setIprou1nnServicetaCommen DisplayString
                         }

setIprou1nnServicetaDportf OBJECT-TYPE
                           SYNTAX INTEGER (0..65535)
                           MAX-ACCESS read-write
                           STATUS current
                           DESCRIPTION "D-port-from"
                           ::= {  setIprou1nnServicetaEntry 1 }

setIprou1nnServicetaDportt OBJECT-TYPE
                           SYNTAX INTEGER (0..65535)
                           MAX-ACCESS read-write
                           STATUS current
                           DESCRIPTION "D-port-to"
                           ::= {  setIprou1nnServicetaEntry 3 }

setIprou1nnServicetaProtoc OBJECT-TYPE
                           SYNTAX INTEGER{
                             tcp(1),
                             udp(2),
                             tcp-plus-udp(0)
                           }
                           MAX-ACCESS read-write
                           STATUS current
                           DESCRIPTION "Protocol"
                           ::= {  setIprou1nnServicetaEntry 8 }

setIprou1nnServicetaPeer OBJECT-TYPE
                           SYNTAX DisplayString (SIZE(0..16))
                           MAX-ACCESS read-write
                           STATUS current
                           DESCRIPTION "Peer"
                           ::= {  setIprou1nnServicetaEntry 7 }

setIprou1nnServicetaWanadd OBJECT-TYPE
                           SYNTAX IpAddress
                           MAX-ACCESS read-write
                           STATUS current
                           DESCRIPTION "WAN-Address"
                           ::= {  setIprou1nnServicetaEntry 9 }

setIprou1nnServicetaIntran OBJECT-TYPE
                           SYNTAX IpAddress
                           MAX-ACCESS read-write
                           STATUS current
                           DESCRIPTION "Intranet-Address"
                           ::= {  setIprou1nnServicetaEntry 2 }

setIprou1nnServicetaMappor OBJECT-TYPE
                           SYNTAX INTEGER (0..65535)
                           MAX-ACCESS read-write
                           STATUS current
                           DESCRIPTION "Map-Port"
                           ::= {  setIprou1nnServicetaEntry 4 }

setIprou1nnServicetaActive OBJECT-TYPE
                           SYNTAX INTEGER{
                             no(1),
                             yes(0)
                           }
                           MAX-ACCESS read-write
                           STATUS current
                           DESCRIPTION "Active"
                           ::= {  setIprou1nnServicetaEntry 5 }

setIprou1nnServicetaCommen OBJECT-TYPE
                           SYNTAX DisplayString (SIZE(0..64))
                           MAX-ACCESS read-write
                           STATUS current
                           DESCRIPTION "Comment"
                           ::= {  setIprou1nnServicetaEntry 6 }

setIprou1nnTable1nnaTable OBJECT-TYPE
                          SYNTAX SEQUENCE OF SetIprou1nnTable1nnaEntry
                          MAX-ACCESS not-accessible
                          STATUS current
                          DESCRIPTION "Table-1-N-NAT"
                          ::= {  setIprou1nn 5 }

setIprou1nnTable1nnaEntry OBJECT-TYPE
                          SYNTAX SetIprou1nnTable1nnaEntry
                          MAX-ACCESS not-accessible
                          STATUS current
                          DESCRIPTION "entry in table"
                          INDEX { setIprou1nnTable1nnaInt }
                          ::= {  setIprou1nnTable1nnaTable 1 }

SetIprou1nnTable1nnaEntry ::= SEQUENCE {
                          setIprou1nnTable1nnaInt IpAddress,
                          setIprou1nnTable1nnaSou INTEGER,
                          setIprou1nnTable1nnaPro INTEGER,
                          setIprou1nnTable1nnaTim INTEGER,
                          setIprou1nnTable1nnaHan DisplayString,
                          setIprou1nnTable1nnaRem IpAddress
                         }

setIprou1nnTable1nnaInt OBJECT-TYPE
                        SYNTAX IpAddress
                        MAX-ACCESS read-only
                        STATUS current
                        DESCRIPTION "Intranet-Address"
                        ::= {  setIprou1nnTable1nnaEntry 1 }

setIprou1nnTable1nnaSou OBJECT-TYPE
                        SYNTAX INTEGER (0..65535)
                        MAX-ACCESS read-only
                        STATUS current
                        DESCRIPTION "Source-Port"
                        ::= {  setIprou1nnTable1nnaEntry 2 }

setIprou1nnTable1nnaPro OBJECT-TYPE
                        SYNTAX INTEGER{
                          tcp(6),
                          udp(17),
                          icmp(1)
                        }
                        MAX-ACCESS read-only
                        STATUS current
                        DESCRIPTION "Protocol"
                        ::= {  setIprou1nnTable1nnaEntry 3 }

setIprou1nnTable1nnaTim OBJECT-TYPE
                        SYNTAX INTEGER (0..65535)
                        MAX-ACCESS read-only
                        STATUS current
                        DESCRIPTION "Timeout"
                        ::= {  setIprou1nnTable1nnaEntry 4 }

setIprou1nnTable1nnaHan OBJECT-TYPE
                        SYNTAX DisplayString (SIZE(0..255))
                        MAX-ACCESS read-only
                        STATUS current
                        DESCRIPTION "Handler"
                        ::= {  setIprou1nnTable1nnaEntry 5 }

setIprou1nnTable1nnaRem OBJECT-TYPE
                        SYNTAX IpAddress
                        MAX-ACCESS read-only
                        STATUS current
                        DESCRIPTION "remote-Address"
                        ::= {  setIprou1nnTable1nnaEntry 6 }

setIprou1nnFragments OBJECT-TYPE
                     SYNTAX INTEGER {
                       filter(0),
                       route(1),
                       reassemble(2)
                     }
                     MAX-ACCESS read-write
                     STATUS current
                     DESCRIPTION "Fragments"
                     ::= {  setIprou1nn 6 }

setIprou1nnFragmenta OBJECT-TYPE
                     SYNTAX INTEGER
                     MAX-ACCESS read-write
                     STATUS current
                     DESCRIPTION "Fragment-Aging-Seconds"
                     ::= {  setIprou1nn 7 }

setIprou1nnIpsecagin OBJECT-TYPE
                     SYNTAX INTEGER
                     MAX-ACCESS read-write
                     STATUS current
                     DESCRIPTION "IPSec-Aging-Seconds"
                     ::= {  setIprou1nn 8 }

setIprou1nnIpsectablTable OBJECT-TYPE
                          SYNTAX SEQUENCE OF SetIprou1nnIpsectablEntry
                          MAX-ACCESS not-accessible
                          STATUS current
                          DESCRIPTION "IPSec-Table"
                          ::= {  setIprou1nn 9 }

setIprou1nnIpsectablEntry OBJECT-TYPE
                          SYNTAX SetIprou1nnIpsectablEntry
                          MAX-ACCESS not-accessible
                          STATUS current
                          DESCRIPTION "entry in table"
                          INDEX { setIprou1nnIpsectablRemotea }
                          ::= {  setIprou1nnIpsectablTable 1 }

SetIprou1nnIpsectablEntry ::= SEQUENCE {
                          setIprou1nnIpsectablRemotea IpAddress,
                          setIprou1nnIpsectablLocalad IpAddress,
                          setIprou1nnIpsectablRchi DisplayString,
                          setIprou1nnIpsectablRclo DisplayString,
                          setIprou1nnIpsectablLchi DisplayString,
                          setIprou1nnIpsectablLclo DisplayString,
                          setIprou1nnIpsectablRemotes DisplayString,
                          setIprou1nnIpsectablLocalsp DisplayString,
                          setIprou1nnIpsectablTimeout INTEGER,
                          setIprou1nnIpsectablCo INTEGER,
                          setIprou1nnIpsectablNl INTEGER,
                          setIprou1nnIpsectablNr INTEGER,
                          setIprou1nnIpsectablDp INTEGER,
                          setIprou1nnIpsectablFlags DisplayString
                         }

setIprou1nnIpsectablRemotea OBJECT-TYPE
                            SYNTAX IpAddress
                            MAX-ACCESS read-only
                            STATUS current
                            DESCRIPTION "remote-Address"
                            ::= {  setIprou1nnIpsectablEntry 1 }

setIprou1nnIpsectablLocalad OBJECT-TYPE
                            SYNTAX IpAddress
                            MAX-ACCESS read-only
                            STATUS current
                            DESCRIPTION "local-Address"
                            ::= {  setIprou1nnIpsectablEntry 2 }

setIprou1nnIpsectablRchi OBJECT-TYPE
                            SYNTAX DisplayString (SIZE(0..8))
                            MAX-ACCESS read-only
                            STATUS current
                            DESCRIPTION "rc-hi"
                            ::= {  setIprou1nnIpsectablEntry 3 }

setIprou1nnIpsectablRclo OBJECT-TYPE
                            SYNTAX DisplayString (SIZE(0..8))
                            MAX-ACCESS read-only
                            STATUS current
                            DESCRIPTION "rc-lo"
                            ::= {  setIprou1nnIpsectablEntry 4 }

setIprou1nnIpsectablLchi OBJECT-TYPE
                            SYNTAX DisplayString (SIZE(0..8))
                            MAX-ACCESS read-only
                            STATUS current
                            DESCRIPTION "lc-hi"
                            ::= {  setIprou1nnIpsectablEntry 5 }

setIprou1nnIpsectablLclo OBJECT-TYPE
                            SYNTAX DisplayString (SIZE(0..8))
                            MAX-ACCESS read-only
                            STATUS current
                            DESCRIPTION "lc-lo"
                            ::= {  setIprou1nnIpsectablEntry 6 }

setIprou1nnIpsectablRemotes OBJECT-TYPE
                            SYNTAX DisplayString (SIZE(0..8))
                            MAX-ACCESS read-only
                            STATUS current
                            DESCRIPTION "remote-SPI"
                            ::= {  setIprou1nnIpsectablEntry 7 }

setIprou1nnIpsectablLocalsp OBJECT-TYPE
                            SYNTAX DisplayString (SIZE(0..8))
                            MAX-ACCESS read-only
                            STATUS current
                            DESCRIPTION "local-SPI"
                            ::= {  setIprou1nnIpsectablEntry 8 }

setIprou1nnIpsectablTimeout OBJECT-TYPE
                            SYNTAX INTEGER (0..2147483647)
                            MAX-ACCESS read-only
                            STATUS current
                            DESCRIPTION "Timeout"
                            ::= {  setIprou1nnIpsectablEntry 9 }

setIprou1nnIpsectablCo OBJECT-TYPE
                            SYNTAX INTEGER (0..255)
                            MAX-ACCESS read-only
                            STATUS current
                            DESCRIPTION "CO"
                            ::= {  setIprou1nnIpsectablEntry 11 }

setIprou1nnIpsectablNl OBJECT-TYPE
                            SYNTAX INTEGER (0..255)
                            MAX-ACCESS read-only
                            STATUS current
                            DESCRIPTION "NL"
                            ::= {  setIprou1nnIpsectablEntry 12 }

setIprou1nnIpsectablNr OBJECT-TYPE
                            SYNTAX INTEGER (0..255)
                            MAX-ACCESS read-only
                            STATUS current
                            DESCRIPTION "NR"
                            ::= {  setIprou1nnIpsectablEntry 13 }

setIprou1nnIpsectablDp OBJECT-TYPE
                            SYNTAX INTEGER (0..255)
                            MAX-ACCESS read-only
                            STATUS current
                            DESCRIPTION "DP"
                            ::= {  setIprou1nnIpsectablEntry 14 }

setIprou1nnIpsectablFlags OBJECT-TYPE
                            SYNTAX DisplayString (SIZE(0..4))
                            MAX-ACCESS read-only
                            STATUS current
                            DESCRIPTION "Flags"
                            ::= {  setIprou1nnIpsectablEntry 10 }

setIprou1nnIdspoofin OBJECT-TYPE
                     SYNTAX INTEGER {
                       no(0),
                       yes(1)
                     }
                     MAX-ACCESS read-write
                     STATUS current
                     DESCRIPTION "ID-Spoofing"
                     ::= {  setIprou1nn 10 }

setIprouFir OBJECT IDENTIFIER ::= { setIprou 10}
setIprouFirOpera OBJECT-TYPE
                 SYNTAX INTEGER {
                   no(0),
                   yes(1)
                 }
                 MAX-ACCESS read-write
                 STATUS current
                 DESCRIPTION "Operating"
                 ::= {  setIprouFir 11 }

setIprouFirActioTable OBJECT-TYPE
                      SYNTAX SEQUENCE OF SetIprouFirActioEntry
                      MAX-ACCESS not-accessible
                      STATUS current
                      DESCRIPTION "Actions"
                      ::= {  setIprouFir 4 }

setIprouFirActioEntry OBJECT-TYPE
                      SYNTAX SetIprouFirActioEntry
                      MAX-ACCESS not-accessible
                      STATUS current
                      DESCRIPTION "entry in table"
                      INDEX { setIprouFirActioNam }
                      ::= {  setIprouFirActioTable 1 }

SetIprouFirActioEntry ::= SEQUENCE {
                      setIprouFirActioNam DisplayString,
                      setIprouFirActioDes DisplayString
                     }

setIprouFirActioNam OBJECT-TYPE
                    SYNTAX DisplayString (SIZE(0..32))
                    MAX-ACCESS read-write
                    STATUS current
                    DESCRIPTION "Name"
                    ::= {  setIprouFirActioEntry 1 }

setIprouFirActioDes OBJECT-TYPE
                    SYNTAX DisplayString (SIZE(0..64))
                    MAX-ACCESS read-write
                    STATUS current
                    DESCRIPTION "Description"
                    ::= {  setIprouFirActioEntry 2 }

setIprouFirObjecTable OBJECT-TYPE
                      SYNTAX SEQUENCE OF SetIprouFirObjecEntry
                      MAX-ACCESS not-accessible
                      STATUS current
                      DESCRIPTION "Objects"
                      ::= {  setIprouFir 1 }

setIprouFirObjecEntry OBJECT-TYPE
                      SYNTAX SetIprouFirObjecEntry
                      MAX-ACCESS not-accessible
                      STATUS current
                      DESCRIPTION "entry in table"
                      INDEX { setIprouFirObjecNam }
                      ::= {  setIprouFirObjecTable 1 }

SetIprouFirObjecEntry ::= SEQUENCE {
                      setIprouFirObjecNam DisplayString,
                      setIprouFirObjecDes DisplayString
                     }

setIprouFirObjecNam OBJECT-TYPE
                    SYNTAX DisplayString (SIZE(0..32))
                    MAX-ACCESS read-write
                    STATUS current
                    DESCRIPTION "Name"
                    ::= {  setIprouFirObjecEntry 1 }

setIprouFirObjecDes OBJECT-TYPE
                    SYNTAX DisplayString (SIZE(0..64))
                    MAX-ACCESS read-write
                    STATUS current
                    DESCRIPTION "Description"
                    ::= {  setIprouFirObjecEntry 2 }

setIprouFirRulesTable OBJECT-TYPE
                      SYNTAX SEQUENCE OF SetIprouFirRulesEntry
                      MAX-ACCESS not-accessible
                      STATUS current
                      DESCRIPTION "Rules"
                      ::= {  setIprouFir 2 }

setIprouFirRulesEntry OBJECT-TYPE
                      SYNTAX SetIprouFirRulesEntry
                      MAX-ACCESS not-accessible
                      STATUS current
                      DESCRIPTION "entry in table"
                      INDEX { setIprouFirRulesNam }
                      ::= {  setIprouFirRulesTable 1 }

SetIprouFirRulesEntry ::= SEQUENCE {
                      setIprouFirRulesNam DisplayString,
                      setIprouFirRulesPro DisplayString,
                      setIprouFirRulesSou DisplayString,
                      setIprouFirRulesDes DisplayString,
                      setIprouFirRulesAct DisplayString,
                      setIprouFirRulesLin INTEGER,
                      setIprouFirRulesPri INTEGER,
                      setIprouFirRulesFir INTEGER,
                      setIprouFirRulesSta INTEGER,
                      setIprouFirRulesRtg INTEGER,
                      setIprouFirRulesCom DisplayString
                     }

setIprouFirRulesNam OBJECT-TYPE
                    SYNTAX DisplayString (SIZE(0..32))
                    MAX-ACCESS read-write
                    STATUS current
                    DESCRIPTION "Name"
                    ::= {  setIprouFirRulesEntry 1 }

setIprouFirRulesPro OBJECT-TYPE
                    SYNTAX DisplayString (SIZE(0..10))
                    MAX-ACCESS read-write
                    STATUS current
                    DESCRIPTION "Prot."
                    ::= {  setIprouFirRulesEntry 2 }

setIprouFirRulesSou OBJECT-TYPE
                    SYNTAX DisplayString (SIZE(0..40))
                    MAX-ACCESS read-write
                    STATUS current
                    DESCRIPTION "Source"
                    ::= {  setIprouFirRulesEntry 3 }

setIprouFirRulesDes OBJECT-TYPE
                    SYNTAX DisplayString (SIZE(0..40))
                    MAX-ACCESS read-write
                    STATUS current
                    DESCRIPTION "Destination"
                    ::= {  setIprouFirRulesEntry 4 }

setIprouFirRulesAct OBJECT-TYPE
                    SYNTAX DisplayString (SIZE(0..40))
                    MAX-ACCESS read-write
                    STATUS current
                    DESCRIPTION "Action"
                    ::= {  setIprouFirRulesEntry 7 }

setIprouFirRulesLin OBJECT-TYPE
                    SYNTAX INTEGER{
                      no(0),
                      yes(1)
                    }
                    MAX-ACCESS read-write
                    STATUS current
                    DESCRIPTION "Linked"
                    ::= {  setIprouFirRulesEntry 8 }

setIprouFirRulesPri OBJECT-TYPE
                    SYNTAX INTEGER (0..65535)
                    MAX-ACCESS read-write
                    STATUS current
                    DESCRIPTION "Prio"
                    ::= {  setIprouFirRulesEntry 9 }

setIprouFirRulesFir OBJECT-TYPE
                    SYNTAX INTEGER{
                      no(1),
                      yes(0)
                    }
                    MAX-ACCESS read-write
                    STATUS current
                    DESCRIPTION "Firewall-Rule"
                    ::= {  setIprouFirRulesEntry 10 }

setIprouFirRulesSta OBJECT-TYPE
                    SYNTAX INTEGER{
                      no(1),
                      yes(0)
                    }
                    MAX-ACCESS read-write
                    STATUS current
                    DESCRIPTION "Stateful"
                    ::= {  setIprouFirRulesEntry 12 }

setIprouFirRulesRtg OBJECT-TYPE
                    SYNTAX INTEGER (0..65535)
                    MAX-ACCESS read-write
                    STATUS current
                    DESCRIPTION "Rtg-tag"
                    ::= {  setIprouFirRulesEntry 14 }

setIprouFirRulesCom OBJECT-TYPE
                    SYNTAX DisplayString (SIZE(0..64))
                    MAX-ACCESS read-write
                    STATUS current
                    DESCRIPTION "Comment"
                    ::= {  setIprouFirRulesEntry 13 }

setIprouFirFilteTable OBJECT-TYPE
                      SYNTAX SEQUENCE OF SetIprouFirFilteEntry
                      MAX-ACCESS not-accessible
                      STATUS current
                      DESCRIPTION "Filter-List"
                      ::= {  setIprouFir 3 }

setIprouFirFilteEntry OBJECT-TYPE
                      SYNTAX SetIprouFirFilteEntry
                      MAX-ACCESS not-accessible
                      STATUS current
                      DESCRIPTION "entry in table"
                      INDEX { setIprouFirFilteIdx }
                      ::= {  setIprouFirFilteTable 1 }

SetIprouFirFilteEntry ::= SEQUENCE {
                      setIprouFirFilteIdx INTEGER,
                      setIprouFirFilteProt INTEGER,
                      setIprouFirFilteSrcm DisplayString,
                      setIprouFirFilteSrca IpAddress,
                      setIprouFirFilteSrcn IpAddress,
                      setIprouFirFilteSst INTEGER,
                      setIprouFirFilteSend INTEGER,
                      setIprouFirFilteDstm DisplayString,
                      setIprouFirFilteDsta IpAddress,
                      setIprouFirFilteDstn IpAddress,
                      setIprouFirFilteDst INTEGER,
                      setIprouFirFilteDend INTEGER,
                      setIprouFirFilteActi DisplayString,
                      setIprouFirFilteLink INTEGER,
                      setIprouFirFiltePrio INTEGER,
                      setIprouFirFilteRtgt INTEGER
                     }

setIprouFirFilteIdx OBJECT-TYPE
                     SYNTAX INTEGER (0..65535)
                     MAX-ACCESS read-only
                     STATUS current
                     DESCRIPTION "Idx."
                     ::= {  setIprouFirFilteEntry 1 }

setIprouFirFilteProt OBJECT-TYPE
                     SYNTAX INTEGER (0..255)
                     MAX-ACCESS read-only
                     STATUS current
                     DESCRIPTION "Prot."
                     ::= {  setIprouFirFilteEntry 2 }

setIprouFirFilteSrcm OBJECT-TYPE
                     SYNTAX DisplayString (SIZE(0..12))
                     MAX-ACCESS read-only
                     STATUS current
                     DESCRIPTION "Src-MAC"
                     ::= {  setIprouFirFilteEntry 13 }

setIprouFirFilteSrca OBJECT-TYPE
                     SYNTAX IpAddress
                     MAX-ACCESS read-only
                     STATUS current
                     DESCRIPTION "Src-Address"
                     ::= {  setIprouFirFilteEntry 3 }

setIprouFirFilteSrcn OBJECT-TYPE
                     SYNTAX IpAddress
                     MAX-ACCESS read-only
                     STATUS current
                     DESCRIPTION "Src-Netmask"
                     ::= {  setIprouFirFilteEntry 4 }

setIprouFirFilteSst OBJECT-TYPE
                     SYNTAX INTEGER (0..65535)
                     MAX-ACCESS read-only
                     STATUS current
                     DESCRIPTION "S-St."
                     ::= {  setIprouFirFilteEntry 5 }

setIprouFirFilteSend OBJECT-TYPE
                     SYNTAX INTEGER (0..65535)
                     MAX-ACCESS read-only
                     STATUS current
                     DESCRIPTION "S-End"
                     ::= {  setIprouFirFilteEntry 6 }

setIprouFirFilteDstm OBJECT-TYPE
                     SYNTAX DisplayString (SIZE(0..12))
                     MAX-ACCESS read-only
                     STATUS current
                     DESCRIPTION "Dst-MAC"
                     ::= {  setIprouFirFilteEntry 14 }

setIprouFirFilteDsta OBJECT-TYPE
                     SYNTAX IpAddress
                     MAX-ACCESS read-only
                     STATUS current
                     DESCRIPTION "Dst-Address"
                     ::= {  setIprouFirFilteEntry 7 }

setIprouFirFilteDstn OBJECT-TYPE
                     SYNTAX IpAddress
                     MAX-ACCESS read-only
                     STATUS current
                     DESCRIPTION "Dst-Netmask"
                     ::= {  setIprouFirFilteEntry 8 }

setIprouFirFilteDst OBJECT-TYPE
                     SYNTAX INTEGER (0..65535)
                     MAX-ACCESS read-only
                     STATUS current
                     DESCRIPTION "D-St."
                     ::= {  setIprouFirFilteEntry 9 }

setIprouFirFilteDend OBJECT-TYPE
                     SYNTAX INTEGER (0..65535)
                     MAX-ACCESS read-only
                     STATUS current
                     DESCRIPTION "D-End"
                     ::= {  setIprouFirFilteEntry 10 }

setIprouFirFilteActi OBJECT-TYPE
                     SYNTAX DisplayString (SIZE(0..255))
                     MAX-ACCESS read-only
                     STATUS current
                     DESCRIPTION "Action"
                     ::= {  setIprouFirFilteEntry 11 }

setIprouFirFilteLink OBJECT-TYPE
                     SYNTAX INTEGER{
                       no(0),
                       yes(1)
                     }
                     MAX-ACCESS read-only
                     STATUS current
                     DESCRIPTION "Linked"
                     ::= {  setIprouFirFilteEntry 15 }

setIprouFirFiltePrio OBJECT-TYPE
                     SYNTAX INTEGER (0..65535)
                     MAX-ACCESS read-only
                     STATUS current
                     DESCRIPTION "Prio"
                     ::= {  setIprouFirFilteEntry 16 }

setIprouFirFilteRtgt OBJECT-TYPE
                     SYNTAX INTEGER (0..65535)
                     MAX-ACCESS read-only
                     STATUS current
                     DESCRIPTION "Rtg-tag"
                     ::= {  setIprouFirFilteEntry 17 }

setIprouFirConneTable OBJECT-TYPE
                      SYNTAX SEQUENCE OF SetIprouFirConneEntry
                      MAX-ACCESS not-accessible
                      STATUS current
                      DESCRIPTION "Connection-List"
                      ::= {  setIprouFir 5 }

setIprouFirConneEntry OBJECT-TYPE
                      SYNTAX SetIprouFirConneEntry
                      MAX-ACCESS not-accessible
                      STATUS current
                      DESCRIPTION "entry in table"
                      INDEX { setIprouFirConneSrca, setIprouFirConneDsta, setIprouFirConneProt, setIprouFirConneSrcp, setIprouFirConneDstp }
                      ::= {  setIprouFirConneTable 1 }

SetIprouFirConneEntry ::= SEQUENCE {
                      setIprouFirConneSrca IpAddress,
                      setIprouFirConneDsta IpAddress,
                      setIprouFirConneProt INTEGER,
                      setIprouFirConneSrcp INTEGER,
                      setIprouFirConneDstp INTEGER,
                      setIprouFirConneRtgt INTEGER,
                      setIprouFirConneTime INTEGER,
                      setIprouFirConneFlag INTEGER,
                      setIprouFirConneFilt DisplayString,
                      setIprouFirConneSrcr DisplayString,
                      setIprouFirConneDest DisplayString
                     }

setIprouFirConneSrca OBJECT-TYPE
                     SYNTAX IpAddress
                     MAX-ACCESS read-only
                     STATUS current
                     DESCRIPTION "Src-Address"
                     ::= {  setIprouFirConneEntry 1 }

setIprouFirConneDsta OBJECT-TYPE
                     SYNTAX IpAddress
                     MAX-ACCESS read-only
                     STATUS current
                     DESCRIPTION "Dst-Address"
                     ::= {  setIprouFirConneEntry 2 }

setIprouFirConneProt OBJECT-TYPE
                     SYNTAX INTEGER (0..255)
                     MAX-ACCESS read-only
                     STATUS current
                     DESCRIPTION "Prot."
                     ::= {  setIprouFirConneEntry 3 }

setIprouFirConneSrcp OBJECT-TYPE
                     SYNTAX INTEGER (0..65535)
                     MAX-ACCESS read-only
                     STATUS current
                     DESCRIPTION "Src-Port"
                     ::= {  setIprouFirConneEntry 4 }

setIprouFirConneDstp OBJECT-TYPE
                     SYNTAX INTEGER (0..65535)
                     MAX-ACCESS read-only
                     STATUS current
                     DESCRIPTION "Dst-Port"
                     ::= {  setIprouFirConneEntry 5 }

setIprouFirConneRtgt OBJECT-TYPE
                     SYNTAX INTEGER (0..65535)
                     MAX-ACCESS read-only
                     STATUS current
                     DESCRIPTION "Rtg-tag"
                     ::= {  setIprouFirConneEntry 11 }

setIprouFirConneTime OBJECT-TYPE
                     SYNTAX INTEGER (0..65535)
                     MAX-ACCESS read-only
                     STATUS current
                     DESCRIPTION "Timeout"
                     ::= {  setIprouFirConneEntry 6 }

setIprouFirConneFlag OBJECT-TYPE
                     SYNTAX INTEGER (0..2147483647)
                     MAX-ACCESS read-only
                     STATUS current
                     DESCRIPTION "Flags"
                     ::= {  setIprouFirConneEntry 7 }

setIprouFirConneFilt OBJECT-TYPE
                     SYNTAX DisplayString (SIZE(0..255))
                     MAX-ACCESS read-only
                     STATUS current
                     DESCRIPTION "Filter-Rule"
                     ::= {  setIprouFirConneEntry 8 }

setIprouFirConneSrcr OBJECT-TYPE
                     SYNTAX DisplayString (SIZE(0..255))
                     MAX-ACCESS read-only
                     STATUS current
                     DESCRIPTION "Src-Route"
                     ::= {  setIprouFirConneEntry 9 }

setIprouFirConneDest OBJECT-TYPE
                     SYNTAX DisplayString (SIZE(0..255))
                     MAX-ACCESS read-only
                     STATUS current
                     DESCRIPTION "Dest-Route"
                     ::= {  setIprouFirConneEntry 10 }

setIprouFirOpenpTable OBJECT-TYPE
                      SYNTAX SEQUENCE OF SetIprouFirOpenpEntry
                      MAX-ACCESS not-accessible
                      STATUS current
                      DESCRIPTION "Open-Port-List"
                      ::= {  setIprouFir 19 }

setIprouFirOpenpEntry OBJECT-TYPE
                      SYNTAX SetIprouFirOpenpEntry
                      MAX-ACCESS not-accessible
                      STATUS current
                      DESCRIPTION "entry in table"
                      INDEX { setIprouFirOpenpSrca, setIprouFirOpenpDsta, setIprouFirOpenpProt, setIprouFirOpenpDstp }
                      ::= {  setIprouFirOpenpTable 1 }

SetIprouFirOpenpEntry ::= SEQUENCE {
                      setIprouFirOpenpSrca IpAddress,
                      setIprouFirOpenpDsta IpAddress,
                      setIprouFirOpenpProt INTEGER,
                      setIprouFirOpenpDstp INTEGER,
                      setIprouFirOpenpTime INTEGER,
                      setIprouFirOpenpFilt DisplayString,
                      setIprouFirOpenpSrcr DisplayString
                     }

setIprouFirOpenpSrca OBJECT-TYPE
                     SYNTAX IpAddress
                     MAX-ACCESS read-only
                     STATUS current
                     DESCRIPTION "Src-Address"
                     ::= {  setIprouFirOpenpEntry 1 }

setIprouFirOpenpDsta OBJECT-TYPE
                     SYNTAX IpAddress
                     MAX-ACCESS read-only
                     STATUS current
                     DESCRIPTION "Dst-Address"
                     ::= {  setIprouFirOpenpEntry 2 }

setIprouFirOpenpProt OBJECT-TYPE
                     SYNTAX INTEGER (0..255)
                     MAX-ACCESS read-only
                     STATUS current
                     DESCRIPTION "Prot."
                     ::= {  setIprouFirOpenpEntry 3 }

setIprouFirOpenpDstp OBJECT-TYPE
                     SYNTAX INTEGER (0..65535)
                     MAX-ACCESS read-only
                     STATUS current
                     DESCRIPTION "Dst-Port"
                     ::= {  setIprouFirOpenpEntry 5 }

setIprouFirOpenpTime OBJECT-TYPE
                     SYNTAX INTEGER (0..65535)
                     MAX-ACCESS read-only
                     STATUS current
                     DESCRIPTION "Timeout"
                     ::= {  setIprouFirOpenpEntry 6 }

setIprouFirOpenpFilt OBJECT-TYPE
                     SYNTAX DisplayString (SIZE(0..255))
                     MAX-ACCESS read-only
                     STATUS current
                     DESCRIPTION "Filter-Rule"
                     ::= {  setIprouFirOpenpEntry 8 }

setIprouFirOpenpSrcr OBJECT-TYPE
                     SYNTAX DisplayString (SIZE(0..255))
                     MAX-ACCESS read-only
                     STATUS current
                     DESCRIPTION "Src-Route"
                     ::= {  setIprouFirOpenpEntry 9 }

setIprouFirHostbTable OBJECT-TYPE
                      SYNTAX SEQUENCE OF SetIprouFirHostbEntry
                      MAX-ACCESS not-accessible
                      STATUS current
                      DESCRIPTION "Host-Block-List"
                      ::= {  setIprouFir 6 }

setIprouFirHostbEntry OBJECT-TYPE
                      SYNTAX SetIprouFirHostbEntry
                      MAX-ACCESS not-accessible
                      STATUS current
                      DESCRIPTION "entry in table"
                      INDEX { setIprouFirHostbSrc }
                      ::= {  setIprouFirHostbTable 1 }

SetIprouFirHostbEntry ::= SEQUENCE {
                      setIprouFirHostbSrc IpAddress,
                      setIprouFirHostbTim INTEGER,
                      setIprouFirHostbFil DisplayString
                     }

setIprouFirHostbSrc OBJECT-TYPE
                    SYNTAX IpAddress
                    MAX-ACCESS read-only
                    STATUS current
                    DESCRIPTION "Src-Address"
                    ::= {  setIprouFirHostbEntry 1 }

setIprouFirHostbTim OBJECT-TYPE
                    SYNTAX INTEGER (0..2147483647)
                    MAX-ACCESS read-only
                    STATUS current
                    DESCRIPTION "Timeout"
                    ::= {  setIprouFirHostbEntry 2 }

setIprouFirHostbFil OBJECT-TYPE
                    SYNTAX DisplayString (SIZE(0..255))
                    MAX-ACCESS read-only
                    STATUS current
                    DESCRIPTION "Filter-Rule"
                    ::= {  setIprouFirHostbEntry 3 }

setIprouFirPortbTable OBJECT-TYPE
                      SYNTAX SEQUENCE OF SetIprouFirPortbEntry
                      MAX-ACCESS not-accessible
                      STATUS current
                      DESCRIPTION "Port-Block-List"
                      ::= {  setIprouFir 7 }

setIprouFirPortbEntry OBJECT-TYPE
                      SYNTAX SetIprouFirPortbEntry
                      MAX-ACCESS not-accessible
                      STATUS current
                      DESCRIPTION "entry in table"
                      INDEX { setIprouFirPortbDsta }
                      ::= {  setIprouFirPortbTable 1 }

SetIprouFirPortbEntry ::= SEQUENCE {
                      setIprouFirPortbDsta IpAddress,
                      setIprouFirPortbProt INTEGER,
                      setIprouFirPortbDstp INTEGER,
                      setIprouFirPortbTime INTEGER,
                      setIprouFirPortbFilt DisplayString
                     }

setIprouFirPortbDsta OBJECT-TYPE
                     SYNTAX IpAddress
                     MAX-ACCESS read-only
                     STATUS current
                     DESCRIPTION "Dst-Address"
                     ::= {  setIprouFirPortbEntry 1 }

setIprouFirPortbProt OBJECT-TYPE
                     SYNTAX INTEGER (0..65535)
                     MAX-ACCESS read-only
                     STATUS current
                     DESCRIPTION "Prot."
                     ::= {  setIprouFirPortbEntry 2 }

setIprouFirPortbDstp OBJECT-TYPE
                     SYNTAX INTEGER (0..65535)
                     MAX-ACCESS read-only
                     STATUS current
                     DESCRIPTION "Dst-Port"
                     ::= {  setIprouFirPortbEntry 3 }

setIprouFirPortbTime OBJECT-TYPE
                     SYNTAX INTEGER (0..2147483647)
                     MAX-ACCESS read-only
                     STATUS current
                     DESCRIPTION "Timeout"
                     ::= {  setIprouFirPortbEntry 4 }

setIprouFirPortbFilt OBJECT-TYPE
                     SYNTAX DisplayString (SIZE(0..255))
                     MAX-ACCESS read-only
                     STATUS current
                     DESCRIPTION "Filter-Rule"
                     ::= {  setIprouFirPortbEntry 5 }

setIprouFirMaxha OBJECT-TYPE
                 SYNTAX INTEGER
                 MAX-ACCESS read-write
                 STATUS current
                 DESCRIPTION "Max.-Half-Open-Conns."
                 ::= {  setIprouFir 8 }

setIprouFirDosac OBJECT-TYPE
                 SYNTAX DisplayString (SIZE(0..29))
                 MAX-ACCESS read-write
                 STATUS current
                 DESCRIPTION "DoS-Action"
                 ::= {  setIprouFir 9 }

setIprouFirPorts OBJECT-TYPE
                 SYNTAX INTEGER
                 MAX-ACCESS read-write
                 STATUS current
                 DESCRIPTION "Port-Scan-Threshold"
                 ::= {  setIprouFir 12 }

setIprouFirIdsac OBJECT-TYPE
                 SYNTAX DisplayString (SIZE(0..29))
                 MAX-ACCESS read-write
                 STATUS current
                 DESCRIPTION "IDS-Action"
                 ::= {  setIprouFir 13 }

setIprouFirAdmin OBJECT-TYPE
                 SYNTAX DisplayString (SIZE(0..255))
                 MAX-ACCESS read-write
                 STATUS current
                 DESCRIPTION "Admin.-Email"
                 ::= {  setIprouFir 10 }

setIprouFirPingb OBJECT-TYPE
                 SYNTAX INTEGER {
                   off(0),
                   allways(1),
                   wan(2),
                   default-route(3)
                 }
                 MAX-ACCESS read-write
                 STATUS current
                 DESCRIPTION "Ping-Block"
                 ::= {  setIprouFir 14 }

setIprouFirSteal OBJECT-TYPE
                 SYNTAX INTEGER {
                   off(0),
                   allways(1),
                   wan(2),
                   default-route(3)
                 }
                 MAX-ACCESS read-write
                 STATUS current
                 DESCRIPTION "Stealth-Mode"
                 ::= {  setIprouFir 15 }

setIprouFirAuthp OBJECT-TYPE
                 SYNTAX INTEGER {
                   closed(0),
                   stealth(1)
                 }
                 MAX-ACCESS read-write
                 STATUS current
                 DESCRIPTION "Auth-Port"
                 ::= {  setIprouFir 16 }

setIprouFirDenys OBJECT-TYPE
                 SYNTAX INTEGER {
                   off(0),
                   allways(1),
                   wan(2),
                   default-route(3)
                 }
                 MAX-ACCESS read-write
                 STATUS current
                 DESCRIPTION "Deny-Session-Recover"
                 ::= {  setIprouFir 17 }

setIprouFirAppli OBJECT IDENTIFIER ::= { setIprouFir 20}
setIprouFirAppliFtp OBJECT IDENTIFIER ::= { setIprouFirAppli 1}
setIprouFirAppliFtpFtp OBJECT-TYPE
                       SYNTAX INTEGER {
                         off(0),
                         allways(1),
                         wan(2),
                         default-route(3)
                       }
                       MAX-ACCESS read-write
                       STATUS current
                       DESCRIPTION "FTP-Block"
                       ::= {  setIprouFirAppliFtp 1 }

setIprouFirAppliFtpAct OBJECT-TYPE
                       SYNTAX INTEGER {
                         off(0),
                         allways(1),
                         wan(2),
                         default-route(3)
                       }
                       MAX-ACCESS read-write
                       STATUS current
                       DESCRIPTION "Active-FTP-Block"
                       ::= {  setIprouFirAppliFtp 2 }

setIprouFirAppliFtpMin OBJECT-TYPE
                       SYNTAX INTEGER
                       MAX-ACCESS read-write
                       STATUS current
                       DESCRIPTION "Min-Port"
                       ::= {  setIprouFirAppliFtp 3 }

setIprouFirAppliFtpChe OBJECT-TYPE
                       SYNTAX INTEGER {
                         off(0),
                         allways(1),
                         wan(2),
                         default-route(3)
                       }
                       MAX-ACCESS read-write
                       STATUS current
                       DESCRIPTION "Check-Host-IP"
                       ::= {  setIprouFirAppliFtp 4 }

setIprouFirAppliFtpFxp OBJECT-TYPE
                       SYNTAX INTEGER {
                         off(0),
                         allways(1),
                         wan(2),
                         default-route(3)
                       }
                       MAX-ACCESS read-write
                       STATUS current
                       DESCRIPTION "FXP-Block"
                       ::= {  setIprouFirAppliFtp 5 }

setIprouFirAppliIrc OBJECT IDENTIFIER ::= { setIprouFirAppli 2}
setIprouFirAppliIrcIrc OBJECT-TYPE
                       SYNTAX INTEGER {
                         off(0),
                         allways(1),
                         wan(2),
                         default-route(3)
                       }
                       MAX-ACCESS read-write
                       STATUS current
                       DESCRIPTION "IRC-Block"
                       ::= {  setIprouFirAppliIrc 1 }

setIprouFirAppliIrcDdc OBJECT-TYPE
                       SYNTAX INTEGER {
                         off(0),
                         allways(1),
                         wan(2),
                         default-route(3)
                       }
                       MAX-ACCESS read-write
                       STATUS current
                       DESCRIPTION "DDC-Block"
                       ::= {  setIprouFirAppliIrc 2 }

setIprouFirAppliIrcMin OBJECT-TYPE
                       SYNTAX INTEGER
                       MAX-ACCESS read-write
                       STATUS current
                       DESCRIPTION "Min-Port"
                       ::= {  setIprouFirAppliIrc 3 }

setIprouFirAppliIrcChe OBJECT-TYPE
                       SYNTAX INTEGER {
                         off(0),
                         allways(1),
                         wan(2),
                         default-route(3)
                       }
                       MAX-ACCESS read-write
                       STATUS current
                       DESCRIPTION "Check-Host-IP"
                       ::= {  setIprouFirAppliIrc 4 }

setIprouFirAppliApp OBJECT-TYPE
                    SYNTAX DisplayString (SIZE(0..29))
                    MAX-ACCESS read-write
                    STATUS current
                    DESCRIPTION "Appl.-Action"
                    ::= {  setIprouFirAppli 10 }

setIprouNnnTable OBJECT-TYPE
                 SYNTAX SEQUENCE OF SetIprouNnnEntry
                 MAX-ACCESS not-accessible
                 STATUS current
                 DESCRIPTION "N-N-NAT"
                 ::= {  setIprou 19 }

setIprouNnnEntry OBJECT-TYPE
                 SYNTAX SetIprouNnnEntry
                 MAX-ACCESS not-accessible
                 STATUS current
                 DESCRIPTION "entry in table"
                 INDEX { setIprouNnnIdx }
                 ::= {  setIprouNnnTable 1 }

SetIprouNnnEntry ::= SEQUENCE {
                 setIprouNnnIdx DisplayString,
                 setIprouNnnSrca IpAddress,
                 setIprouNnnSrcm IpAddress,
                 setIprouNnnDsts DisplayString,
                 setIprouNnnMapp IpAddress
                }

setIprouNnnIdx OBJECT-TYPE
                SYNTAX DisplayString (SIZE(0..4))
                MAX-ACCESS read-write
                STATUS current
                DESCRIPTION "Idx."
                ::= {  setIprouNnnEntry 1 }

setIprouNnnSrca OBJECT-TYPE
                SYNTAX IpAddress
                MAX-ACCESS read-write
                STATUS current
                DESCRIPTION "Src-Address"
                ::= {  setIprouNnnEntry 2 }

setIprouNnnSrcm OBJECT-TYPE
                SYNTAX IpAddress
                MAX-ACCESS read-write
                STATUS current
                DESCRIPTION "Src-Mask"
                ::= {  setIprouNnnEntry 3 }

setIprouNnnDsts OBJECT-TYPE
                SYNTAX DisplayString (SIZE(0..16))
                MAX-ACCESS read-write
                STATUS current
                DESCRIPTION "Dst-Station"
                ::= {  setIprouNnnEntry 4 }

setIprouNnnMapp OBJECT-TYPE
                SYNTAX IpAddress
                MAX-ACCESS read-write
                STATUS current
                DESCRIPTION "Mapped-Network"
                ::= {  setIprouNnnEntry 5 }

setIprouVrr OBJECT IDENTIFIER ::= { setIprou 21}
setIprouVrrOpe OBJECT-TYPE
               SYNTAX INTEGER {
                 no(0),
                 yes(1)
               }
               MAX-ACCESS read-write
               STATUS current
               DESCRIPTION "Operating"
               ::= {  setIprouVrr 1 }

setIprouVrrVrrTable OBJECT-TYPE
                    SYNTAX SEQUENCE OF SetIprouVrrVrrEntry
                    MAX-ACCESS not-accessible
                    STATUS current
                    DESCRIPTION "VRRP-List"
                    ::= {  setIprouVrr 2 }

setIprouVrrVrrEntry OBJECT-TYPE
                    SYNTAX SetIprouVrrVrrEntry
                    MAX-ACCESS not-accessible
                    STATUS current
                    DESCRIPTION "entry in table"
                    INDEX { setIprouVrrVrrRou }
                    ::= {  setIprouVrrVrrTable 1 }

SetIprouVrrVrrEntry ::= SEQUENCE {
                    setIprouVrrVrrRou INTEGER,
                    setIprouVrrVrrVir IpAddress,
                    setIprouVrrVrrPri INTEGER,
                    setIprouVrrVrrBpr INTEGER,
                    setIprouVrrVrrPee DisplayString,
                    setIprouVrrVrrCom DisplayString
                   }

setIprouVrrVrrRou OBJECT-TYPE
                  SYNTAX INTEGER (0..255)
                  MAX-ACCESS read-write
                  STATUS current
                  DESCRIPTION "Router-ID"
                  ::= {  setIprouVrrVrrEntry 1 }

setIprouVrrVrrVir OBJECT-TYPE
                  SYNTAX IpAddress
                  MAX-ACCESS read-write
                  STATUS current
                  DESCRIPTION "virt.-Address"
                  ::= {  setIprouVrrVrrEntry 2 }

setIprouVrrVrrPri OBJECT-TYPE
                  SYNTAX INTEGER (0..255)
                  MAX-ACCESS read-write
                  STATUS current
                  DESCRIPTION "Prio"
                  ::= {  setIprouVrrVrrEntry 3 }

setIprouVrrVrrBpr OBJECT-TYPE
                  SYNTAX INTEGER (0..255)
                  MAX-ACCESS read-write
                  STATUS current
                  DESCRIPTION "B-Prio"
                  ::= {  setIprouVrrVrrEntry 4 }

setIprouVrrVrrPee OBJECT-TYPE
                  SYNTAX DisplayString (SIZE(0..16))
                  MAX-ACCESS read-write
                  STATUS current
                  DESCRIPTION "Peer"
                  ::= {  setIprouVrrVrrEntry 5 }

setIprouVrrVrrCom OBJECT-TYPE
                  SYNTAX DisplayString (SIZE(0..64))
                  MAX-ACCESS read-write
                  STATUS current
                  DESCRIPTION "Comment"
                  ::= {  setIprouVrrVrrEntry 6 }

setIprouVrrRec OBJECT-TYPE
               SYNTAX INTEGER
               MAX-ACCESS read-write
               STATUS current
               DESCRIPTION "Reconnect-Delay"
               ::= {  setIprouVrr 3 }

setIprouVrrAdv OBJECT-TYPE
               SYNTAX INTEGER
               MAX-ACCESS read-write
               STATUS current
               DESCRIPTION "Advert.-Intervall"
               ::= {  setIprouVrr 4 }

setIprouVrrInt OBJECT-TYPE
               SYNTAX INTEGER {
                 no(0),
                 yes(1)
               }
               MAX-ACCESS read-write
               STATUS current
               DESCRIPTION "Internal-Services"
               ::= {  setIprouVrr 5 }

setSnmp OBJECT IDENTIFIER ::= { set 9}
setSnmpSendtrap OBJECT-TYPE
                SYNTAX INTEGER {
                  no(0),
                  yes(1)
                }
                MAX-ACCESS read-write
                STATUS current
                DESCRIPTION "Send-Traps"
                ::= {  setSnmp 1 }

setSnmpIptrapsTable OBJECT-TYPE
                     SYNTAX SEQUENCE OF SetSnmpIptrapsEntry
                     MAX-ACCESS not-accessible
                     STATUS current
                     DESCRIPTION "IP-Traps"
                     ::= {  setSnmp 2 }

setSnmpIptrapsEntry OBJECT-TYPE
                     SYNTAX SetSnmpIptrapsEntry
                     MAX-ACCESS not-accessible
                     STATUS current
                     DESCRIPTION "entry in table"
                     INDEX { setSnmpIptrapsTra }
                     ::= {  setSnmpIptrapsTable 1 }

SetSnmpIptrapsEntry ::= SEQUENCE {
                     setSnmpIptrapsTra IpAddress,
                     setSnmpIptrapsLoo DisplayString
                    }

setSnmpIptrapsTra OBJECT-TYPE
                  SYNTAX IpAddress
                  MAX-ACCESS read-write
                  STATUS current
                  DESCRIPTION "Trap-IP"
                  ::= {  setSnmpIptrapsEntry 1 }

setSnmpIptrapsLoo OBJECT-TYPE
                  SYNTAX DisplayString (SIZE(0..16))
                  MAX-ACCESS read-write
                  STATUS current
                  DESCRIPTION "Loopback-Addr."
                  ::= {  setSnmpIptrapsEntry 3 }

setSnmpAdminist OBJECT-TYPE
                SYNTAX DisplayString (SIZE(0..255))
                MAX-ACCESS read-write
                STATUS current
                DESCRIPTION "Administrator"
                ::= {  setSnmp 3 }

setSnmpLocation OBJECT-TYPE
                SYNTAX DisplayString (SIZE(0..255))
                MAX-ACCESS read-write
                STATUS current
                DESCRIPTION "Location"
                ::= {  setSnmp 4 }

setSnmpRegister OBJECT-TYPE
                SYNTAX DisplayString
                MAX-ACCESS read-write
                STATUS current
                DESCRIPTION "Register-Monitor"
                ::= {  setSnmp 5 }

setSnmpDeletemo OBJECT-TYPE
                SYNTAX DisplayString
                MAX-ACCESS read-write
                STATUS current
                DESCRIPTION "Delete-Monitor"
                ::= {  setSnmp 6 }

setSnmpMonitortTable OBJECT-TYPE
                     SYNTAX SEQUENCE OF SetSnmpMonitortEntry
                     MAX-ACCESS not-accessible
                     STATUS current
                     DESCRIPTION "Monitor-Table"
                     ::= {  setSnmp 7 }

setSnmpMonitortEntry OBJECT-TYPE
                     SYNTAX SetSnmpMonitortEntry
                     MAX-ACCESS not-accessible
                     STATUS current
                     DESCRIPTION "entry in table"
                     INDEX { setSnmpMonitortIpa, setSnmpMonitortPor }
                     ::= {  setSnmpMonitortTable 1 }

SetSnmpMonitortEntry ::= SEQUENCE {
                     setSnmpMonitortIpa IpAddress,
                     setSnmpMonitortPor INTEGER,
                     setSnmpMonitortMac DisplayString,
                     setSnmpMonitortVla INTEGER,
                     setSnmpMonitortTim INTEGER,
                     setSnmpMonitortPee DisplayString,
                     setSnmpMonitortLoo IpAddress,
                     setSnmpMonitortLan DisplayString
                    }

setSnmpMonitortIpa OBJECT-TYPE
                   SYNTAX IpAddress
                   MAX-ACCESS read-only
                   STATUS current
                   DESCRIPTION "IP-Address"
                   ::= {  setSnmpMonitortEntry 1 }

setSnmpMonitortPor OBJECT-TYPE
                   SYNTAX INTEGER (0..65535)
                   MAX-ACCESS read-only
                   STATUS current
                   DESCRIPTION "Port"
                   ::= {  setSnmpMonitortEntry 2 }

setSnmpMonitortMac OBJECT-TYPE
                   SYNTAX DisplayString (SIZE(0..12))
                   MAX-ACCESS read-only
                   STATUS current
                   DESCRIPTION "MAC-Address"
                   ::= {  setSnmpMonitortEntry 4 }

setSnmpMonitortVla OBJECT-TYPE
                   SYNTAX INTEGER (0..65535)
                   MAX-ACCESS read-only
                   STATUS current
                   DESCRIPTION "VLAN-ID"
                   ::= {  setSnmpMonitortEntry 7 }

setSnmpMonitortTim OBJECT-TYPE
                   SYNTAX INTEGER (0..65535)
                   MAX-ACCESS read-only
                   STATUS current
                   DESCRIPTION "Timeout"
                   ::= {  setSnmpMonitortEntry 3 }

setSnmpMonitortPee OBJECT-TYPE
                   SYNTAX DisplayString (SIZE(0..16))
                   MAX-ACCESS read-only
                   STATUS current
                   DESCRIPTION "Peer"
                   ::= {  setSnmpMonitortEntry 5 }

setSnmpMonitortLoo OBJECT-TYPE
                   SYNTAX IpAddress
                   MAX-ACCESS read-only
                   STATUS current
                   DESCRIPTION "Loopback-Addr."
                   ::= {  setSnmpMonitortEntry 6 }

setSnmpMonitortLan OBJECT-TYPE
                   SYNTAX DisplayString (SIZE(0..255))
                   MAX-ACCESS read-only
                   STATUS current
                   DESCRIPTION "LAN-Ifc"
                   ::= {  setSnmpMonitortEntry 8 }

setSnmpPassword OBJECT-TYPE
                SYNTAX INTEGER {
                  no(0),
                  yes(1)
                }
                MAX-ACCESS read-write
                STATUS current
                DESCRIPTION "Password-Required-for-SNMP-Read-Access"
                ::= {  setSnmp 10 }

setSnmpComment1 OBJECT-TYPE
                SYNTAX DisplayString (SIZE(0..255))
                MAX-ACCESS read-write
                STATUS current
                DESCRIPTION "Comment-1"
                ::= {  setSnmp 11 }

setSnmpComment2 OBJECT-TYPE
                SYNTAX DisplayString (SIZE(0..255))
                MAX-ACCESS read-write
                STATUS current
                DESCRIPTION "Comment-2"
                ::= {  setSnmp 12 }

setSnmpComment3 OBJECT-TYPE
                SYNTAX DisplayString (SIZE(0..255))
                MAX-ACCESS read-write
                STATUS current
                DESCRIPTION "Comment-3"
                ::= {  setSnmp 13 }

setSnmpComment4 OBJECT-TYPE
                SYNTAX DisplayString (SIZE(0..255))
                MAX-ACCESS read-write
                STATUS current
                DESCRIPTION "Comment-4"
                ::= {  setSnmp 14 }

setDhcp OBJECT IDENTIFIER ::= { set 10}
setDhcpNetTable OBJECT-TYPE
                SYNTAX SEQUENCE OF SetDhcpNetEntry
                MAX-ACCESS not-accessible
                STATUS current
                DESCRIPTION "Network-list"
                ::= {  setDhcp 20 }

setDhcpNetEntry OBJECT-TYPE
                SYNTAX SetDhcpNetEntry
                MAX-ACCESS not-accessible
                STATUS current
                DESCRIPTION "entry in table"
                INDEX { setDhcpNetNetworknam }
                ::= {  setDhcpNetTable 1 }

SetDhcpNetEntry ::= SEQUENCE {
                setDhcpNetNetworknam DisplayString,
                setDhcpNetStartaddre IpAddress,
                setDhcpNetEndaddress IpAddress,
                setDhcpNetNetmask IpAddress,
                setDhcpNetBroadcasta IpAddress,
                setDhcpNetGatewayadd IpAddress,
                setDhcpNetDnsdefault IpAddress,
                setDhcpNetDnsbackup IpAddress,
                setDhcpNetNbnsdefaul IpAddress,
                setDhcpNetNbnsbackup IpAddress,
                setDhcpNetOperating INTEGER,
                setDhcpNetBroadcastb INTEGER,
                setDhcpNetMasterserv IpAddress,
                setDhcpNetCache INTEGER,
                setDhcpNetAdaption INTEGER
               }

setDhcpNetNetworknam OBJECT-TYPE
                     SYNTAX DisplayString (SIZE(0..16))
                     MAX-ACCESS read-write
                     STATUS current
                     DESCRIPTION "Network-name"
                     ::= {  setDhcpNetEntry 1 }

setDhcpNetStartaddre OBJECT-TYPE
                     SYNTAX IpAddress
                     MAX-ACCESS read-write
                     STATUS current
                     DESCRIPTION "Start-Address-Pool"
                     ::= {  setDhcpNetEntry 2 }

setDhcpNetEndaddress OBJECT-TYPE
                     SYNTAX IpAddress
                     MAX-ACCESS read-write
                     STATUS current
                     DESCRIPTION "End-Address-Pool"
                     ::= {  setDhcpNetEntry 3 }

setDhcpNetNetmask OBJECT-TYPE
                     SYNTAX IpAddress
                     MAX-ACCESS read-write
                     STATUS current
                     DESCRIPTION "Netmask"
                     ::= {  setDhcpNetEntry 4 }

setDhcpNetBroadcasta OBJECT-TYPE
                     SYNTAX IpAddress
                     MAX-ACCESS read-write
                     STATUS current
                     DESCRIPTION "Broadcast-Address"
                     ::= {  setDhcpNetEntry 5 }

setDhcpNetGatewayadd OBJECT-TYPE
                     SYNTAX IpAddress
                     MAX-ACCESS read-write
                     STATUS current
                     DESCRIPTION "Gateway-Address"
                     ::= {  setDhcpNetEntry 6 }

setDhcpNetDnsdefault OBJECT-TYPE
                     SYNTAX IpAddress
                     MAX-ACCESS read-write
                     STATUS current
                     DESCRIPTION "DNS-Default"
                     ::= {  setDhcpNetEntry 7 }

setDhcpNetDnsbackup OBJECT-TYPE
                     SYNTAX IpAddress
                     MAX-ACCESS read-write
                     STATUS current
                     DESCRIPTION "DNS-Backup"
                     ::= {  setDhcpNetEntry 8 }

setDhcpNetNbnsdefaul OBJECT-TYPE
                     SYNTAX IpAddress
                     MAX-ACCESS read-write
                     STATUS current
                     DESCRIPTION "NBNS-Default"
                     ::= {  setDhcpNetEntry 9 }

setDhcpNetNbnsbackup OBJECT-TYPE
                     SYNTAX IpAddress
                     MAX-ACCESS read-write
                     STATUS current
                     DESCRIPTION "NBNS-Backup"
                     ::= {  setDhcpNetEntry 10 }

setDhcpNetOperating OBJECT-TYPE
                     SYNTAX INTEGER{
                       no(0),
                       yes(1),
                       auto(2),
                       relay(16),
                       client(4)
                     }
                     MAX-ACCESS read-write
                     STATUS current
                     DESCRIPTION "Operating"
                     ::= {  setDhcpNetEntry 11 }

setDhcpNetBroadcastb OBJECT-TYPE
                     SYNTAX INTEGER{
                       no(0),
                       yes(1)
                     }
                     MAX-ACCESS read-write
                     STATUS current
                     DESCRIPTION "Broadcast-Bit"
                     ::= {  setDhcpNetEntry 12 }

setDhcpNetMasterserv OBJECT-TYPE
                     SYNTAX IpAddress
                     MAX-ACCESS read-write
                     STATUS current
                     DESCRIPTION "Master-Server"
                     ::= {  setDhcpNetEntry 13 }

setDhcpNetCache OBJECT-TYPE
                     SYNTAX INTEGER{
                       no(0),
                       yes(1)
                     }
                     MAX-ACCESS read-write
                     STATUS current
                     DESCRIPTION "Cache"
                     ::= {  setDhcpNetEntry 14 }

setDhcpNetAdaption OBJECT-TYPE
                     SYNTAX INTEGER{
                       no(0),
                       yes(1)
                     }
                     MAX-ACCESS read-write
                     STATUS current
                     DESCRIPTION "Adaption"
                     ::= {  setDhcpNetEntry 15 }

setDhcpPorTable OBJECT-TYPE
                SYNTAX SEQUENCE OF SetDhcpPorEntry
                MAX-ACCESS not-accessible
                STATUS current
                DESCRIPTION "Ports"
                ::= {  setDhcp 18 }

setDhcpPorEntry OBJECT-TYPE
                SYNTAX SetDhcpPorEntry
                MAX-ACCESS not-accessible
                STATUS current
                DESCRIPTION "entry in table"
                INDEX { setDhcpPorPor }
                ::= {  setDhcpPorTable 1 }

SetDhcpPorEntry ::= SEQUENCE {
                setDhcpPorPor DisplayString,
                setDhcpPorEna INTEGER
               }

setDhcpPorPor OBJECT-TYPE
              SYNTAX DisplayString (SIZE(0..9))
              MAX-ACCESS read-only
              STATUS current
              DESCRIPTION "Port"
              ::= {  setDhcpPorEntry 2 }

setDhcpPorEna OBJECT-TYPE
              SYNTAX INTEGER{
                no(0),
                yes(1)
              }
              MAX-ACCESS read-write
              STATUS current
              DESCRIPTION "Enable-DHCP"
              ::= {  setDhcpPorEntry 3 }

setDhcpMax OBJECT-TYPE
           SYNTAX INTEGER
           MAX-ACCESS read-write
           STATUS current
           DESCRIPTION "Max.-Lease-Time-Minutes"
           ::= {  setDhcp 6 }

setDhcpDef OBJECT-TYPE
           SYNTAX INTEGER
           MAX-ACCESS read-write
           STATUS current
           DESCRIPTION "Default-Lease-Time-Minutes"
           ::= {  setDhcp 7 }

setDhcpDhcTable OBJECT-TYPE
                SYNTAX SEQUENCE OF SetDhcpDhcEntry
                MAX-ACCESS not-accessible
                STATUS current
                DESCRIPTION "DHCP-Table"
                ::= {  setDhcp 8 }

setDhcpDhcEntry OBJECT-TYPE
                SYNTAX SetDhcpDhcEntry
                MAX-ACCESS not-accessible
                STATUS current
                DESCRIPTION "entry in table"
                INDEX { setDhcpDhcIpa, setDhcpDhcNet }
                ::= {  setDhcpDhcTable 1 }

SetDhcpDhcEntry ::= SEQUENCE {
                setDhcpDhcIpa IpAddress,
                setDhcpDhcMac DisplayString,
                setDhcpDhcTim INTEGER,
                setDhcpDhcHos DisplayString,
                setDhcpDhcTyp BITS,
                setDhcpDhcLan INTEGER,
                setDhcpDhcVla INTEGER,
                setDhcpDhcNet DisplayString
               }

setDhcpDhcIpa OBJECT-TYPE
              SYNTAX IpAddress
              MAX-ACCESS read-only
              STATUS current
              DESCRIPTION "IP-Address"
              ::= {  setDhcpDhcEntry 1 }

setDhcpDhcMac OBJECT-TYPE
              SYNTAX DisplayString (SIZE(0..12))
              MAX-ACCESS read-only
              STATUS current
              DESCRIPTION "MAC-Address"
              ::= {  setDhcpDhcEntry 2 }

setDhcpDhcTim OBJECT-TYPE
              SYNTAX INTEGER (0..2147483647)
              MAX-ACCESS read-only
              STATUS current
              DESCRIPTION "Timeout"
              ::= {  setDhcpDhcEntry 3 }

setDhcpDhcHos OBJECT-TYPE
              SYNTAX DisplayString (SIZE(0..64))
              MAX-ACCESS read-only
              STATUS current
              DESCRIPTION "Hostname"
              ::= {  setDhcpDhcEntry 4 }

setDhcpDhcTyp OBJECT-TYPE
              SYNTAX BITS{
                new(1),
                new(2),
                dyn(16),
                unkn(4),
                stat(8),
                bootp(32),
                relay(2048)
              }
              MAX-ACCESS read-only
              STATUS current
              DESCRIPTION "Type"
              ::= {  setDhcpDhcEntry 5 }

setDhcpDhcLan OBJECT-TYPE
              SYNTAX INTEGER{
                lan-1(0),
                wlan-1(1),
                p2p-1-1(2),
                p2p-1-2(3),
                p2p-1-3(4),
                p2p-1-4(5),
                p2p-1-5(6),
                p2p-1-6(7),
                wlan-1-2(8),
                wlan-1-3(9),
                wlan-1-4(10),
                wlan-1-5(11),
                wlan-1-6(12),
                wlan-1-7(13),
                wlan-1-8(14),
                brg-1(15),
                brg-2(16),
                brg-3(17),
                brg-4(18),
                brg-5(19),
                brg-6(20),
                brg-7(21),
                brg-8(22),
                any(255)
              }
              MAX-ACCESS read-only
              STATUS current
              DESCRIPTION "LAN-Ifc"
              ::= {  setDhcpDhcEntry 6 }

setDhcpDhcVla OBJECT-TYPE
              SYNTAX INTEGER (0..65535)
              MAX-ACCESS read-only
              STATUS current
              DESCRIPTION "VLAN-ID"
              ::= {  setDhcpDhcEntry 8 }

setDhcpDhcNet OBJECT-TYPE
              SYNTAX DisplayString (SIZE(0..17))
              MAX-ACCESS read-only
              STATUS current
              DESCRIPTION "Network-name"
              ::= {  setDhcpDhcEntry 9 }

setDhcpHosTable OBJECT-TYPE
                SYNTAX SEQUENCE OF SetDhcpHosEntry
                MAX-ACCESS not-accessible
                STATUS current
                DESCRIPTION "Hosts"
                ::= {  setDhcp 9 }

setDhcpHosEntry OBJECT-TYPE
                SYNTAX SetDhcpHosEntry
                MAX-ACCESS not-accessible
                STATUS current
                DESCRIPTION "entry in table"
                INDEX { setDhcpHosMac }
                ::= {  setDhcpHosTable 1 }

SetDhcpHosEntry ::= SEQUENCE {
                setDhcpHosMac DisplayString,
                setDhcpHosIpa IpAddress,
                setDhcpHosHos DisplayString,
                setDhcpHosIma DisplayString
               }

setDhcpHosMac OBJECT-TYPE
              SYNTAX DisplayString (SIZE(0..12))
              MAX-ACCESS read-write
              STATUS current
              DESCRIPTION "MAC-Address"
              ::= {  setDhcpHosEntry 1 }

setDhcpHosIpa OBJECT-TYPE
              SYNTAX IpAddress
              MAX-ACCESS read-write
              STATUS current
              DESCRIPTION "IP-Address"
              ::= {  setDhcpHosEntry 2 }

setDhcpHosHos OBJECT-TYPE
              SYNTAX DisplayString (SIZE(0..30))
              MAX-ACCESS read-write
              STATUS current
              DESCRIPTION "Hostname"
              ::= {  setDhcpHosEntry 3 }

setDhcpHosIma OBJECT-TYPE
              SYNTAX DisplayString (SIZE(0..16))
              MAX-ACCESS read-write
              STATUS current
              DESCRIPTION "Image-alias"
              ::= {  setDhcpHosEntry 4 }

setDhcpAliTable OBJECT-TYPE
                SYNTAX SEQUENCE OF SetDhcpAliEntry
                MAX-ACCESS not-accessible
                STATUS current
                DESCRIPTION "Alias-List"
                ::= {  setDhcp 10 }

setDhcpAliEntry OBJECT-TYPE
                SYNTAX SetDhcpAliEntry
                MAX-ACCESS not-accessible
                STATUS current
                DESCRIPTION "entry in table"
                INDEX { setDhcpAliImagea }
                ::= {  setDhcpAliTable 1 }

SetDhcpAliEntry ::= SEQUENCE {
                setDhcpAliImagea DisplayString,
                setDhcpAliImages IpAddress,
                setDhcpAliImagef DisplayString
               }

setDhcpAliImagea OBJECT-TYPE
                 SYNTAX DisplayString (SIZE(0..16))
                 MAX-ACCESS read-write
                 STATUS current
                 DESCRIPTION "Image-alias"
                 ::= {  setDhcpAliEntry 1 }

setDhcpAliImages OBJECT-TYPE
                 SYNTAX IpAddress
                 MAX-ACCESS read-write
                 STATUS current
                 DESCRIPTION "Image-Server"
                 ::= {  setDhcpAliEntry 3 }

setDhcpAliImagef OBJECT-TYPE
                 SYNTAX DisplayString (SIZE(0..60))
                 MAX-ACCESS read-write
                 STATUS current
                 DESCRIPTION "Image-file"
                 ::= {  setDhcpAliEntry 2 }

setDhcpAddTable OBJECT-TYPE
                SYNTAX SEQUENCE OF SetDhcpAddEntry
                MAX-ACCESS not-accessible
                STATUS current
                DESCRIPTION "Additional-Options"
                ::= {  setDhcp 21 }

setDhcpAddEntry OBJECT-TYPE
                SYNTAX SetDhcpAddEntry
                MAX-ACCESS not-accessible
                STATUS current
                DESCRIPTION "entry in table"
                INDEX { setDhcpAddOptionn, setDhcpAddNetwork }
                ::= {  setDhcpAddTable 1 }

SetDhcpAddEntry ::= SEQUENCE {
                setDhcpAddOptionn INTEGER,
                setDhcpAddNetwork DisplayString,
                setDhcpAddOptionv DisplayString
               }

setDhcpAddOptionn OBJECT-TYPE
                  SYNTAX INTEGER (0..255)
                  MAX-ACCESS read-write
                  STATUS current
                  DESCRIPTION "Option-Number"
                  ::= {  setDhcpAddEntry 1 }

setDhcpAddNetwork OBJECT-TYPE
                  SYNTAX DisplayString (SIZE(0..16))
                  MAX-ACCESS read-write
                  STATUS current
                  DESCRIPTION "Network-name"
                  ::= {  setDhcpAddEntry 2 }

setDhcpAddOptionv OBJECT-TYPE
                  SYNTAX DisplayString (SIZE(0..128))
                  MAX-ACCESS read-write
                  STATUS current
                  DESCRIPTION "Option-Value"
                  ::= {  setDhcpAddEntry 3 }

setDhcpUse OBJECT-TYPE
           SYNTAX DisplayString (SIZE(0..63))
           MAX-ACCESS read-write
           STATUS current
           DESCRIPTION "User-Class-Identifer"
           ::= {  setDhcp 19 }

setDns OBJECT IDENTIFIER ::= { set 17}
setDnsOper OBJECT-TYPE
           SYNTAX INTEGER {
             no(0),
             yes(1)
           }
           MAX-ACCESS read-write
           STATUS current
           DESCRIPTION "Operating"
           ::= {  setDns 1 }

setDnsDoma OBJECT-TYPE
           SYNTAX DisplayString (SIZE(0..64))
           MAX-ACCESS read-write
           STATUS current
           DESCRIPTION "Domain"
           ::= {  setDns 2 }

setDnsSubdTable OBJECT-TYPE
                SYNTAX SEQUENCE OF SetDnsSubdEntry
                MAX-ACCESS not-accessible
                STATUS current
                DESCRIPTION "Sub-Domains"
                ::= {  setDns 13 }

setDnsSubdEntry OBJECT-TYPE
                SYNTAX SetDnsSubdEntry
                MAX-ACCESS not-accessible
                STATUS current
                DESCRIPTION "entry in table"
                INDEX { setDnsSubdNet }
                ::= {  setDnsSubdTable 1 }

SetDnsSubdEntry ::= SEQUENCE {
                setDnsSubdNet DisplayString,
                setDnsSubdSub DisplayString
               }

setDnsSubdNet OBJECT-TYPE
              SYNTAX DisplayString (SIZE(0..16))
              MAX-ACCESS read-write
              STATUS current
              DESCRIPTION "Network-name"
              ::= {  setDnsSubdEntry 1 }

setDnsSubdSub OBJECT-TYPE
              SYNTAX DisplayString (SIZE(0..64))
              MAX-ACCESS read-write
              STATUS current
              DESCRIPTION "Sub-Domain"
              ::= {  setDnsSubdEntry 2 }

setDnsReso OBJECT-TYPE
           SYNTAX INTEGER {
             no(0),
             yes(1)
           }
           MAX-ACCESS read-write
           STATUS current
           DESCRIPTION "Resolve-Domain"
           ::= {  setDns 12 }

setDnsDhcp OBJECT-TYPE
           SYNTAX INTEGER {
             no(0),
             yes(1)
           }
           MAX-ACCESS read-write
           STATUS current
           DESCRIPTION "DHCP-Usage"
           ::= {  setDns 3 }

setDnsNetb OBJECT-TYPE
           SYNTAX INTEGER {
             no(0),
             yes(1)
           }
           MAX-ACCESS read-write
           STATUS current
           DESCRIPTION "NetBIOS-Usage"
           ::= {  setDns 4 }

setDnsDnslTable OBJECT-TYPE
                SYNTAX SEQUENCE OF SetDnsDnslEntry
                MAX-ACCESS not-accessible
                STATUS current
                DESCRIPTION "DNS-List"
                ::= {  setDns 5 }

setDnsDnslEntry OBJECT-TYPE
                SYNTAX SetDnsDnslEntry
                MAX-ACCESS not-accessible
                STATUS current
                DESCRIPTION "entry in table"
                INDEX { setDnsDnslHos }
                ::= {  setDnsDnslTable 1 }

SetDnsDnslEntry ::= SEQUENCE {
                setDnsDnslHos DisplayString,
                setDnsDnslIpa IpAddress
               }

setDnsDnslHos OBJECT-TYPE
              SYNTAX DisplayString (SIZE(0..64))
              MAX-ACCESS read-write
              STATUS current
              DESCRIPTION "Host-name"
              ::= {  setDnsDnslEntry 1 }

setDnsDnslIpa OBJECT-TYPE
              SYNTAX IpAddress
              MAX-ACCESS read-write
              STATUS current
              DESCRIPTION "IP-Address"
              ::= {  setDnsDnslEntry 2 }

setDnsFiltTable OBJECT-TYPE
                SYNTAX SEQUENCE OF SetDnsFiltEntry
                MAX-ACCESS not-accessible
                STATUS current
                DESCRIPTION "Filter-List"
                ::= {  setDns 6 }

setDnsFiltEntry OBJECT-TYPE
                SYNTAX SetDnsFiltEntry
                MAX-ACCESS not-accessible
                STATUS current
                DESCRIPTION "entry in table"
                INDEX { setDnsFiltIdx }
                ::= {  setDnsFiltTable 1 }

SetDnsFiltEntry ::= SEQUENCE {
                setDnsFiltIdx DisplayString,
                setDnsFiltDom DisplayString,
                setDnsFiltIpa IpAddress,
                setDnsFiltNet IpAddress
               }

setDnsFiltIdx OBJECT-TYPE
              SYNTAX DisplayString (SIZE(0..4))
              MAX-ACCESS read-write
              STATUS current
              DESCRIPTION "Idx."
              ::= {  setDnsFiltEntry 1 }

setDnsFiltDom OBJECT-TYPE
              SYNTAX DisplayString (SIZE(0..64))
              MAX-ACCESS read-write
              STATUS current
              DESCRIPTION "Domain"
              ::= {  setDnsFiltEntry 2 }

setDnsFiltIpa OBJECT-TYPE
              SYNTAX IpAddress
              MAX-ACCESS read-write
              STATUS current
              DESCRIPTION "IP-Address"
              ::= {  setDnsFiltEntry 3 }

setDnsFiltNet OBJECT-TYPE
              SYNTAX IpAddress
              MAX-ACCESS read-write
              STATUS current
              DESCRIPTION "Netmask"
              ::= {  setDnsFiltEntry 4 }

setDnsDyndTable OBJECT-TYPE
                SYNTAX SEQUENCE OF SetDnsDyndEntry
                MAX-ACCESS not-accessible
                STATUS current
                DESCRIPTION "Dyn.-DNS-List"
                ::= {  setDns 8 }

setDnsDyndEntry OBJECT-TYPE
                SYNTAX SetDnsDyndEntry
                MAX-ACCESS not-accessible
                STATUS current
                DESCRIPTION "entry in table"
                INDEX { setDnsDyndHos }
                ::= {  setDnsDyndTable 1 }

SetDnsDyndEntry ::= SEQUENCE {
                setDnsDyndHos DisplayString,
                setDnsDyndIpa IpAddress,
                setDnsDyndTim INTEGER
               }

setDnsDyndHos OBJECT-TYPE
              SYNTAX DisplayString (SIZE(0..64))
              MAX-ACCESS read-only
              STATUS current
              DESCRIPTION "Host-name"
              ::= {  setDnsDyndEntry 1 }

setDnsDyndIpa OBJECT-TYPE
              SYNTAX IpAddress
              MAX-ACCESS read-only
              STATUS current
              DESCRIPTION "IP-Address"
              ::= {  setDnsDyndEntry 2 }

setDnsDyndTim OBJECT-TYPE
              SYNTAX INTEGER (0..2147483647)
              MAX-ACCESS read-only
              STATUS current
              DESCRIPTION "Timeout"
              ::= {  setDnsDyndEntry 3 }

setDnsDnsdTable OBJECT-TYPE
                SYNTAX SEQUENCE OF SetDnsDnsdEntry
                MAX-ACCESS not-accessible
                STATUS current
                DESCRIPTION "DNS-Destinations"
                ::= {  setDns 9 }

setDnsDnsdEntry OBJECT-TYPE
                SYNTAX SetDnsDnsdEntry
                MAX-ACCESS not-accessible
                STATUS current
                DESCRIPTION "entry in table"
                INDEX { setDnsDnsdDom }
                ::= {  setDnsDnsdTable 1 }

SetDnsDnsdEntry ::= SEQUENCE {
                setDnsDnsdDom DisplayString,
                setDnsDnsdDes DisplayString
               }

setDnsDnsdDom OBJECT-TYPE
              SYNTAX DisplayString (SIZE(0..64))
              MAX-ACCESS read-write
              STATUS current
              DESCRIPTION "Domain-name"
              ::= {  setDnsDnsdEntry 1 }

setDnsDnsdDes OBJECT-TYPE
              SYNTAX DisplayString (SIZE(0..31))
              MAX-ACCESS read-write
              STATUS current
              DESCRIPTION "Destination"
              ::= {  setDnsDnsdEntry 2 }

setDnsLeas OBJECT-TYPE
           SYNTAX INTEGER
           MAX-ACCESS read-write
           STATUS current
           DESCRIPTION "Leasetime"
           ::= {  setDns 7 }

setDnsServTable OBJECT-TYPE
                SYNTAX SEQUENCE OF SetDnsServEntry
                MAX-ACCESS not-accessible
                STATUS current
                DESCRIPTION "Service-Location-List"
                ::= {  setDns 10 }

setDnsServEntry OBJECT-TYPE
                SYNTAX SetDnsServEntry
                MAX-ACCESS not-accessible
                STATUS current
                DESCRIPTION "entry in table"
                INDEX { setDnsServSer }
                ::= {  setDnsServTable 1 }

SetDnsServEntry ::= SEQUENCE {
                setDnsServSer DisplayString,
                setDnsServHos DisplayString,
                setDnsServPor INTEGER
               }

setDnsServSer OBJECT-TYPE
              SYNTAX DisplayString (SIZE(0..64))
              MAX-ACCESS read-write
              STATUS current
              DESCRIPTION "Service-Name"
              ::= {  setDnsServEntry 1 }

setDnsServHos OBJECT-TYPE
              SYNTAX DisplayString (SIZE(0..64))
              MAX-ACCESS read-write
              STATUS current
              DESCRIPTION "Host-name"
              ::= {  setDnsServEntry 2 }

setDnsServPor OBJECT-TYPE
              SYNTAX INTEGER (0..65535)
              MAX-ACCESS read-write
              STATUS current
              DESCRIPTION "Port"
              ::= {  setDnsServEntry 3 }

setDnsDynaTable OBJECT-TYPE
                SYNTAX SEQUENCE OF SetDnsDynaEntry
                MAX-ACCESS not-accessible
                STATUS current
                DESCRIPTION "Dynamic-SRV-List"
                ::= {  setDns 11 }

setDnsDynaEntry OBJECT-TYPE
                SYNTAX SetDnsDynaEntry
                MAX-ACCESS not-accessible
                STATUS current
                DESCRIPTION "entry in table"
                INDEX { setDnsDynaSer }
                ::= {  setDnsDynaTable 1 }

SetDnsDynaEntry ::= SEQUENCE {
                setDnsDynaSer DisplayString,
                setDnsDynaHos DisplayString,
                setDnsDynaPor INTEGER
               }

setDnsDynaSer OBJECT-TYPE
              SYNTAX DisplayString (SIZE(0..64))
              MAX-ACCESS read-only
              STATUS current
              DESCRIPTION "Service-Name"
              ::= {  setDnsDynaEntry 1 }

setDnsDynaHos OBJECT-TYPE
              SYNTAX DisplayString (SIZE(0..64))
              MAX-ACCESS read-only
              STATUS current
              DESCRIPTION "Host-name"
              ::= {  setDnsDynaEntry 2 }

setDnsDynaPor OBJECT-TYPE
              SYNTAX INTEGER (0..65535)
              MAX-ACCESS read-only
              STATUS current
              DESCRIPTION "Port"
              ::= {  setDnsDynaEntry 3 }

setLanbr OBJECT IDENTIFIER ::= { set 20}
setLanbrIso OBJECT-TYPE
            SYNTAX INTEGER {
              no(0),
              yes(1)
            }
            MAX-ACCESS read-write
            STATUS current
            DESCRIPTION "Isolated-Mode"
            ::= {  setLanbr 8 }

setLanbrPorTable OBJECT-TYPE
                 SYNTAX SEQUENCE OF SetLanbrPorEntry
                 MAX-ACCESS not-accessible
                 STATUS current
                 DESCRIPTION "Port-Data"
                 ::= {  setLanbr 11 }

setLanbrPorEntry OBJECT-TYPE
                 SYNTAX SetLanbrPorEntry
                 MAX-ACCESS not-accessible
                 STATUS current
                 DESCRIPTION "entry in table"
                 INDEX { setLanbrPorPor }
                 ::= {  setLanbrPorTable 1 }

SetLanbrPorEntry ::= SEQUENCE {
                 setLanbrPorPor DisplayString,
                 setLanbrPorAct INTEGER,
                 setLanbrPorBri INTEGER,
                 setLanbrPorDhc INTEGER,
                 setLanbrPorPoi INTEGER
                }

setLanbrPorPor OBJECT-TYPE
               SYNTAX DisplayString (SIZE(0..9))
               MAX-ACCESS read-only
               STATUS current
               DESCRIPTION "Port"
               ::= {  setLanbrPorEntry 2 }

setLanbrPorAct OBJECT-TYPE
               SYNTAX INTEGER{
                 no(0),
                 yes(1)
               }
               MAX-ACCESS read-write
               STATUS current
               DESCRIPTION "Active"
               ::= {  setLanbrPorEntry 3 }

setLanbrPorBri OBJECT-TYPE
               SYNTAX INTEGER{
                 brg-1(0),
                 brg-2(1),
                 brg-3(2),
                 brg-4(3),
                 brg-5(4),
                 brg-6(5),
                 brg-7(6),
                 brg-8(7),
                 none(255)
               }
               MAX-ACCESS read-write
               STATUS current
               DESCRIPTION "Bridge-Group"
               ::= {  setLanbrPorEntry 5 }

setLanbrPorDhc OBJECT-TYPE
               SYNTAX INTEGER (0..255)
               MAX-ACCESS read-write
               STATUS current
               DESCRIPTION "DHCP-Limit"
               ::= {  setLanbrPorEntry 6 }

setLanbrPorPoi OBJECT-TYPE
               SYNTAX INTEGER{
                 auto(0),
                 force-true(1),
                 force-false(2)
               }
               MAX-ACCESS read-write
               STATUS current
               DESCRIPTION "Point-To-Point-Port"
               ::= {  setLanbrPorEntry 7 }

setLanbrAgi OBJECT-TYPE
            SYNTAX INTEGER
            MAX-ACCESS read-write
            STATUS current
            DESCRIPTION "Aging-Time"
            ::= {  setLanbr 12 }

setLanbrEncTable OBJECT-TYPE
                 SYNTAX SEQUENCE OF SetLanbrEncEntry
                 MAX-ACCESS not-accessible
                 STATUS current
                 DESCRIPTION "Encapsulation-Table"
                 ::= {  setLanbr 4 }

setLanbrEncEntry OBJECT-TYPE
                 SYNTAX SetLanbrEncEntry
                 MAX-ACCESS not-accessible
                 STATUS current
                 DESCRIPTION "entry in table"
                 INDEX { setLanbrEncPro }
                 ::= {  setLanbrEncTable 1 }

SetLanbrEncEntry ::= SEQUENCE {
                 setLanbrEncPro INTEGER,
                 setLanbrEncEnc INTEGER
                }

setLanbrEncPro OBJECT-TYPE
               SYNTAX INTEGER (0..65535)
               MAX-ACCESS read-write
               STATUS current
               DESCRIPTION "Protocol"
               ::= {  setLanbrEncEntry 1 }

setLanbrEncEnc OBJECT-TYPE
               SYNTAX INTEGER{
                 eth-ii(0),
                 snap(1)
               }
               MAX-ACCESS read-write
               STATUS current
               DESCRIPTION "Encapsulation"
               ::= {  setLanbrEncEntry 2 }

setLanbrProTable OBJECT-TYPE
                 SYNTAX SEQUENCE OF SetLanbrProEntry
                 MAX-ACCESS not-accessible
                 STATUS current
                 DESCRIPTION "Protocol-Table"
                 ::= {  setLanbr 10 }

setLanbrProEntry OBJECT-TYPE
                 SYNTAX SetLanbrProEntry
                 MAX-ACCESS not-accessible
                 STATUS current
                 DESCRIPTION "entry in table"
                 INDEX { setLanbrProName }
                 ::= {  setLanbrProTable 1 }

SetLanbrProEntry ::= SEQUENCE {
                 setLanbrProName DisplayString,
                 setLanbrProDhcpsr INTEGER,
                 setLanbrProDestma MacAddress,
                 setLanbrProProtoc DisplayString,
                 setLanbrProIpnetw IpAddress,
                 setLanbrProIpnetm IpAddress,
                 setLanbrProSubpro INTEGER,
                 setLanbrProPort INTEGER,
                 setLanbrProPorten INTEGER,
                 setLanbrProIfclis DisplayString,
                 setLanbrProAction INTEGER,
                 setLanbrProRedire IpAddress
                }

setLanbrProName OBJECT-TYPE
                  SYNTAX DisplayString (SIZE(0..15))
                  MAX-ACCESS read-write
                  STATUS current
                  DESCRIPTION "Name"
                  ::= {  setLanbrProEntry 1 }

setLanbrProDhcpsr OBJECT-TYPE
                  SYNTAX INTEGER{
                    irrelevant(0),
                    no(1),
                    yes(2)
                  }
                  MAX-ACCESS read-write
                  STATUS current
                  DESCRIPTION "DHCP-Src-MAC"
                  ::= {  setLanbrProEntry 12 }

setLanbrProDestma OBJECT-TYPE
                  SYNTAX MacAddress
                  MAX-ACCESS read-write
                  STATUS current
                  DESCRIPTION "Dest-MAC-Addr."
                  ::= {  setLanbrProEntry 9 }

setLanbrProProtoc OBJECT-TYPE
                  SYNTAX DisplayString (SIZE(0..4))
                  MAX-ACCESS read-write
                  STATUS current
                  DESCRIPTION "Protocol"
                  ::= {  setLanbrProEntry 2 }

setLanbrProIpnetw OBJECT-TYPE
                  SYNTAX IpAddress
                  MAX-ACCESS read-write
                  STATUS current
                  DESCRIPTION "IP-Network"
                  ::= {  setLanbrProEntry 10 }

setLanbrProIpnetm OBJECT-TYPE
                  SYNTAX IpAddress
                  MAX-ACCESS read-write
                  STATUS current
                  DESCRIPTION "IP-Netmask"
                  ::= {  setLanbrProEntry 11 }

setLanbrProSubpro OBJECT-TYPE
                  SYNTAX INTEGER (0..65535)
                  MAX-ACCESS read-write
                  STATUS current
                  DESCRIPTION "Sub-Protocol"
                  ::= {  setLanbrProEntry 3 }

setLanbrProPort OBJECT-TYPE
                  SYNTAX INTEGER (0..65535)
                  MAX-ACCESS read-write
                  STATUS current
                  DESCRIPTION "Port"
                  ::= {  setLanbrProEntry 4 }

setLanbrProPorten OBJECT-TYPE
                  SYNTAX INTEGER (0..65535)
                  MAX-ACCESS read-write
                  STATUS current
                  DESCRIPTION "Port-End"
                  ::= {  setLanbrProEntry 5 }

setLanbrProIfclis OBJECT-TYPE
                  SYNTAX DisplayString (SIZE(0..251))
                  MAX-ACCESS read-write
                  STATUS current
                  DESCRIPTION "Ifc-List"
                  ::= {  setLanbrProEntry 6 }

setLanbrProAction OBJECT-TYPE
                  SYNTAX INTEGER{
                    drop(0),
                    pass(1),
                    redirect(2)
                  }
                  MAX-ACCESS read-write
                  STATUS current
                  DESCRIPTION "Action"
                  ::= {  setLanbrProEntry 7 }

setLanbrProRedire OBJECT-TYPE
                  SYNTAX IpAddress
                  MAX-ACCESS read-write
                  STATUS current
                  DESCRIPTION "Redirect-IP-Address"
                  ::= {  setLanbrProEntry 8 }

setLanbrSpa OBJECT IDENTIFIER ::= { setLanbr 20}
setLanbrSpaOpe OBJECT-TYPE
               SYNTAX INTEGER {
                 no(0),
                 yes(1)
               }
               MAX-ACCESS read-write
               STATUS current
               DESCRIPTION "Operating"
               ::= {  setLanbrSpa 1 }

setLanbrSpaPro OBJECT-TYPE
               SYNTAX INTEGER {
                 classic(0),
                 rapid(1)
               }
               MAX-ACCESS read-write
               STATUS current
               DESCRIPTION "Protocol-Version"
               ::= {  setLanbrSpa 12 }

setLanbrSpaPat OBJECT-TYPE
               SYNTAX INTEGER {
                 classic(0),
                 rapid(1)
               }
               MAX-ACCESS read-write
               STATUS current
               DESCRIPTION "Path-Cost-Computation"
               ::= {  setLanbrSpa 14 }

setLanbrSpaBri OBJECT-TYPE
               SYNTAX INTEGER
               MAX-ACCESS read-write
               STATUS current
               DESCRIPTION "Bridge-Priority"
               ::= {  setLanbrSpa 2 }

setLanbrSpaPorTable OBJECT-TYPE
                    SYNTAX SEQUENCE OF SetLanbrSpaPorEntry
                    MAX-ACCESS not-accessible
                    STATUS current
                    DESCRIPTION "Port-Data"
                    ::= {  setLanbrSpa 11 }

setLanbrSpaPorEntry OBJECT-TYPE
                    SYNTAX SetLanbrSpaPorEntry
                    MAX-ACCESS not-accessible
                    STATUS current
                    DESCRIPTION "entry in table"
                    INDEX { setLanbrSpaPorPor }
                    ::= {  setLanbrSpaPorTable 1 }

SetLanbrSpaPorEntry ::= SEQUENCE {
                    setLanbrSpaPorPor DisplayString,
                    setLanbrSpaPorPri INTEGER,
                    setLanbrSpaPorEdg INTEGER,
                    setLanbrSpaPorPat INTEGER
                   }

setLanbrSpaPorPor OBJECT-TYPE
                  SYNTAX DisplayString (SIZE(0..9))
                  MAX-ACCESS read-only
                  STATUS current
                  DESCRIPTION "Port"
                  ::= {  setLanbrSpaPorEntry 2 }

setLanbrSpaPorPri OBJECT-TYPE
                  SYNTAX INTEGER (0..255)
                  MAX-ACCESS read-write
                  STATUS current
                  DESCRIPTION "Priority"
                  ::= {  setLanbrSpaPorEntry 4 }

setLanbrSpaPorEdg OBJECT-TYPE
                  SYNTAX INTEGER{
                    no(0),
                    yes(1)
                  }
                  MAX-ACCESS read-write
                  STATUS current
                  DESCRIPTION "Edge-Port"
                  ::= {  setLanbrSpaPorEntry 6 }

setLanbrSpaPorPat OBJECT-TYPE
                  SYNTAX INTEGER (0..2147483647)
                  MAX-ACCESS read-write
                  STATUS current
                  DESCRIPTION "Path-Cost-Override"
                  ::= {  setLanbrSpaPorEntry 7 }

setLanbrSpaMax OBJECT-TYPE
               SYNTAX INTEGER
               MAX-ACCESS read-write
               STATUS current
               DESCRIPTION "Max-Age"
               ::= {  setLanbrSpa 5 }

setLanbrSpaHel OBJECT-TYPE
               SYNTAX INTEGER
               MAX-ACCESS read-write
               STATUS current
               DESCRIPTION "Hello-Time"
               ::= {  setLanbrSpa 6 }

setLanbrSpaFor OBJECT-TYPE
               SYNTAX INTEGER
               MAX-ACCESS read-write
               STATUS current
               DESCRIPTION "Forward-Delay"
               ::= {  setLanbrSpa 7 }

setLanbrSpaTra OBJECT-TYPE
               SYNTAX INTEGER
               MAX-ACCESS read-write
               STATUS current
               DESCRIPTION "Transmit-Hold-Count"
               ::= {  setLanbrSpa 13 }

setHttp OBJECT IDENTIFIER ::= { set 21}
setHttpDoc OBJECT-TYPE
           SYNTAX DisplayString (SIZE(0..99))
           MAX-ACCESS read-write
           STATUS current
           DESCRIPTION "Document-Root"
           ::= {  setHttp 1 }

setHttpUse OBJECT-TYPE
           SYNTAX INTEGER {
             no(0),
             yes(1)
           }
           MAX-ACCESS read-write
           STATUS current
           DESCRIPTION "Use-CSS"
           ::= {  setHttp 2 }

setHttpFon OBJECT-TYPE
           SYNTAX DisplayString (SIZE(0..39))
           MAX-ACCESS read-write
           STATUS current
           DESCRIPTION "Font-Family"
           ::= {  setHttp 3 }

setHttpPag OBJECT-TYPE
           SYNTAX INTEGER {
             images(0),
             texts(1)
           }
           MAX-ACCESS read-write
           STATUS current
           DESCRIPTION "Page-Headers"
           ::= {  setHttp 5 }

setHttpErr OBJECT-TYPE
           SYNTAX INTEGER {
             standard(0),
             nifty(1)
           }
           MAX-ACCESS read-write
           STATUS current
           DESCRIPTION "Error-Page-Style"
           ::= {  setHttp 6 }

setHttpPor OBJECT-TYPE
           SYNTAX INTEGER
           MAX-ACCESS read-write
           STATUS current
           DESCRIPTION "Port"
           ::= {  setHttp 7 }

setHttpSsl OBJECT-TYPE
           SYNTAX INTEGER
           MAX-ACCESS read-write
           STATUS current
           DESCRIPTION "SSL-Port"
           ::= {  setHttp 8 }

setHttpMax OBJECT-TYPE
           SYNTAX INTEGER
           MAX-ACCESS read-write
           STATUS current
           DESCRIPTION "Max-Tunnel-Connections"
           ::= {  setHttp 9 }

setHttpTun OBJECT-TYPE
           SYNTAX INTEGER
           MAX-ACCESS read-write
           STATUS current
           DESCRIPTION "Tunnel-Idle-Timeout"
           ::= {  setHttp 10 }

setHttpRol OBJECT IDENTIFIER ::= { setHttp 20}
setHttpRolOperating OBJECT-TYPE
                    SYNTAX INTEGER {
                      no(0),
                      yes(1)
                    }
                    MAX-ACCESS read-write
                    STATUS current
                    DESCRIPTION "Operating"
                    ::= {  setHttpRol 1 }

setHttpRolTitle OBJECT-TYPE
                    SYNTAX DisplayString (SIZE(0..50))
                    MAX-ACCESS read-write
                    STATUS current
                    DESCRIPTION "Title"
                    ::= {  setHttpRol 2 }

setHttpRolVariablesTable OBJECT-TYPE
                         SYNTAX SEQUENCE OF SetHttpRolVariablesEntry
                         MAX-ACCESS not-accessible
                         STATUS current
                         DESCRIPTION "Variables"
                         ::= {  setHttpRol 3 }

setHttpRolVariablesEntry OBJECT-TYPE
                         SYNTAX SetHttpRolVariablesEntry
                         MAX-ACCESS not-accessible
                         STATUS current
                         DESCRIPTION "entry in table"
                         INDEX { setHttpRolVariablesInd }
                         ::= {  setHttpRolVariablesTable 1 }

SetHttpRolVariablesEntry ::= SEQUENCE {
                         setHttpRolVariablesInd INTEGER,
                         setHttpRolVariablesIde DisplayString,
                         setHttpRolVariablesTit DisplayString,
                         setHttpRolVariablesTyp INTEGER,
                         setHttpRolVariablesMin INTEGER,
                         setHttpRolVariablesMax INTEGER,
                         setHttpRolVariablesDef DisplayString
                        }

setHttpRolVariablesInd OBJECT-TYPE
                       SYNTAX INTEGER (0..2147483647)
                       MAX-ACCESS read-write
                       STATUS current
                       DESCRIPTION "Index"
                       ::= {  setHttpRolVariablesEntry 1 }

setHttpRolVariablesIde OBJECT-TYPE
                       SYNTAX DisplayString (SIZE(0..16))
                       MAX-ACCESS read-write
                       STATUS current
                       DESCRIPTION "Ident"
                       ::= {  setHttpRolVariablesEntry 2 }

setHttpRolVariablesTit OBJECT-TYPE
                       SYNTAX DisplayString (SIZE(0..40))
                       MAX-ACCESS read-write
                       STATUS current
                       DESCRIPTION "Title"
                       ::= {  setHttpRolVariablesEntry 3 }

setHttpRolVariablesTyp OBJECT-TYPE
                       SYNTAX INTEGER{
                         label(0),
                         integer(1),
                         string(2),
                         password(3),
                         checkmark(4)
                       }
                       MAX-ACCESS read-write
                       STATUS current
                       DESCRIPTION "Type"
                       ::= {  setHttpRolVariablesEntry 4 }

setHttpRolVariablesMin OBJECT-TYPE
                       SYNTAX INTEGER (0..2147483647)
                       MAX-ACCESS read-write
                       STATUS current
                       DESCRIPTION "Min-Value"
                       ::= {  setHttpRolVariablesEntry 5 }

setHttpRolVariablesMax OBJECT-TYPE
                       SYNTAX INTEGER (0..2147483647)
                       MAX-ACCESS read-write
                       STATUS current
                       DESCRIPTION "Max-Value"
                       ::= {  setHttpRolVariablesEntry 6 }

setHttpRolVariablesDef OBJECT-TYPE
                       SYNTAX DisplayString (SIZE(0..30))
                       MAX-ACCESS read-write
                       STATUS current
                       DESCRIPTION "Default-Value"
                       ::= {  setHttpRolVariablesEntry 7 }

setHttpRolRenumberv OBJECT-TYPE
                    SYNTAX DisplayString
                    MAX-ACCESS read-write
                    STATUS current
                    DESCRIPTION "Renumber-Variables"
                    ::= {  setHttpRol 5 }

setHttpRolActionsTable OBJECT-TYPE
                         SYNTAX SEQUENCE OF SetHttpRolActionsEntry
                         MAX-ACCESS not-accessible
                         STATUS current
                         DESCRIPTION "Actions"
                         ::= {  setHttpRol 4 }

setHttpRolActionsEntry OBJECT-TYPE
                         SYNTAX SetHttpRolActionsEntry
                         MAX-ACCESS not-accessible
                         STATUS current
                         DESCRIPTION "entry in table"
                         INDEX { setHttpRolActionsInd }
                         ::= {  setHttpRolActionsTable 1 }

SetHttpRolActionsEntry ::= SEQUENCE {
                         setHttpRolActionsInd INTEGER,
                         setHttpRolActionsAct DisplayString
                        }

setHttpRolActionsInd OBJECT-TYPE
                     SYNTAX INTEGER (0..2147483647)
                     MAX-ACCESS read-write
                     STATUS current
                     DESCRIPTION "Index"
                     ::= {  setHttpRolActionsEntry 1 }

setHttpRolActionsAct OBJECT-TYPE
                     SYNTAX DisplayString (SIZE(0..251))
                     MAX-ACCESS read-write
                     STATUS current
                     DESCRIPTION "Action"
                     ::= {  setHttpRolActionsEntry 2 }

setHttpRolRenumbera OBJECT-TYPE
                    SYNTAX DisplayString
                    MAX-ACCESS read-write
                    STATUS current
                    DESCRIPTION "Renumber-Actions"
                    ::= {  setHttpRol 6 }

setSyslo OBJECT IDENTIFIER ::= { set 22}
setSysloOpe OBJECT-TYPE
            SYNTAX INTEGER {
              no(0),
              yes(1)
            }
            MAX-ACCESS read-write
            STATUS current
            DESCRIPTION "Operating"
            ::= {  setSyslo 1 }

setSysloSerTable OBJECT-TYPE
                 SYNTAX SEQUENCE OF SetSysloSerEntry
                 MAX-ACCESS not-accessible
                 STATUS current
                 DESCRIPTION "Server"
                 ::= {  setSyslo 2 }

setSysloSerEntry OBJECT-TYPE
                 SYNTAX SetSysloSerEntry
                 MAX-ACCESS not-accessible
                 STATUS current
                 DESCRIPTION "entry in table"
                 INDEX { setSysloSerIdx }
                 ::= {  setSysloSerTable 1 }

SetSysloSerEntry ::= SEQUENCE {
                 setSysloSerIdx DisplayString,
                 setSysloSerIpa IpAddress,
                 setSysloSerSou INTEGER,
                 setSysloSerLev INTEGER,
                 setSysloSerLoo DisplayString
                }

setSysloSerIdx OBJECT-TYPE
               SYNTAX DisplayString (SIZE(0..4))
               MAX-ACCESS read-write
               STATUS current
               DESCRIPTION "Idx."
               ::= {  setSysloSerEntry 1 }

setSysloSerIpa OBJECT-TYPE
               SYNTAX IpAddress
               MAX-ACCESS read-write
               STATUS current
               DESCRIPTION "IP-Address"
               ::= {  setSysloSerEntry 2 }

setSysloSerSou OBJECT-TYPE
               SYNTAX INTEGER (0..255)
               MAX-ACCESS read-write
               STATUS current
               DESCRIPTION "Source"
               ::= {  setSysloSerEntry 3 }

setSysloSerLev OBJECT-TYPE
               SYNTAX INTEGER (0..255)
               MAX-ACCESS read-write
               STATUS current
               DESCRIPTION "Level"
               ::= {  setSysloSerEntry 4 }

setSysloSerLoo OBJECT-TYPE
               SYNTAX DisplayString (SIZE(0..16))
               MAX-ACCESS read-write
               STATUS current
               DESCRIPTION "Loopback-Addr."
               ::= {  setSysloSerEntry 6 }

setSysloFacTable OBJECT-TYPE
                 SYNTAX SEQUENCE OF SetSysloFacEntry
                 MAX-ACCESS not-accessible
                 STATUS current
                 DESCRIPTION "Facility-Mapper"
                 ::= {  setSyslo 3 }

setSysloFacEntry OBJECT-TYPE
                 SYNTAX SetSysloFacEntry
                 MAX-ACCESS not-accessible
                 STATUS current
                 DESCRIPTION "entry in table"
                 INDEX { setSysloFacSou }
                 ::= {  setSysloFacTable 1 }

SetSysloFacEntry ::= SEQUENCE {
                 setSysloFacSou INTEGER,
                 setSysloFacFac INTEGER
                }

setSysloFacSou OBJECT-TYPE
               SYNTAX INTEGER{
                 system(1),
                 login(2),
                 systemtime(4),
                 console-login(8),
                 connections(16),
                 accounting(32),
                 administration(64),
                 router(128)
               }
               MAX-ACCESS read-only
               STATUS current
               DESCRIPTION "Source"
               ::= {  setSysloFacEntry 1 }

setSysloFacFac OBJECT-TYPE
               SYNTAX INTEGER{
                 kern(0),
                 user(1),
                 mail(2),
                 daemon(3),
                 auth(4),
                 syslog(5),
                 lpr(6),
                 news(7),
                 uucp(8),
                 cron(9),
                 authpriv(10),
                 local0(16),
                 local1(17),
                 local2(18),
                 local3(19),
                 local4(20),
                 local5(21),
                 local6(22),
                 local7(23)
               }
               MAX-ACCESS read-write
               STATUS current
               DESCRIPTION "Facility"
               ::= {  setSysloFacEntry 2 }

setSysloPor OBJECT-TYPE
            SYNTAX INTEGER
            MAX-ACCESS read-write
            STATUS current
            DESCRIPTION "Port"
            ::= {  setSyslo 4 }

setNetbi OBJECT IDENTIFIER ::= { set 16}
setNetbiOpe OBJECT-TYPE
            SYNTAX INTEGER {
              no(0),
              yes(1)
            }
            MAX-ACCESS read-write
            STATUS current
            DESCRIPTION "Operating"
            ::= {  setNetbi 1 }

setNetbiNetTable OBJECT-TYPE
                 SYNTAX SEQUENCE OF SetNetbiNetEntry
                 MAX-ACCESS not-accessible
                 STATUS current
                 DESCRIPTION "Networks"
                 ::= {  setNetbi 12 }

setNetbiNetEntry OBJECT-TYPE
                 SYNTAX SetNetbiNetEntry
                 MAX-ACCESS not-accessible
                 STATUS current
                 DESCRIPTION "entry in table"
                 INDEX { setNetbiNetNet }
                 ::= {  setNetbiNetTable 1 }

SetNetbiNetEntry ::= SEQUENCE {
                 setNetbiNetNet DisplayString,
                 setNetbiNetOpe INTEGER,
                 setNetbiNetNtd DisplayString
                }

setNetbiNetNet OBJECT-TYPE
               SYNTAX DisplayString (SIZE(0..16))
               MAX-ACCESS read-write
               STATUS current
               DESCRIPTION "Network-name"
               ::= {  setNetbiNetEntry 1 }

setNetbiNetOpe OBJECT-TYPE
               SYNTAX INTEGER{
                 no(0),
                 yes(1)
               }
               MAX-ACCESS read-write
               STATUS current
               DESCRIPTION "Operating"
               ::= {  setNetbiNetEntry 2 }

setNetbiNetNtd OBJECT-TYPE
               SYNTAX DisplayString (SIZE(0..15))
               MAX-ACCESS read-write
               STATUS current
               DESCRIPTION "NT-Domain"
               ::= {  setNetbiNetEntry 3 }

setNetbiSco OBJECT-TYPE
            SYNTAX DisplayString (SIZE(0..64))
            MAX-ACCESS read-write
            STATUS current
            DESCRIPTION "Scope-ID"
            ::= {  setNetbi 2 }

setNetbiPeeTable OBJECT-TYPE
                 SYNTAX SEQUENCE OF SetNetbiPeeEntry
                 MAX-ACCESS not-accessible
                 STATUS current
                 DESCRIPTION "Peers"
                 ::= {  setNetbi 4 }

setNetbiPeeEntry OBJECT-TYPE
                 SYNTAX SetNetbiPeeEntry
                 MAX-ACCESS not-accessible
                 STATUS current
                 DESCRIPTION "entry in table"
                 INDEX { setNetbiPeeNam }
                 ::= {  setNetbiPeeTable 1 }

SetNetbiPeeEntry ::= SEQUENCE {
                 setNetbiPeeNam DisplayString,
                 setNetbiPeeTyp INTEGER
                }

setNetbiPeeNam OBJECT-TYPE
               SYNTAX DisplayString (SIZE(0..16))
               MAX-ACCESS read-write
               STATUS current
               DESCRIPTION "Name"
               ::= {  setNetbiPeeEntry 1 }

setNetbiPeeTyp OBJECT-TYPE
               SYNTAX INTEGER{
                 workstation(1),
                 router(0)
               }
               MAX-ACCESS read-write
               STATUS current
               DESCRIPTION "Type"
               ::= {  setNetbiPeeEntry 3 }

setNetbiGroTable OBJECT-TYPE
                 SYNTAX SEQUENCE OF SetNetbiGroEntry
                 MAX-ACCESS not-accessible
                 STATUS current
                 DESCRIPTION "Group-List"
                 ::= {  setNetbi 5 }

setNetbiGroEntry OBJECT-TYPE
                 SYNTAX SetNetbiGroEntry
                 MAX-ACCESS not-accessible
                 STATUS current
                 DESCRIPTION "entry in table"
                 INDEX { setNetbiGroGro, setNetbiGroTyp, setNetbiGroIpa, setNetbiGroRtg }
                 ::= {  setNetbiGroTable 1 }

SetNetbiGroEntry ::= SEQUENCE {
                 setNetbiGroGro DisplayString,
                 setNetbiGroTyp DisplayString,
                 setNetbiGroIpa IpAddress,
                 setNetbiGroRtg INTEGER,
                 setNetbiGroPee DisplayString,
                 setNetbiGroNet DisplayString,
                 setNetbiGroTim INTEGER,
                 setNetbiGroFla DisplayString
                }

setNetbiGroGro OBJECT-TYPE
               SYNTAX DisplayString (SIZE(0..15))
               MAX-ACCESS read-only
               STATUS current
               DESCRIPTION "Group/Domain"
               ::= {  setNetbiGroEntry 1 }

setNetbiGroTyp OBJECT-TYPE
               SYNTAX DisplayString (SIZE(0..1))
               MAX-ACCESS read-only
               STATUS current
               DESCRIPTION "Type"
               ::= {  setNetbiGroEntry 2 }

setNetbiGroIpa OBJECT-TYPE
               SYNTAX IpAddress
               MAX-ACCESS read-only
               STATUS current
               DESCRIPTION "IP-Address"
               ::= {  setNetbiGroEntry 3 }

setNetbiGroRtg OBJECT-TYPE
               SYNTAX INTEGER (0..65535)
               MAX-ACCESS read-only
               STATUS current
               DESCRIPTION "Rtg-tag"
               ::= {  setNetbiGroEntry 8 }

setNetbiGroPee OBJECT-TYPE
               SYNTAX DisplayString (SIZE(0..16))
               MAX-ACCESS read-only
               STATUS current
               DESCRIPTION "Peer"
               ::= {  setNetbiGroEntry 4 }

setNetbiGroNet OBJECT-TYPE
               SYNTAX DisplayString (SIZE(0..16))
               MAX-ACCESS read-only
               STATUS current
               DESCRIPTION "Network-name"
               ::= {  setNetbiGroEntry 7 }

setNetbiGroTim OBJECT-TYPE
               SYNTAX INTEGER (0..2147483647)
               MAX-ACCESS read-only
               STATUS current
               DESCRIPTION "Timeout"
               ::= {  setNetbiGroEntry 5 }

setNetbiGroFla OBJECT-TYPE
               SYNTAX DisplayString (SIZE(0..2))
               MAX-ACCESS read-only
               STATUS current
               DESCRIPTION "Flags"
               ::= {  setNetbiGroEntry 6 }

setNetbiHosTable OBJECT-TYPE
                 SYNTAX SEQUENCE OF SetNetbiHosEntry
                 MAX-ACCESS not-accessible
                 STATUS current
                 DESCRIPTION "Host-List"
                 ::= {  setNetbi 6 }

setNetbiHosEntry OBJECT-TYPE
                 SYNTAX SetNetbiHosEntry
                 MAX-ACCESS not-accessible
                 STATUS current
                 DESCRIPTION "entry in table"
                 INDEX { setNetbiHosNam, setNetbiHosTyp, setNetbiHosIpa, setNetbiHosRtg }
                 ::= {  setNetbiHosTable 1 }

SetNetbiHosEntry ::= SEQUENCE {
                 setNetbiHosNam DisplayString,
                 setNetbiHosTyp DisplayString,
                 setNetbiHosIpa IpAddress,
                 setNetbiHosRtg INTEGER,
                 setNetbiHosPee DisplayString,
                 setNetbiHosNet DisplayString,
                 setNetbiHosTim INTEGER,
                 setNetbiHosFla DisplayString
                }

setNetbiHosNam OBJECT-TYPE
               SYNTAX DisplayString (SIZE(0..15))
               MAX-ACCESS read-only
               STATUS current
               DESCRIPTION "Name"
               ::= {  setNetbiHosEntry 1 }

setNetbiHosTyp OBJECT-TYPE
               SYNTAX DisplayString (SIZE(0..1))
               MAX-ACCESS read-only
               STATUS current
               DESCRIPTION "Type"
               ::= {  setNetbiHosEntry 2 }

setNetbiHosIpa OBJECT-TYPE
               SYNTAX IpAddress
               MAX-ACCESS read-only
               STATUS current
               DESCRIPTION "IP-Address"
               ::= {  setNetbiHosEntry 3 }

setNetbiHosRtg OBJECT-TYPE
               SYNTAX INTEGER (0..65535)
               MAX-ACCESS read-only
               STATUS current
               DESCRIPTION "Rtg-tag"
               ::= {  setNetbiHosEntry 8 }

setNetbiHosPee OBJECT-TYPE
               SYNTAX DisplayString (SIZE(0..16))
               MAX-ACCESS read-only
               STATUS current
               DESCRIPTION "Peer"
               ::= {  setNetbiHosEntry 4 }

setNetbiHosNet OBJECT-TYPE
               SYNTAX DisplayString (SIZE(0..16))
               MAX-ACCESS read-only
               STATUS current
               DESCRIPTION "Network-name"
               ::= {  setNetbiHosEntry 7 }

setNetbiHosTim OBJECT-TYPE
               SYNTAX INTEGER (0..2147483647)
               MAX-ACCESS read-only
               STATUS current
               DESCRIPTION "Timeout"
               ::= {  setNetbiHosEntry 5 }

setNetbiHosFla OBJECT-TYPE
               SYNTAX DisplayString (SIZE(0..2))
               MAX-ACCESS read-only
               STATUS current
               DESCRIPTION "Flags"
               ::= {  setNetbiHosEntry 6 }

setNetbiSerTable OBJECT-TYPE
                 SYNTAX SEQUENCE OF SetNetbiSerEntry
                 MAX-ACCESS not-accessible
                 STATUS current
                 DESCRIPTION "Server-List"
                 ::= {  setNetbi 7 }

setNetbiSerEntry OBJECT-TYPE
                 SYNTAX SetNetbiSerEntry
                 MAX-ACCESS not-accessible
                 STATUS current
                 DESCRIPTION "entry in table"
                 INDEX { setNetbiSerHos, setNetbiSerGro, setNetbiSerIpa, setNetbiSerRtg }
                 ::= {  setNetbiSerTable 1 }

SetNetbiSerEntry ::= SEQUENCE {
                 setNetbiSerHos DisplayString,
                 setNetbiSerGro DisplayString,
                 setNetbiSerIpa DisplayString,
                 setNetbiSerRtg INTEGER,
                 setNetbiSerOsv DisplayString,
                 setNetbiSerSmb DisplayString,
                 setNetbiSerSer DisplayString,
                 setNetbiSerPee DisplayString,
                 setNetbiSerNet DisplayString,
                 setNetbiSerTim INTEGER,
                 setNetbiSerFla DisplayString
                }

setNetbiSerHos OBJECT-TYPE
               SYNTAX DisplayString (SIZE(0..15))
               MAX-ACCESS read-only
               STATUS current
               DESCRIPTION "Host"
               ::= {  setNetbiSerEntry 1 }

setNetbiSerGro OBJECT-TYPE
               SYNTAX DisplayString (SIZE(0..16))
               MAX-ACCESS read-only
               STATUS current
               DESCRIPTION "Group/Domain"
               ::= {  setNetbiSerEntry 2 }

setNetbiSerIpa OBJECT-TYPE
               SYNTAX DisplayString (SIZE(0..15))
               MAX-ACCESS read-only
               STATUS current
               DESCRIPTION "IP-Address"
               ::= {  setNetbiSerEntry 4 }

setNetbiSerRtg OBJECT-TYPE
               SYNTAX INTEGER (0..65535)
               MAX-ACCESS read-only
               STATUS current
               DESCRIPTION "Rtg-tag"
               ::= {  setNetbiSerEntry 12 }

setNetbiSerOsv OBJECT-TYPE
               SYNTAX DisplayString (SIZE(0..2))
               MAX-ACCESS read-only
               STATUS current
               DESCRIPTION "OS-Ver."
               ::= {  setNetbiSerEntry 5 }

setNetbiSerSmb OBJECT-TYPE
               SYNTAX DisplayString (SIZE(0..2))
               MAX-ACCESS read-only
               STATUS current
               DESCRIPTION "SMB-Ver."
               ::= {  setNetbiSerEntry 6 }

setNetbiSerSer OBJECT-TYPE
               SYNTAX DisplayString (SIZE(0..4))
               MAX-ACCESS read-only
               STATUS current
               DESCRIPTION "Server-Typ"
               ::= {  setNetbiSerEntry 7 }

setNetbiSerPee OBJECT-TYPE
               SYNTAX DisplayString (SIZE(0..16))
               MAX-ACCESS read-only
               STATUS current
               DESCRIPTION "Peer"
               ::= {  setNetbiSerEntry 8 }

setNetbiSerNet OBJECT-TYPE
               SYNTAX DisplayString (SIZE(0..16))
               MAX-ACCESS read-only
               STATUS current
               DESCRIPTION "Network-name"
               ::= {  setNetbiSerEntry 11 }

setNetbiSerTim OBJECT-TYPE
               SYNTAX INTEGER (0..2147483647)
               MAX-ACCESS read-only
               STATUS current
               DESCRIPTION "Timeout"
               ::= {  setNetbiSerEntry 9 }

setNetbiSerFla OBJECT-TYPE
               SYNTAX DisplayString (SIZE(0..2))
               MAX-ACCESS read-only
               STATUS current
               DESCRIPTION "Flags"
               ::= {  setNetbiSerEntry 10 }

setNetbiBroTable OBJECT-TYPE
                 SYNTAX SEQUENCE OF SetNetbiBroEntry
                 MAX-ACCESS not-accessible
                 STATUS current
                 DESCRIPTION "Browser-List"
                 ::= {  setNetbi 13 }

setNetbiBroEntry OBJECT-TYPE
                 SYNTAX SetNetbiBroEntry
                 MAX-ACCESS not-accessible
                 STATUS current
                 DESCRIPTION "entry in table"
                 INDEX { setNetbiBroBro, setNetbiBroGro, setNetbiBroIpa, setNetbiBroRtg }
                 ::= {  setNetbiBroTable 1 }

SetNetbiBroEntry ::= SEQUENCE {
                 setNetbiBroBro DisplayString,
                 setNetbiBroGro DisplayString,
                 setNetbiBroIpa DisplayString,
                 setNetbiBroRtg INTEGER,
                 setNetbiBroOsv DisplayString,
                 setNetbiBroSer DisplayString,
                 setNetbiBroPee DisplayString,
                 setNetbiBroNet DisplayString,
                 setNetbiBroTim INTEGER,
                 setNetbiBroFla DisplayString
                }

setNetbiBroBro OBJECT-TYPE
               SYNTAX DisplayString (SIZE(0..15))
               MAX-ACCESS read-only
               STATUS current
               DESCRIPTION "Browser"
               ::= {  setNetbiBroEntry 1 }

setNetbiBroGro OBJECT-TYPE
               SYNTAX DisplayString (SIZE(0..16))
               MAX-ACCESS read-only
               STATUS current
               DESCRIPTION "Group/Domain"
               ::= {  setNetbiBroEntry 2 }

setNetbiBroIpa OBJECT-TYPE
               SYNTAX DisplayString (SIZE(0..15))
               MAX-ACCESS read-only
               STATUS current
               DESCRIPTION "IP-Address"
               ::= {  setNetbiBroEntry 4 }

setNetbiBroRtg OBJECT-TYPE
               SYNTAX INTEGER (0..65535)
               MAX-ACCESS read-only
               STATUS current
               DESCRIPTION "Rtg-tag"
               ::= {  setNetbiBroEntry 12 }

setNetbiBroOsv OBJECT-TYPE
               SYNTAX DisplayString (SIZE(0..2))
               MAX-ACCESS read-only
               STATUS current
               DESCRIPTION "OS-Ver."
               ::= {  setNetbiBroEntry 5 }

setNetbiBroSer OBJECT-TYPE
               SYNTAX DisplayString (SIZE(0..4))
               MAX-ACCESS read-only
               STATUS current
               DESCRIPTION "Server-Typ"
               ::= {  setNetbiBroEntry 7 }

setNetbiBroPee OBJECT-TYPE
               SYNTAX DisplayString (SIZE(0..16))
               MAX-ACCESS read-only
               STATUS current
               DESCRIPTION "Peer"
               ::= {  setNetbiBroEntry 8 }

setNetbiBroNet OBJECT-TYPE
               SYNTAX DisplayString (SIZE(0..16))
               MAX-ACCESS read-only
               STATUS current
               DESCRIPTION "Network-name"
               ::= {  setNetbiBroEntry 11 }

setNetbiBroTim OBJECT-TYPE
               SYNTAX INTEGER (0..2147483647)
               MAX-ACCESS read-only
               STATUS current
               DESCRIPTION "Timeout"
               ::= {  setNetbiBroEntry 9 }

setNetbiBroFla OBJECT-TYPE
               SYNTAX DisplayString (SIZE(0..2))
               MAX-ACCESS read-only
               STATUS current
               DESCRIPTION "Flags"
               ::= {  setNetbiBroEntry 10 }

setNetbiSup OBJECT-TYPE
            SYNTAX INTEGER {
              no(0),
              yes(1)
            }
            MAX-ACCESS read-write
            STATUS current
            DESCRIPTION "Support-Browsing"
            ::= {  setNetbi 14 }

setNetbiWat OBJECT-TYPE
            SYNTAX INTEGER {
              spoof(1),
              route(0)
            }
            MAX-ACCESS read-write
            STATUS current
            DESCRIPTION "Watchdogs"
            ::= {  setNetbi 8 }

setNetbiUpd OBJECT-TYPE
            SYNTAX INTEGER {
              pback(0),
              trig(1),
              time(2)
            }
            MAX-ACCESS read-write
            STATUS current
            DESCRIPTION "Update"
            ::= {  setNetbi 9 }

setNetbiWan OBJECT-TYPE
            SYNTAX INTEGER
            MAX-ACCESS read-write
            STATUS current
            DESCRIPTION "WAN-Update-Minutes"
            ::= {  setNetbi 10 }

setNetbiLea OBJECT-TYPE
            SYNTAX INTEGER
            MAX-ACCESS read-write
            STATUS current
            DESCRIPTION "Leasetime"
            ::= {  setNetbi 11 }

setConfi OBJECT IDENTIFIER ::= { set 11}
setConfiPasswor OBJECT-TYPE
                SYNTAX INTEGER {
                  no(0),
                  yes(1)
                }
                MAX-ACCESS read-write
                STATUS current
                DESCRIPTION "Password-Required-for-SNMP-Read-Access"
                ::= {  setConfi 3 }

setConfiMaximum OBJECT-TYPE
                SYNTAX INTEGER
                MAX-ACCESS read-write
                STATUS current
                DESCRIPTION "Maximum-Connections"
                ::= {  setConfi 4 }

setConfiConfiga OBJECT-TYPE
                SYNTAX INTEGER
                MAX-ACCESS read-write
                STATUS current
                DESCRIPTION "Config-Aging-Minutes"
                ::= {  setConfi 5 }

setConfiOutband OBJECT-TYPE
                SYNTAX INTEGER
                MAX-ACCESS read-write
                STATUS current
                DESCRIPTION "Outband-Aging-Minutes"
                ::= {  setConfi 33 }

setConfiLoginer OBJECT-TYPE
                SYNTAX INTEGER
                MAX-ACCESS read-write
                STATUS current
                DESCRIPTION "Login-Errors"
                ::= {  setConfi 7 }

setConfiLockmin OBJECT-TYPE
                SYNTAX INTEGER
                MAX-ACCESS read-write
                STATUS current
                DESCRIPTION "Lock-Minutes"
                ::= {  setConfi 8 }

setConfiLanguag OBJECT-TYPE
                SYNTAX INTEGER {
                  english(1),
                  deutsch(2)
                }
                MAX-ACCESS read-write
                STATUS current
                DESCRIPTION "Language"
                ::= {  setConfi 6 }

setConfiTftpcli OBJECT IDENTIFIER ::= { setConfi 13}
setConfiTftpcliConfigadd OBJECT-TYPE
                         SYNTAX DisplayString (SIZE(0..31))
                         MAX-ACCESS read-write
                         STATUS current
                         DESCRIPTION "Config-Address"
                         ::= {  setConfiTftpcli 1 }

setConfiTftpcliConfigfil OBJECT-TYPE
                         SYNTAX DisplayString (SIZE(0..63))
                         MAX-ACCESS read-write
                         STATUS current
                         DESCRIPTION "Config-Filename"
                         ::= {  setConfiTftpcli 2 }

setConfiTftpcliFirmwarea OBJECT-TYPE
                         SYNTAX DisplayString (SIZE(0..31))
                         MAX-ACCESS read-write
                         STATUS current
                         DESCRIPTION "Firmware-Address"
                         ::= {  setConfiTftpcli 3 }

setConfiTftpcliFirmwaref OBJECT-TYPE
                         SYNTAX DisplayString (SIZE(0..63))
                         MAX-ACCESS read-write
                         STATUS current
                         DESCRIPTION "Firmware-Filename"
                         ::= {  setConfiTftpcli 4 }

setConfiTftpcliScriptadd OBJECT-TYPE
                         SYNTAX DisplayString (SIZE(0..31))
                         MAX-ACCESS read-write
                         STATUS current
                         DESCRIPTION "Script-Address"
                         ::= {  setConfiTftpcli 6 }

setConfiTftpcliScriptfil OBJECT-TYPE
                         SYNTAX DisplayString (SIZE(0..63))
                         MAX-ACCESS read-write
                         STATUS current
                         DESCRIPTION "Script-Filename"
                         ::= {  setConfiTftpcli 7 }

setConfiTftpcliBytesperh OBJECT-TYPE
                         SYNTAX INTEGER
                         MAX-ACCESS read-write
                         STATUS current
                         DESCRIPTION "Bytes-per-Hashmark"
                         ::= {  setConfiTftpcli 5 }

setConfiAccesstTable OBJECT-TYPE
                     SYNTAX SEQUENCE OF SetConfiAccesstEntry
                     MAX-ACCESS not-accessible
                     STATUS current
                     DESCRIPTION "Access-Table"
                     ::= {  setConfi 15 }

setConfiAccesstEntry OBJECT-TYPE
                     SYNTAX SetConfiAccesstEntry
                     MAX-ACCESS not-accessible
                     STATUS current
                     DESCRIPTION "entry in table"
                     INDEX { setConfiAccesstIfc }
                     ::= {  setConfiAccesstTable 1 }

SetConfiAccesstEntry ::= SEQUENCE {
                     setConfiAccesstIfc INTEGER,
                     setConfiAccesstTelnet INTEGER,
                     setConfiAccesstTftp INTEGER,
                     setConfiAccesstHttp INTEGER,
                     setConfiAccesstSnmp INTEGER,
                     setConfiAccesstHttps INTEGER,
                     setConfiAccesstTelnets INTEGER,
                     setConfiAccesstSsh INTEGER
                    }

setConfiAccesstIfc OBJECT-TYPE
                       SYNTAX INTEGER{
                         lan(1),
                         wan(2),
                         wlan(3)
                       }
                       MAX-ACCESS read-only
                       STATUS current
                       DESCRIPTION "Ifc."
                       ::= {  setConfiAccesstEntry 1 }

setConfiAccesstTelnet OBJECT-TYPE
                       SYNTAX INTEGER{
                         yes(1),
                         read(4),
                         no(0)
                       }
                       MAX-ACCESS read-write
                       STATUS current
                       DESCRIPTION "Telnet"
                       ::= {  setConfiAccesstEntry 2 }

setConfiAccesstTftp OBJECT-TYPE
                       SYNTAX INTEGER{
                         yes(1),
                         read(4),
                         no(0)
                       }
                       MAX-ACCESS read-write
                       STATUS current
                       DESCRIPTION "TFTP"
                       ::= {  setConfiAccesstEntry 3 }

setConfiAccesstHttp OBJECT-TYPE
                       SYNTAX INTEGER{
                         yes(1),
                         read(4),
                         no(0)
                       }
                       MAX-ACCESS read-write
                       STATUS current
                       DESCRIPTION "HTTP"
                       ::= {  setConfiAccesstEntry 4 }

setConfiAccesstSnmp OBJECT-TYPE
                       SYNTAX INTEGER{
                         yes(1),
                         read(4),
                         no(0)
                       }
                       MAX-ACCESS read-write
                       STATUS current
                       DESCRIPTION "SNMP"
                       ::= {  setConfiAccesstEntry 5 }

setConfiAccesstHttps OBJECT-TYPE
                       SYNTAX INTEGER{
                         yes(1),
                         read(4),
                         no(0)
                       }
                       MAX-ACCESS read-write
                       STATUS current
                       DESCRIPTION "HTTPS"
                       ::= {  setConfiAccesstEntry 6 }

setConfiAccesstTelnets OBJECT-TYPE
                       SYNTAX INTEGER{
                         yes(1),
                         read(4),
                         no(0)
                       }
                       MAX-ACCESS read-write
                       STATUS current
                       DESCRIPTION "Telnet-SSL"
                       ::= {  setConfiAccesstEntry 7 }

setConfiAccesstSsh OBJECT-TYPE
                       SYNTAX INTEGER{
                         yes(1),
                         read(4),
                         no(0)
                       }
                       MAX-ACCESS read-write
                       STATUS current
                       DESCRIPTION "SSH"
                       ::= {  setConfiAccesstEntry 8 }

setConfiScreenh OBJECT-TYPE
                SYNTAX INTEGER
                MAX-ACCESS read-write
                STATUS current
                DESCRIPTION "Screen-Height"
                ::= {  setConfi 16 }

setConfiCrashme OBJECT-TYPE
                SYNTAX DisplayString (SIZE(0..32))
                MAX-ACCESS read-write
                STATUS current
                DESCRIPTION "Crash-Message"
                ::= {  setConfi 40 }

setConfiAdminge OBJECT-TYPE
                SYNTAX INTEGER {
                  unknown(0),
                  male(1),
                  female(2),
                  geek(3)
                }
                MAX-ACCESS read-write
                STATUS current
                DESCRIPTION "Admin-Gender"
                ::= {  setConfi 41 }

setConfiAsserta OBJECT-TYPE
                SYNTAX INTEGER {
                  log-only(0),
                  reboot(1)
                }
                MAX-ACCESS read-write
                STATUS current
                DESCRIPTION "Assert-Action"
                ::= {  setConfi 42 }

setConfiPrompt OBJECT-TYPE
                SYNTAX DisplayString (SIZE(0..31))
                MAX-ACCESS read-write
                STATUS current
                DESCRIPTION "Prompt"
                ::= {  setConfi 17 }

setConfiLedtest OBJECT-TYPE
                SYNTAX INTEGER {
                  off(0),
                  green(2),
                  red(1),
                  orange(3),
                  no-test(255)
                }
                MAX-ACCESS read-write
                STATUS current
                DESCRIPTION "LED-Test"
                ::= {  setConfi 18 }

setConfiCrontabTable OBJECT-TYPE
                     SYNTAX SEQUENCE OF SetConfiCrontabEntry
                     MAX-ACCESS not-accessible
                     STATUS current
                     DESCRIPTION "Cron-Table"
                     ::= {  setConfi 20 }

setConfiCrontabEntry OBJECT-TYPE
                     SYNTAX SetConfiCrontabEntry
                     MAX-ACCESS not-accessible
                     STATUS current
                     DESCRIPTION "entry in table"
                     INDEX { setConfiCrontabInde }
                     ::= {  setConfiCrontabTable 1 }

SetConfiCrontabEntry ::= SEQUENCE {
                     setConfiCrontabInde INTEGER,
                     setConfiCrontabActi INTEGER,
                     setConfiCrontabBase INTEGER,
                     setConfiCrontabVari INTEGER,
                     setConfiCrontabMinu DisplayString,
                     setConfiCrontabHour DisplayString,
                     setConfiCrontabDayo DisplayString,
                     setConfiCrontabDay DisplayString,
                     setConfiCrontabMont DisplayString,
                     setConfiCrontabComm DisplayString,
                     setConfiCrontabOwne DisplayString
                    }

setConfiCrontabInde OBJECT-TYPE
                    SYNTAX INTEGER (0..65535)
                    MAX-ACCESS read-write
                    STATUS current
                    DESCRIPTION "Index"
                    ::= {  setConfiCrontabEntry 1 }

setConfiCrontabActi OBJECT-TYPE
                    SYNTAX INTEGER{
                      yes(0),
                      no(1)
                    }
                    MAX-ACCESS read-write
                    STATUS current
                    DESCRIPTION "Active"
                    ::= {  setConfiCrontabEntry 9 }

setConfiCrontabBase OBJECT-TYPE
                    SYNTAX INTEGER{
                      real-time(0),
                      operation-time(1)
                    }
                    MAX-ACCESS read-write
                    STATUS current
                    DESCRIPTION "Base"
                    ::= {  setConfiCrontabEntry 8 }

setConfiCrontabVari OBJECT-TYPE
                    SYNTAX INTEGER (0..65535)
                    MAX-ACCESS read-write
                    STATUS current
                    DESCRIPTION "Variation"
                    ::= {  setConfiCrontabEntry 11 }

setConfiCrontabMinu OBJECT-TYPE
                    SYNTAX DisplayString (SIZE(0..50))
                    MAX-ACCESS read-write
                    STATUS current
                    DESCRIPTION "Minute"
                    ::= {  setConfiCrontabEntry 2 }

setConfiCrontabHour OBJECT-TYPE
                    SYNTAX DisplayString (SIZE(0..50))
                    MAX-ACCESS read-write
                    STATUS current
                    DESCRIPTION "Hour"
                    ::= {  setConfiCrontabEntry 3 }

setConfiCrontabDayo OBJECT-TYPE
                    SYNTAX DisplayString (SIZE(0..50))
                    MAX-ACCESS read-write
                    STATUS current
                    DESCRIPTION "DayOfWeek"
                    ::= {  setConfiCrontabEntry 4 }

setConfiCrontabDay OBJECT-TYPE
                    SYNTAX DisplayString (SIZE(0..50))
                    MAX-ACCESS read-write
                    STATUS current
                    DESCRIPTION "Day"
                    ::= {  setConfiCrontabEntry 5 }

setConfiCrontabMont OBJECT-TYPE
                    SYNTAX DisplayString (SIZE(0..50))
                    MAX-ACCESS read-write
                    STATUS current
                    DESCRIPTION "Month"
                    ::= {  setConfiCrontabEntry 6 }

setConfiCrontabComm OBJECT-TYPE
                    SYNTAX DisplayString (SIZE(0..100))
                    MAX-ACCESS read-write
                    STATUS current
                    DESCRIPTION "Command"
                    ::= {  setConfiCrontabEntry 7 }

setConfiCrontabOwne OBJECT-TYPE
                    SYNTAX DisplayString (SIZE(0..16))
                    MAX-ACCESS read-write
                    STATUS current
                    DESCRIPTION "Owner"
                    ::= {  setConfiCrontabEntry 10 }

setConfiAdminsTable OBJECT-TYPE
                     SYNTAX SEQUENCE OF SetConfiAdminsEntry
                     MAX-ACCESS not-accessible
                     STATUS current
                     DESCRIPTION "Admins"
                     ::= {  setConfi 21 }

setConfiAdminsEntry OBJECT-TYPE
                     SYNTAX SetConfiAdminsEntry
                     MAX-ACCESS not-accessible
                     STATUS current
                     DESCRIPTION "entry in table"
                     INDEX { setConfiAdminsAdm }
                     ::= {  setConfiAdminsTable 1 }

SetConfiAdminsEntry ::= SEQUENCE {
                     setConfiAdminsAdm DisplayString,
                     setConfiAdminsPas DisplayString,
                     setConfiAdminsAct INTEGER,
                     setConfiAdminsAcc INTEGER,
                     setConfiAdminsFun BITS
                    }

setConfiAdminsAdm OBJECT-TYPE
                  SYNTAX DisplayString (SIZE(0..16))
                  MAX-ACCESS read-write
                  STATUS current
                  DESCRIPTION "Administrator"
                  ::= {  setConfiAdminsEntry 1 }

setConfiAdminsPas OBJECT-TYPE
                  SYNTAX DisplayString (SIZE(0..16))
                  MAX-ACCESS read-write
                  STATUS current
                  DESCRIPTION "Password"
                  ::= {  setConfiAdminsEntry 2 }

setConfiAdminsAct OBJECT-TYPE
                  SYNTAX INTEGER{
                    no(1),
                    yes(0)
                  }
                  MAX-ACCESS read-write
                  STATUS current
                  DESCRIPTION "Active"
                  ::= {  setConfiAdminsEntry 4 }

setConfiAdminsAcc OBJECT-TYPE
                  SYNTAX INTEGER{
                    none(0),
                    admin-ro-limit(8388608),
                    admin-ro(16777216),
                    admin-rw(16777472),
                    supervisor(-1)
                  }
                  MAX-ACCESS read-write
                  STATUS current
                  DESCRIPTION "Access-Rights"
                  ::= {  setConfiAdminsEntry 5 }

setConfiAdminsFun OBJECT-TYPE
                  SYNTAX BITS{
                    basic-wizard(1),
                    security-wizard(2),
                    internet-wizard(4),
                    ras-wizard(16),
                    provider-selection(8),
                    lanlan-wizard(32),
                    time-setting(64),
                    device-search(128),
                    wlan-linktest(256),
                    rollout-wizard(8192),
                    wlan-wizard(4096)
                  }
                  MAX-ACCESS read-write
                  STATUS current
                  DESCRIPTION "Function-Rights"
                  ::= {  setConfiAdminsEntry 3 }

setConfiPredefaTable OBJECT-TYPE
                     SYNTAX SEQUENCE OF SetConfiPredefaEntry
                     MAX-ACCESS not-accessible
                     STATUS current
                     DESCRIPTION "Predef.-Admins"
                     ::= {  setConfi 27 }

setConfiPredefaEntry OBJECT-TYPE
                     SYNTAX SetConfiPredefaEntry
                     MAX-ACCESS not-accessible
                     STATUS current
                     DESCRIPTION "entry in table"
                     INDEX { setConfiPredefaNam }
                     ::= {  setConfiPredefaTable 1 }

SetConfiPredefaEntry ::= SEQUENCE {
                     setConfiPredefaNam DisplayString
                    }

setConfiPredefaNam OBJECT-TYPE
                   SYNTAX DisplayString (SIZE(0..15))
                   MAX-ACCESS read-only
                   STATUS current
                   DESCRIPTION "Name"
                   ::= {  setConfiPredefaEntry 1 }

setConfiLan OBJECT-TYPE
                SYNTAX INTEGER
                MAX-ACCESS not-accessible
                STATUS current
                DESCRIPTION "LAN"
                ::= {  setConfi 1 }

setConfiWlancon OBJECT-TYPE
                SYNTAX INTEGER
                MAX-ACCESS not-accessible
                STATUS current
                DESCRIPTION "WLAN-Config"
                ::= {  setConfi 11 }

setConfiWan OBJECT-TYPE
                SYNTAX INTEGER
                MAX-ACCESS not-accessible
                STATUS current
                DESCRIPTION "WAN"
                ::= {  setConfi 2 }

setConfiTelnetp OBJECT-TYPE
                SYNTAX INTEGER
                MAX-ACCESS read-write
                STATUS current
                DESCRIPTION "Telnet-Port"
                ::= {  setConfi 23 }

setConfiTelnets OBJECT-TYPE
                SYNTAX INTEGER
                MAX-ACCESS read-write
                STATUS current
                DESCRIPTION "Telnet-SSL-Port"
                ::= {  setConfi 24 }

setConfiResetbu OBJECT-TYPE
                SYNTAX INTEGER {
                  ignore(0),
                  boot-only(1),
                  reset-or-boot(2)
                }
                MAX-ACCESS read-write
                STATUS current
                DESCRIPTION "Reset-button"
                ::= {  setConfi 32 }

setConfiMonitor OBJECT IDENTIFIER ::= { setConfi 35}
setConfiMonitorTracemask1 OBJECT-TYPE
                          SYNTAX INTEGER
                          MAX-ACCESS read-only
                          STATUS current
                          DESCRIPTION "Tracemask1"
                          ::= {  setConfiMonitor 1 }

setConfiMonitorTracemask2 OBJECT-TYPE
                          SYNTAX INTEGER
                          MAX-ACCESS read-only
                          STATUS current
                          DESCRIPTION "Tracemask2"
                          ::= {  setConfiMonitor 2 }

setConfiUpdatec OBJECT IDENTIFIER ::= { setConfi 30}
setConfiUpdatecOperati OBJECT-TYPE
                       SYNTAX INTEGER {
                         no(0),
                         yes(1)
                       }
                       MAX-ACCESS read-write
                       STATUS current
                       DESCRIPTION "Operating"
                       ::= {  setConfiUpdatec 1 }

setConfiUpdatecServern OBJECT-TYPE
                       SYNTAX DisplayString (SIZE(0..64))
                       MAX-ACCESS read-write
                       STATUS current
                       DESCRIPTION "Server-Name"
                       ::= {  setConfiUpdatec 2 }

setConfiUpdatecServerp OBJECT-TYPE
                       SYNTAX INTEGER
                       MAX-ACCESS read-write
                       STATUS current
                       DESCRIPTION "Server-Port"
                       ::= {  setConfiUpdatec 3 }

setConfiUpdatecRespons OBJECT-TYPE
                       SYNTAX INTEGER
                       MAX-ACCESS read-write
                       STATUS current
                       DESCRIPTION "Response-Timeout"
                       ::= {  setConfiUpdatec 4 }

setConfiUpdatecRetryfa OBJECT-TYPE
                       SYNTAX INTEGER
                       MAX-ACCESS read-write
                       STATUS current
                       DESCRIPTION "Retry-Failure"
                       ::= {  setConfiUpdatec 5 }

setConfiUpdatecRetryok OBJECT-TYPE
                       SYNTAX INTEGER
                       MAX-ACCESS read-write
                       STATUS current
                       DESCRIPTION "Retry-Ok"
                       ::= {  setConfiUpdatec 6 }

setConfiUpdatecLastfir OBJECT-TYPE
                       SYNTAX DisplayString (SIZE(0..21))
                       MAX-ACCESS read-only
                       STATUS current
                       DESCRIPTION "Last-Firmware-Update"
                       ::= {  setConfiUpdatec 7 }

setConfiUpdatecLastcon OBJECT-TYPE
                       SYNTAX DisplayString (SIZE(0..21))
                       MAX-ACCESS read-only
                       STATUS current
                       DESCRIPTION "Last-Config-Update"
                       ::= {  setConfiUpdatec 8 }

setConfiSshport OBJECT-TYPE
                SYNTAX INTEGER
                MAX-ACCESS read-write
                STATUS current
                DESCRIPTION "SSH-Port"
                ::= {  setConfi 25 }

setConfiSshauthTable OBJECT-TYPE
                     SYNTAX SEQUENCE OF SetConfiSshauthEntry
                     MAX-ACCESS not-accessible
                     STATUS current
                     DESCRIPTION "SSH-Authentication-Methods"
                     ::= {  setConfi 26 }

setConfiSshauthEntry OBJECT-TYPE
                     SYNTAX SetConfiSshauthEntry
                     MAX-ACCESS not-accessible
                     STATUS current
                     DESCRIPTION "entry in table"
                     INDEX { setConfiSshauthIfc }
                     ::= {  setConfiSshauthTable 1 }

SetConfiSshauthEntry ::= SEQUENCE {
                     setConfiSshauthIfc INTEGER,
                     setConfiSshauthMet INTEGER
                    }

setConfiSshauthIfc OBJECT-TYPE
                   SYNTAX INTEGER{
                     lan(1),
                     wan(2),
                     wlan(3)
                   }
                   MAX-ACCESS read-only
                   STATUS current
                   DESCRIPTION "Ifc."
                   ::= {  setConfiSshauthEntry 1 }

setConfiSshauthMet OBJECT-TYPE
                   SYNTAX INTEGER{
                     public-key(1),
                     password(2),
                     all(255)
                   }
                   MAX-ACCESS read-write
                   STATUS current
                   DESCRIPTION "Methods"
                   ::= {  setConfiSshauthEntry 2 }

setWlan OBJECT IDENTIFIER ::= { set 12}
setWlanBrokenlink OBJECT-TYPE
                  SYNTAX INTEGER {
                    no(0),
                    yes(1)
                  }
                  MAX-ACCESS read-write
                  STATUS current
                  DESCRIPTION "Broken-Link-Detection"
                  ::= {  setWlan 39 }

setWlanSpareheap OBJECT-TYPE
                  SYNTAX INTEGER
                  MAX-ACCESS read-write
                  STATUS current
                  DESCRIPTION "Spare-Heap"
                  ::= {  setWlan 3 }

setWlanIappprotoc OBJECT-TYPE
                  SYNTAX INTEGER {
                    no(0),
                    yes(1)
                  }
                  MAX-ACCESS read-write
                  STATUS current
                  DESCRIPTION "IAPP-Protocol"
                  ::= {  setWlan 12 }

setWlanIappannoun OBJECT-TYPE
                  SYNTAX INTEGER
                  MAX-ACCESS read-write
                  STATUS current
                  DESCRIPTION "IAPP-Announce-Interval"
                  ::= {  setWlan 13 }

setWlanIapphandov OBJECT-TYPE
                  SYNTAX INTEGER
                  MAX-ACCESS read-write
                  STATUS current
                  DESCRIPTION "IAPP-Handover-Timeout"
                  ::= {  setWlan 14 }

setWlanCountry OBJECT-TYPE
                  SYNTAX INTEGER {
                    unknown(0),
                    albania(8),
                    argentina(32),
                    australia(36),
                    austria(40),
                    bahrain(48),
                    bangladesh(50),
                    belarus(112),
                    belgium(56),
                    bosnia-herzegovina(70),
                    brazil(76),
                    brunei-darussalam(96),
                    bulgaria(100),
                    canada(124),
                    chile(152),
                    china(156),
                    colombia(170),
                    costa-rica(188),
                    croatia(191),
                    cyprus(196),
                    czech(203),
                    denmark(208),
                    ecuador(218),
                    egalistan(999),
                    egypt(818),
                    estonia(233),
                    finland(246),
                    france(250),
                    germany(276),
                    ghana(288),
                    greece(300),
                    guatemala(320),
                    honduras(340),
                    hong-kong(344),
                    hungary(348),
                    iceland(352),
                    india(356),
                    indonesia(360),
                    ireland(372),
                    israel(376),
                    italy(380),
                    japan(392),
                    jordan(400),
                    south-korea(410),
                    kuwait(414),
                    latvia(428),
                    lebanon(422),
                    liechtenstein(438),
                    lithuania(440),
                    luxembourg(442),
                    macau(446),
                    macedonia(807),
                    malaysia(458),
                    malta(470),
                    mexico(484),
                    moldavia(498),
                    morocco(504),
                    netherlands(528),
                    new-zealand(554),
                    nicaragua(558),
                    norway(578),
                    oman(512),
                    pakistan(586),
                    panama(591),
                    paraguay(600),
                    peru(604),
                    philippines(608),
                    poland(616),
                    portugal(620),
                    puerto-rico(630),
                    qatar(634),
                    romania(642),
                    russia(643),
                    saudi-arabia(682),
                    singapore(702),
                    slovak(703),
                    slovenia(705),
                    south-africa(710),
                    spain(724),
                    sweden(752),
                    switzerland(756),
                    taiwan(158),
                    tanzania(834),
                    thailand(764),
                    tunisia(788),
                    turkey(792),
                    uganda(800),
                    ukraine(804),
                    united-arab-emirates(784),
                    united-kingdom(826),
                    united-states-fcc(840),
                    uruguay(858),
                    venezuela(862)
                  }
                  MAX-ACCESS read-write
                  STATUS current
                  DESCRIPTION "Country"
                  ::= {  setWlan 36 }

setWlanIndooronly OBJECT-TYPE
                  SYNTAX INTEGER {
                    no(0),
                    yes(1)
                  }
                  MAX-ACCESS read-write
                  STATUS current
                  DESCRIPTION "Indoor-Only-Operation"
                  ::= {  setWlan 46 }

setWlanMailaddres OBJECT-TYPE
                  SYNTAX DisplayString (SIZE(0..254))
                  MAX-ACCESS read-write
                  STATUS current
                  DESCRIPTION "Mail-Address"
                  ::= {  setWlan 41 }

setWlanCardreinit OBJECT-TYPE
                  SYNTAX INTEGER
                  MAX-ACCESS read-write
                  STATUS current
                  DESCRIPTION "Card-Reinit-Cycle"
                  ::= {  setWlan 100 }

setWlanNoisecalib OBJECT-TYPE
                  SYNTAX INTEGER
                  MAX-ACCESS read-write
                  STATUS current
                  DESCRIPTION "Noise-Calibration-Cycle"
                  ::= {  setWlan 101 }

setWlanNoiseoffseTable OBJECT-TYPE
                       SYNTAX SEQUENCE OF SetWlanNoiseoffseEntry
                       MAX-ACCESS not-accessible
                       STATUS current
                       DESCRIPTION "Noise-Offsets"
                       ::= {  setWlan 109 }

setWlanNoiseoffseEntry OBJECT-TYPE
                       SYNTAX SetWlanNoiseoffseEntry
                       MAX-ACCESS not-accessible
                       STATUS current
                       DESCRIPTION "entry in table"
                       INDEX { setWlanNoiseoffseBan, setWlanNoiseoffseCha, setWlanNoiseoffseInt }
                       ::= {  setWlanNoiseoffseTable 1 }

SetWlanNoiseoffseEntry ::= SEQUENCE {
                       setWlanNoiseoffseBan INTEGER,
                       setWlanNoiseoffseCha INTEGER,
                       setWlanNoiseoffseInt INTEGER,
                       setWlanNoiseoffseVal INTEGER
                      }

setWlanNoiseoffseBan OBJECT-TYPE
                     SYNTAX INTEGER{
                       e2-4ghz(1)
                     }
                     MAX-ACCESS read-write
                     STATUS current
                     DESCRIPTION "Band"
                     ::= {  setWlanNoiseoffseEntry 1 }

setWlanNoiseoffseCha OBJECT-TYPE
                     SYNTAX INTEGER (0..65535)
                     MAX-ACCESS read-write
                     STATUS current
                     DESCRIPTION "Channel"
                     ::= {  setWlanNoiseoffseEntry 2 }

setWlanNoiseoffseInt OBJECT-TYPE
                     SYNTAX INTEGER{
                       wlan-1(1)
                     }
                     MAX-ACCESS read-write
                     STATUS current
                     DESCRIPTION "Interface"
                     ::= {  setWlanNoiseoffseEntry 3 }

setWlanNoiseoffseVal OBJECT-TYPE
                     SYNTAX INTEGER (-128..127)
                     MAX-ACCESS read-write
                     STATUS current
                     DESCRIPTION "Value"
                     ::= {  setWlanNoiseoffseEntry 4 }

setWlanThermrecal OBJECT-TYPE
                  SYNTAX INTEGER
                  MAX-ACCESS read-write
                  STATUS current
                  DESCRIPTION "Therm.-Recal.-Cycle"
                  ::= {  setWlan 105 }

setWlanTracemac OBJECT-TYPE
                  SYNTAX MacAddress
                  MAX-ACCESS read-write
                  STATUS current
                  DESCRIPTION "Trace-MAC"
                  ::= {  setWlan 103 }

setWlanTracelevel OBJECT-TYPE
                  SYNTAX INTEGER
                  MAX-ACCESS read-write
                  STATUS current
                  DESCRIPTION "Trace-Level"
                  ::= {  setWlan 110 }

setWlanNoiseimmun OBJECT IDENTIFIER ::= { setWlan 111}
setWlanNoiseimmunNoi OBJECT-TYPE
                     SYNTAX INTEGER
                     MAX-ACCESS read-write
                     STATUS current
                     DESCRIPTION "Noise-Immunity-Level"
                     ::= {  setWlanNoiseimmun 1 }

setWlanNoiseimmunOfd OBJECT-TYPE
                     SYNTAX INTEGER
                     MAX-ACCESS read-write
                     STATUS current
                     DESCRIPTION "OFDM-Weak-Signal-Detection"
                     ::= {  setWlanNoiseimmun 2 }

setWlanNoiseimmunCck OBJECT-TYPE
                     SYNTAX INTEGER
                     MAX-ACCESS read-write
                     STATUS current
                     DESCRIPTION "CCK-Weak-Signal-Detection-Threshold"
                     ::= {  setWlanNoiseimmun 3 }

setWlanNoiseimmunFir OBJECT-TYPE
                     SYNTAX INTEGER
                     MAX-ACCESS read-write
                     STATUS current
                     DESCRIPTION "Fir-Step-Level"
                     ::= {  setWlanNoiseimmun 4 }

setWlanNoiseimmunSpu OBJECT-TYPE
                     SYNTAX INTEGER
                     MAX-ACCESS read-write
                     STATUS current
                     DESCRIPTION "Spurious-Immunity-Level"
                     ::= {  setWlanNoiseimmun 5 }

setWlanInterstati OBJECT-TYPE
                  SYNTAX INTEGER {
                    yes(1),
                    locally-off(0),
                    gserverlly-off(2)
                  }
                  MAX-ACCESS read-write
                  STATUS current
                  DESCRIPTION "Inter-Station-Traffic"
                  ::= {  setWlan 26 }

setWlanIdletimeou OBJECT-TYPE
                  SYNTAX INTEGER
                  MAX-ACCESS read-write
                  STATUS current
                  DESCRIPTION "Idle-Timeout"
                  ::= {  setWlan 43 }

setWlanSupervises OBJECT-TYPE
                  SYNTAX INTEGER {
                    no(0),
                    yes(1)
                  }
                  MAX-ACCESS read-write
                  STATUS current
                  DESCRIPTION "Supervise-Stations"
                  ::= {  setWlan 27 }

setWlanArphandlin OBJECT-TYPE
                  SYNTAX INTEGER {
                    no(0),
                    yes(1)
                  }
                  MAX-ACCESS read-write
                  STATUS current
                  DESCRIPTION "ARP-Handling"
                  ::= {  setWlan 38 }

setWlanAllowilleg OBJECT-TYPE
                  SYNTAX INTEGER {
                    no(0),
                    yes(1)
                  }
                  MAX-ACCESS read-write
                  STATUS current
                  DESCRIPTION "Allow-Illegal-Association-Without-Authentication"
                  ::= {  setWlan 44 }

setWlanAccesslistTable OBJECT-TYPE
                       SYNTAX SEQUENCE OF SetWlanAccesslistEntry
                       MAX-ACCESS not-accessible
                       STATUS current
                       DESCRIPTION "Access-List"
                       ::= {  setWlan 7 }

setWlanAccesslistEntry OBJECT-TYPE
                       SYNTAX SetWlanAccesslistEntry
                       MAX-ACCESS not-accessible
                       STATUS current
                       DESCRIPTION "entry in table"
                       INDEX { setWlanAccesslistMac }
                       ::= {  setWlanAccesslistTable 1 }

SetWlanAccesslistEntry ::= SEQUENCE {
                       setWlanAccesslistMac MacAddress,
                       setWlanAccesslistNam DisplayString,
                       setWlanAccesslistWpa DisplayString,
                       setWlanAccesslistTxl INTEGER,
                       setWlanAccesslistRxl INTEGER,
                       setWlanAccesslistVla INTEGER,
                       setWlanAccesslistCom DisplayString
                      }

setWlanAccesslistMac OBJECT-TYPE
                     SYNTAX MacAddress
                     MAX-ACCESS read-write
                     STATUS current
                     DESCRIPTION "MAC-Address"
                     ::= {  setWlanAccesslistEntry 1 }

setWlanAccesslistNam OBJECT-TYPE
                     SYNTAX DisplayString (SIZE(0..32))
                     MAX-ACCESS read-write
                     STATUS current
                     DESCRIPTION "Name"
                     ::= {  setWlanAccesslistEntry 2 }

setWlanAccesslistWpa OBJECT-TYPE
                     SYNTAX DisplayString (SIZE(0..63))
                     MAX-ACCESS read-write
                     STATUS current
                     DESCRIPTION "WPA-Passphrase"
                     ::= {  setWlanAccesslistEntry 4 }

setWlanAccesslistTxl OBJECT-TYPE
                     SYNTAX INTEGER (0..2147483647)
                     MAX-ACCESS read-write
                     STATUS current
                     DESCRIPTION "Tx-Limit"
                     ::= {  setWlanAccesslistEntry 5 }

setWlanAccesslistRxl OBJECT-TYPE
                     SYNTAX INTEGER (0..2147483647)
                     MAX-ACCESS read-write
                     STATUS current
                     DESCRIPTION "Rx-Limit"
                     ::= {  setWlanAccesslistEntry 6 }

setWlanAccesslistVla OBJECT-TYPE
                     SYNTAX INTEGER (0..65535)
                     MAX-ACCESS read-write
                     STATUS current
                     DESCRIPTION "VLAN-Id"
                     ::= {  setWlanAccesslistEntry 7 }

setWlanAccesslistCom OBJECT-TYPE
                     SYNTAX DisplayString (SIZE(0..30))
                     MAX-ACCESS read-write
                     STATUS current
                     DESCRIPTION "Comment"
                     ::= {  setWlanAccesslistEntry 3 }

setWlanAccessmode OBJECT-TYPE
                  SYNTAX INTEGER {
                    negative(0),
                    positive(1)
                  }
                  MAX-ACCESS read-write
                  STATUS current
                  DESCRIPTION "Access-Mode"
                  ::= {  setWlan 8 }

setWlanRadiusacce OBJECT IDENTIFIER ::= { setWlan 29}
setWlanRadiusacceServeradd OBJECT-TYPE
                           SYNTAX IpAddress
                           MAX-ACCESS read-write
                           STATUS current
                           DESCRIPTION "Server-Address"
                           ::= {  setWlanRadiusacce 1 }

setWlanRadiusacceAuthport OBJECT-TYPE
                           SYNTAX INTEGER
                           MAX-ACCESS read-write
                           STATUS current
                           DESCRIPTION "Auth.-Port"
                           ::= {  setWlanRadiusacce 2 }

setWlanRadiusacceSecret OBJECT-TYPE
                           SYNTAX DisplayString (SIZE(0..32))
                           MAX-ACCESS read-write
                           STATUS current
                           DESCRIPTION "Secret"
                           ::= {  setWlanRadiusacce 3 }

setWlanRadiusacceLoopbacka OBJECT-TYPE
                           SYNTAX DisplayString (SIZE(0..16))
                           MAX-ACCESS read-write
                           STATUS current
                           DESCRIPTION "Loopback-Address"
                           ::= {  setWlanRadiusacce 11 }

setWlanRadiusacceProtocol OBJECT-TYPE
                           SYNTAX INTEGER {
                             radius(0),
                             radsec(1)
                           }
                           MAX-ACCESS read-write
                           STATUS current
                           DESCRIPTION "Protocol"
                           ::= {  setWlanRadiusacce 13 }

setWlanRadiusacceBackupser OBJECT-TYPE
                           SYNTAX IpAddress
                           MAX-ACCESS read-write
                           STATUS current
                           DESCRIPTION "Backup-Server-IP-Address"
                           ::= {  setWlanRadiusacce 4 }

setWlanRadiusacceBackupaut OBJECT-TYPE
                           SYNTAX INTEGER
                           MAX-ACCESS read-write
                           STATUS current
                           DESCRIPTION "Backup-Auth.-Port"
                           ::= {  setWlanRadiusacce 5 }

setWlanRadiusacceBackupsec OBJECT-TYPE
                           SYNTAX DisplayString (SIZE(0..32))
                           MAX-ACCESS read-write
                           STATUS current
                           DESCRIPTION "Backup-Secret"
                           ::= {  setWlanRadiusacce 6 }

setWlanRadiusacceBackuploo OBJECT-TYPE
                           SYNTAX DisplayString (SIZE(0..16))
                           MAX-ACCESS read-write
                           STATUS current
                           DESCRIPTION "Backup-Loopback-Address"
                           ::= {  setWlanRadiusacce 12 }

setWlanRadiusacceBackuppro OBJECT-TYPE
                           SYNTAX INTEGER {
                             radius(0),
                             radsec(1)
                           }
                           MAX-ACCESS read-write
                           STATUS current
                           DESCRIPTION "Backup-Protocol"
                           ::= {  setWlanRadiusacce 14 }

setWlanRadiusacceResponsel OBJECT-TYPE
                           SYNTAX INTEGER
                           MAX-ACCESS read-write
                           STATUS current
                           DESCRIPTION "Response-Lifetime"
                           ::= {  setWlanRadiusacce 7 }

setWlanRadiusaccePasswords OBJECT-TYPE
                           SYNTAX INTEGER {
                             secret(0),
                             mac-address(1)
                           }
                           MAX-ACCESS read-write
                           STATUS current
                           DESCRIPTION "Password-Source"
                           ::= {  setWlanRadiusacce 8 }

setWlanRadiusacceRecheckcy OBJECT-TYPE
                           SYNTAX INTEGER
                           MAX-ACCESS read-write
                           STATUS current
                           DESCRIPTION "Recheck-Cycle"
                           ::= {  setWlanRadiusacce 9 }

setWlanRadiusacceProvidese OBJECT-TYPE
                           SYNTAX INTEGER {
                             no(0),
                             yes(1)
                           }
                           MAX-ACCESS read-write
                           STATUS current
                           DESCRIPTION "Provide-Server-Database"
                           ::= {  setWlanRadiusacce 10 }

setWlanRadiusacco OBJECT IDENTIFIER ::= { setWlan 45}
setWlanRadiusaccoServeradd OBJECT-TYPE
                           SYNTAX IpAddress
                           MAX-ACCESS read-write
                           STATUS current
                           DESCRIPTION "Server-Address"
                           ::= {  setWlanRadiusacco 1 }

setWlanRadiusaccoAccntport OBJECT-TYPE
                           SYNTAX INTEGER
                           MAX-ACCESS read-write
                           STATUS current
                           DESCRIPTION "Accnt.-Port"
                           ::= {  setWlanRadiusacco 2 }

setWlanRadiusaccoSecret OBJECT-TYPE
                           SYNTAX DisplayString (SIZE(0..32))
                           MAX-ACCESS read-write
                           STATUS current
                           DESCRIPTION "Secret"
                           ::= {  setWlanRadiusacco 3 }

setWlanRadiusaccoLoopbacka OBJECT-TYPE
                           SYNTAX DisplayString (SIZE(0..16))
                           MAX-ACCESS read-write
                           STATUS current
                           DESCRIPTION "Loopback-Address"
                           ::= {  setWlanRadiusacco 10 }

setWlanRadiusaccoProtocol OBJECT-TYPE
                           SYNTAX INTEGER {
                             radius(0),
                             radsec(1)
                           }
                           MAX-ACCESS read-write
                           STATUS current
                           DESCRIPTION "Protocol"
                           ::= {  setWlanRadiusacco 12 }

setWlanRadiusaccoBackupser OBJECT-TYPE
                           SYNTAX IpAddress
                           MAX-ACCESS read-write
                           STATUS current
                           DESCRIPTION "Backup-Server-IP-Address"
                           ::= {  setWlanRadiusacco 4 }

setWlanRadiusaccoBackupacc OBJECT-TYPE
                           SYNTAX INTEGER
                           MAX-ACCESS read-write
                           STATUS current
                           DESCRIPTION "Backup-Accnt.-Port"
                           ::= {  setWlanRadiusacco 5 }

setWlanRadiusaccoBackupsec OBJECT-TYPE
                           SYNTAX DisplayString (SIZE(0..32))
                           MAX-ACCESS read-write
                           STATUS current
                           DESCRIPTION "Backup-Secret"
                           ::= {  setWlanRadiusacco 6 }

setWlanRadiusaccoBackuploo OBJECT-TYPE
                           SYNTAX DisplayString (SIZE(0..16))
                           MAX-ACCESS read-write
                           STATUS current
                           DESCRIPTION "Backup-Loopback-Address"
                           ::= {  setWlanRadiusacco 11 }

setWlanRadiusaccoBackuppro OBJECT-TYPE
                           SYNTAX INTEGER {
                             radius(0),
                             radsec(1)
                           }
                           MAX-ACCESS read-write
                           STATUS current
                           DESCRIPTION "Backup-Protocol"
                           ::= {  setWlanRadiusacco 13 }

setWlanRadiusaccoClientbrg OBJECT-TYPE
                           SYNTAX INTEGER {
                             all-traffic(0),
                             bridge-traffic-only(1),
                             client-traffic-only(2),
                             separate-accounting(3)
                           }
                           MAX-ACCESS read-write
                           STATUS current
                           DESCRIPTION "Client-Brg.-Handling"
                           ::= {  setWlanRadiusacco 7 }

setWlanRadiusaccoInterimup OBJECT-TYPE
                           SYNTAX INTEGER
                           MAX-ACCESS read-write
                           STATUS current
                           DESCRIPTION "Interim-Update-Period"
                           ::= {  setWlanRadiusacco 8 }

setWlanRadiusaccoExcludedv OBJECT-TYPE
                           SYNTAX INTEGER
                           MAX-ACCESS read-write
                           STATUS current
                           DESCRIPTION "Excluded-VLAN"
                           ::= {  setWlanRadiusacco 9 }

setWlanRadarpatteTable OBJECT-TYPE
                       SYNTAX SEQUENCE OF SetWlanRadarpatteEntry
                       MAX-ACCESS not-accessible
                       STATUS current
                       DESCRIPTION "Radar-Pattern-Thresholds"
                       ::= {  setWlan 107 }

setWlanRadarpatteEntry OBJECT-TYPE
                       SYNTAX SetWlanRadarpatteEntry
                       MAX-ACCESS not-accessible
                       STATUS current
                       DESCRIPTION "entry in table"
                       INDEX { setWlanRadarpattePat }
                       ::= {  setWlanRadarpatteTable 1 }

SetWlanRadarpatteEntry ::= SEQUENCE {
                       setWlanRadarpattePat INTEGER,
                       setWlanRadarpatteThr INTEGER
                      }

setWlanRadarpattePat OBJECT-TYPE
                     SYNTAX INTEGER (0..2147483647)
                     MAX-ACCESS read-write
                     STATUS current
                     DESCRIPTION "Pattern-pps"
                     ::= {  setWlanRadarpatteEntry 1 }

setWlanRadarpatteThr OBJECT-TYPE
                     SYNTAX INTEGER (0..2147483647)
                     MAX-ACCESS read-write
                     STATUS current
                     DESCRIPTION "Threshold"
                     ::= {  setWlanRadarpatteEntry 2 }

setWlanRadarloadt OBJECT-TYPE
                  SYNTAX INTEGER
                  MAX-ACCESS read-write
                  STATUS current
                  DESCRIPTION "Radar-Load-Threshold"
                  ::= {  setWlan 108 }

setWlanSignalaver OBJECT IDENTIFIER ::= { setWlan 50}
setWlanSignalaverMet OBJECT-TYPE
                     SYNTAX INTEGER {
                       standard(0),
                       filtered(1)
                     }
                     MAX-ACCESS read-write
                     STATUS current
                     DESCRIPTION "Method"
                     ::= {  setWlanSignalaver 1 }

setWlanSignalaverSta OBJECT IDENTIFIER ::= { setWlanSignalaver 2}
setWlanSignalaverStaFac OBJECT-TYPE
                        SYNTAX INTEGER
                        MAX-ACCESS read-write
                        STATUS current
                        DESCRIPTION "Factor"
                        ::= {  setWlanSignalaverSta 1 }

setWlanSignalaverFil OBJECT IDENTIFIER ::= { setWlanSignalaver 3}
setWlanSignalaverFilCt OBJECT-TYPE
                        SYNTAX INTEGER
                        MAX-ACCESS read-write
                        STATUS current
                        DESCRIPTION "Ct"
                        ::= {  setWlanSignalaverFil 1 }

setWlanSignalaverFilCoeTable OBJECT-TYPE
                             SYNTAX SEQUENCE OF SetWlanSignalaverFilCoeEntry
                             MAX-ACCESS not-accessible
                             STATUS current
                             DESCRIPTION "Coefficients"
                             ::= {  setWlanSignalaverFil 2 }

setWlanSignalaverFilCoeEntry OBJECT-TYPE
                             SYNTAX SetWlanSignalaverFilCoeEntry
                             MAX-ACCESS not-accessible
                             STATUS current
                             DESCRIPTION "entry in table"
                             INDEX { setWlanSignalaverFilCoeInd }
                             ::= {  setWlanSignalaverFilCoeTable 1 }

SetWlanSignalaverFilCoeEntry ::= SEQUENCE {
                             setWlanSignalaverFilCoeInd INTEGER,
                             setWlanSignalaverFilCoeVal INTEGER
                            }

setWlanSignalaverFilCoeInd OBJECT-TYPE
                           SYNTAX INTEGER (0..255)
                           MAX-ACCESS read-only
                           STATUS current
                           DESCRIPTION "Index"
                           ::= {  setWlanSignalaverFilCoeEntry 1 }

setWlanSignalaverFilCoeVal OBJECT-TYPE
                           SYNTAX INTEGER (-2147483648..2147483647)
                           MAX-ACCESS read-write
                           STATUS current
                           DESCRIPTION "Value"
                           ::= {  setWlanSignalaverFilCoeEntry 2 }

setLcr OBJECT IDENTIFIER ::= { set 15}
setLcrRou OBJECT-TYPE
          SYNTAX INTEGER {
            no(0),
            yes(1)
          }
          MAX-ACCESS read-write
          STATUS current
          DESCRIPTION "Router-Usage"
          ::= {  setLcr 1 }

setLcrTimTable OBJECT-TYPE
               SYNTAX SEQUENCE OF SetLcrTimEntry
               MAX-ACCESS not-accessible
               STATUS current
               DESCRIPTION "Time-List"
               ::= {  setLcr 4 }

setLcrTimEntry OBJECT-TYPE
               SYNTAX SetLcrTimEntry
               MAX-ACCESS not-accessible
               STATUS current
               DESCRIPTION "entry in table"
               INDEX { setLcrTimInd }
               ::= {  setLcrTimTable 1 }

SetLcrTimEntry ::= SEQUENCE {
               setLcrTimInd INTEGER,
               setLcrTimPre DisplayString,
               setLcrTimDay BITS,
               setLcrTimSta DisplayString,
               setLcrTimSto DisplayString,
               setLcrTimNum DisplayString,
               setLcrTimFal INTEGER
              }

setLcrTimInd OBJECT-TYPE
             SYNTAX INTEGER (0..65535)
             MAX-ACCESS read-write
             STATUS current
             DESCRIPTION "Index"
             ::= {  setLcrTimEntry 1 }

setLcrTimPre OBJECT-TYPE
             SYNTAX DisplayString (SIZE(0..5))
             MAX-ACCESS read-write
             STATUS current
             DESCRIPTION "Prefix"
             ::= {  setLcrTimEntry 2 }

setLcrTimDay OBJECT-TYPE
             SYNTAX BITS{
               monday(1),
               tuesday(2),
               wednesday(4),
               thursday(8),
               friday(16),
               saturday(32),
               sunday(64),
               holiday(128)
             }
             MAX-ACCESS read-write
             STATUS current
             DESCRIPTION "Days"
             ::= {  setLcrTimEntry 3 }

setLcrTimSta OBJECT-TYPE
             SYNTAX DisplayString (SIZE(0..5))
             MAX-ACCESS read-write
             STATUS current
             DESCRIPTION "Start"
             ::= {  setLcrTimEntry 4 }

setLcrTimSto OBJECT-TYPE
             SYNTAX DisplayString (SIZE(0..5))
             MAX-ACCESS read-write
             STATUS current
             DESCRIPTION "Stop"
             ::= {  setLcrTimEntry 5 }

setLcrTimNum OBJECT-TYPE
             SYNTAX DisplayString (SIZE(0..29))
             MAX-ACCESS read-write
             STATUS current
             DESCRIPTION "Number-List"
             ::= {  setLcrTimEntry 6 }

setLcrTimFal OBJECT-TYPE
             SYNTAX INTEGER{
               no(0),
               yes(1)
             }
             MAX-ACCESS read-write
             STATUS current
             DESCRIPTION "Fallback"
             ::= {  setLcrTimEntry 7 }

setLcrHolTable OBJECT-TYPE
               SYNTAX SEQUENCE OF SetLcrHolEntry
               MAX-ACCESS not-accessible
               STATUS current
               DESCRIPTION "Holidays"
               ::= {  setLcr 5 }

setLcrHolEntry OBJECT-TYPE
               SYNTAX SetLcrHolEntry
               MAX-ACCESS not-accessible
               STATUS current
               DESCRIPTION "entry in table"
               INDEX { setLcrHolInd }
               ::= {  setLcrHolTable 1 }

SetLcrHolEntry ::= SEQUENCE {
               setLcrHolInd INTEGER,
               setLcrHolDat DisplayString
              }

setLcrHolInd OBJECT-TYPE
             SYNTAX INTEGER (0..65535)
             MAX-ACCESS read-write
             STATUS current
             DESCRIPTION "Index"
             ::= {  setLcrHolEntry 1 }

setLcrHolDat OBJECT-TYPE
             SYNTAX DisplayString (SIZE(0..13))
             MAX-ACCESS read-write
             STATUS current
             DESCRIPTION "Date"
             ::= {  setLcrHolEntry 2 }

setTime OBJECT IDENTIFIER ::= { set 14}
setTimeFet OBJECT-TYPE
           SYNTAX INTEGER {
             none(0),
             ntp(2)
           }
           MAX-ACCESS read-write
           STATUS current
           DESCRIPTION "Fetch-Method"
           ::= {  setTime 1 }

setTimeCur OBJECT-TYPE
           SYNTAX DisplayString
           MAX-ACCESS read-only
           STATUS current
           DESCRIPTION "Current-Time"
           ::= {  setTime 2 }

setTimeUtc OBJECT-TYPE
           SYNTAX INTEGER
           MAX-ACCESS read-only
           STATUS current
           DESCRIPTION "UTC-in-Seconds"
           ::= {  setTime 7 }

setTimeTim OBJECT-TYPE
           SYNTAX INTEGER {
             e0(0),
             plus-1(1),
             plus-2(2),
             plus-3(3),
             plus-4(4),
             plus-5(5),
             plus-6(6),
             plus-7(7),
             plus-8(8),
             plus-9(9),
             plus-10(10),
             plus-11(11),
             plus-12(12),
             plus-13(13),
             plus-14(14),
             minus-1(255),
             minus-2(254),
             minus-3(253),
             minus-4(252),
             minus-5(251),
             minus-6(250),
             minus-7(249),
             minus-8(248),
             minus-9(247),
             minus-10(246),
             minus-11(245),
             minus-12(244)
           }
           MAX-ACCESS read-write
           STATUS current
           DESCRIPTION "Timezone"
           ::= {  setTime 10 }

setTimeDay OBJECT-TYPE
           SYNTAX INTEGER {
             no(0),
             yes(1),
             europe-eu(2),
             russia(3),
             usa(4),
             user-defined(255)
           }
           MAX-ACCESS read-write
           STATUS current
           DESCRIPTION "Daylight-saving-time"
           ::= {  setTime 11 }

setTimeDstTable OBJECT-TYPE
                SYNTAX SEQUENCE OF SetTimeDstEntry
                MAX-ACCESS not-accessible
                STATUS current
                DESCRIPTION "DST-clock-changes"
                ::= {  setTime 12 }

setTimeDstEntry OBJECT-TYPE
                SYNTAX SetTimeDstEntry
                MAX-ACCESS not-accessible
                STATUS current
                DESCRIPTION "entry in table"
                INDEX { setTimeDstEve }
                ::= {  setTimeDstTable 1 }

SetTimeDstEntry ::= SEQUENCE {
                setTimeDstEve INTEGER,
                setTimeDstInd INTEGER,
                setTimeDstDay INTEGER,
                setTimeDstMon INTEGER,
                setTimeDstHou INTEGER,
                setTimeDstMin INTEGER,
                setTimeDstTim INTEGER
               }

setTimeDstEve OBJECT-TYPE
              SYNTAX INTEGER{
                start(1),
                end(2)
              }
              MAX-ACCESS read-only
              STATUS current
              DESCRIPTION "Event"
              ::= {  setTimeDstEntry 1 }

setTimeDstInd OBJECT-TYPE
              SYNTAX INTEGER{
                e4-last(252),
                e3-last(253),
                e2-last(254),
                last(255),
                first(1),
                second(2),
                third(3),
                fourth(4)
              }
              MAX-ACCESS read-write
              STATUS current
              DESCRIPTION "Index"
              ::= {  setTimeDstEntry 2 }

setTimeDstDay OBJECT-TYPE
              SYNTAX INTEGER{
                monday(1),
                tuesday(2),
                wednesday(3),
                thursday(4),
                friday(5),
                saturday(6),
                sunday(0)
              }
              MAX-ACCESS read-write
              STATUS current
              DESCRIPTION "Day"
              ::= {  setTimeDstEntry 3 }

setTimeDstMon OBJECT-TYPE
              SYNTAX INTEGER{
                january(1),
                february(2),
                march(3),
                april(4),
                may(5),
                june(6),
                july(7),
                august(8),
                september(9),
                october(10),
                november(11),
                december(12)
              }
              MAX-ACCESS read-write
              STATUS current
              DESCRIPTION "Month"
              ::= {  setTimeDstEntry 4 }

setTimeDstHou OBJECT-TYPE
              SYNTAX INTEGER (0..255)
              MAX-ACCESS read-write
              STATUS current
              DESCRIPTION "Hour"
              ::= {  setTimeDstEntry 5 }

setTimeDstMin OBJECT-TYPE
              SYNTAX INTEGER (0..255)
              MAX-ACCESS read-write
              STATUS current
              DESCRIPTION "Minute"
              ::= {  setTimeDstEntry 6 }

setTimeDstTim OBJECT-TYPE
              SYNTAX INTEGER{
                utc(1),
                lst(0)
              }
              MAX-ACCESS read-write
              STATUS current
              DESCRIPTION "Time-type"
              ::= {  setTimeDstEntry 7 }

setTimeGet OBJECT-TYPE
           SYNTAX DisplayString
           MAX-ACCESS read-write
           STATUS current
           DESCRIPTION "Get-Time"
           ::= {  setTime 13 }

setInter OBJECT IDENTIFIER ::= { set 23}
setInterMod OBJECT IDENTIFIER ::= { setInter 40}
setInterModRingcou OBJECT-TYPE
                   SYNTAX INTEGER
                   MAX-ACCESS read-write
                   STATUS current
                   DESCRIPTION "Ring-Count"
                   ::= {  setInterMod 1 }

setInterModEchooff OBJECT-TYPE
                   SYNTAX DisplayString (SIZE(0..9))
                   MAX-ACCESS read-write
                   STATUS current
                   DESCRIPTION "Echo-Off-Command"
                   ::= {  setInterMod 2 }

setInterModResetco OBJECT-TYPE
                   SYNTAX DisplayString (SIZE(0..9))
                   MAX-ACCESS read-write
                   STATUS current
                   DESCRIPTION "Reset-Command"
                   ::= {  setInterMod 3 }

setInterModInitcom OBJECT-TYPE
                   SYNTAX DisplayString (SIZE(0..63))
                   MAX-ACCESS read-write
                   STATUS current
                   DESCRIPTION "Init-Command"
                   ::= {  setInterMod 4 }

setInterModRequest OBJECT-TYPE
                   SYNTAX DisplayString (SIZE(0..9))
                   MAX-ACCESS read-write
                   STATUS current
                   DESCRIPTION "Request-ID"
                   ::= {  setInterMod 6 }

setInterModInitdia OBJECT-TYPE
                   SYNTAX DisplayString (SIZE(0..63))
                   MAX-ACCESS read-write
                   STATUS current
                   DESCRIPTION "Init.-Dial"
                   ::= {  setInterMod 11 }

setInterModDialcom OBJECT-TYPE
                   SYNTAX DisplayString (SIZE(0..31))
                   MAX-ACCESS read-write
                   STATUS current
                   DESCRIPTION "Dial-Command"
                   ::= {  setInterMod 5 }

setInterModInitans OBJECT-TYPE
                   SYNTAX DisplayString (SIZE(0..63))
                   MAX-ACCESS read-write
                   STATUS current
                   DESCRIPTION "Init.-Answer"
                   ::= {  setInterMod 12 }

setInterModAnswerc OBJECT-TYPE
                   SYNTAX DisplayString (SIZE(0..9))
                   MAX-ACCESS read-write
                   STATUS current
                   DESCRIPTION "Answer-Command"
                   ::= {  setInterMod 7 }

setInterModDisconn OBJECT-TYPE
                   SYNTAX DisplayString (SIZE(0..9))
                   MAX-ACCESS read-write
                   STATUS current
                   DESCRIPTION "Disconnect-Command"
                   ::= {  setInterMod 8 }

setInterModEscapes OBJECT-TYPE
                   SYNTAX DisplayString (SIZE(0..9))
                   MAX-ACCESS read-write
                   STATUS current
                   DESCRIPTION "Escape-Sequence"
                   ::= {  setInterMod 9 }

setInterModEscapep OBJECT-TYPE
                   SYNTAX INTEGER
                   MAX-ACCESS read-write
                   STATUS current
                   DESCRIPTION "Escape-Promt-Delay-(ms)"
                   ::= {  setInterMod 10 }

setInterModCycleti OBJECT-TYPE
                   SYNTAX INTEGER
                   MAX-ACCESS read-write
                   STATUS current
                   DESCRIPTION "Cycletime-AT-Poll-(s)"
                   ::= {  setInterMod 13 }

setInterModAtpollc OBJECT-TYPE
                   SYNTAX INTEGER
                   MAX-ACCESS read-write
                   STATUS current
                   DESCRIPTION "AT-Poll-Count"
                   ::= {  setInterMod 14 }

setInterWla OBJECT IDENTIFIER ::= { setInter 20}
setInterWlaOperationalTable OBJECT-TYPE
                            SYNTAX SEQUENCE OF SetInterWlaOperationalEntry
                            MAX-ACCESS not-accessible
                            STATUS current
                            DESCRIPTION "Operational"
                            ::= {  setInterWla 7 }

setInterWlaOperationalEntry OBJECT-TYPE
                            SYNTAX SetInterWlaOperationalEntry
                            MAX-ACCESS not-accessible
                            STATUS current
                            DESCRIPTION "entry in table"
                            INDEX { setInterWlaOperationalIfc }
                            ::= {  setInterWlaOperationalTable 1 }

SetInterWlaOperationalEntry ::= SEQUENCE {
                            setInterWlaOperationalIfc INTEGER,
                            setInterWlaOperationalOperatin INTEGER,
                            setInterWlaOperationalOperatio INTEGER,
                            setInterWlaOperationalLinkledf INTEGER
                           }

setInterWlaOperationalIfc OBJECT-TYPE
                               SYNTAX INTEGER{
                                 wlan-1(1)
                               }
                               MAX-ACCESS read-write
                               STATUS current
                               DESCRIPTION "Ifc"
                               ::= {  setInterWlaOperationalEntry 1 }

setInterWlaOperationalOperatin OBJECT-TYPE
                               SYNTAX INTEGER{
                                 yes(0),
                                 no(1)
                               }
                               MAX-ACCESS read-write
                               STATUS current
                               DESCRIPTION "Operating"
                               ::= {  setInterWlaOperationalEntry 2 }

setInterWlaOperationalOperatio OBJECT-TYPE
                               SYNTAX INTEGER{
                                 access-point(1),
                                 managed-ap(4),
                                 station(0)
                               }
                               MAX-ACCESS read-write
                               STATUS current
                               DESCRIPTION "Operation-Mode"
                               ::= {  setInterWlaOperationalEntry 3 }

setInterWlaOperationalLinkledf OBJECT-TYPE
                               SYNTAX INTEGER{
                                 normal(0),
                                 client-mode-strength(1),
                                 p2p-1-strength(8),
                                 p2p-2-strength(9),
                                 p2p-3-strength(10),
                                 p2p-4-strength(11),
                                 p2p-5-strength(12),
                                 p2p-6-strength(13)
                               }
                               MAX-ACCESS read-write
                               STATUS current
                               DESCRIPTION "Link-LED-Function"
                               ::= {  setInterWlaOperationalEntry 4 }

setInterWlaNetworkTable OBJECT-TYPE
                            SYNTAX SEQUENCE OF SetInterWlaNetworkEntry
                            MAX-ACCESS not-accessible
                            STATUS current
                            DESCRIPTION "Network"
                            ::= {  setInterWla 1 }

setInterWlaNetworkEntry OBJECT-TYPE
                            SYNTAX SetInterWlaNetworkEntry
                            MAX-ACCESS not-accessible
                            STATUS current
                            DESCRIPTION "entry in table"
                            INDEX { setInterWlaNetworkIfc }
                            ::= {  setInterWlaNetworkTable 1 }

SetInterWlaNetworkEntry ::= SEQUENCE {
                            setInterWlaNetworkIfc INTEGER,
                            setInterWlaNetworkOpe INTEGER,
                            setInterWlaNetworkNet DisplayString,
                            setInterWlaNetworkMac INTEGER,
                            setInterWlaNetworkRad INTEGER,
                            setInterWlaNetworkClo INTEGER,
                            setInterWlaNetworkMax INTEGER,
                            setInterWlaNetworkClb INTEGER
                           }

setInterWlaNetworkIfc OBJECT-TYPE
                      SYNTAX INTEGER{
                        wlan-1(1),
                        wlan-1-2(16),
                        wlan-1-3(17),
                        wlan-1-4(18),
                        wlan-1-5(19),
                        wlan-1-6(20),
                        wlan-1-7(21),
                        wlan-1-8(22)
                      }
                      MAX-ACCESS read-write
                      STATUS current
                      DESCRIPTION "Ifc"
                      ::= {  setInterWlaNetworkEntry 1 }

setInterWlaNetworkOpe OBJECT-TYPE
                      SYNTAX INTEGER{
                        yes(0),
                        no(1)
                      }
                      MAX-ACCESS read-write
                      STATUS current
                      DESCRIPTION "Operating"
                      ::= {  setInterWlaNetworkEntry 8 }

setInterWlaNetworkNet OBJECT-TYPE
                      SYNTAX DisplayString (SIZE(0..32))
                      MAX-ACCESS read-write
                      STATUS current
                      DESCRIPTION "Network-Name"
                      ::= {  setInterWlaNetworkEntry 2 }

setInterWlaNetworkMac OBJECT-TYPE
                      SYNTAX INTEGER{
                        yes(0),
                        no(1)
                      }
                      MAX-ACCESS read-write
                      STATUS current
                      DESCRIPTION "MAC-Filter"
                      ::= {  setInterWlaNetworkEntry 9 }

setInterWlaNetworkRad OBJECT-TYPE
                      SYNTAX INTEGER{
                        no(0),
                        yes(1)
                      }
                      MAX-ACCESS read-write
                      STATUS current
                      DESCRIPTION "RADIUS-Accounting"
                      ::= {  setInterWlaNetworkEntry 12 }

setInterWlaNetworkClo OBJECT-TYPE
                      SYNTAX INTEGER{
                        no(0),
                        yes(1)
                      }
                      MAX-ACCESS read-write
                      STATUS current
                      DESCRIPTION "Closed-Network"
                      ::= {  setInterWlaNetworkEntry 4 }

setInterWlaNetworkMax OBJECT-TYPE
                      SYNTAX INTEGER (0..65535)
                      MAX-ACCESS read-write
                      STATUS current
                      DESCRIPTION "Max-Stations"
                      ::= {  setInterWlaNetworkEntry 10 }

setInterWlaNetworkClb OBJECT-TYPE
                      SYNTAX INTEGER{
                        no(0),
                        yes(1),
                        exclusive(2)
                      }
                      MAX-ACCESS read-write
                      STATUS current
                      DESCRIPTION "Cl.-Brg.-Support"
                      ::= {  setInterWlaNetworkEntry 11 }

setInterWlaRadiosettinTable OBJECT-TYPE
                            SYNTAX SEQUENCE OF SetInterWlaRadiosettinEntry
                            MAX-ACCESS not-accessible
                            STATUS current
                            DESCRIPTION "Radio-Settings"
                            ::= {  setInterWla 8 }

setInterWlaRadiosettinEntry OBJECT-TYPE
                            SYNTAX SetInterWlaRadiosettinEntry
                            MAX-ACCESS not-accessible
                            STATUS current
                            DESCRIPTION "entry in table"
                            INDEX { setInterWlaRadiosettinIfc }
                            ::= {  setInterWlaRadiosettinTable 1 }

SetInterWlaRadiosettinEntry ::= SEQUENCE {
                            setInterWlaRadiosettinIfc INTEGER,
                            setInterWlaRadiosettinRadioband INTEGER,
                            setInterWlaRadiosettinSubbands INTEGER,
                            setInterWlaRadiosettinRadiochannel INTEGER,
                            setInterWlaRadiosettinChannellist DisplayString,
                            setInterWlaRadiosettin24ghzmode INTEGER,
                            setInterWlaRadiosettinAntennagain INTEGER,
                            setInterWlaRadiosettinTxpowerreductio INTEGER,
                            setInterWlaRadiosettinMaximumdistance INTEGER,
                            setInterWlaRadiosettinDiversity INTEGER,
                            setInterWlaRadiosettinApdensity INTEGER,
                            setInterWlaRadiosettinBackgroundscan INTEGER,
                            setInterWlaRadiosettinBackgroundscanu INTEGER,
                            setInterWlaRadiosettinDfsrescanhours DisplayString
                           }

setInterWlaRadiosettinIfc OBJECT-TYPE
                                      SYNTAX INTEGER{
                                        wlan-1(1)
                                      }
                                      MAX-ACCESS read-write
                                      STATUS current
                                      DESCRIPTION "Ifc"
                                      ::= {  setInterWlaRadiosettinEntry 1 }

setInterWlaRadiosettinRadioband OBJECT-TYPE
                                      SYNTAX INTEGER{
                                        e2-4ghz(1)
                                      }
                                      MAX-ACCESS read-write
                                      STATUS current
                                      DESCRIPTION "Radio-Band"
                                      ::= {  setInterWlaRadiosettinEntry 6 }

setInterWlaRadiosettinSubbands OBJECT-TYPE
                                      SYNTAX INTEGER{
                                        band-1(1),
                                        band-2(2),
                                        band-3(4),
                                        band-1-plus-2(3),
                                        band-1-plus-3(5),
                                        band-2-plus-3(6),
                                        band-1-plus-2-plus-3(7)
                                      }
                                      MAX-ACCESS read-write
                                      STATUS current
                                      DESCRIPTION "Subbands"
                                      ::= {  setInterWlaRadiosettinEntry 7 }

setInterWlaRadiosettinRadiochannel OBJECT-TYPE
                                      SYNTAX INTEGER (0..255)
                                      MAX-ACCESS read-write
                                      STATUS current
                                      DESCRIPTION "Radio-Channel"
                                      ::= {  setInterWlaRadiosettinEntry 8 }

setInterWlaRadiosettinChannellist OBJECT-TYPE
                                      SYNTAX DisplayString (SIZE(0..48))
                                      MAX-ACCESS read-write
                                      STATUS current
                                      DESCRIPTION "Channel-List"
                                      ::= {  setInterWlaRadiosettinEntry 13 }

setInterWlaRadiosettin24ghzmode OBJECT-TYPE
                                      SYNTAX INTEGER{
                                        e11bg-mixed(0),
                                        e11g-only(1),
                                        e11b-only(2),
                                        e2m-mixed(3),
                                        e108mbps(4)
                                      }
                                      MAX-ACCESS read-write
                                      STATUS current
                                      DESCRIPTION "2.4GHz-Mode"
                                      ::= {  setInterWlaRadiosettinEntry 9 }

setInterWlaRadiosettinAntennagain OBJECT-TYPE
                                      SYNTAX INTEGER (-128..127)
                                      MAX-ACCESS read-write
                                      STATUS current
                                      DESCRIPTION "Antenna-Gain"
                                      ::= {  setInterWlaRadiosettinEntry 12 }

setInterWlaRadiosettinTxpowerreductio OBJECT-TYPE
                                      SYNTAX INTEGER (0..255)
                                      MAX-ACCESS read-write
                                      STATUS current
                                      DESCRIPTION "Tx-Power-Reduction"
                                      ::= {  setInterWlaRadiosettinEntry 2 }

setInterWlaRadiosettinMaximumdistance OBJECT-TYPE
                                      SYNTAX INTEGER (0..65535)
                                      MAX-ACCESS read-write
                                      STATUS current
                                      DESCRIPTION "Maximum-Distance"
                                      ::= {  setInterWlaRadiosettinEntry 4 }

setInterWlaRadiosettinDiversity OBJECT-TYPE
                                      SYNTAX INTEGER{
                                        rx-only(0),
                                        tx-rx(1),
                                        none(2)
                                      }
                                      MAX-ACCESS read-write
                                      STATUS current
                                      DESCRIPTION "Diversity"
                                      ::= {  setInterWlaRadiosettinEntry 5 }

setInterWlaRadiosettinApdensity OBJECT-TYPE
                                      SYNTAX INTEGER{
                                        low(1),
                                        medium(2),
                                        high(3),
                                        minicell(4),
                                        microcell(5),
                                        off(0)
                                      }
                                      MAX-ACCESS read-write
                                      STATUS current
                                      DESCRIPTION "AP-Density"
                                      ::= {  setInterWlaRadiosettinEntry 10 }

setInterWlaRadiosettinBackgroundscan OBJECT-TYPE
                                      SYNTAX INTEGER (0..2147483647)
                                      MAX-ACCESS read-write
                                      STATUS current
                                      DESCRIPTION "Background-Scan"
                                      ::= {  setInterWlaRadiosettinEntry 14 }

setInterWlaRadiosettinBackgroundscanu OBJECT-TYPE
                                      SYNTAX INTEGER{
                                        seconds(0),
                                        milliseconds(1),
                                        microseconds(2),
                                        minutes(3),
                                        hours(4),
                                        days(5),
                                        weeks(6),
                                        fortnights(7)
                                      }
                                      MAX-ACCESS read-write
                                      STATUS current
                                      DESCRIPTION "Background-Scan-Unit"
                                      ::= {  setInterWlaRadiosettinEntry 18 }

setInterWlaRadiosettinDfsrescanhours OBJECT-TYPE
                                      SYNTAX DisplayString (SIZE(0..19))
                                      MAX-ACCESS read-write
                                      STATUS current
                                      DESCRIPTION "DFS-Rescan-Hours"
                                      ::= {  setInterWlaRadiosettinEntry 15 }

setInterWlaTransmissioTable OBJECT-TYPE
                            SYNTAX SEQUENCE OF SetInterWlaTransmissioEntry
                            MAX-ACCESS not-accessible
                            STATUS current
                            DESCRIPTION "Transmission"
                            ::= {  setInterWla 2 }

setInterWlaTransmissioEntry OBJECT-TYPE
                            SYNTAX SetInterWlaTransmissioEntry
                            MAX-ACCESS not-accessible
                            STATUS current
                            DESCRIPTION "entry in table"
                            INDEX { setInterWlaTransmissioIfc }
                            ::= {  setInterWlaTransmissioTable 1 }

SetInterWlaTransmissioEntry ::= SEQUENCE {
                            setInterWlaTransmissioIfc INTEGER,
                            setInterWlaTransmissioPack INTEGER,
                            setInterWlaTransmissioMint INTEGER,
                            setInterWlaTransmissioMaxt INTEGER,
                            setInterWlaTransmissioBasi INTEGER,
                            setInterWlaTransmissioHard INTEGER,
                            setInterWlaTransmissioSoft INTEGER,
                            setInterWlaTransmissio11bp INTEGER,
                            setInterWlaTransmissioRtst INTEGER,
                            setInterWlaTransmissioMinf INTEGER
                           }

setInterWlaTransmissioIfc OBJECT-TYPE
                           SYNTAX INTEGER{
                             wlan-1(1),
                             wlan-1-2(16),
                             wlan-1-3(17),
                             wlan-1-4(18),
                             wlan-1-5(19),
                             wlan-1-6(20),
                             wlan-1-7(21),
                             wlan-1-8(22)
                           }
                           MAX-ACCESS read-write
                           STATUS current
                           DESCRIPTION "Ifc"
                           ::= {  setInterWlaTransmissioEntry 1 }

setInterWlaTransmissioPack OBJECT-TYPE
                           SYNTAX INTEGER (0..65535)
                           MAX-ACCESS read-write
                           STATUS current
                           DESCRIPTION "Packet-Size"
                           ::= {  setInterWlaTransmissioEntry 2 }

setInterWlaTransmissioMint OBJECT-TYPE
                           SYNTAX INTEGER{
                             auto(0),
                             e1m(1),
                             e2m(2),
                             e5-5m(4),
                             e11m(6),
                             e6m(8),
                             e9m(9),
                             e12m(10),
                             e18m(11),
                             e24m(12),
                             e36m(13),
                             e48m(14),
                             e54m(15),
                             t-12m(20),
                             t-18m(21),
                             t-24m(22),
                             t-36m(23),
                             t-48m(24),
                             t-72m(25),
                             t-96m(26),
                             t-108m(27)
                           }
                           MAX-ACCESS read-write
                           STATUS current
                           DESCRIPTION "Min-Tx-Rate"
                           ::= {  setInterWlaTransmissioEntry 3 }

setInterWlaTransmissioMaxt OBJECT-TYPE
                           SYNTAX INTEGER{
                             auto(0),
                             e1m(1),
                             e2m(2),
                             e5-5m(4),
                             e11m(6),
                             e6m(8),
                             e9m(9),
                             e12m(10),
                             e18m(11),
                             e24m(12),
                             e36m(13),
                             e48m(14),
                             e54m(15),
                             t-12m(20),
                             t-18m(21),
                             t-24m(22),
                             t-36m(23),
                             t-48m(24),
                             t-72m(25),
                             t-96m(26),
                             t-108m(27)
                           }
                           MAX-ACCESS read-write
                           STATUS current
                           DESCRIPTION "Max-Tx-Rate"
                           ::= {  setInterWlaTransmissioEntry 9 }

setInterWlaTransmissioBasi OBJECT-TYPE
                           SYNTAX INTEGER{
                             e1m(1),
                             e2m(2),
                             e5-5m(4),
                             e11m(6),
                             e6m(8),
                             e9m(9),
                             e12m(10),
                             e18m(11),
                             e24m(12),
                             e36m(13),
                             e48m(14),
                             e54m(15),
                             t-12m(20),
                             t-18m(21),
                             t-24m(22),
                             t-36m(23),
                             t-48m(24),
                             t-72m(25),
                             t-96m(26),
                             t-108m(27)
                           }
                           MAX-ACCESS read-write
                           STATUS current
                           DESCRIPTION "Basic-Rate"
                           ::= {  setInterWlaTransmissioEntry 4 }

setInterWlaTransmissioHard OBJECT-TYPE
                           SYNTAX INTEGER (0..255)
                           MAX-ACCESS read-write
                           STATUS current
                           DESCRIPTION "Hard-Retries"
                           ::= {  setInterWlaTransmissioEntry 12 }

setInterWlaTransmissioSoft OBJECT-TYPE
                           SYNTAX INTEGER (0..255)
                           MAX-ACCESS read-write
                           STATUS current
                           DESCRIPTION "Soft-Retries"
                           ::= {  setInterWlaTransmissioEntry 11 }

setInterWlaTransmissio11bp OBJECT-TYPE
                           SYNTAX INTEGER{
                             auto(0),
                             long(1)
                           }
                           MAX-ACCESS read-write
                           STATUS current
                           DESCRIPTION "11b-Preamble"
                           ::= {  setInterWlaTransmissioEntry 7 }

setInterWlaTransmissioRtst OBJECT-TYPE
                           SYNTAX INTEGER (0..65535)
                           MAX-ACCESS read-write
                           STATUS current
                           DESCRIPTION "RTS-Threshold"
                           ::= {  setInterWlaTransmissioEntry 6 }

setInterWlaTransmissioMinf OBJECT-TYPE
                           SYNTAX INTEGER (0..65535)
                           MAX-ACCESS read-write
                           STATUS current
                           DESCRIPTION "Min-Frag-Len"
                           ::= {  setInterWlaTransmissioEntry 10 }

setInterWlaPerformanceTable OBJECT-TYPE
                            SYNTAX SEQUENCE OF SetInterWlaPerformanceEntry
                            MAX-ACCESS not-accessible
                            STATUS current
                            DESCRIPTION "Performance"
                            ::= {  setInterWla 9 }

setInterWlaPerformanceEntry OBJECT-TYPE
                            SYNTAX SetInterWlaPerformanceEntry
                            MAX-ACCESS not-accessible
                            STATUS current
                            DESCRIPTION "entry in table"
                            INDEX { setInterWlaPerformanceIfc }
                            ::= {  setInterWlaPerformanceTable 1 }

SetInterWlaPerformanceEntry ::= SEQUENCE {
                            setInterWlaPerformanceIfc INTEGER,
                            setInterWlaPerformanceQos INTEGER,
                            setInterWlaPerformanceTxb INTEGER,
                            setInterWlaPerformanceCom INTEGER
                           }

setInterWlaPerformanceIfc OBJECT-TYPE
                          SYNTAX INTEGER{
                            wlan-1(1)
                          }
                          MAX-ACCESS read-write
                          STATUS current
                          DESCRIPTION "Ifc"
                          ::= {  setInterWlaPerformanceEntry 1 }

setInterWlaPerformanceQos OBJECT-TYPE
                          SYNTAX INTEGER{
                            no(0),
                            yes(1)
                          }
                          MAX-ACCESS read-write
                          STATUS current
                          DESCRIPTION "QoS"
                          ::= {  setInterWlaPerformanceEntry 5 }

setInterWlaPerformanceTxb OBJECT-TYPE
                          SYNTAX INTEGER (0..65535)
                          MAX-ACCESS read-write
                          STATUS current
                          DESCRIPTION "Tx-Bursting"
                          ::= {  setInterWlaPerformanceEntry 2 }

setInterWlaPerformanceCom OBJECT-TYPE
                          SYNTAX INTEGER{
                            no(0),
                            yes(1)
                          }
                          MAX-ACCESS read-write
                          STATUS current
                          DESCRIPTION "Compression"
                          ::= {  setInterWlaPerformanceEntry 3 }

setInterWlaEncryptionTable OBJECT-TYPE
                            SYNTAX SEQUENCE OF SetInterWlaEncryptionEntry
                            MAX-ACCESS not-accessible
                            STATUS current
                            DESCRIPTION "Encryption"
                            ::= {  setInterWla 3 }

setInterWlaEncryptionEntry OBJECT-TYPE
                            SYNTAX SetInterWlaEncryptionEntry
                            MAX-ACCESS not-accessible
                            STATUS current
                            DESCRIPTION "entry in table"
                            INDEX { setInterWlaEncryptionIfc }
                            ::= {  setInterWlaEncryptionTable 1 }

SetInterWlaEncryptionEntry ::= SEQUENCE {
                            setInterWlaEncryptionIfc INTEGER,
                            setInterWlaEncryptionEncr INTEGER,
                            setInterWlaEncryptionDefa INTEGER,
                            setInterWlaEncryptionMeth INTEGER,
                            setInterWlaEncryptionKey DisplayString,
                            setInterWlaEncryptionWpav INTEGER,
                            setInterWlaEncryptionWpa1 INTEGER,
                            setInterWlaEncryptionWpa2 INTEGER,
                            setInterWlaEncryptionWpar INTEGER,
                            setInterWlaEncryptionClie INTEGER,
                            setInterWlaEncryptionAuth INTEGER
                           }

setInterWlaEncryptionIfc OBJECT-TYPE
                          SYNTAX INTEGER{
                            wlan-1(1),
                            wlan-1-2(16),
                            wlan-1-3(17),
                            wlan-1-4(18),
                            wlan-1-5(19),
                            wlan-1-6(20),
                            wlan-1-7(21),
                            wlan-1-8(22)
                          }
                          MAX-ACCESS read-write
                          STATUS current
                          DESCRIPTION "Ifc"
                          ::= {  setInterWlaEncryptionEntry 1 }

setInterWlaEncryptionEncr OBJECT-TYPE
                          SYNTAX INTEGER{
                            no(0),
                            yes(2)
                          }
                          MAX-ACCESS read-write
                          STATUS current
                          DESCRIPTION "Encryption"
                          ::= {  setInterWlaEncryptionEntry 2 }

setInterWlaEncryptionDefa OBJECT-TYPE
                          SYNTAX INTEGER (0..255)
                          MAX-ACCESS read-write
                          STATUS current
                          DESCRIPTION "Default-Key"
                          ::= {  setInterWlaEncryptionEntry 3 }

setInterWlaEncryptionMeth OBJECT-TYPE
                          SYNTAX INTEGER{
                            e802-11i-wpa-psk(32),
                            wep-128-bits(16),
                            wep-104-bits(13),
                            wep-40-bits(5),
                            e802-11i-wpa-802-1x(33),
                            wep-128-bits-802-1x(36),
                            wep-104-bits-802-1x(35),
                            wep-40-bits-802-1x(34)
                          }
                          MAX-ACCESS read-write
                          STATUS current
                          DESCRIPTION "Method"
                          ::= {  setInterWlaEncryptionEntry 4 }

setInterWlaEncryptionKey OBJECT-TYPE
                          SYNTAX DisplayString (SIZE(0..63))
                          MAX-ACCESS read-write
                          STATUS current
                          DESCRIPTION "Key"
                          ::= {  setInterWlaEncryptionEntry 6 }

setInterWlaEncryptionWpav OBJECT-TYPE
                          SYNTAX INTEGER{
                            wpa1(2),
                            wpa2(4),
                            wpa1-2(6)
                          }
                          MAX-ACCESS read-write
                          STATUS current
                          DESCRIPTION "WPA-Version"
                          ::= {  setInterWlaEncryptionEntry 9 }

setInterWlaEncryptionWpa1 OBJECT-TYPE
                          SYNTAX INTEGER{
                            tkip(1),
                            aes(2),
                            tkip-aes(3)
                          }
                          MAX-ACCESS read-write
                          STATUS current
                          DESCRIPTION "WPA1-Session-Keytypes"
                          ::= {  setInterWlaEncryptionEntry 12 }

setInterWlaEncryptionWpa2 OBJECT-TYPE
                          SYNTAX INTEGER{
                            tkip(1),
                            aes(2),
                            tkip-aes(3)
                          }
                          MAX-ACCESS read-write
                          STATUS current
                          DESCRIPTION "WPA2-Session-Keytypes"
                          ::= {  setInterWlaEncryptionEntry 13 }

setInterWlaEncryptionWpar OBJECT-TYPE
                          SYNTAX INTEGER (0..2147483647)
                          MAX-ACCESS read-write
                          STATUS current
                          DESCRIPTION "WPA-Rekeying-Cycle"
                          ::= {  setInterWlaEncryptionEntry 11 }

setInterWlaEncryptionClie OBJECT-TYPE
                          SYNTAX INTEGER{
                            tls(3328),
                            ttls-pap(5383),
                            ttls-chap(5384),
                            ttls-mschap(5567),
                            ttls-mschapv2(5402),
                            ttls-md5(5380),
                            peap-mschapv2(6426),
                            peap-gtc(6406)
                          }
                          MAX-ACCESS read-write
                          STATUS current
                          DESCRIPTION "Client-EAP-Method"
                          ::= {  setInterWlaEncryptionEntry 10 }

setInterWlaEncryptionAuth OBJECT-TYPE
                          SYNTAX INTEGER{
                            open-system(0),
                            shared-key(1)
                          }
                          MAX-ACCESS read-write
                          STATUS current
                          DESCRIPTION "Authentication"
                          ::= {  setInterWlaEncryptionEntry 5 }

setInterWlaGroupencrypTable OBJECT-TYPE
                            SYNTAX SEQUENCE OF SetInterWlaGroupencrypEntry
                            MAX-ACCESS not-accessible
                            STATUS current
                            DESCRIPTION "Group-Encryption-Keys"
                            ::= {  setInterWla 4 }

setInterWlaGroupencrypEntry OBJECT-TYPE
                            SYNTAX SetInterWlaGroupencrypEntry
                            MAX-ACCESS not-accessible
                            STATUS current
                            DESCRIPTION "entry in table"
                            INDEX { setInterWlaGroupencrypIfc }
                            ::= {  setInterWlaGroupencrypTable 1 }

SetInterWlaGroupencrypEntry ::= SEQUENCE {
                            setInterWlaGroupencrypIfc INTEGER,
                            setInterWlaGroupencrypKeytype2 INTEGER,
                            setInterWlaGroupencrypKey2 DisplayString,
                            setInterWlaGroupencrypKeytype3 INTEGER,
                            setInterWlaGroupencrypKey3 DisplayString,
                            setInterWlaGroupencrypKeytype4 INTEGER,
                            setInterWlaGroupencrypKey4 DisplayString
                           }

setInterWlaGroupencrypIfc OBJECT-TYPE
                               SYNTAX INTEGER{
                                 wlan-1(1)
                               }
                               MAX-ACCESS read-write
                               STATUS current
                               DESCRIPTION "Ifc"
                               ::= {  setInterWlaGroupencrypEntry 1 }

setInterWlaGroupencrypKeytype2 OBJECT-TYPE
                               SYNTAX INTEGER{
                                 wep-40-bits(5),
                                 wep-104-bits(13),
                                 wep-128-bits(16)
                               }
                               MAX-ACCESS read-write
                               STATUS current
                               DESCRIPTION "Keytype-2"
                               ::= {  setInterWlaGroupencrypEntry 7 }

setInterWlaGroupencrypKey2 OBJECT-TYPE
                               SYNTAX DisplayString (SIZE(0..63))
                               MAX-ACCESS read-write
                               STATUS current
                               DESCRIPTION "Key-2"
                               ::= {  setInterWlaGroupencrypEntry 3 }

setInterWlaGroupencrypKeytype3 OBJECT-TYPE
                               SYNTAX INTEGER{
                                 wep-40-bits(5),
                                 wep-104-bits(13),
                                 wep-128-bits(16)
                               }
                               MAX-ACCESS read-write
                               STATUS current
                               DESCRIPTION "Keytype-3"
                               ::= {  setInterWlaGroupencrypEntry 8 }

setInterWlaGroupencrypKey3 OBJECT-TYPE
                               SYNTAX DisplayString (SIZE(0..63))
                               MAX-ACCESS read-write
                               STATUS current
                               DESCRIPTION "Key-3"
                               ::= {  setInterWlaGroupencrypEntry 4 }

setInterWlaGroupencrypKeytype4 OBJECT-TYPE
                               SYNTAX INTEGER{
                                 wep-40-bits(5),
                                 wep-104-bits(13),
                                 wep-128-bits(16)
                               }
                               MAX-ACCESS read-write
                               STATUS current
                               DESCRIPTION "Keytype-4"
                               ::= {  setInterWlaGroupencrypEntry 9 }

setInterWlaGroupencrypKey4 OBJECT-TYPE
                               SYNTAX DisplayString (SIZE(0..63))
                               MAX-ACCESS read-write
                               STATUS current
                               DESCRIPTION "Key-4"
                               ::= {  setInterWlaGroupencrypEntry 5 }

setInterWlaInterpointsTable OBJECT-TYPE
                            SYNTAX SEQUENCE OF SetInterWlaInterpointsEntry
                            MAX-ACCESS not-accessible
                            STATUS current
                            DESCRIPTION "Interpoint-Settings"
                            ::= {  setInterWla 5 }

setInterWlaInterpointsEntry OBJECT-TYPE
                            SYNTAX SetInterWlaInterpointsEntry
                            MAX-ACCESS not-accessible
                            STATUS current
                            DESCRIPTION "entry in table"
                            INDEX { setInterWlaInterpointsIfc }
                            ::= {  setInterWlaInterpointsTable 1 }

SetInterWlaInterpointsEntry ::= SEQUENCE {
                            setInterWlaInterpointsIfc INTEGER,
                            setInterWlaInterpointsEna INTEGER,
                            setInterWlaInterpointsLoc DisplayString,
                            setInterWlaInterpointsIso INTEGER,
                            setInterWlaInterpointsCha INTEGER,
                            setInterWlaInterpointsKey INTEGER,
                            setInterWlaInterpointsLin INTEGER
                           }

setInterWlaInterpointsIfc OBJECT-TYPE
                          SYNTAX INTEGER{
                            wlan-1(1)
                          }
                          MAX-ACCESS read-write
                          STATUS current
                          DESCRIPTION "Ifc"
                          ::= {  setInterWlaInterpointsEntry 1 }

setInterWlaInterpointsEna OBJECT-TYPE
                          SYNTAX INTEGER{
                            no(0),
                            yes(1),
                            exclusive(2)
                          }
                          MAX-ACCESS read-write
                          STATUS current
                          DESCRIPTION "Enable"
                          ::= {  setInterWlaInterpointsEntry 2 }

setInterWlaInterpointsLoc OBJECT-TYPE
                          SYNTAX DisplayString (SIZE(0..16))
                          MAX-ACCESS read-write
                          STATUS current
                          DESCRIPTION "Local-Name"
                          ::= {  setInterWlaInterpointsEntry 13 }

setInterWlaInterpointsIso OBJECT-TYPE
                          SYNTAX INTEGER{
                            no(0),
                            yes(1)
                          }
                          MAX-ACCESS read-write
                          STATUS current
                          DESCRIPTION "Isolated-Mode"
                          ::= {  setInterWlaInterpointsEntry 9 }

setInterWlaInterpointsCha OBJECT-TYPE
                          SYNTAX INTEGER{
                            master(0),
                            slave(1)
                          }
                          MAX-ACCESS read-write
                          STATUS current
                          DESCRIPTION "Channel-Selection-Scheme"
                          ::= {  setInterWlaInterpointsEntry 10 }

setInterWlaInterpointsKey OBJECT-TYPE
                          SYNTAX INTEGER{
                            default(0),
                            auto(3)
                          }
                          MAX-ACCESS read-write
                          STATUS current
                          DESCRIPTION "Key-Handshake-Role"
                          ::= {  setInterWlaInterpointsEntry 12 }

setInterWlaInterpointsLin OBJECT-TYPE
                          SYNTAX INTEGER (0..2147483647)
                          MAX-ACCESS read-write
                          STATUS current
                          DESCRIPTION "Link-Loss-Timeout"
                          ::= {  setInterWlaInterpointsEntry 11 }

setInterWlaInterpointpTable OBJECT-TYPE
                            SYNTAX SEQUENCE OF SetInterWlaInterpointpEntry
                            MAX-ACCESS not-accessible
                            STATUS current
                            DESCRIPTION "Interpoint-Peers"
                            ::= {  setInterWla 12 }

setInterWlaInterpointpEntry OBJECT-TYPE
                            SYNTAX SetInterWlaInterpointpEntry
                            MAX-ACCESS not-accessible
                            STATUS current
                            DESCRIPTION "entry in table"
                            INDEX { setInterWlaInterpointpIfc }
                            ::= {  setInterWlaInterpointpTable 1 }

SetInterWlaInterpointpEntry ::= SEQUENCE {
                            setInterWlaInterpointpIfc INTEGER,
                            setInterWlaInterpointpOpe INTEGER,
                            setInterWlaInterpointpRec INTEGER,
                            setInterWlaInterpointpMac MacAddress,
                            setInterWlaInterpointpPee DisplayString
                           }

setInterWlaInterpointpIfc OBJECT-TYPE
                          SYNTAX INTEGER{
                            p2p-1-1(1),
                            p2p-1-2(2),
                            p2p-1-3(3),
                            p2p-1-4(4),
                            p2p-1-5(5),
                            p2p-1-6(6)
                          }
                          MAX-ACCESS read-write
                          STATUS current
                          DESCRIPTION "Ifc"
                          ::= {  setInterWlaInterpointpEntry 1 }

setInterWlaInterpointpOpe OBJECT-TYPE
                          SYNTAX INTEGER{
                            no(0),
                            yes(1)
                          }
                          MAX-ACCESS read-write
                          STATUS current
                          DESCRIPTION "Operating"
                          ::= {  setInterWlaInterpointpEntry 5 }

setInterWlaInterpointpRec OBJECT-TYPE
                          SYNTAX INTEGER{
                            mac-address(0),
                            name(1)
                          }
                          MAX-ACCESS read-write
                          STATUS current
                          DESCRIPTION "Recognize-By"
                          ::= {  setInterWlaInterpointpEntry 2 }

setInterWlaInterpointpMac OBJECT-TYPE
                          SYNTAX MacAddress
                          MAX-ACCESS read-write
                          STATUS current
                          DESCRIPTION "MAC-Address"
                          ::= {  setInterWlaInterpointpEntry 3 }

setInterWlaInterpointpPee OBJECT-TYPE
                          SYNTAX DisplayString (SIZE(0..16))
                          MAX-ACCESS read-write
                          STATUS current
                          DESCRIPTION "Peer-Name"
                          ::= {  setInterWlaInterpointpEntry 4 }

setInterWlaBeaconingTable OBJECT-TYPE
                            SYNTAX SEQUENCE OF SetInterWlaBeaconingEntry
                            MAX-ACCESS not-accessible
                            STATUS current
                            DESCRIPTION "Beaconing"
                            ::= {  setInterWla 10 }

setInterWlaBeaconingEntry OBJECT-TYPE
                            SYNTAX SetInterWlaBeaconingEntry
                            MAX-ACCESS not-accessible
                            STATUS current
                            DESCRIPTION "entry in table"
                            INDEX { setInterWlaBeaconingIfc }
                            ::= {  setInterWlaBeaconingTable 1 }

SetInterWlaBeaconingEntry ::= SEQUENCE {
                            setInterWlaBeaconingIfc INTEGER,
                            setInterWlaBeaconingBeaconp INTEGER,
                            setInterWlaBeaconingDtimper INTEGER,
                            setInterWlaBeaconingBeacono INTEGER
                           }

setInterWlaBeaconingIfc OBJECT-TYPE
                            SYNTAX INTEGER{
                              wlan-1(1)
                            }
                            MAX-ACCESS read-write
                            STATUS current
                            DESCRIPTION "Ifc"
                            ::= {  setInterWlaBeaconingEntry 1 }

setInterWlaBeaconingBeaconp OBJECT-TYPE
                            SYNTAX INTEGER (0..65535)
                            MAX-ACCESS read-write
                            STATUS current
                            DESCRIPTION "Beacon-Period"
                            ::= {  setInterWlaBeaconingEntry 2 }

setInterWlaBeaconingDtimper OBJECT-TYPE
                            SYNTAX INTEGER (0..255)
                            MAX-ACCESS read-write
                            STATUS current
                            DESCRIPTION "DTIM-Period"
                            ::= {  setInterWlaBeaconingEntry 3 }

setInterWlaBeaconingBeacono OBJECT-TYPE
                            SYNTAX INTEGER{
                              cyclic(0),
                              staggered(1),
                              simple-burst(2)
                            }
                            MAX-ACCESS read-write
                            STATUS current
                            DESCRIPTION "Beacon-Order"
                            ::= {  setInterWlaBeaconingEntry 4 }

setInterWlaClientmodesTable OBJECT-TYPE
                            SYNTAX SEQUENCE OF SetInterWlaClientmodesEntry
                            MAX-ACCESS not-accessible
                            STATUS current
                            DESCRIPTION "Client-Modes"
                            ::= {  setInterWla 6 }

setInterWlaClientmodesEntry OBJECT-TYPE
                            SYNTAX SetInterWlaClientmodesEntry
                            MAX-ACCESS not-accessible
                            STATUS current
                            DESCRIPTION "entry in table"
                            INDEX { setInterWlaClientmodesIfc }
                            ::= {  setInterWlaClientmodesTable 1 }

SetInterWlaClientmodesEntry ::= SEQUENCE {
                            setInterWlaClientmodesIfc INTEGER,
                            setInterWlaClientmodesCon INTEGER,
                            setInterWlaClientmodesNet INTEGER,
                            setInterWlaClientmodesSca INTEGER,
                            setInterWlaClientmodesPre MacAddress,
                            setInterWlaClientmodesAdd INTEGER,
                            setInterWlaClientmodesClb INTEGER,
                            setInterWlaClientmodesTxl INTEGER,
                            setInterWlaClientmodesRxl INTEGER
                           }

setInterWlaClientmodesIfc OBJECT-TYPE
                          SYNTAX INTEGER{
                            wlan-1(1)
                          }
                          MAX-ACCESS read-write
                          STATUS current
                          DESCRIPTION "Ifc"
                          ::= {  setInterWlaClientmodesEntry 1 }

setInterWlaClientmodesCon OBJECT-TYPE
                          SYNTAX INTEGER{
                            no(0),
                            yes(1)
                          }
                          MAX-ACCESS read-write
                          STATUS current
                          DESCRIPTION "Connection-Keepalive"
                          ::= {  setInterWlaClientmodesEntry 3 }

setInterWlaClientmodesNet OBJECT-TYPE
                          SYNTAX INTEGER{
                            infrastructure(4)
                          }
                          MAX-ACCESS read-write
                          STATUS current
                          DESCRIPTION "Network-Types"
                          ::= {  setInterWlaClientmodesEntry 4 }

setInterWlaClientmodesSca OBJECT-TYPE
                          SYNTAX INTEGER{
                            e2-4ghz(1)
                          }
                          MAX-ACCESS read-write
                          STATUS current
                          DESCRIPTION "Scan-Bands"
                          ::= {  setInterWlaClientmodesEntry 5 }

setInterWlaClientmodesPre OBJECT-TYPE
                          SYNTAX MacAddress
                          MAX-ACCESS read-write
                          STATUS current
                          DESCRIPTION "Preferred-BSS"
                          ::= {  setInterWlaClientmodesEntry 6 }

setInterWlaClientmodesAdd OBJECT-TYPE
                          SYNTAX INTEGER{
                            no(0),
                            yes(1)
                          }
                          MAX-ACCESS read-write
                          STATUS current
                          DESCRIPTION "Address-Adaption"
                          ::= {  setInterWlaClientmodesEntry 7 }

setInterWlaClientmodesClb OBJECT-TYPE
                          SYNTAX INTEGER{
                            no(0),
                            yes(1)
                          }
                          MAX-ACCESS read-write
                          STATUS current
                          DESCRIPTION "Cl.-Brg.-Support"
                          ::= {  setInterWlaClientmodesEntry 8 }

setInterWlaClientmodesTxl OBJECT-TYPE
                          SYNTAX INTEGER (0..2147483647)
                          MAX-ACCESS read-write
                          STATUS current
                          DESCRIPTION "Tx-Limit"
                          ::= {  setInterWlaClientmodesEntry 9 }

setInterWlaClientmodesRxl OBJECT-TYPE
                          SYNTAX INTEGER (0..2147483647)
                          MAX-ACCESS read-write
                          STATUS current
                          DESCRIPTION "Rx-Limit"
                          ::= {  setInterWlaClientmodesEntry 10 }

setInterWlaRoamingTable OBJECT-TYPE
                            SYNTAX SEQUENCE OF SetInterWlaRoamingEntry
                            MAX-ACCESS not-accessible
                            STATUS current
                            DESCRIPTION "Roaming"
                            ::= {  setInterWla 11 }

setInterWlaRoamingEntry OBJECT-TYPE
                            SYNTAX SetInterWlaRoamingEntry
                            MAX-ACCESS not-accessible
                            STATUS current
                            DESCRIPTION "entry in table"
                            INDEX { setInterWlaRoamingIfc }
                            ::= {  setInterWlaRoamingTable 1 }

SetInterWlaRoamingEntry ::= SEQUENCE {
                            setInterWlaRoamingIfc INTEGER,
                            setInterWlaRoamingSoftroaming INTEGER,
                            setInterWlaRoamingBeaconmisst INTEGER,
                            setInterWlaRoamingRoamingthre INTEGER,
                            setInterWlaRoamingNoroamingth INTEGER,
                            setInterWlaRoamingForceroamin INTEGER,
                            setInterWlaRoamingConnectthre INTEGER,
                            setInterWlaRoamingConnecthold INTEGER,
                            setInterWlaRoamingMinconnects INTEGER,
                            setInterWlaRoamingMinconnecth INTEGER
                           }

setInterWlaRoamingIfc OBJECT-TYPE
                              SYNTAX INTEGER{
                                wlan-1(1)
                              }
                              MAX-ACCESS read-write
                              STATUS current
                              DESCRIPTION "Ifc"
                              ::= {  setInterWlaRoamingEntry 1 }

setInterWlaRoamingSoftroaming OBJECT-TYPE
                              SYNTAX INTEGER{
                                no(0),
                                yes(1)
                              }
                              MAX-ACCESS read-write
                              STATUS current
                              DESCRIPTION "Soft-Roaming"
                              ::= {  setInterWlaRoamingEntry 6 }

setInterWlaRoamingBeaconmisst OBJECT-TYPE
                              SYNTAX INTEGER (0..255)
                              MAX-ACCESS read-write
                              STATUS current
                              DESCRIPTION "Beacon-Miss-Threshold"
                              ::= {  setInterWlaRoamingEntry 2 }

setInterWlaRoamingRoamingthre OBJECT-TYPE
                              SYNTAX INTEGER (0..255)
                              MAX-ACCESS read-write
                              STATUS current
                              DESCRIPTION "Roaming-Threshold"
                              ::= {  setInterWlaRoamingEntry 3 }

setInterWlaRoamingNoroamingth OBJECT-TYPE
                              SYNTAX INTEGER (0..255)
                              MAX-ACCESS read-write
                              STATUS current
                              DESCRIPTION "No-Roaming-Threshold"
                              ::= {  setInterWlaRoamingEntry 4 }

setInterWlaRoamingForceroamin OBJECT-TYPE
                              SYNTAX INTEGER (0..255)
                              MAX-ACCESS read-write
                              STATUS current
                              DESCRIPTION "Force-Roaming-Threshold"
                              ::= {  setInterWlaRoamingEntry 5 }

setInterWlaRoamingConnectthre OBJECT-TYPE
                              SYNTAX INTEGER (0..255)
                              MAX-ACCESS read-write
                              STATUS current
                              DESCRIPTION "Connect-Threshold"
                              ::= {  setInterWlaRoamingEntry 7 }

setInterWlaRoamingConnecthold OBJECT-TYPE
                              SYNTAX INTEGER (0..255)
                              MAX-ACCESS read-write
                              STATUS current
                              DESCRIPTION "Connect-Hold-Threshold"
                              ::= {  setInterWlaRoamingEntry 8 }

setInterWlaRoamingMinconnects OBJECT-TYPE
                              SYNTAX INTEGER (-128..127)
                              MAX-ACCESS read-write
                              STATUS current
                              DESCRIPTION "Min-Connect-Signal-Level"
                              ::= {  setInterWlaRoamingEntry 9 }

setInterWlaRoamingMinconnecth OBJECT-TYPE
                              SYNTAX INTEGER (-128..127)
                              MAX-ACCESS read-write
                              STATUS current
                              DESCRIPTION "Min-Connect-Hold-Signal-Level"
                              ::= {  setInterWlaRoamingEntry 10 }

setInterLanTable OBJECT-TYPE
                 SYNTAX SEQUENCE OF SetInterLanEntry
                 MAX-ACCESS not-accessible
                 STATUS current
                 DESCRIPTION "LAN-Interfaces"
                 ::= {  setInter 21 }

setInterLanEntry OBJECT-TYPE
                 SYNTAX SetInterLanEntry
                 MAX-ACCESS not-accessible
                 STATUS current
                 DESCRIPTION "entry in table"
                 INDEX { setInterLanIfc }
                 ::= {  setInterLanTable 1 }

SetInterLanEntry ::= SEQUENCE {
                 setInterLanIfc INTEGER,
                 setInterLanCon INTEGER,
                 setInterLanMdi INTEGER
                }

setInterLanIfc OBJECT-TYPE
               SYNTAX INTEGER{
                 lan-1(1)
               }
               MAX-ACCESS read-only
               STATUS current
               DESCRIPTION "Ifc"
               ::= {  setInterLanEntry 1 }

setInterLanCon OBJECT-TYPE
               SYNTAX INTEGER{
                 auto(0),
                 e10b-t(1),
                 fd10b-tx(2),
                 e100b-tx(3),
                 fd100b-tx(4),
                 power-down(255)
               }
               MAX-ACCESS read-write
               STATUS current
               DESCRIPTION "Connector"
               ::= {  setInterLanEntry 2 }

setInterLanMdi OBJECT-TYPE
               SYNTAX INTEGER{
                 auto(0),
                 mdi(1),
                 mdix(2)
               }
               MAX-ACCESS read-write
               STATUS current
               DESCRIPTION "MDI-Mode"
               ::= {  setInterLanEntry 3 }

setInterDslTable OBJECT-TYPE
                 SYNTAX SEQUENCE OF SetInterDslEntry
                 MAX-ACCESS not-accessible
                 STATUS current
                 DESCRIPTION "DSLoL-Interface"
                 ::= {  setInter 4 }

setInterDslEntry OBJECT-TYPE
                 SYNTAX SetInterDslEntry
                 MAX-ACCESS not-accessible
                 STATUS current
                 DESCRIPTION "entry in table"
                 INDEX { setInterDslIfc }
                 ::= {  setInterDslTable 1 }

SetInterDslEntry ::= SEQUENCE {
                 setInterDslIfc INTEGER,
                 setInterDslOpe INTEGER,
                 setInterDslMod INTEGER,
                 setInterDslUps INTEGER,
                 setInterDslExt INTEGER,
                 setInterDslDow INTEGER,
                 setInterDslTyp INTEGER,
                 setInterDslLan INTEGER
                }

setInterDslIfc OBJECT-TYPE
               SYNTAX INTEGER{
                 dsl-1(1),
                 ext(2)
               }
               MAX-ACCESS read-only
               STATUS current
               DESCRIPTION "Ifc"
               ::= {  setInterDslEntry 1 }

setInterDslOpe OBJECT-TYPE
               SYNTAX INTEGER{
                 no(0),
                 yes(16)
               }
               MAX-ACCESS read-write
               STATUS current
               DESCRIPTION "Operating"
               ::= {  setInterDslEntry 2 }

setInterDslMod OBJECT-TYPE
               SYNTAX INTEGER{
                 auto(0),
                 exclusive(1)
               }
               MAX-ACCESS read-write
               STATUS current
               DESCRIPTION "Mode"
               ::= {  setInterDslEntry 6 }

setInterDslUps OBJECT-TYPE
               SYNTAX INTEGER (0..2147483647)
               MAX-ACCESS read-write
               STATUS current
               DESCRIPTION "Upstream-Rate"
               ::= {  setInterDslEntry 16 }

setInterDslExt OBJECT-TYPE
               SYNTAX INTEGER (0..2147483647)
               MAX-ACCESS read-write
               STATUS current
               DESCRIPTION "Ext.-Overhead"
               ::= {  setInterDslEntry 17 }

setInterDslDow OBJECT-TYPE
               SYNTAX INTEGER (0..2147483647)
               MAX-ACCESS read-write
               STATUS current
               DESCRIPTION "Downstream-Rate"
               ::= {  setInterDslEntry 18 }

setInterDslTyp OBJECT-TYPE
               SYNTAX INTEGER (0..2147483647)
               MAX-ACCESS read-only
               STATUS current
               DESCRIPTION "Type-of-interface"
               ::= {  setInterDslEntry 15 }

setInterDslLan OBJECT-TYPE
               SYNTAX INTEGER{
                 lan-1(256),
                 wlan-1(512),
                 p2p-1-1(768),
                 p2p-1-2(769),
                 p2p-1-3(770),
                 p2p-1-4(771),
                 p2p-1-5(772),
                 p2p-1-6(773),
                 wlan-1-2(1024),
                 wlan-1-3(1025),
                 wlan-1-4(1026),
                 wlan-1-5(1027),
                 wlan-1-6(1028),
                 wlan-1-7(1029),
                 wlan-1-8(1030),
                 brg-1(1536),
                 brg-2(1537),
                 brg-3(1538),
                 brg-4(1539),
                 brg-5(1540),
                 brg-6(1541),
                 brg-7(1542),
                 brg-8(1543),
                 any(65535)
               }
               MAX-ACCESS read-write
               STATUS current
               DESCRIPTION "LAN-Ifc"
               ::= {  setInterDslEntry 23 }

setInterUmtTable OBJECT-TYPE
                 SYNTAX SEQUENCE OF SetInterUmtEntry
                 MAX-ACCESS not-accessible
                 STATUS current
                 DESCRIPTION "UMTS-Modem"
                 ::= {  setInter 7 }

setInterUmtEntry OBJECT-TYPE
                 SYNTAX SetInterUmtEntry
                 MAX-ACCESS not-accessible
                 STATUS current
                 DESCRIPTION "entry in table"
                 INDEX { setInterUmtIfc }
                 ::= {  setInterUmtTable 1 }

SetInterUmtEntry ::= SEQUENCE {
                 setInterUmtIfc INTEGER,
                 setInterUmtOpe INTEGER,
                 setInterUmtTyp INTEGER,
                 setInterUmtDat INTEGER
                }

setInterUmtIfc OBJECT-TYPE
               SYNTAX INTEGER{
                 dsl-1(1),
                 ext(2)
               }
               MAX-ACCESS read-only
               STATUS current
               DESCRIPTION "Ifc"
               ::= {  setInterUmtEntry 1 }

setInterUmtOpe OBJECT-TYPE
               SYNTAX INTEGER{
                 no(0),
                 modem(1)
               }
               MAX-ACCESS read-write
               STATUS current
               DESCRIPTION "Operating"
               ::= {  setInterUmtEntry 2 }

setInterUmtTyp OBJECT-TYPE
               SYNTAX INTEGER (0..2147483647)
               MAX-ACCESS read-only
               STATUS current
               DESCRIPTION "Type-of-interface"
               ::= {  setInterUmtEntry 15 }

setInterUmtDat OBJECT-TYPE
               SYNTAX INTEGER{
                 e19200(19200),
                 e38400(38400),
                 e57600(57600),
                 e115200(115200)
               }
               MAX-ACCESS read-write
               STATUS current
               DESCRIPTION "Data-Rate"
               ::= {  setInterUmtEntry 21 }

setRadiu OBJECT IDENTIFIER ::= { set 25}
setRadiuAutht OBJECT-TYPE
              SYNTAX INTEGER
              MAX-ACCESS read-write
              STATUS current
              DESCRIPTION "Auth.-Timeout"
              ::= {  setRadiu 4 }

setRadiuAuthr OBJECT-TYPE
              SYNTAX INTEGER
              MAX-ACCESS read-write
              STATUS current
              DESCRIPTION "Auth.-Retry"
              ::= {  setRadiu 5 }

setRadiuBacku OBJECT-TYPE
              SYNTAX INTEGER {
                block(0),
                cyclic(1)
              }
              MAX-ACCESS read-write
              STATUS current
              DESCRIPTION "Backup-Query-Strategy"
              ::= {  setRadiu 9 }

setRadiuServe OBJECT IDENTIFIER ::= { setRadiu 10}
setRadiuServeAuthentific OBJECT-TYPE
                         SYNTAX INTEGER
                         MAX-ACCESS read-write
                         STATUS current
                         DESCRIPTION "Authentification-Port"
                         ::= {  setRadiuServe 1 }

setRadiuServeAccountingp OBJECT-TYPE
                         SYNTAX INTEGER
                         MAX-ACCESS read-write
                         STATUS current
                         DESCRIPTION "Accounting-Port"
                         ::= {  setRadiuServe 11 }

setRadiuServeRadsecport OBJECT-TYPE
                         SYNTAX INTEGER
                         MAX-ACCESS read-write
                         STATUS current
                         DESCRIPTION "RADSEC-Port"
                         ::= {  setRadiuServe 13 }

setRadiuServeClientsTable OBJECT-TYPE
                              SYNTAX SEQUENCE OF SetRadiuServeClientsEntry
                              MAX-ACCESS not-accessible
                              STATUS current
                              DESCRIPTION "Clients"
                              ::= {  setRadiuServe 2 }

setRadiuServeClientsEntry OBJECT-TYPE
                              SYNTAX SetRadiuServeClientsEntry
                              MAX-ACCESS not-accessible
                              STATUS current
                              DESCRIPTION "entry in table"
                              INDEX { setRadiuServeClientsIpnetw, setRadiuServeClientsIpnetm }
                              ::= {  setRadiuServeClientsTable 1 }

SetRadiuServeClientsEntry ::= SEQUENCE {
                              setRadiuServeClientsIpnetw IpAddress,
                              setRadiuServeClientsIpnetm IpAddress,
                              setRadiuServeClientsProtoc INTEGER,
                              setRadiuServeClientsSecret DisplayString
                             }

setRadiuServeClientsIpnetw OBJECT-TYPE
                           SYNTAX IpAddress
                           MAX-ACCESS read-write
                           STATUS current
                           DESCRIPTION "IP-Network"
                           ::= {  setRadiuServeClientsEntry 1 }

setRadiuServeClientsIpnetm OBJECT-TYPE
                           SYNTAX IpAddress
                           MAX-ACCESS read-write
                           STATUS current
                           DESCRIPTION "IP-Netmask"
                           ::= {  setRadiuServeClientsEntry 3 }

setRadiuServeClientsProtoc OBJECT-TYPE
                           SYNTAX INTEGER{
                             radius(0),
                             radsec(1),
                             all(255)
                           }
                           MAX-ACCESS read-write
                           STATUS current
                           DESCRIPTION "Protocols"
                           ::= {  setRadiuServeClientsEntry 4 }

setRadiuServeClientsSecret OBJECT-TYPE
                           SYNTAX DisplayString (SIZE(0..32))
                           MAX-ACCESS read-write
                           STATUS current
                           DESCRIPTION "Secret"
                           ::= {  setRadiuServeClientsEntry 2 }

setRadiuServeUsersTable OBJECT-TYPE
                              SYNTAX SEQUENCE OF SetRadiuServeUsersEntry
                              MAX-ACCESS not-accessible
                              STATUS current
                              DESCRIPTION "Users"
                              ::= {  setRadiuServe 7 }

setRadiuServeUsersEntry OBJECT-TYPE
                              SYNTAX SetRadiuServeUsersEntry
                              MAX-ACCESS not-accessible
                              STATUS current
                              DESCRIPTION "entry in table"
                              INDEX { setRadiuServeUsersUse }
                              ::= {  setRadiuServeUsersTable 1 }

SetRadiuServeUsersEntry ::= SEQUENCE {
                              setRadiuServeUsersUse DisplayString,
                              setRadiuServeUsersPas DisplayString,
                              setRadiuServeUsersLim BITS
                             }

setRadiuServeUsersUse OBJECT-TYPE
                      SYNTAX DisplayString (SIZE(0..48))
                      MAX-ACCESS read-write
                      STATUS current
                      DESCRIPTION "User-Name"
                      ::= {  setRadiuServeUsersEntry 1 }

setRadiuServeUsersPas OBJECT-TYPE
                      SYNTAX DisplayString (SIZE(0..32))
                      MAX-ACCESS read-write
                      STATUS current
                      DESCRIPTION "Password"
                      ::= {  setRadiuServeUsersEntry 2 }

setRadiuServeUsersLim OBJECT-TYPE
                      SYNTAX BITS{
                        pap(1),
                        chap(2),
                        mschap(4),
                        mschapv2(8),
                        eap(16),
                        all(32768)
                      }
                      MAX-ACCESS read-write
                      STATUS current
                      DESCRIPTION "Limit-Auth-Methods"
                      ::= {  setRadiuServeUsersEntry 3 }

setRadiuServeForwardservTable OBJECT-TYPE
                              SYNTAX SEQUENCE OF SetRadiuServeForwardservEntry
                              MAX-ACCESS not-accessible
                              STATUS current
                              DESCRIPTION "Forward-Servers"
                              ::= {  setRadiuServe 3 }

setRadiuServeForwardservEntry OBJECT-TYPE
                              SYNTAX SetRadiuServeForwardservEntry
                              MAX-ACCESS not-accessible
                              STATUS current
                              DESCRIPTION "entry in table"
                              INDEX { setRadiuServeForwardservRea }
                              ::= {  setRadiuServeForwardservTable 1 }

SetRadiuServeForwardservEntry ::= SEQUENCE {
                              setRadiuServeForwardservRea DisplayString,
                              setRadiuServeForwardservIpa IpAddress,
                              setRadiuServeForwardservPor INTEGER,
                              setRadiuServeForwardservSec DisplayString,
                              setRadiuServeForwardservLoo DisplayString,
                              setRadiuServeForwardservPro INTEGER,
                              setRadiuServeForwardservBac DisplayString
                             }

setRadiuServeForwardservRea OBJECT-TYPE
                            SYNTAX DisplayString (SIZE(0..24))
                            MAX-ACCESS read-write
                            STATUS current
                            DESCRIPTION "Realm"
                            ::= {  setRadiuServeForwardservEntry 1 }

setRadiuServeForwardservIpa OBJECT-TYPE
                            SYNTAX IpAddress
                            MAX-ACCESS read-write
                            STATUS current
                            DESCRIPTION "IP-Address"
                            ::= {  setRadiuServeForwardservEntry 2 }

setRadiuServeForwardservPor OBJECT-TYPE
                            SYNTAX INTEGER (0..65535)
                            MAX-ACCESS read-write
                            STATUS current
                            DESCRIPTION "Port"
                            ::= {  setRadiuServeForwardservEntry 3 }

setRadiuServeForwardservSec OBJECT-TYPE
                            SYNTAX DisplayString (SIZE(0..32))
                            MAX-ACCESS read-write
                            STATUS current
                            DESCRIPTION "Secret"
                            ::= {  setRadiuServeForwardservEntry 4 }

setRadiuServeForwardservLoo OBJECT-TYPE
                            SYNTAX DisplayString (SIZE(0..16))
                            MAX-ACCESS read-write
                            STATUS current
                            DESCRIPTION "Loopback-Addr."
                            ::= {  setRadiuServeForwardservEntry 6 }

setRadiuServeForwardservPro OBJECT-TYPE
                            SYNTAX INTEGER{
                              radius(0),
                              radsec(1)
                            }
                            MAX-ACCESS read-write
                            STATUS current
                            DESCRIPTION "Protocol"
                            ::= {  setRadiuServeForwardservEntry 7 }

setRadiuServeForwardservBac OBJECT-TYPE
                            SYNTAX DisplayString (SIZE(0..24))
                            MAX-ACCESS read-write
                            STATUS current
                            DESCRIPTION "Backup"
                            ::= {  setRadiuServeForwardservEntry 5 }

setRadiuServeDefaultreal OBJECT-TYPE
                         SYNTAX DisplayString (SIZE(0..24))
                         MAX-ACCESS read-write
                         STATUS current
                         DESCRIPTION "Default-Realm"
                         ::= {  setRadiuServe 5 }

setRadiuServeEmptyrealm OBJECT-TYPE
                         SYNTAX DisplayString (SIZE(0..24))
                         MAX-ACCESS read-write
                         STATUS current
                         DESCRIPTION "Empty-Realm"
                         ::= {  setRadiuServe 6 }

setRadiuServeAccountingi OBJECT-TYPE
                         SYNTAX INTEGER
                         MAX-ACCESS read-write
                         STATUS current
                         DESCRIPTION "Accounting-Interim-Interval"
                         ::= {  setRadiuServe 12 }

setRadiuServeEap OBJECT IDENTIFIER ::= { setRadiuServe 10}
setRadiuServeEapTun OBJECT-TYPE
                    SYNTAX DisplayString (SIZE(0..24))
                    MAX-ACCESS read-write
                    STATUS current
                    DESCRIPTION "Tunnel-Server"
                    ::= {  setRadiuServeEap 1 }

setRadiuServeEapTls OBJECT-TYPE
                    SYNTAX INTEGER {
                      no(0),
                      yes(1)
                    }
                    MAX-ACCESS read-write
                    STATUS current
                    DESCRIPTION "TLS-Check-Username"
                    ::= {  setRadiuServeEap 2 }

setRadiuServeEapTtl OBJECT-TYPE
                    SYNTAX INTEGER {
                      none(0),
                      md5(4),
                      otp(5),
                      gtc(6),
                      sim(18),
                      aka(23),
                      mschapv2(26)
                    }
                    MAX-ACCESS read-write
                    STATUS current
                    DESCRIPTION "TTLS-Default-Tunnel-Method"
                    ::= {  setRadiuServeEap 5 }

setRadiuServeEapPea OBJECT-TYPE
                    SYNTAX INTEGER {
                      none(0),
                      md5(4),
                      otp(5),
                      gtc(6),
                      sim(18),
                      aka(23),
                      mschapv2(26)
                    }
                    MAX-ACCESS read-write
                    STATUS current
                    DESCRIPTION "PEAP-Default-Tunnel-Method"
                    ::= {  setRadiuServeEap 6 }

setRadiuServeEapRea OBJECT-TYPE
                    SYNTAX INTEGER
                    MAX-ACCESS read-write
                    STATUS current
                    DESCRIPTION "Reauth-Period"
                    ::= {  setRadiuServeEap 3 }

setRadiuServeEapRet OBJECT-TYPE
                    SYNTAX INTEGER
                    MAX-ACCESS read-write
                    STATUS current
                    DESCRIPTION "Retransmit-Timeout"
                    ::= {  setRadiuServeEap 4 }

setNtp OBJECT IDENTIFIER ::= { set 26}
setNtpSer OBJECT-TYPE
          SYNTAX INTEGER {
            no(0),
            yes(1)
          }
          MAX-ACCESS read-write
          STATUS current
          DESCRIPTION "Server-Operating"
          ::= {  setNtp 2 }

setNtpBcm OBJECT-TYPE
          SYNTAX INTEGER {
            no(0),
            yes(1)
          }
          MAX-ACCESS read-write
          STATUS current
          DESCRIPTION "BC-Mode"
          ::= {  setNtp 3 }

setNtpBci OBJECT-TYPE
          SYNTAX INTEGER
          MAX-ACCESS read-write
          STATUS current
          DESCRIPTION "BC-Interval"
          ::= {  setNtp 4 }

setNtpRqi OBJECT-TYPE
          SYNTAX INTEGER
          MAX-ACCESS read-write
          STATUS current
          DESCRIPTION "RQ-Interval"
          ::= {  setNtp 7 }

setNtpRqt OBJECT-TYPE
          SYNTAX INTEGER
          MAX-ACCESS read-write
          STATUS current
          DESCRIPTION "RQ-Tries"
          ::= {  setNtp 12 }

setNtpRqaTable OBJECT-TYPE
               SYNTAX SEQUENCE OF SetNtpRqaEntry
               MAX-ACCESS not-accessible
               STATUS current
               DESCRIPTION "RQ-Address"
               ::= {  setNtp 11 }

setNtpRqaEntry OBJECT-TYPE
               SYNTAX SetNtpRqaEntry
               MAX-ACCESS not-accessible
               STATUS current
               DESCRIPTION "entry in table"
               INDEX { setNtpRqaRqa }
               ::= {  setNtpRqaTable 1 }

SetNtpRqaEntry ::= SEQUENCE {
               setNtpRqaRqa DisplayString,
               setNtpRqaLoo DisplayString
              }

setNtpRqaRqa OBJECT-TYPE
             SYNTAX DisplayString (SIZE(0..31))
             MAX-ACCESS read-write
             STATUS current
             DESCRIPTION "RQ-Address"
             ::= {  setNtpRqaEntry 1 }

setNtpRqaLoo OBJECT-TYPE
             SYNTAX DisplayString (SIZE(0..16))
             MAX-ACCESS read-write
             STATUS current
             DESCRIPTION "Loopback-Addr."
             ::= {  setNtpRqaEntry 2 }

setNtpC0 OBJECT-TYPE
          SYNTAX IpAddress
          MAX-ACCESS not-accessible
          STATUS current
          DESCRIPTION "C0"
          ::= {  setNtp 8 }

setMail OBJECT IDENTIFIER ::= { set 27}
setMailSmtps OBJECT-TYPE
             SYNTAX DisplayString (SIZE(0..31))
             MAX-ACCESS read-write
             STATUS current
             DESCRIPTION "SMTP-Server"
             ::= {  setMail 1 }

setMailSmtpp OBJECT-TYPE
             SYNTAX INTEGER
             MAX-ACCESS read-write
             STATUS current
             DESCRIPTION "SMTP-Port"
             ::= {  setMail 2 }

setMailPop3s OBJECT-TYPE
             SYNTAX DisplayString (SIZE(0..31))
             MAX-ACCESS read-write
             STATUS current
             DESCRIPTION "POP3-Server"
             ::= {  setMail 3 }

setMailPop3p OBJECT-TYPE
             SYNTAX INTEGER
             MAX-ACCESS read-write
             STATUS current
             DESCRIPTION "POP3-Port"
             ::= {  setMail 4 }

setMailLoopb OBJECT-TYPE
             SYNTAX DisplayString (SIZE(0..16))
             MAX-ACCESS read-write
             STATUS current
             DESCRIPTION "Loopback-Addr."
             ::= {  setMail 11 }

setMailUsern OBJECT-TYPE
             SYNTAX DisplayString (SIZE(0..63))
             MAX-ACCESS read-write
             STATUS current
             DESCRIPTION "User-Name"
             ::= {  setMail 5 }

setMailPassw OBJECT-TYPE
             SYNTAX DisplayString (SIZE(0..31))
             MAX-ACCESS read-write
             STATUS current
             DESCRIPTION "Password"
             ::= {  setMail 6 }

setMailEmail OBJECT-TYPE
             SYNTAX DisplayString (SIZE(0..63))
             MAX-ACCESS read-write
             STATUS current
             DESCRIPTION "E-Mail-Sender"
             ::= {  setMail 7 }

setMailSenda OBJECT-TYPE
             SYNTAX INTEGER
             MAX-ACCESS read-write
             STATUS current
             DESCRIPTION "Send-Again-(min.)"
             ::= {  setMail 8 }

setMailHoldt OBJECT-TYPE
             SYNTAX INTEGER
             MAX-ACCESS read-write
             STATUS current
             DESCRIPTION "Hold-Time-(hrs.)"
             ::= {  setMail 9 }

setMailBuffe OBJECT-TYPE
             SYNTAX INTEGER
             MAX-ACCESS read-write
             STATUS current
             DESCRIPTION "Buffers"
             ::= {  setMail 10 }

setPppoe OBJECT IDENTIFIER ::= { set 31}
setPppoeOpe OBJECT-TYPE
            SYNTAX INTEGER {
              no(0),
              yes(1)
            }
            MAX-ACCESS read-write
            STATUS current
            DESCRIPTION "Operating"
            ::= {  setPppoe 1 }

setPppoeNamTable OBJECT-TYPE
                 SYNTAX SEQUENCE OF SetPppoeNamEntry
                 MAX-ACCESS not-accessible
                 STATUS current
                 DESCRIPTION "Name-List"
                 ::= {  setPppoe 2 }

setPppoeNamEntry OBJECT-TYPE
                 SYNTAX SetPppoeNamEntry
                 MAX-ACCESS not-accessible
                 STATUS current
                 DESCRIPTION "entry in table"
                 INDEX { setPppoeNamPee }
                 ::= {  setPppoeNamTable 1 }

SetPppoeNamEntry ::= SEQUENCE {
                 setPppoeNamPee DisplayString,
                 setPppoeNamSht INTEGER,
                 setPppoeNamMac DisplayString
                }

setPppoeNamPee OBJECT-TYPE
               SYNTAX DisplayString (SIZE(0..16))
               MAX-ACCESS read-write
               STATUS current
               DESCRIPTION "Peer"
               ::= {  setPppoeNamEntry 1 }

setPppoeNamSht OBJECT-TYPE
               SYNTAX INTEGER (0..65535)
               MAX-ACCESS read-write
               STATUS current
               DESCRIPTION "SH-Time"
               ::= {  setPppoeNamEntry 2 }

setPppoeNamMac OBJECT-TYPE
               SYNTAX DisplayString (SIZE(0..12))
               MAX-ACCESS read-write
               STATUS current
               DESCRIPTION "MAC-Address"
               ::= {  setPppoeNamEntry 3 }

setPppoeSer OBJECT-TYPE
            SYNTAX DisplayString (SIZE(0..32))
            MAX-ACCESS read-write
            STATUS current
            DESCRIPTION "Service"
            ::= {  setPppoe 3 }

setPppoeSes OBJECT-TYPE
            SYNTAX INTEGER
            MAX-ACCESS read-write
            STATUS current
            DESCRIPTION "Session-Limit"
            ::= {  setPppoe 4 }

setPppoePorTable OBJECT-TYPE
                 SYNTAX SEQUENCE OF SetPppoePorEntry
                 MAX-ACCESS not-accessible
                 STATUS current
                 DESCRIPTION "Ports"
                 ::= {  setPppoe 5 }

setPppoePorEntry OBJECT-TYPE
                 SYNTAX SetPppoePorEntry
                 MAX-ACCESS not-accessible
                 STATUS current
                 DESCRIPTION "entry in table"
                 INDEX { setPppoePorPor }
                 ::= {  setPppoePorTable 1 }

SetPppoePorEntry ::= SEQUENCE {
                 setPppoePorPor DisplayString,
                 setPppoePorEna INTEGER
                }

setPppoePorPor OBJECT-TYPE
               SYNTAX DisplayString (SIZE(0..10))
               MAX-ACCESS read-only
               STATUS current
               DESCRIPTION "Port"
               ::= {  setPppoePorEntry 2 }

setPppoePorEna OBJECT-TYPE
               SYNTAX INTEGER{
                 no(0),
                 yes(1)
               }
               MAX-ACCESS read-write
               STATUS current
               DESCRIPTION "Enable-PPPoE"
               ::= {  setPppoePorEntry 3 }

setVlan OBJECT IDENTIFIER ::= { set 32}
setVlanOpe OBJECT-TYPE
           SYNTAX INTEGER {
             no(0),
             yes(1)
           }
           MAX-ACCESS read-write
           STATUS current
           DESCRIPTION "Operating"
           ::= {  setVlan 4 }

setVlanNetTable OBJECT-TYPE
                SYNTAX SEQUENCE OF SetVlanNetEntry
                MAX-ACCESS not-accessible
                STATUS current
                DESCRIPTION "Networks"
                ::= {  setVlan 1 }

setVlanNetEntry OBJECT-TYPE
                SYNTAX SetVlanNetEntry
                MAX-ACCESS not-accessible
                STATUS current
                DESCRIPTION "entry in table"
                INDEX { setVlanNetNam }
                ::= {  setVlanNetTable 1 }

SetVlanNetEntry ::= SEQUENCE {
                setVlanNetNam DisplayString,
                setVlanNetVla INTEGER,
                setVlanNetPor DisplayString
               }

setVlanNetNam OBJECT-TYPE
              SYNTAX DisplayString (SIZE(0..16))
              MAX-ACCESS read-write
              STATUS current
              DESCRIPTION "Name"
              ::= {  setVlanNetEntry 1 }

setVlanNetVla OBJECT-TYPE
              SYNTAX INTEGER (0..65535)
              MAX-ACCESS read-write
              STATUS current
              DESCRIPTION "VLAN-ID"
              ::= {  setVlanNetEntry 2 }

setVlanNetPor OBJECT-TYPE
              SYNTAX DisplayString (SIZE(0..251))
              MAX-ACCESS read-write
              STATUS current
              DESCRIPTION "Ports"
              ::= {  setVlanNetEntry 4 }

setVlanTag OBJECT-TYPE
           SYNTAX DisplayString (SIZE(0..4))
           MAX-ACCESS read-write
           STATUS current
           DESCRIPTION "Tag-Value"
           ::= {  setVlan 5 }

setVlanPorTable OBJECT-TYPE
                SYNTAX SEQUENCE OF SetVlanPorEntry
                MAX-ACCESS not-accessible
                STATUS current
                DESCRIPTION "Port-Table"
                ::= {  setVlan 2 }

setVlanPorEntry OBJECT-TYPE
                SYNTAX SetVlanPorEntry
                MAX-ACCESS not-accessible
                STATUS current
                DESCRIPTION "entry in table"
                INDEX { setVlanPorPort }
                ::= {  setVlanPorTable 1 }

SetVlanPorEntry ::= SEQUENCE {
                setVlanPorPort DisplayString,
                setVlanPorTaggi INTEGER,
                setVlanPorAllow INTEGER,
                setVlanPorPortv INTEGER
               }

setVlanPorPort OBJECT-TYPE
                SYNTAX DisplayString (SIZE(0..9))
                MAX-ACCESS read-only
                STATUS current
                DESCRIPTION "Port"
                ::= {  setVlanPorEntry 1 }

setVlanPorTaggi OBJECT-TYPE
                SYNTAX INTEGER{
                  ingress-mixed(0),
                  never(1),
                  mixed(2),
                  always(3)
                }
                MAX-ACCESS read-write
                STATUS current
                DESCRIPTION "Tagging-Mode"
                ::= {  setVlanPorEntry 6 }

setVlanPorAllow OBJECT-TYPE
                SYNTAX INTEGER{
                  no(0),
                  yes(1)
                }
                MAX-ACCESS read-write
                STATUS current
                DESCRIPTION "Allow-All-VLANs"
                ::= {  setVlanPorEntry 4 }

setVlanPorPortv OBJECT-TYPE
                SYNTAX INTEGER (0..65535)
                MAX-ACCESS read-write
                STATUS current
                DESCRIPTION "Port-VLAN-Id"
                ::= {  setVlanPorEntry 5 }

setIeee8 OBJECT IDENTIFIER ::= { set 30}
setIeee8PorTable OBJECT-TYPE
                 SYNTAX SEQUENCE OF SetIeee8PorEntry
                 MAX-ACCESS not-accessible
                 STATUS current
                 DESCRIPTION "Ports"
                 ::= {  setIeee8 4 }

setIeee8PorEntry OBJECT-TYPE
                 SYNTAX SetIeee8PorEntry
                 MAX-ACCESS not-accessible
                 STATUS current
                 DESCRIPTION "entry in table"
                 INDEX { setIeee8PorPort }
                 ::= {  setIeee8PorTable 1 }

SetIeee8PorEntry ::= SEQUENCE {
                 setIeee8PorPort DisplayString,
                 setIeee8PorPortcon INTEGER,
                 setIeee8PorReauthm INTEGER,
                 setIeee8PorMaxreq INTEGER,
                 setIeee8PorTxperio INTEGER,
                 setIeee8PorSupptim INTEGER,
                 setIeee8PorServert INTEGER,
                 setIeee8PorQuietpe INTEGER,
                 setIeee8PorReauthe INTEGER,
                 setIeee8PorReauthi INTEGER,
                 setIeee8PorKeytran INTEGER,
                 setIeee8PorKeytxin INTEGER
                }

setIeee8PorPort OBJECT-TYPE
                   SYNTAX DisplayString (SIZE(0..15))
                   MAX-ACCESS read-only
                   STATUS current
                   DESCRIPTION "Port"
                   ::= {  setIeee8PorEntry 2 }

setIeee8PorPortcon OBJECT-TYPE
                   SYNTAX INTEGER{
                     force-unauth(0),
                     force-auth(1),
                     auto(2)
                   }
                   MAX-ACCESS read-write
                   STATUS current
                   DESCRIPTION "Port-Control"
                   ::= {  setIeee8PorEntry 3 }

setIeee8PorReauthm OBJECT-TYPE
                   SYNTAX INTEGER (0..255)
                   MAX-ACCESS read-write
                   STATUS current
                   DESCRIPTION "Re-Auth-Max"
                   ::= {  setIeee8PorEntry 4 }

setIeee8PorMaxreq OBJECT-TYPE
                   SYNTAX INTEGER (0..255)
                   MAX-ACCESS read-write
                   STATUS current
                   DESCRIPTION "Max-Req"
                   ::= {  setIeee8PorEntry 5 }

setIeee8PorTxperio OBJECT-TYPE
                   SYNTAX INTEGER (0..65535)
                   MAX-ACCESS read-write
                   STATUS current
                   DESCRIPTION "Tx-Period"
                   ::= {  setIeee8PorEntry 6 }

setIeee8PorSupptim OBJECT-TYPE
                   SYNTAX INTEGER (0..65535)
                   MAX-ACCESS read-write
                   STATUS current
                   DESCRIPTION "Supp-Timeout"
                   ::= {  setIeee8PorEntry 7 }

setIeee8PorServert OBJECT-TYPE
                   SYNTAX INTEGER (0..65535)
                   MAX-ACCESS read-write
                   STATUS current
                   DESCRIPTION "Server-Timeout"
                   ::= {  setIeee8PorEntry 8 }

setIeee8PorQuietpe OBJECT-TYPE
                   SYNTAX INTEGER (0..65535)
                   MAX-ACCESS read-write
                   STATUS current
                   DESCRIPTION "Quiet-Period"
                   ::= {  setIeee8PorEntry 9 }

setIeee8PorReauthe OBJECT-TYPE
                   SYNTAX INTEGER{
                     no(0),
                     yes(1)
                   }
                   MAX-ACCESS read-write
                   STATUS current
                   DESCRIPTION "Re-Authentication"
                   ::= {  setIeee8PorEntry 10 }

setIeee8PorReauthi OBJECT-TYPE
                   SYNTAX INTEGER (0..65535)
                   MAX-ACCESS read-write
                   STATUS current
                   DESCRIPTION "Re-Auth-Interval"
                   ::= {  setIeee8PorEntry 11 }

setIeee8PorKeytran OBJECT-TYPE
                   SYNTAX INTEGER{
                     no(0),
                     yes(1)
                   }
                   MAX-ACCESS read-write
                   STATUS current
                   DESCRIPTION "Key-Transmission"
                   ::= {  setIeee8PorEntry 12 }

setIeee8PorKeytxin OBJECT-TYPE
                   SYNTAX INTEGER (0..65535)
                   MAX-ACCESS read-write
                   STATUS current
                   DESCRIPTION "Key-Tx-Interval"
                   ::= {  setIeee8PorEntry 13 }

setIeee8RadTable OBJECT-TYPE
                 SYNTAX SEQUENCE OF SetIeee8RadEntry
                 MAX-ACCESS not-accessible
                 STATUS current
                 DESCRIPTION "RADIUS-Server"
                 ::= {  setIeee8 3 }

setIeee8RadEntry OBJECT-TYPE
                 SYNTAX SetIeee8RadEntry
                 MAX-ACCESS not-accessible
                 STATUS current
                 DESCRIPTION "entry in table"
                 INDEX { setIeee8RadNam }
                 ::= {  setIeee8RadTable 1 }

SetIeee8RadEntry ::= SEQUENCE {
                 setIeee8RadNam DisplayString,
                 setIeee8RadIpa IpAddress,
                 setIeee8RadPor INTEGER,
                 setIeee8RadSec DisplayString,
                 setIeee8RadLoo DisplayString,
                 setIeee8RadPro INTEGER,
                 setIeee8RadBac DisplayString
                }

setIeee8RadNam OBJECT-TYPE
               SYNTAX DisplayString (SIZE(0..16))
               MAX-ACCESS read-write
               STATUS current
               DESCRIPTION "Name"
               ::= {  setIeee8RadEntry 1 }

setIeee8RadIpa OBJECT-TYPE
               SYNTAX IpAddress
               MAX-ACCESS read-write
               STATUS current
               DESCRIPTION "IP-Address"
               ::= {  setIeee8RadEntry 2 }

setIeee8RadPor OBJECT-TYPE
               SYNTAX INTEGER (0..65535)
               MAX-ACCESS read-write
               STATUS current
               DESCRIPTION "Port"
               ::= {  setIeee8RadEntry 3 }

setIeee8RadSec OBJECT-TYPE
               SYNTAX DisplayString (SIZE(0..32))
               MAX-ACCESS read-write
               STATUS current
               DESCRIPTION "Secret"
               ::= {  setIeee8RadEntry 4 }

setIeee8RadLoo OBJECT-TYPE
               SYNTAX DisplayString (SIZE(0..16))
               MAX-ACCESS read-write
               STATUS current
               DESCRIPTION "Loopback-Addr."
               ::= {  setIeee8RadEntry 6 }

setIeee8RadPro OBJECT-TYPE
               SYNTAX INTEGER{
                 radius(0),
                 radsec(1)
               }
               MAX-ACCESS read-write
               STATUS current
               DESCRIPTION "Protocol"
               ::= {  setIeee8RadEntry 7 }

setIeee8RadBac OBJECT-TYPE
               SYNTAX DisplayString (SIZE(0..16))
               MAX-ACCESS read-write
               STATUS current
               DESCRIPTION "Backup"
               ::= {  setIeee8RadEntry 5 }

setEchos OBJECT IDENTIFIER ::= { set 35}
setEchosOpe OBJECT-TYPE
            SYNTAX INTEGER {
              no(0),
              yes(1)
            }
            MAX-ACCESS read-write
            STATUS current
            DESCRIPTION "Operating"
            ::= {  setEchos 1 }

setEchosAccTable OBJECT-TYPE
                 SYNTAX SEQUENCE OF SetEchosAccEntry
                 MAX-ACCESS not-accessible
                 STATUS current
                 DESCRIPTION "Access-Table"
                 ::= {  setEchos 2 }

setEchosAccEntry OBJECT-TYPE
                 SYNTAX SetEchosAccEntry
                 MAX-ACCESS not-accessible
                 STATUS current
                 DESCRIPTION "entry in table"
                 INDEX { setEchosAccIpa, setEchosAccNet }
                 ::= {  setEchosAccTable 1 }

SetEchosAccEntry ::= SEQUENCE {
                 setEchosAccIpa IpAddress,
                 setEchosAccNet IpAddress,
                 setEchosAccPro INTEGER,
                 setEchosAccAkt INTEGER,
                 setEchosAccCom DisplayString
                }

setEchosAccIpa OBJECT-TYPE
               SYNTAX IpAddress
               MAX-ACCESS read-write
               STATUS current
               DESCRIPTION "IP-Address"
               ::= {  setEchosAccEntry 1 }

setEchosAccNet OBJECT-TYPE
               SYNTAX IpAddress
               MAX-ACCESS read-write
               STATUS current
               DESCRIPTION "Netmask"
               ::= {  setEchosAccEntry 2 }

setEchosAccPro OBJECT-TYPE
               SYNTAX INTEGER{
                 none(0),
                 tcp(1),
                 udp(2),
                 tcp-plus-udp(3)
               }
               MAX-ACCESS read-write
               STATUS current
               DESCRIPTION "Protokoll"
               ::= {  setEchosAccEntry 3 }

setEchosAccAkt OBJECT-TYPE
               SYNTAX INTEGER{
                 yes(0),
                 no(1)
               }
               MAX-ACCESS read-write
               STATUS current
               DESCRIPTION "Aktive"
               ::= {  setEchosAccEntry 4 }

setEchosAccCom OBJECT-TYPE
               SYNTAX DisplayString (SIZE(0..31))
               MAX-ACCESS read-write
               STATUS current
               DESCRIPTION "Comment"
               ::= {  setEchosAccEntry 5 }

setEchosTcp OBJECT-TYPE
            SYNTAX INTEGER
            MAX-ACCESS read-write
            STATUS current
            DESCRIPTION "TCP-Timeout"
            ::= {  setEchos 3 }

setCerti OBJECT IDENTIFIER ::= { set 39}
setCertiSce OBJECT IDENTIFIER ::= { setCerti 1}
setCertiSceSce OBJECT-TYPE
               SYNTAX INTEGER {
                 no(0),
                 yes(1)
               }
               MAX-ACCESS read-write
               STATUS current
               DESCRIPTION "SCEP-Operating"
               ::= {  setCertiSce 1 }

setCertiSceRet OBJECT-TYPE
               SYNTAX INTEGER
               MAX-ACCESS read-write
               STATUS current
               DESCRIPTION "Retry-After-Error-Interval"
               ::= {  setCertiSce 11 }

setCertiSceChe OBJECT-TYPE
               SYNTAX INTEGER
               MAX-ACCESS read-write
               STATUS current
               DESCRIPTION "Check-Pending-Requests-Interval"
               ::= {  setCertiSce 12 }

setCertiSceDev OBJECT-TYPE
               SYNTAX INTEGER
               MAX-ACCESS read-write
               STATUS current
               DESCRIPTION "Device-Certificate-Update-Before"
               ::= {  setCertiSce 2 }

setCertiSceCac OBJECT-TYPE
               SYNTAX INTEGER
               MAX-ACCESS read-write
               STATUS current
               DESCRIPTION "CA-Certificate-Update-Before"
               ::= {  setCertiSce 3 }

setCertiSceCasTable OBJECT-TYPE
                    SYNTAX SEQUENCE OF SetCertiSceCasEntry
                    MAX-ACCESS not-accessible
                    STATUS current
                    DESCRIPTION "CAs"
                    ::= {  setCertiSce 6 }

setCertiSceCasEntry OBJECT-TYPE
                    SYNTAX SetCertiSceCasEntry
                    MAX-ACCESS not-accessible
                    STATUS current
                    DESCRIPTION "entry in table"
                    INDEX { setCertiSceCasName }
                    ::= {  setCertiSceCasTable 1 }

SetCertiSceCasEntry ::= SEQUENCE {
                    setCertiSceCasName DisplayString,
                    setCertiSceCasUrl DisplayString,
                    setCertiSceCasDn DisplayString,
                    setCertiSceCasEncalg INTEGER,
                    setCertiSceCasIdentifier DisplayString,
                    setCertiSceCasRaautoapprove INTEGER,
                    setCertiSceCasCasignaturealg INTEGER,
                    setCertiSceCasCafingerprinta INTEGER,
                    setCertiSceCasCafingerprint DisplayString,
                    setCertiSceCasApplication INTEGER,
                    setCertiSceCasLoopbackaddr DisplayString
                   }

setCertiSceCasName OBJECT-TYPE
                             SYNTAX DisplayString (SIZE(0..16))
                             MAX-ACCESS read-write
                             STATUS current
                             DESCRIPTION "Name"
                             ::= {  setCertiSceCasEntry 1 }

setCertiSceCasUrl OBJECT-TYPE
                             SYNTAX DisplayString (SIZE(0..251))
                             MAX-ACCESS read-write
                             STATUS current
                             DESCRIPTION "URL"
                             ::= {  setCertiSceCasEntry 2 }

setCertiSceCasDn OBJECT-TYPE
                             SYNTAX DisplayString (SIZE(0..251))
                             MAX-ACCESS read-write
                             STATUS current
                             DESCRIPTION "DN"
                             ::= {  setCertiSceCasEntry 3 }

setCertiSceCasEncalg OBJECT-TYPE
                             SYNTAX INTEGER{
                               des(0),
                               e3des(1),
                               blowfish(2)
                             }
                             MAX-ACCESS read-write
                             STATUS current
                             DESCRIPTION "Enc-Alg"
                             ::= {  setCertiSceCasEntry 4 }

setCertiSceCasIdentifier OBJECT-TYPE
                             SYNTAX DisplayString (SIZE(0..251))
                             MAX-ACCESS read-write
                             STATUS current
                             DESCRIPTION "Identifier"
                             ::= {  setCertiSceCasEntry 5 }

setCertiSceCasRaautoapprove OBJECT-TYPE
                             SYNTAX INTEGER{
                               no(0),
                               yes(1)
                             }
                             MAX-ACCESS read-write
                             STATUS current
                             DESCRIPTION "RA-Autoapprove"
                             ::= {  setCertiSceCasEntry 7 }

setCertiSceCasCasignaturealg OBJECT-TYPE
                             SYNTAX INTEGER{
                               md5(0),
                               sha1(1)
                             }
                             MAX-ACCESS read-write
                             STATUS current
                             DESCRIPTION "CA-Signature-Algorithm"
                             ::= {  setCertiSceCasEntry 6 }

setCertiSceCasCafingerprinta OBJECT-TYPE
                             SYNTAX INTEGER{
                               off(0),
                               sha1(1),
                               md5(2)
                             }
                             MAX-ACCESS read-write
                             STATUS current
                             DESCRIPTION "CA-Fingerprint-Algorithm"
                             ::= {  setCertiSceCasEntry 8 }

setCertiSceCasCafingerprint OBJECT-TYPE
                             SYNTAX DisplayString (SIZE(0..59))
                             MAX-ACCESS read-write
                             STATUS current
                             DESCRIPTION "CA-Fingerprint"
                             ::= {  setCertiSceCasEntry 9 }

setCertiSceCasApplication OBJECT-TYPE
                             SYNTAX INTEGER{
                               general(2),
                               wlan-controller(1),
                               eap-tls(3)
                             }
                             MAX-ACCESS read-write
                             STATUS current
                             DESCRIPTION "Application"
                             ::= {  setCertiSceCasEntry 10 }

setCertiSceCasLoopbackaddr OBJECT-TYPE
                             SYNTAX DisplayString (SIZE(0..16))
                             MAX-ACCESS read-write
                             STATUS current
                             DESCRIPTION "Loopback-Addr."
                             ::= {  setCertiSceCasEntry 11 }

setCertiSceCerTable OBJECT-TYPE
                    SYNTAX SEQUENCE OF SetCertiSceCerEntry
                    MAX-ACCESS not-accessible
                    STATUS current
                    DESCRIPTION "Certificates"
                    ::= {  setCertiSce 7 }

setCertiSceCerEntry OBJECT-TYPE
                    SYNTAX SetCertiSceCerEntry
                    MAX-ACCESS not-accessible
                    STATUS current
                    DESCRIPTION "entry in table"
                    INDEX { setCertiSceCerName }
                    ::= {  setCertiSceCerTable 1 }

SetCertiSceCerEntry ::= SEQUENCE {
                    setCertiSceCerName DisplayString,
                    setCertiSceCerCadn DisplayString,
                    setCertiSceCerSubject DisplayString,
                    setCertiSceCerChalleng DisplayString,
                    setCertiSceCerSubjecta DisplayString,
                    setCertiSceCerKeyusage DisplayString,
                    setCertiSceCerExtended DisplayString,
                    setCertiSceCerDevicece INTEGER,
                    setCertiSceCerApplicat INTEGER
                   }

setCertiSceCerName OBJECT-TYPE
                       SYNTAX DisplayString (SIZE(0..16))
                       MAX-ACCESS read-write
                       STATUS current
                       DESCRIPTION "Name"
                       ::= {  setCertiSceCerEntry 1 }

setCertiSceCerCadn OBJECT-TYPE
                       SYNTAX DisplayString (SIZE(0..251))
                       MAX-ACCESS read-write
                       STATUS current
                       DESCRIPTION "CADN"
                       ::= {  setCertiSceCerEntry 2 }

setCertiSceCerSubject OBJECT-TYPE
                       SYNTAX DisplayString (SIZE(0..251))
                       MAX-ACCESS read-write
                       STATUS current
                       DESCRIPTION "Subject"
                       ::= {  setCertiSceCerEntry 3 }

setCertiSceCerChalleng OBJECT-TYPE
                       SYNTAX DisplayString (SIZE(0..251))
                       MAX-ACCESS read-write
                       STATUS current
                       DESCRIPTION "ChallengePwd"
                       ::= {  setCertiSceCerEntry 4 }

setCertiSceCerSubjecta OBJECT-TYPE
                       SYNTAX DisplayString (SIZE(0..251))
                       MAX-ACCESS read-write
                       STATUS current
                       DESCRIPTION "SubjectAltName"
                       ::= {  setCertiSceCerEntry 5 }

setCertiSceCerKeyusage OBJECT-TYPE
                       SYNTAX DisplayString (SIZE(0..251))
                       MAX-ACCESS read-write
                       STATUS current
                       DESCRIPTION "KeyUsage"
                       ::= {  setCertiSceCerEntry 6 }

setCertiSceCerExtended OBJECT-TYPE
                       SYNTAX DisplayString (SIZE(0..251))
                       MAX-ACCESS read-write
                       STATUS current
                       DESCRIPTION "Extended-KeyUsage"
                       ::= {  setCertiSceCerEntry 9 }

setCertiSceCerDevicece OBJECT-TYPE
                       SYNTAX INTEGER (0..2147483647)
                       MAX-ACCESS read-write
                       STATUS current
                       DESCRIPTION "Device-Certificate-Keylength"
                       ::= {  setCertiSceCerEntry 7 }

setCertiSceCerApplicat OBJECT-TYPE
                       SYNTAX INTEGER{
                         wlan-controller(1),
                         eap-tls(3)
                       }
                       MAX-ACCESS read-write
                       STATUS current
                       DESCRIPTION "Application"
                       ::= {  setCertiSceCerEntry 8 }

setCertiSceRei OBJECT-TYPE
               SYNTAX DisplayString
               MAX-ACCESS read-write
               STATUS current
               DESCRIPTION "Reinit"
               ::= {  setCertiSce 8 }

setCertiSceUpd OBJECT-TYPE
               SYNTAX DisplayString
               MAX-ACCESS read-write
               STATUS current
               DESCRIPTION "Update"
               ::= {  setCertiSce 9 }

setCertiSceCle OBJECT-TYPE
               SYNTAX DisplayString
               MAX-ACCESS read-write
               STATUS current
               DESCRIPTION "Clear-SCEP-Filesystem"
               ::= {  setCertiSce 10 }

setPerfo OBJECT IDENTIFIER ::= { set 36}
setPerfoRttmonaTable OBJECT-TYPE
                     SYNTAX SEQUENCE OF SetPerfoRttmonaEntry
                     MAX-ACCESS not-accessible
                     STATUS current
                     DESCRIPTION "RttMonAdmin"
                     ::= {  setPerfo 2 }

setPerfoRttmonaEntry OBJECT-TYPE
                     SYNTAX SetPerfoRttmonaEntry
                     MAX-ACCESS not-accessible
                     STATUS current
                     DESCRIPTION "entry in table"
                     INDEX { setPerfoRttmonaInd }
                     ::= {  setPerfoRttmonaTable 1 }

SetPerfoRttmonaEntry ::= SEQUENCE {
                     setPerfoRttmonaInd INTEGER,
                     setPerfoRttmonaTyp INTEGER,
                     setPerfoRttmonaFre INTEGER,
                     setPerfoRttmonaTim INTEGER,
                     setPerfoRttmonaSta INTEGER
                    }

setPerfoRttmonaInd OBJECT-TYPE
                   SYNTAX INTEGER (0..2147483647)
                   MAX-ACCESS read-write
                   STATUS current
                   DESCRIPTION "Index"
                   ::= {  setPerfoRttmonaEntry 1 }

setPerfoRttmonaTyp OBJECT-TYPE
                   SYNTAX INTEGER{
                     jitter(9)
                   }
                   MAX-ACCESS read-write
                   STATUS current
                   DESCRIPTION "Type"
                   ::= {  setPerfoRttmonaEntry 4 }

setPerfoRttmonaFre OBJECT-TYPE
                   SYNTAX INTEGER (0..2147483647)
                   MAX-ACCESS read-write
                   STATUS current
                   DESCRIPTION "Frequency"
                   ::= {  setPerfoRttmonaEntry 6 }

setPerfoRttmonaTim OBJECT-TYPE
                   SYNTAX INTEGER (0..2147483647)
                   MAX-ACCESS read-write
                   STATUS current
                   DESCRIPTION "Timeout"
                   ::= {  setPerfoRttmonaEntry 7 }

setPerfoRttmonaSta OBJECT-TYPE
                   SYNTAX INTEGER{
                     active(1),
                     not-in-service(2),
                     not-ready(3),
                     create(5),
                     destroy(6)
                   }
                   MAX-ACCESS read-write
                   STATUS current
                   DESCRIPTION "Status"
                   ::= {  setPerfoRttmonaEntry 9 }

setPerfoRttmoneTable OBJECT-TYPE
                     SYNTAX SEQUENCE OF SetPerfoRttmoneEntry
                     MAX-ACCESS not-accessible
                     STATUS current
                     DESCRIPTION "RttMonEchoAdmin"
                     ::= {  setPerfo 3 }

setPerfoRttmoneEntry OBJECT-TYPE
                     SYNTAX SetPerfoRttmoneEntry
                     MAX-ACCESS not-accessible
                     STATUS current
                     DESCRIPTION "entry in table"
                     INDEX { setPerfoRttmoneIndex }
                     ::= {  setPerfoRttmoneTable 1 }

SetPerfoRttmoneEntry ::= SEQUENCE {
                     setPerfoRttmoneIndex INTEGER,
                     setPerfoRttmoneProtocol INTEGER,
                     setPerfoRttmoneDestinationa IpAddress,
                     setPerfoRttmonePacketsize INTEGER,
                     setPerfoRttmoneDestinationp INTEGER,
                     setPerfoRttmoneInterval INTEGER,
                     setPerfoRttmonePacketcount INTEGER
                    }

setPerfoRttmoneIndex OBJECT-TYPE
                            SYNTAX INTEGER (0..2147483647)
                            MAX-ACCESS read-only
                            STATUS current
                            DESCRIPTION "Index"
                            ::= {  setPerfoRttmoneEntry 255 }

setPerfoRttmoneProtocol OBJECT-TYPE
                            SYNTAX INTEGER{
                              echo(3)
                            }
                            MAX-ACCESS read-write
                            STATUS current
                            DESCRIPTION "Protocol"
                            ::= {  setPerfoRttmoneEntry 1 }

setPerfoRttmoneDestinationa OBJECT-TYPE
                            SYNTAX IpAddress
                            MAX-ACCESS read-write
                            STATUS current
                            DESCRIPTION "Destination-Address"
                            ::= {  setPerfoRttmoneEntry 2 }

setPerfoRttmonePacketsize OBJECT-TYPE
                            SYNTAX INTEGER (0..65535)
                            MAX-ACCESS read-write
                            STATUS current
                            DESCRIPTION "Packet-Size"
                            ::= {  setPerfoRttmoneEntry 3 }

setPerfoRttmoneDestinationp OBJECT-TYPE
                            SYNTAX INTEGER (0..65535)
                            MAX-ACCESS read-write
                            STATUS current
                            DESCRIPTION "Destination-Port"
                            ::= {  setPerfoRttmoneEntry 5 }

setPerfoRttmoneInterval OBJECT-TYPE
                            SYNTAX INTEGER (0..2147483647)
                            MAX-ACCESS read-write
                            STATUS current
                            DESCRIPTION "Interval"
                            ::= {  setPerfoRttmoneEntry 17 }

setPerfoRttmonePacketcount OBJECT-TYPE
                            SYNTAX INTEGER (0..2147483647)
                            MAX-ACCESS read-write
                            STATUS current
                            DESCRIPTION "Packet-Count"
                            ::= {  setPerfoRttmoneEntry 18 }

setPerfoRttmonsTable OBJECT-TYPE
                     SYNTAX SEQUENCE OF SetPerfoRttmonsEntry
                     MAX-ACCESS not-accessible
                     STATUS current
                     DESCRIPTION "RttMonStatistics"
                     ::= {  setPerfo 4 }

setPerfoRttmonsEntry OBJECT-TYPE
                     SYNTAX SetPerfoRttmonsEntry
                     MAX-ACCESS not-accessible
                     STATUS current
                     DESCRIPTION "entry in table"
                     INDEX { setPerfoRttmonsIndex }
                     ::= {  setPerfoRttmonsTable 1 }

SetPerfoRttmonsEntry ::= SEQUENCE {
                     setPerfoRttmonsIndex INTEGER,
                     setPerfoRttmonsCompletions INTEGER,
                     setPerfoRttmonsRttcount INTEGER,
                     setPerfoRttmonsRttsum INTEGER,
                     setPerfoRttmonsRttmin INTEGER,
                     setPerfoRttmonsRttmax INTEGER,
                     setPerfoRttmonsJitterminpossd INTEGER,
                     setPerfoRttmonsJittermaxpossd INTEGER,
                     setPerfoRttmonsJittercountposs INTEGER,
                     setPerfoRttmonsJittersumpossd INTEGER,
                     setPerfoRttmonsJitterminposds INTEGER,
                     setPerfoRttmonsJittermaxposds INTEGER,
                     setPerfoRttmonsJittercountposd INTEGER,
                     setPerfoRttmonsJittersumposds INTEGER,
                     setPerfoRttmonsJitterminnegsd INTEGER,
                     setPerfoRttmonsJittermaxnegsd INTEGER,
                     setPerfoRttmonsJittercountnegs INTEGER,
                     setPerfoRttmonsJittersumnegsd INTEGER,
                     setPerfoRttmonsJitterminnegds INTEGER,
                     setPerfoRttmonsJittermaxnegds INTEGER,
                     setPerfoRttmonsJittercountnegd INTEGER,
                     setPerfoRttmonsJittersumnegds INTEGER,
                     setPerfoRttmonsPacketlosssd INTEGER,
                     setPerfoRttmonsPacketlossds INTEGER,
                     setPerfoRttmonsAveragejitter INTEGER,
                     setPerfoRttmonsAveragejittersd INTEGER,
                     setPerfoRttmonsAveragejitterds INTEGER
                    }

setPerfoRttmonsIndex OBJECT-TYPE
                               SYNTAX INTEGER (0..2147483647)
                               MAX-ACCESS read-only
                               STATUS current
                               DESCRIPTION "Index"
                               ::= {  setPerfoRttmonsEntry 255 }

setPerfoRttmonsCompletions OBJECT-TYPE
                               SYNTAX INTEGER (0..2147483647)
                               MAX-ACCESS read-only
                               STATUS current
                               DESCRIPTION "Completions"
                               ::= {  setPerfoRttmonsEntry 2 }

setPerfoRttmonsRttcount OBJECT-TYPE
                               SYNTAX INTEGER (0..2147483647)
                               MAX-ACCESS read-only
                               STATUS current
                               DESCRIPTION "RTT-Count"
                               ::= {  setPerfoRttmonsEntry 4 }

setPerfoRttmonsRttsum OBJECT-TYPE
                               SYNTAX INTEGER (0..2147483647)
                               MAX-ACCESS read-only
                               STATUS current
                               DESCRIPTION "RTT-Sum"
                               ::= {  setPerfoRttmonsEntry 5 }

setPerfoRttmonsRttmin OBJECT-TYPE
                               SYNTAX INTEGER (0..2147483647)
                               MAX-ACCESS read-only
                               STATUS current
                               DESCRIPTION "RTT-Min"
                               ::= {  setPerfoRttmonsEntry 8 }

setPerfoRttmonsRttmax OBJECT-TYPE
                               SYNTAX INTEGER (0..2147483647)
                               MAX-ACCESS read-only
                               STATUS current
                               DESCRIPTION "RTT-Max"
                               ::= {  setPerfoRttmonsEntry 9 }

setPerfoRttmonsJitterminpossd OBJECT-TYPE
                               SYNTAX INTEGER (0..2147483647)
                               MAX-ACCESS read-only
                               STATUS current
                               DESCRIPTION "Jitter-Min-Pos-SD"
                               ::= {  setPerfoRttmonsEntry 10 }

setPerfoRttmonsJittermaxpossd OBJECT-TYPE
                               SYNTAX INTEGER (0..2147483647)
                               MAX-ACCESS read-only
                               STATUS current
                               DESCRIPTION "Jitter-Max-Pos-SD"
                               ::= {  setPerfoRttmonsEntry 11 }

setPerfoRttmonsJittercountposs OBJECT-TYPE
                               SYNTAX INTEGER (0..2147483647)
                               MAX-ACCESS read-only
                               STATUS current
                               DESCRIPTION "Jitter-Count-Pos-SD"
                               ::= {  setPerfoRttmonsEntry 12 }

setPerfoRttmonsJittersumpossd OBJECT-TYPE
                               SYNTAX INTEGER (0..2147483647)
                               MAX-ACCESS read-only
                               STATUS current
                               DESCRIPTION "Jitter-Sum-Pos-SD"
                               ::= {  setPerfoRttmonsEntry 13 }

setPerfoRttmonsJitterminposds OBJECT-TYPE
                               SYNTAX INTEGER (0..2147483647)
                               MAX-ACCESS read-only
                               STATUS current
                               DESCRIPTION "Jitter-Min-Pos-DS"
                               ::= {  setPerfoRttmonsEntry 16 }

setPerfoRttmonsJittermaxposds OBJECT-TYPE
                               SYNTAX INTEGER (0..2147483647)
                               MAX-ACCESS read-only
                               STATUS current
                               DESCRIPTION "Jitter-Max-Pos-DS"
                               ::= {  setPerfoRttmonsEntry 17 }

setPerfoRttmonsJittercountposd OBJECT-TYPE
                               SYNTAX INTEGER (0..2147483647)
                               MAX-ACCESS read-only
                               STATUS current
                               DESCRIPTION "Jitter-Count-Pos-DS"
                               ::= {  setPerfoRttmonsEntry 18 }

setPerfoRttmonsJittersumposds OBJECT-TYPE
                               SYNTAX INTEGER (0..2147483647)
                               MAX-ACCESS read-only
                               STATUS current
                               DESCRIPTION "Jitter-Sum-Pos-DS"
                               ::= {  setPerfoRttmonsEntry 19 }

setPerfoRttmonsJitterminnegsd OBJECT-TYPE
                               SYNTAX INTEGER (0..2147483647)
                               MAX-ACCESS read-only
                               STATUS current
                               DESCRIPTION "Jitter-Min-Neg-SD"
                               ::= {  setPerfoRttmonsEntry 22 }

setPerfoRttmonsJittermaxnegsd OBJECT-TYPE
                               SYNTAX INTEGER (0..2147483647)
                               MAX-ACCESS read-only
                               STATUS current
                               DESCRIPTION "Jitter-Max-Neg-SD"
                               ::= {  setPerfoRttmonsEntry 23 }

setPerfoRttmonsJittercountnegs OBJECT-TYPE
                               SYNTAX INTEGER (0..2147483647)
                               MAX-ACCESS read-only
                               STATUS current
                               DESCRIPTION "Jitter-Count-Neg-SD"
                               ::= {  setPerfoRttmonsEntry 24 }

setPerfoRttmonsJittersumnegsd OBJECT-TYPE
                               SYNTAX INTEGER (0..2147483647)
                               MAX-ACCESS read-only
                               STATUS current
                               DESCRIPTION "Jitter-Sum-Neg-SD"
                               ::= {  setPerfoRttmonsEntry 25 }

setPerfoRttmonsJitterminnegds OBJECT-TYPE
                               SYNTAX INTEGER (0..2147483647)
                               MAX-ACCESS read-only
                               STATUS current
                               DESCRIPTION "Jitter-Min-Neg-DS"
                               ::= {  setPerfoRttmonsEntry 28 }

setPerfoRttmonsJittermaxnegds OBJECT-TYPE
                               SYNTAX INTEGER (0..2147483647)
                               MAX-ACCESS read-only
                               STATUS current
                               DESCRIPTION "Jitter-Max-Neg-DS"
                               ::= {  setPerfoRttmonsEntry 29 }

setPerfoRttmonsJittercountnegd OBJECT-TYPE
                               SYNTAX INTEGER (0..2147483647)
                               MAX-ACCESS read-only
                               STATUS current
                               DESCRIPTION "Jitter-Count-Neg-DS"
                               ::= {  setPerfoRttmonsEntry 30 }

setPerfoRttmonsJittersumnegds OBJECT-TYPE
                               SYNTAX INTEGER (0..2147483647)
                               MAX-ACCESS read-only
                               STATUS current
                               DESCRIPTION "Jitter-Sum-Neg-DS"
                               ::= {  setPerfoRttmonsEntry 31 }

setPerfoRttmonsPacketlosssd OBJECT-TYPE
                               SYNTAX INTEGER (0..2147483647)
                               MAX-ACCESS read-only
                               STATUS current
                               DESCRIPTION "Packet-Loss-SD"
                               ::= {  setPerfoRttmonsEntry 34 }

setPerfoRttmonsPacketlossds OBJECT-TYPE
                               SYNTAX INTEGER (0..2147483647)
                               MAX-ACCESS read-only
                               STATUS current
                               DESCRIPTION "Packet-Loss-DS"
                               ::= {  setPerfoRttmonsEntry 35 }

setPerfoRttmonsAveragejitter OBJECT-TYPE
                               SYNTAX INTEGER (0..2147483647)
                               MAX-ACCESS read-only
                               STATUS current
                               DESCRIPTION "Average-Jitter"
                               ::= {  setPerfoRttmonsEntry 62 }

setPerfoRttmonsAveragejittersd OBJECT-TYPE
                               SYNTAX INTEGER (0..2147483647)
                               MAX-ACCESS read-only
                               STATUS current
                               DESCRIPTION "Average-Jitter-SD"
                               ::= {  setPerfoRttmonsEntry 63 }

setPerfoRttmonsAveragejitterds OBJECT-TYPE
                               SYNTAX INTEGER (0..2147483647)
                               MAX-ACCESS read-only
                               STATUS current
                               DESCRIPTION "Average-Jitter-DS"
                               ::= {  setPerfoRttmonsEntry 64 }

setWlanm OBJECT IDENTIFIER ::= { set 37}
setWlanmStaTable OBJECT-TYPE
                 SYNTAX SEQUENCE OF SetWlanmStaEntry
                 MAX-ACCESS not-accessible
                 STATUS current
                 DESCRIPTION "Static-WLC-Configuration"
                 ::= {  setWlanm 1 }

setWlanmStaEntry OBJECT-TYPE
                 SYNTAX SetWlanmStaEntry
                 MAX-ACCESS not-accessible
                 STATUS current
                 DESCRIPTION "entry in table"
                 INDEX { setWlanmStaIpa }
                 ::= {  setWlanmStaTable 1 }

SetWlanmStaEntry ::= SEQUENCE {
                 setWlanmStaIpa DisplayString,
                 setWlanmStaPor INTEGER,
                 setWlanmStaLoo DisplayString
                }

setWlanmStaIpa OBJECT-TYPE
               SYNTAX DisplayString (SIZE(0..63))
               MAX-ACCESS read-write
               STATUS current
               DESCRIPTION "IP-Address"
               ::= {  setWlanmStaEntry 1 }

setWlanmStaPor OBJECT-TYPE
               SYNTAX INTEGER (0..65535)
               MAX-ACCESS read-write
               STATUS current
               DESCRIPTION "Port"
               ::= {  setWlanmStaEntry 2 }

setWlanmStaLoo OBJECT-TYPE
               SYNTAX DisplayString (SIZE(0..16))
               MAX-ACCESS read-write
               STATUS current
               DESCRIPTION "Loopback-Addr."
               ::= {  setWlanmStaEntry 3 }

setWlanmLog OBJECT-TYPE
            SYNTAX INTEGER
            MAX-ACCESS read-write
            STATUS current
            DESCRIPTION "Log-Entries"
            ::= {  setWlanm 120 }

firVerTable OBJECT-TYPE
            SYNTAX SEQUENCE OF FirVerEntry
            MAX-ACCESS not-accessible
            STATUS current
            DESCRIPTION "Version-Table"
            ::= {  fir 1 }

firVerEntry OBJECT-TYPE
            SYNTAX FirVerEntry
            MAX-ACCESS not-accessible
            STATUS current
            DESCRIPTION "entry in table"
            INDEX { firVerIfc }
            ::= {  firVerTable 1 }

FirVerEntry ::= SEQUENCE {
            firVerIfc INTEGER,
            firVerMod DisplayString,
            firVerVer DisplayString,
            firVerSer DisplayString
           }

firVerIfc OBJECT-TYPE
          SYNTAX INTEGER{
            ifc(1)
          }
          MAX-ACCESS read-only
          STATUS current
          DESCRIPTION "Ifc"
          ::= {  firVerEntry 1 }

firVerMod OBJECT-TYPE
          SYNTAX DisplayString (SIZE(0..64))
          MAX-ACCESS read-only
          STATUS current
          DESCRIPTION "Module"
          ::= {  firVerEntry 2 }

firVerVer OBJECT-TYPE
          SYNTAX DisplayString (SIZE(0..25))
          MAX-ACCESS read-only
          STATUS current
          DESCRIPTION "Version"
          ::= {  firVerEntry 3 }

firVerSer OBJECT-TYPE
          SYNTAX DisplayString (SIZE(0..14))
          MAX-ACCESS read-only
          STATUS current
          DESCRIPTION "Serial-number"
          ::= {  firVerEntry 4 }

firTabTable OBJECT-TYPE
            SYNTAX SEQUENCE OF FirTabEntry
            MAX-ACCESS not-accessible
            STATUS current
            DESCRIPTION "Table-Firmsafe"
            ::= {  fir 2 }

firTabEntry OBJECT-TYPE
            SYNTAX FirTabEntry
            MAX-ACCESS not-accessible
            STATUS current
            DESCRIPTION "entry in table"
            INDEX { firTabPos }
            ::= {  firTabTable 1 }

FirTabEntry ::= SEQUENCE {
            firTabPos INTEGER,
            firTabSta INTEGER,
            firTabVer DisplayString,
            firTabDat DisplayString,
            firTabSiz INTEGER,
            firTabInd INTEGER
           }

firTabPos OBJECT-TYPE
          SYNTAX INTEGER (0..255)
          MAX-ACCESS read-only
          STATUS current
          DESCRIPTION "Position"
          ::= {  firTabEntry 1 }

firTabSta OBJECT-TYPE
          SYNTAX INTEGER{
            loader(2),
            active(1),
            inactive(0),
            minimal-plus-active(5),
            minimal-plus-inactive(4)
          }
          MAX-ACCESS read-write
          STATUS current
          DESCRIPTION "Status"
          ::= {  firTabEntry 2 }

firTabVer OBJECT-TYPE
          SYNTAX DisplayString (SIZE(0..5))
          MAX-ACCESS read-only
          STATUS current
          DESCRIPTION "Version"
          ::= {  firTabEntry 3 }

firTabDat OBJECT-TYPE
          SYNTAX DisplayString (SIZE(0..9))
          MAX-ACCESS read-only
          STATUS current
          DESCRIPTION "Date"
          ::= {  firTabEntry 4 }

firTabSiz OBJECT-TYPE
          SYNTAX INTEGER (0..2147483647)
          MAX-ACCESS read-only
          STATUS current
          DESCRIPTION "Size"
          ::= {  firTabEntry 5 }

firTabInd OBJECT-TYPE
          SYNTAX INTEGER (0..2147483647)
          MAX-ACCESS read-only
          STATUS current
          DESCRIPTION "Index"
          ::= {  firTabEntry 6 }

firMod OBJECT-TYPE
       SYNTAX INTEGER {
         immediate(0),
         login(1),
         manual(2)
       }
       MAX-ACCESS read-write
       STATUS current
       DESCRIPTION "Mode-Firmsafe"
       ::= {  fir 3 }

firTim OBJECT-TYPE
       SYNTAX INTEGER
       MAX-ACCESS read-write
       STATUS current
       DESCRIPTION "Timeout-Firmsafe"
       ::= {  fir 4 }

firFea OBJECT-TYPE
       SYNTAX DisplayString (SIZE(0..34))
       MAX-ACCESS read-only
       STATUS current
       DESCRIPTION "Feature-Word"
       ::= {  fir 7 }

othMan OBJECT IDENTIFIER ::= { oth 1}
othManCon OBJECT-TYPE
          SYNTAX DisplayString
          MAX-ACCESS read-write
          STATUS current
          DESCRIPTION "Connect"
          ::= {  othMan 1 }

othManDis OBJECT-TYPE
          SYNTAX DisplayString
          MAX-ACCESS read-write
          STATUS current
          DESCRIPTION "Disconnect"
          ::= {  othMan 2 }

othBoo OBJECT-TYPE
       SYNTAX DisplayString
       MAX-ACCESS read-write
       STATUS current
       DESCRIPTION "Boot-System"
       ::= {  oth 2 }

othCol OBJECT-TYPE
       SYNTAX DisplayString
       MAX-ACCESS read-write
       STATUS current
       DESCRIPTION "Cold-Boot"
       ::= {  oth 5 }



-- traps

trapgrp OBJECT IDENTIFIER ::= { lancom-l54g 0 }
traps   OBJECT IDENTIFIER ::= { trapgrp 0 }

trpStatChan NOTIFICATION-TYPE
            OBJECTS {
             sysDescr,
             sysName,
             staSnmpEveCou,
             staWanConnectio,
             staChannState,
             staChannApp,
             staChannMode,
             staChannCause,
             staChannNumbe,
             staChannSubad,
             staChannCharg,
             staChannExtra,
             staChannConnt,
             staChannConns,
             staChannIsdnd,
             staChannPhcha,
             staChannPptpc
            }
            STATUS current
            DESCRIPTION "StatChan"
            ::= { traps 1 }

trpFwUplStart NOTIFICATION-TYPE
              OBJECTS {
               sysDescr,
               sysName,
               staSnmpEveCou,
               staConfiEventlogSyste,
               staConfiEventlogEvent,
               staConfiEventlogAcces,
               staConfiEventlogIpadd
              }
              STATUS current
              DESCRIPTION "FwUplStart"
              ::= { traps 4 }

trpUplSucc NOTIFICATION-TYPE
           OBJECTS {
            sysDescr,
            sysName,
            staSnmpEveCou,
            staConfiEventlogSyste,
            staConfiEventlogEvent,
            staConfiEventlogAcces,
            staConfiEventlogIpadd,
            staConfiEventlogInfo1,
            staConfiEventlogInfo2
           }
           STATUS current
           DESCRIPTION "UplSucc"
           ::= { traps 5 }

trpUplFailTo NOTIFICATION-TYPE
             OBJECTS {
              sysDescr,
              sysName,
              staSnmpEveCou,
              staConfiEventlogSyste,
              staConfiEventlogEvent,
              staConfiEventlogAcces,
              staConfiEventlogIpadd,
              staConfiEventlogInfo1,
              staConfiEventlogInfo2
             }
             STATUS current
             DESCRIPTION "UplFailTo"
             ::= { traps 6 }

trpUplFailIncl NOTIFICATION-TYPE
               OBJECTS {
                sysDescr,
                sysName,
                staSnmpEveCou,
                staConfiEventlogSyste,
                staConfiEventlogEvent,
                staConfiEventlogAcces,
                staConfiEventlogIpadd,
                staConfiEventlogInfo1,
                staConfiEventlogInfo2
               }
               STATUS current
               DESCRIPTION "UplFailIncl"
               ::= { traps 7 }

trpUplFailBadDev NOTIFICATION-TYPE
                 OBJECTS {
                  sysDescr,
                  sysName,
                  staSnmpEveCou,
                  staConfiEventlogSyste,
                  staConfiEventlogEvent,
                  staConfiEventlogAcces,
                  staConfiEventlogIpadd,
                  staConfiEventlogInfo1,
                  staConfiEventlogInfo2
                 }
                 STATUS current
                 DESCRIPTION "UplFailBadDev"
                 ::= { traps 8 }

trpLogin NOTIFICATION-TYPE
         OBJECTS {
          sysDescr,
          sysName,
          staSnmpEveCou,
          staConfiEventlogSyste,
          staConfiEventlogEvent,
          staConfiEventlogAcces,
          staConfiEventlogIpadd
         }
         STATUS current
         DESCRIPTION "Login"
         ::= { traps 9 }

trpLogout NOTIFICATION-TYPE
          OBJECTS {
           sysDescr,
           sysName,
           staSnmpEveCou,
           staConfiEventlogSyste,
           staConfiEventlogEvent,
           staConfiEventlogAcces,
           staConfiEventlogIpadd
          }
          STATUS current
          DESCRIPTION "Logout"
          ::= { traps 10 }

trpCnfUplStart NOTIFICATION-TYPE
               OBJECTS {
                sysDescr,
                sysName,
                staSnmpEveCou,
                staConfiEventlogSyste,
                staConfiEventlogEvent,
                staConfiEventlogAcces,
                staConfiEventlogIpadd
               }
               STATUS current
               DESCRIPTION "CnfUplStart"
               ::= { traps 11 }

trpCnfDnlStart NOTIFICATION-TYPE
               OBJECTS {
                sysDescr,
                sysName,
                staSnmpEveCou,
                staConfiEventlogSyste,
                staConfiEventlogEvent,
                staConfiEventlogAcces,
                staConfiEventlogIpadd
               }
               STATUS current
               DESCRIPTION "CnfDnlStart"
               ::= { traps 12 }

trpCnfDnlSucc NOTIFICATION-TYPE
              OBJECTS {
               sysDescr,
               sysName,
               staSnmpEveCou,
               staConfiEventlogSyste,
               staConfiEventlogEvent,
               staConfiEventlogAcces,
               staConfiEventlogIpadd,
               staConfiEventlogInfo1,
               staConfiEventlogInfo2
              }
              STATUS current
              DESCRIPTION "CnfDnlSucc"
              ::= { traps 13 }

trpBssScan NOTIFICATION-TYPE
           OBJECTS {
            sysDescr,
            sysName,
            staSnmpEveCou,
            staWlanInterfIfc
           }
           STATUS current
           DESCRIPTION "BssScan"
           ::= { traps 14 }

trpBssStart NOTIFICATION-TYPE
            OBJECTS {
             sysDescr,
             sysName,
             staSnmpEveCou,
             staWlanWlanpaIfc,
             staWlanNetworBss
            }
            STATUS current
            DESCRIPTION "BssStart"
            ::= { traps 15 }

trpBssJoin NOTIFICATION-TYPE
           OBJECTS {
            sysDescr,
            sysName,
            staSnmpEveCou,
            staWlanWlanpaIfc,
            staWlanNetworBss
           }
           STATUS current
           DESCRIPTION "BssJoin"
           ::= { traps 16 }

trpAuthStation NOTIFICATION-TYPE
               OBJECTS {
                sysDescr,
                sysName,
                staSnmpEveCou,
                staWlanStatioMacadd,
                staWlanStatioIdenti
               }
               STATUS current
               DESCRIPTION "AuthStation"
               ::= { traps 17 }

trpDeAuthStation NOTIFICATION-TYPE
                 OBJECTS {
                  sysDescr,
                  sysName,
                  staSnmpEveCou,
                  staWlanStatioMacadd,
                  staWlanStatioIdenti
                 }
                 STATUS current
                 DESCRIPTION "DeAuthStation"
                 ::= { traps 18 }

trpAssStation NOTIFICATION-TYPE
              OBJECTS {
               sysDescr,
               sysName,
               staSnmpEveCou,
               staWlanStatioMacadd,
               staWlanStatioIdenti
              }
              STATUS current
              DESCRIPTION "AssStation"
              ::= { traps 19 }

trpReAssStation NOTIFICATION-TYPE
                OBJECTS {
                 sysDescr,
                 sysName,
                 staSnmpEveCou,
                 staWlanStatioMacadd,
                 staWlanStatioIdenti
                }
                STATUS current
                DESCRIPTION "ReAssStation"
                ::= { traps 20 }

trpDisAssStation NOTIFICATION-TYPE
                 OBJECTS {
                  sysDescr,
                  sysName,
                  staSnmpEveCou,
                  staWlanStatioMacadd,
                  staWlanStatioIdenti
                 }
                 STATUS current
                 DESCRIPTION "DisAssStation"
                 ::= { traps 21 }

trpAssRej NOTIFICATION-TYPE
          OBJECTS {
           sysDescr,
           sysName,
           staSnmpEveCou,
           staWlanLogtabAdd
          }
          STATUS current
          DESCRIPTION "AssRej"
          ::= { traps 22 }

trpCardHung NOTIFICATION-TYPE
            OBJECTS {
             sysDescr,
             sysName,
             staSnmpEveCou,
             staWlanInterfIfc
            }
            STATUS current
            DESCRIPTION "CardHung"
            ::= { traps 25 }

trpIpFwFlt NOTIFICATION-TYPE
           OBJECTS {
            sysDescr,
            sysName,
            staSnmpEveCou,
            staIprouLogtablSyst,
            staIprouLogtablSrca,
            staIprouLogtablDsta,
            staIprouLogtablProt,
            staIprouLogtablSrcp,
            staIprouLogtablDstp,
            staIprouLogtablFilt,
            staIprouLogtablLimi,
            staIprouLogtablThre,
            staIprouLogtablActi
           }
           STATUS current
           DESCRIPTION "IpFwFlt"
           ::= { traps 26 }

trpPptpConn NOTIFICATION-TYPE
            OBJECTS {
             sysDescr,
             sysName,
             staSnmpEveCou,
             staPptpTun,
             staPptpConChann,
             staPptpConState,
             staPptpConMode,
             staPptpConShtim,
             staPptpConPhysc,
             staPptpConPeera,
             staPptpConIpadd,
             staPptpConDnsde,
             staPptpConNbnsd,
             staPptpConLaste,
             staPptpConDnsba,
             staPptpConNbnsb
            }
            STATUS current
            DESCRIPTION "PptpConn"
            ::= { traps 28 }

trpErrLogin NOTIFICATION-TYPE
            OBJECTS {
             sysDescr,
             sysName,
             staSnmpEveCou,
             staConfiEventlogSyste,
             staConfiEventlogEvent,
             staConfiEventlogAcces,
             staConfiEventlogIpadd
            }
            STATUS current
            DESCRIPTION "ErrLogin"
            ::= { traps 29 }

trpKeyhandshake-Timeout NOTIFICATION-TYPE
                        OBJECTS {
                         sysDescr,
                         sysName,
                         staSnmpEveCou
                        }
                        STATUS current
                        DESCRIPTION "Keyhandshake-Timeout"
                        ::= { traps 33 }

trpSupervision NOTIFICATION-TYPE
               OBJECTS {
                sysDescr,
                sysName,
                staSnmpEveCou,
                staWlanStatioMacadd,
                staWlanStatioIdenti
               }
               STATUS current
               DESCRIPTION "Supervision"
               ::= { traps 35 }

trpPPPoESConn NOTIFICATION-TYPE
              OBJECTS {
               sysDescr,
               sysName,
               staSnmpEveCou,
               staPppoeNum,
               staPppoeConCha,
               staPppoeConMac,
               staPppoeConSta,
               staPppoeConLas,
               staPppoeConSht,
               staPppoeConPee
              }
              STATUS current
              DESCRIPTION "PPPoESConn"
              ::= { traps 39 }

trpVrrp NOTIFICATION-TYPE
        OBJECTS {
         sysDescr,
         sysName,
         staSnmpEveCou,
         staIprouVrrpEveSys,
         staIprouVrrpEveSrc,
         staIprouVrrpEveVri,
         staIprouVrrpEveEve,
         staIprouVrrpEveInf
        }
        STATUS current
        DESCRIPTION "Vrrp"
        ::= { traps 41 }

trpExcEirp NOTIFICATION-TYPE
           OBJECTS {
            sysDescr,
            sysName,
            staSnmpEveCou,
            staWlanWlanpaIfc,
            staWlanWlanpaEirp
           }
           STATUS current
           DESCRIPTION "ExcEirp"
           ::= { traps 42 }

trpIdle-Timeout NOTIFICATION-TYPE
                OBJECTS {
                 sysDescr,
                 sysName,
                 staSnmpEveCou
                }
                STATUS current
                DESCRIPTION "Idle-Timeout"
                ::= { traps 46 }

trpAdmin-Deassoc NOTIFICATION-TYPE
                 OBJECTS {
                  sysDescr,
                  sysName,
                  staSnmpEveCou,
                  staWlanStatioMacadd,
                  staWlanStatioIdenti
                 }
                 STATUS current
                 DESCRIPTION "Admin-Deassoc"
                 ::= { traps 47 }

trpMacChkFail NOTIFICATION-TYPE
              OBJECTS {
               sysDescr,
               sysName,
               staSnmpEveCou,
               staWlanStatioMacadd,
               staWlanStatioIdenti
              }
              STATUS current
              DESCRIPTION "MacChkFail"
              ::= { traps 52 }

trpRoamed NOTIFICATION-TYPE
          OBJECTS {
           sysDescr,
           sysName,
           staSnmpEveCou,
           staWlanStatioMacadd,
           staWlanStatioIdenti
          }
          STATUS current
          DESCRIPTION "Roamed"
          ::= { traps 53 }

trpConnected NOTIFICATION-TYPE
             OBJECTS {
              sysDescr,
              sysName,
              staSnmpEveCou,
              staWlanStatioMacadd,
              staWlanStatioIdenti
             }
             STATUS current
             DESCRIPTION "Connected"
             ::= { traps 54 }

trpCl-LostConn NOTIFICATION-TYPE
               OBJECTS {
                sysDescr,
                sysName,
                staSnmpEveCou,
                staWlanClientInterfIfc,
                staWlanClientInterfState
               }
               STATUS current
               DESCRIPTION "Cl.-LostConn"
               ::= { traps 55 }

trpCl-AuthFail NOTIFICATION-TYPE
               OBJECTS {
                sysDescr,
                sysName,
                staSnmpEveCou,
                staWlanClientInterfIfc,
                staWlanClientInterfState
               }
               STATUS current
               DESCRIPTION "Cl.-AuthFail"
               ::= { traps 56 }

trpCl-AssocFail NOTIFICATION-TYPE
                OBJECTS {
                 sysDescr,
                 sysName,
                 staSnmpEveCou,
                 staWlanClientInterfIfc,
                 staWlanClientInterfState
                }
                STATUS current
                DESCRIPTION "Cl.-AssocFail"
                ::= { traps 57 }

trpCl-Connected NOTIFICATION-TYPE
                OBJECTS {
                 sysDescr,
                 sysName,
                 staSnmpEveCou,
                 staWlanClientInterfIfc,
                 staWlanClientInterfState
                }
                STATUS current
                DESCRIPTION "Cl.-Connected"
                ::= { traps 58 }

trpCl-802-1x-Fail NOTIFICATION-TYPE
                  OBJECTS {
                   sysDescr,
                   sysName,
                   staSnmpEveCou,
                   staWlanClientInterfIfc,
                   staWlanClientInterfState
                  }
                  STATUS current
                  DESCRIPTION "Cl.-802.1x-Fail"
                  ::= { traps 59 }

trpSpGtReE-pOrTsTaTcHg NOTIFICATION-TYPE
                       OBJECTS {
                        sysDescr,
                        sysName,
                        staSnmpEveCou,
                        staLanbrSpaPorttabDes,
                        staLanbrSpaPorttabSta,
                        staLanbrSpaPorttabPat
                       }
                       STATUS current
                       DESCRIPTION "SpGtReE-pOrTsTaTcHg"
                       ::= { traps 1000 }

trpSpGtReE-rStPsTaTcHg NOTIFICATION-TYPE
                       OBJECTS {
                        sysDescr,
                        sysName,
                        staSnmpEveCou,
                        staLanbrSpaRstpporDes,
                        staLanbrSpaRstpporRol,
                        staLanbrSpaRstpporLea,
                        staLanbrSpaRstpporFor,
                        staLanbrSpaRstpporEdg,
                        staLanbrSpaRstpporPro,
                        staLanbrSpaRstpporPat
                       }
                       STATUS current
                       DESCRIPTION "SpGtReE-rStPsTaTcHg"
                       ::= { traps 1001 }

trpSpGtReE-rOoTpOrTcHg NOTIFICATION-TYPE
                       OBJECTS {
                        sysDescr,
                        sysName,
                        staSnmpEveCou,
                        staLanbrSpaRootbri,
                        staLanbrSpaRootpor,
                        staLanbrSpaRootpat
                       }
                       STATUS current
                       DESCRIPTION "SpGtReE-rOoTpOrTcHg"
                       ::= { traps 1002 }

trpHTTP-Tunnel-Open NOTIFICATION-TYPE
                    OBJECTS {
                     sysDescr,
                     sysName,
                     staSnmpEveCou,
                     staTcpipHttpActiveIndex,
                     staTcpipHttpActiveRemotea,
                     staTcpipHttpActiveRemotep,
                     staTcpipHttpActiveLocalho,
                     staTcpipHttpActiveLocalpo,
                     staTcpipHttpActiveIdletim,
                     staTcpipHttpActiveLocalrt
                    }
                    STATUS current
                    DESCRIPTION "HTTP-Tunnel-Open"
                    ::= { traps 2000 }

trpHTTP-Tunnel-Close NOTIFICATION-TYPE
                     OBJECTS {
                      sysDescr,
                      sysName,
                      staSnmpEveCou,
                      staTcpipHttpActiveIndex
                     }
                     STATUS current
                     DESCRIPTION "HTTP-Tunnel-Close"
                     ::= { traps 2001 }

END
