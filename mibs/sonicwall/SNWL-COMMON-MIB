-- *****************************************************************
-- SNWL-COMMON-MIB
--
-- 11-09-07 - Initial Version, Mike Uy
-- 03-10-08 - Removed Imports that are not used to prevent warnings
--            in MIB compilation, Mike Uy 
-- 04-17-09 - Updated E-mail CONTACT-INFO, Rosalea Real
-- 11-11-09 - Updated SonicWALL company address, Mike Uy
-- 07-23-12 - Updated company copyright and organization, Mike Uy
--
-- Copyright (c) 2012 DELL Inc.
-- All rights reserved.
-- *****************************************************************

SNWL-COMMON-MIB DEFINITIONS ::= BEGIN


IMPORTS
    DisplayString			 	FROM SNMPv2-TC

    OBJECT-TYPE,
	MODULE-IDENTITY             FROM SNMPv2-SMI

    sonicwallCommon        		FROM SONICWALL-SMI;

snwlCommonModule MODULE-IDENTITY
	LAST-UPDATED "201207230000Z"
	ORGANIZATION "DELL SonicWall"
	CONTACT-INFO
		"	DELL SonicWall

		   Postal: 2001 Logic Drive
				   San Jose, CA 95124-3452
				   USA

		   Tel: +1 408 745 9600
		   Fax: +1 408 745 9300

		E-mail: products@sonicwall.com"
	DESCRIPTION
		"This MIB module defines functions and features common
		 across all SonicWALL products and platforms."
	REVISION      "200711090000Z"
	DESCRIPTION
		"Initial Version"
    ::= { sonicwallCommon 1 }

-- =======================
-- System Group Lists
-- =======================

snwlSys OBJECT IDENTIFIER ::= { snwlCommonModule 1 }

-- Start of System Group --

snwlSysModel OBJECT-TYPE
	SYNTAX DisplayString
	MAX-ACCESS read-only
	STATUS current
	DESCRIPTION
		"System model name and number"
	::= { snwlSys 1 }

snwlSysSerialNumber OBJECT-TYPE
	SYNTAX DisplayString 
	MAX-ACCESS read-only
	STATUS current
	DESCRIPTION
		"System serial number for this device"
	::= { snwlSys 2 }

snwlSysFirmwareVersion OBJECT-TYPE
	SYNTAX DisplayString 
	MAX-ACCESS read-only
	STATUS current
	DESCRIPTION
		"Current system firmware version"
	::= { snwlSys 3 }

snwlSysROMVersion OBJECT-TYPE
	SYNTAX DisplayString 
	MAX-ACCESS read-only
	STATUS current
	DESCRIPTION
		"Current system ROM version"
	::= { snwlSys 4 }

snwlSysAssetNumber OBJECT-TYPE
	SYNTAX DisplayString 
	MAX-ACCESS read-only
	STATUS current
	DESCRIPTION
		"user-defined string entry used for asset tracking"
	::= { snwlSys 5 }

-- End of System Group --

END
