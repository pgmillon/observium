-- ==========================================================================
-- Copyright (C) 2002 by  HUAWEI TECHNOLOGIES. All rights reserved.
--
-- Description: The purpose of this MIB file is to provide the define of
--              the voice aaa client MIB of HUAWEI 
--              quidway serial router.
-- Reference:
-- Version: V2.0
-- History:
-- V1.0 Initial version
-- V2.0 2004-10-20 Updated by gaolong
--      Re-write whole MIB with SNMPv2-SMI format.
--      Modify module name from 'HUAWEI-AAA-CLIENT-MIB' to 'HUAWEI-VO-AAA-CLIENT-MIB'
-- ==========================================================================
HUAWEI-VO-AAA-CLIENT-MIB DEFINITIONS ::= BEGIN

	IMPORTS			
		OBJECT-TYPE, MODULE-IDENTITY
			FROM SNMPv2-SMI
		voice
			FROM HUAWEI-3COM-OID-MIB;
		
		hwVoiceAAAClientMIB MODULE-IDENTITY 
			LAST-UPDATED "200410200000Z"		-- Oct 20, 2004  GMT
			ORGANIZATION 
				"Huawei-3COM Technologies Co., Ltd."
			CONTACT-INFO 
				"PLAT Team Huawei 3Com Technologies co.,Ltd.								
				Shang-Di Information Industry Base,
				Hai-Dian District Beijing P.R. China
				http://www.huawei-3com.com
				Zip:100085"
			DESCRIPTION 
				" "
			REVISION "200404081345Z"		-- April 08, 2004 at 13:45 GMT
			DESCRIPTION 
				""
			::= { voice 9 }

EntryStatus ::= INTEGER
                         { valid(1),
                           createRequest(2),
                           underCreation(3),
                           invalid(4)
                         }		
--  The status of a table entry.
-- 
-- Setting this object to the value invalid(4) has the
-- effect of invalidating the corresponding entry.
-- That is, it effectively disassociates the mapping
-- identified with said entry.
-- It is an implementation-specific matter as to whether
-- the agent removes an invalidated entry from the table.
-- Accordingly, management stations must be prepared to
-- receive tabular information from agents that
-- corresponds to entries currently not in use.  Proper
-- interpretation of such entries requires examination
-- of the relevant EntryStatus object.
-- 
-- An existing instance of this object cannot be set to
-- createRequest(2).  This object may only be set to
-- createRequest(2) when this instance is created.  When
-- this object is created, the agent may wish to create
-- supplemental object instances with default values
-- to complete a conceptual row in this table.  Because
-- the creation of these default objects is entirely at
-- the option of the agent, the manager must not assume
-- that any will be created, but may make use of any that
-- are created. Immediately after completing the create
-- operation, the agent must set this object to
-- underCreation(3).
-- 
-- When in the underCreation(3) state, an entry is
-- allowed to exist in a possibly incomplete, possibly
-- inconsistent state, usually to allow it to be
-- modified in mutiple PDUs.  When in this state, an
-- entry is not fully active.  Entries shall exist in
-- the underCreation(3) state until the management
-- station is finished configuring the entry and sets
-- this object to valid(1) or aborts, setting this
-- object to invalid(4).  If the agent determines that
-- an entry has been in the underCreation(3) state for
-- an abnormally long time, it may decide that the
-- management station has crashed.  If the agent makes
-- this decision, it may set this object to invalid(4)
-- to reclaim the entry.  A prudent agent will
-- understand that the management station may need to
-- wait for human input and will allow for that
-- possibility in its determination of this abnormally
-- long period.
-- 
-- An entry in the valid(1) state is fully configured and
-- consistent and fully represents the configuration or
-- operation such a row is intended to represent.  For
-- example, it could be a statistical function that is
-- configured and active, or a filter that is available
-- in the list of filters processed by the packet capture
-- process.
-- 
-- A manager is restricted to changing the state of an
-- entry in the following ways:
-- 
--                       create   under
--      To:       valid  Request  Creation  invalid
-- From:
-- valid             OK       NO        OK       OK
-- createRequest    N/A      N/A       N/A      N/A
-- underCreation     OK       NO        OK       OK
-- invalid           NO       NO        NO       OK
-- nonExistent       NO       OK        NO       OK
-- 
-- In the table above, it is not applicable to move the
-- state from the createRequest state to any other
-- state because the manager will never find the
-- variable in that state.  The nonExistent state is
-- not a value of the enumeration, rather it means that
-- the entryStatus variable does not exist at all.
-- 
-- An agent may allow an entryStatus variable to change
-- state in additional ways, so long as the semantics
-- of the states are followed.  This allowance is made
-- to ease the implementation of the agent and is made
-- despite the fact that managers should never
-- excercise these additional state transitions.
		hwVoAAAClientObjects OBJECT IDENTIFIER ::= { hwVoiceAAAClientMIB 1 }

		
--  AAA Client Configuration Object Group
-- 
-- The objects in this group describe and store the configuration parameters
--  on the AAA Client function of this gateway which based on Authentication, 
--  Authorization, Accounting (AAA) protocols.
		hwVoAAAClientCfgObjects OBJECT IDENTIFIER ::= { hwVoAAAClientObjects 1 }

		
		hwVoAAAEnable OBJECT-TYPE
			SYNTAX INTEGER
				{
				enable(1),
				disable(2)
				}
			MAX-ACCESS read-write
			STATUS current
			DESCRIPTION
				"Whether or not the AAA service is enabled "
			DEFVAL { disable }
			::= { hwVoAAAClientCfgObjects 1 }

		
		hwVoAAAClienttype OBJECT-TYPE
			SYNTAX INTEGER
				{
				huawei(1),
				nonstandard-compatible-vsa(2),
				nonstandard-compatible-overload(3),
				ietf-rfc(4)
				}
			MAX-ACCESS read-write
			STATUS current
			DESCRIPTION
				"The AAA client type of this gateway."
			DEFVAL { huawei }
			::= { hwVoAAAClientCfgObjects 2 }

		
		hwVoAAAGwAuthenDidH323 OBJECT-TYPE
			SYNTAX INTEGER
				{
				enable(1),
				disable(2)
				}
			MAX-ACCESS read-write
			STATUS current
			DESCRIPTION
				"Whether or not the Authentication of this gateway is enabled. "
			DEFVAL { disable }
			::= { hwVoAAAClientCfgObjects 3 }

		
		hwVoAAAGwAuthorDidH323 OBJECT-TYPE
			SYNTAX INTEGER
				{
				enable(1),
				disable(2)
				}
			MAX-ACCESS read-write
			STATUS current
			DESCRIPTION
				"Whether or not the Authorization of this gateway is enabled.When
				hwVoAAAGwAuthenDidH323 is disabled,this object cannot be set to 
				enable .
				"
			DEFVAL { disable }
			::= { hwVoAAAClientCfgObjects 4 }

		
		hwVoAAAGwAccounting OBJECT-TYPE
			SYNTAX INTEGER
				{
				enable(1),
				disable(2)
				}
			MAX-ACCESS read-write
			STATUS current
			DESCRIPTION
				"Whether or not the Accounting of this gateway is enabled."
			DEFVAL { disable }
			::= { hwVoAAAClientCfgObjects 5 }

		hwVoAAAGwAccountMethod OBJECT-TYPE
			SYNTAX INTEGER
				{
				none(1),
				start-ack(2),
				start-no-ack(3),
				stop-only(4)
				}
			MAX-ACCESS read-write
			STATUS current
			DESCRIPTION
				"Set the sending mode of accounting packets of this gateway
                    none          No accounting
                    start-ack     send start accounting packets waiting the answer.
                    start-no-ack  send start and stop accounting packets without waiting answer.
                    stop-only     send stop accounting packets waiting the answer.				
				"
			DEFVAL { start-no-ack }
			::= { hwVoAAAClientCfgObjects 6 }

--  AAA Client Local User Table
-- 
-- hwVoAAAClientLocalUserTable
-- Table to store the AAA client user information. The  information 
-- will include the user name and  the user's password. 
		hwVoAAAClientLocalUserTable OBJECT-TYPE
			SYNTAX SEQUENCE OF HWVoAAAClientLocalUserEntry
			MAX-ACCESS not-accessible
			STATUS current
			DESCRIPTION
				"The table contains the information of the AAA client local user ."
			::= { hwVoAAAClientObjects 2 }

		
		hwVoAAAClientLocalUserEntry OBJECT-TYPE
			SYNTAX HWVoAAAClientLocalUserEntry
			MAX-ACCESS not-accessible
			STATUS current
			DESCRIPTION
				"The information regarding a single AAA client local user."
			INDEX { hwVoAAAClientLocalUserName }
			::= { hwVoAAAClientLocalUserTable 1 }

		
		HWVoAAAClientLocalUserEntry ::=
			SEQUENCE { 
				hwVoAAAClientLocalUserName
					OCTET STRING,
				hwVoAAAClientLocalUserPassword
					OCTET STRING,
				hwVoAAAClientLocalRowStatus
					EntryStatus
			 }

		hwVoAAAClientLocalUserName OBJECT-TYPE
			SYNTAX OCTET STRING (SIZE (1..16))
			MAX-ACCESS read-only
			STATUS current
			DESCRIPTION
				"The name of the AAA client local user. "
			::= { hwVoAAAClientLocalUserEntry 1 }

		
		hwVoAAAClientLocalUserPassword OBJECT-TYPE
			SYNTAX OCTET STRING (SIZE (0..16))
			MAX-ACCESS read-write
			STATUS current
			DESCRIPTION
				"The password of the AAA client local user."
			::= { hwVoAAAClientLocalUserEntry 2 }

		
		hwVoAAAClientLocalRowStatus OBJECT-TYPE
			SYNTAX EntryStatus
			MAX-ACCESS read-write
			STATUS current
			DESCRIPTION
				"This object is used to create a new row or modify or
				delete an existing row in this table. "
			::= { hwVoAAAClientLocalUserEntry 3 }

		
--  AAA Gateway Access Number Table
-- 
-- hwVoAAAGwAccessNumberTable
-- Table to store the AAA access number and it's service process attribte of
-- this gateway. The  information will include the access number,the card digit
-- the password digit,the redial times and so on.
		hwVoAAAGwAccessNumberTable OBJECT-TYPE
			SYNTAX SEQUENCE OF HWVoAAAGwAccessNumberEntry
			MAX-ACCESS not-accessible
			STATUS current
			DESCRIPTION
				"The table contains the information of the AAA access number ."
			::= { hwVoAAAClientObjects 3 }

		
		hwVoAAAGwAccessNumberEntry OBJECT-TYPE
			SYNTAX HWVoAAAGwAccessNumberEntry
			MAX-ACCESS not-accessible
			STATUS current
			DESCRIPTION
				"The information regarding a single access number."
			INDEX { hwVoAAAGwAccessnumber }
			::= { hwVoAAAGwAccessNumberTable 1 }

		
		HWVoAAAGwAccessNumberEntry ::=
			SEQUENCE { 
				hwVoAAAGwAccessnumber
					OCTET STRING,
				hwVoAAAGwAuthentication
					INTEGER,
				hwVoAAAGwAuthorization
					INTEGER,
				hwVoAAAGwProcessConfig
					INTEGER,
				hwVoAAAGwCardDigit
					INTEGER,
				hwVoAAAGwPasswordDigit
					INTEGER,
				hwVoAAAGwRedialtimes
					INTEGER,
				hwVoAAAGwRowStatus
					EntryStatus
			 }

		hwVoAAAGwAccessnumber OBJECT-TYPE
			SYNTAX OCTET STRING (SIZE (1..31))
			MAX-ACCESS read-only
			STATUS current
			DESCRIPTION
				"The access number of the AAA client . In this string only character
				from '0' to '9' can present."
			::= { hwVoAAAGwAccessNumberEntry 1 }

		
		hwVoAAAGwAuthentication OBJECT-TYPE
			SYNTAX INTEGER
				{
				enable(1),
				disable(2)
				}
			MAX-ACCESS read-write
			STATUS current
			DESCRIPTION
				"Whether or not the Authentication of this access number is enabled."
			DEFVAL { disable }
			::= { hwVoAAAGwAccessNumberEntry 2 }

		
		hwVoAAAGwAuthorization OBJECT-TYPE
			SYNTAX INTEGER
				{
				enable(1),
				disable(2)
				}
			MAX-ACCESS read-write
			STATUS current
			DESCRIPTION
				"Whether or not the Authorization of this access number is enabled.When
				hwVoAAAGwAuthentication of this access number is disabled,this object 
				cannot be set to enable ."
			DEFVAL { disable }
			::= { hwVoAAAGwAccessNumberEntry 3 }

		
		hwVoAAAGwProcessConfig OBJECT-TYPE
			SYNTAX INTEGER
				{
				callernumber(1),
				cardnumber(2)
				}
			MAX-ACCESS read-write
			STATUS current
			DESCRIPTION
				"The dial process type of this access number ."
			DEFVAL { cardnumber }
			::= { hwVoAAAGwAccessNumberEntry 4 }

		
		hwVoAAAGwCardDigit OBJECT-TYPE
			SYNTAX INTEGER (1..31)
			MAX-ACCESS read-write
			STATUS current
			DESCRIPTION
				"The card number digit of this access number."
			DEFVAL { 12 }
			::= { hwVoAAAGwAccessNumberEntry 5 }

		
		hwVoAAAGwPasswordDigit OBJECT-TYPE
			SYNTAX INTEGER (1..16)
			MAX-ACCESS read-write
			STATUS current
			DESCRIPTION
				"The password digit of this access number. "
			DEFVAL { 6 }
			::= { hwVoAAAGwAccessNumberEntry 6 }

		
		hwVoAAAGwRedialtimes OBJECT-TYPE
			SYNTAX INTEGER (1..10)
			MAX-ACCESS read-write
			STATUS current
			DESCRIPTION
				"The redial times of this access number. "
			DEFVAL { 3 }
			::= { hwVoAAAGwAccessNumberEntry 7 }

		
		hwVoAAAGwRowStatus OBJECT-TYPE
			SYNTAX EntryStatus
			MAX-ACCESS read-write
			STATUS current
			DESCRIPTION
				"This object is used to create a new row or modify or
				delete an existing row in this table. "
			::= { hwVoAAAGwAccessNumberEntry 8 }

		
	
	END
