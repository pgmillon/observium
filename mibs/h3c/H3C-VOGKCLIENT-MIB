-- ==========================================================================
-- Copyright (C) 2004 by Huawei 3Com Technologies. All rights reserved.
--
-- Description: The purpose of this MIB file is to provide the the definition 
--              of GK(Gate Keeper) client configuration.
-- Reference:
-- Version: V1.0
-- History:
-- V1.0 2005-03-22 Initial version, created by Yang Youku
-- ==========================================================================
H3C-VOGKCLIENT-MIB DEFINITIONS ::= BEGIN
    IMPORTS
        OBJECT-TYPE, MODULE-IDENTITY, IpAddress, Integer32
            FROM SNMPv2-SMI
        InetAddressType, InetAddress
             FROM INET-ADDRESS-MIB
        h3cVoice
            FROM HUAWEI-3COM-OID-MIB;   
    
    
            
        h3cVoiceGKClient MODULE-IDENTITY 
            LAST-UPDATED "200503150000Z"
            ORGANIZATION 
                "Huawei-3COM Technologies Co., Ltd."
            CONTACT-INFO 
                "PLAT Team Huawei 3Com Technologies co.,Ltd.                                
                Shang-Di Information Industry Base,
                Hai-Dian District Beijing P.R. China
                http://www.huawei-3com.com
                Zip:100085"
            DESCRIPTION 
                "This MIB file is to provide the the definition of GK 
                client configuration."
            REVISION "200503150000Z"
            DESCRIPTION 
                "The initial version of this MIB file."
            ::= { h3cVoice 8 }

--===========================================================================
--                       h3cVoGKClientObjects
--
--===========================================================================
        h3cVoGKClientObjects OBJECT IDENTIFIER ::= { h3cVoiceGKClient 1 }

        
        h3cVoRasOn OBJECT-TYPE
            SYNTAX INTEGER
                {
                enable(1),
                disable(2)
                }
            MAX-ACCESS read-write
            STATUS current
            DESCRIPTION
                "This object indicates whether the GK(Gate Keeper) client 
                function of this gateaway is enabled. 
                The value couldn't be set to enable unless h3cVoH323GWID,
                h3cVoGwIPAddress, h3cVoH323GKIPAddress, and h3cVoH323GKID 
                has been set."
            ::= { h3cVoGKClientObjects 1 }

        
        h3cVoGwIPAddressType OBJECT-TYPE
            SYNTAX  InetAddressType
            MAX-ACCESS read-write
            STATUS current
            DESCRIPTION
                "This object indicates the IP address type of the the interface 
                through which the gateway is connected to the GK(Gate Keeper).
                The value couldn't be modified unless h3cVoRasOn is 'disable'."
            ::= { h3cVoGKClientObjects 2 }
    
        
        h3cVoGwIPAddress OBJECT-TYPE
            SYNTAX InetAddress
            MAX-ACCESS read-write
            STATUS current
            DESCRIPTION
                "This object indicates the IP address of the interface 
                through which the gateway is connected to the GK(Gate Keeper).
                The value couldn't be modified unless h3cVoRasOn is 'disable'.
                "
            ::= { h3cVoGKClientObjects 3 }

        
        h3cVoH323GWID OBJECT-TYPE
            SYNTAX OCTET STRING (SIZE (0..128))
            MAX-ACCESS read-write
            STATUS current
            DESCRIPTION
                "This object indicates the ID of this H323 gateway.
                The value couldn't be modified unless h3cVoRasOn is 
                'disable'."
            ::= { h3cVoGKClientObjects 4 }

        
        h3cVoH323GKID OBJECT-TYPE
            SYNTAX OCTET STRING (SIZE (0..128))
            MAX-ACCESS read-write
            STATUS current
            DESCRIPTION
                "This object indicates the ID of the GK(Gate Keeper). The value 
                couldn't be modified unless h3cVoRasOn is 'disable'. "
            ::= { h3cVoGKClientObjects 5 }


        h3cVoH323GKIPAddressType OBJECT-TYPE
            SYNTAX  InetAddressType
            MAX-ACCESS read-write
            STATUS current
            DESCRIPTION
                "This object indicates the IP address of the GK(Gate Keeper). The 
                value couldn't be modified unless h3cVoRasOn is 'disable'."
            ::= { h3cVoGKClientObjects 6 }
    
        
        h3cVoH323GKIPAddress OBJECT-TYPE
            SYNTAX InetAddress
            MAX-ACCESS read-write
            STATUS current
            DESCRIPTION
                "This object indicates the IP address of the GK(Gate Keeper). The 
                value couldn't be modified unless h3cVoRasOn is 'disable'."
            ::= { h3cVoGKClientObjects 7 }

        
        h3cVoH323GKPort OBJECT-TYPE
            SYNTAX Integer32 (1..65535)
            MAX-ACCESS read-write
            STATUS current
            DESCRIPTION
                "This object indicates the RAS port of GK(Gate Keeper). The value 
                couldn't be modified unless h3cVoRasOn is 'disable'."
            DEFVAL { 1719 }
            ::= { h3cVoGKClientObjects 8 }


        h3cVoH323GK2ID OBJECT-TYPE
            SYNTAX OCTET STRING (SIZE (0..128))
            MAX-ACCESS read-write
            STATUS current
            DESCRIPTION
                "This object indicates the ID of the slave GK(Gate Keeper).
                The value couldn't be modified unless h3cVoRasOn is 'disable'."
            ::= { h3cVoGKClientObjects 9 }


        h3cVoH323GK2IPAddressType OBJECT-TYPE
            SYNTAX  InetAddressType
            MAX-ACCESS read-write
            STATUS current
            DESCRIPTION
                "This object indicates the IP address of the slave GK(Gate Keeper).
                The value couldn't be modified unless h3cVoRasOn is 'disable'."
            ::= { h3cVoGKClientObjects 10 }

        
        h3cVoH323GK2IPAddress OBJECT-TYPE
            SYNTAX InetAddress
            MAX-ACCESS read-write
            STATUS current
            DESCRIPTION
                "This object indicates the IP address of the slave GK(Gate Keeper).
                The value couldn't be modified unless h3cVoRasOn is 'disable'."
            ::= { h3cVoGKClientObjects 11 }

        
        h3cVoH323GK2Port OBJECT-TYPE
            SYNTAX Integer32 (1..65535)
            MAX-ACCESS read-write
            STATUS current
            DESCRIPTION
                "This object indicates the RAS communication port of slave 
                GK(Gate Keeper).
                The value couldn't be modified unless h3cVoRasOn is 'disable'."
            DEFVAL { 1719 }
            ::= { h3cVoGKClientObjects 12 }


        h3cVoH323GKSecurityCall OBJECT-TYPE
            SYNTAX INTEGER
                {
                enable(1),
                disable(2)
                }
            MAX-ACCESS read-write
            STATUS current
            DESCRIPTION
                "This object indicates whether security call is enabled.
                The value couldn't be modified unless h3cVoRasOn is 'disable'."
            ::= { h3cVoGKClientObjects 13 }


        h3cVoH323GKSecurityPWDType OBJECT-TYPE
            SYNTAX INTEGER
                {
                cipher(1),
                simple(2)
                }
            MAX-ACCESS read-write
            STATUS current
            DESCRIPTION
                "This object indicates the type of security call 
                password." 
            ::= { h3cVoGKClientObjects 14 }


        h3cVoH323GKSecurityPWD OBJECT-TYPE
            SYNTAX OCTET STRING
            MAX-ACCESS read-write
            STATUS current
            DESCRIPTION
                "This object indicates the security call password. This value 
                couldn't be modified unless h3cVoRasOn is 'disable'."
            ::= { h3cVoGKClientObjects 15 }

    END
