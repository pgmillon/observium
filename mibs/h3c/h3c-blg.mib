-- ==================================================================
-- Copyright (c) 2004-2009 Hangzhou H3C Tech. Co., Ltd. All rights reserved.
--
-- Description: This MIB file is used for management of Balance Group
--              information.
-- Reference:
-- Version: V1.0
-- History:
--   V1.0 2009-09-15 Created by xupengfei02152
-- ==================================================================
H3C-BLG-MIB DEFINITIONS ::= BEGIN

IMPORTS
    h3cCommon
        FROM HUAWEI-3COM-OID-MIB
    Integer32, Counter64, OBJECT-TYPE, MODULE-IDENTITY
        FROM SNMPv2-SMI
    TEXTUAL-CONVENTION
        FROM SNMPv2-TC;

h3cBlg MODULE-IDENTITY
    LAST-UPDATED "200909151111Z"
    ORGANIZATION
        "H3C Technologies Co., Ltd."
    CONTACT-INFO
        "Platform Team H3C Technologies Co., Ltd.
        Hai-Dian District Beijing P.R. China
        Http://www.h3c.com
        Zip:100085"
    DESCRIPTION
        "This MIB module defines a set of basic objects for
        configuring switches and routers to set/get balance
        group information."
    REVISION
        "200909151111Z"
    DESCRIPTION
        "The initial version of this MIB."

   ::= { h3cCommon 108 }

CounterClear ::= TEXTUAL-CONVENTION
    STATUS  current
    DESCRIPTION
        "Cleared: reset the value of the group's counter.
         Nouse: 'nouse' will be returned when getting."
    SYNTAX INTEGER
    {
        cleared(1),
        nouse(2)
    }

h3cBlgObjects OBJECT IDENTIFIER  ::= { h3cBlg 1 }

h3cBlgStatsTable  OBJECT-TYPE
    SYNTAX SEQUENCE OF H3cBlgStatsEntry
    MAX-ACCESS not-accessible
    STATUS current
    DESCRIPTION
        "This table contains the statistics information
        about balance groups."
    ::= { h3cBlgObjects 1 }

h3cBlgStatsEntry OBJECT-TYPE
    SYNTAX H3cBlgStatsEntry
    MAX-ACCESS not-accessible
    STATUS current
    DESCRIPTION
        "This list contains statistics information."
    INDEX { h3cBlgIndex }
    ::= { h3cBlgStatsTable 1 }

H3cBlgStatsEntry ::=
   SEQUENCE
   {
       h3cBlgIndex
           Integer32,
       h3cBlgGroupTxPacketCount
           Counter64,
       h3cBlgGroupRxPacketCount
           Counter64,
       h3cBlgGroupTxByteCount
           Counter64,
       h3cBlgGroupRxByteCount
           Counter64,
       h3cBlgGroupCountClear
           CounterClear
   }

h3cBlgIndex OBJECT-TYPE
    SYNTAX      Integer32 (1..2147483647)
    MAX-ACCESS  not-accessible
    STATUS      current
    DESCRIPTION
        "The index of the balance group."
    ::= { h3cBlgStatsEntry 1 }

h3cBlgGroupTxPacketCount OBJECT-TYPE
    SYNTAX      Counter64
    MAX-ACCESS  read-only
    STATUS      current
    DESCRIPTION
        "When retrieved, this object returns the count of
        packets the balance group has sent."
    ::= { h3cBlgStatsEntry 2 }

h3cBlgGroupRxPacketCount OBJECT-TYPE
    SYNTAX      Counter64
    MAX-ACCESS  read-only
    STATUS      current
    DESCRIPTION
        "When retrieved, this object returns the count of
        packets the balance group has received."
    ::= { h3cBlgStatsEntry 3 }

h3cBlgGroupTxByteCount OBJECT-TYPE
    SYNTAX      Counter64
    MAX-ACCESS  read-only
    STATUS      current
    DESCRIPTION
        "When retrieved, this object returns the count of
        bytes the balance group has sent."
    ::= { h3cBlgStatsEntry 4 }

h3cBlgGroupRxByteCount OBJECT-TYPE
    SYNTAX      Counter64
    MAX-ACCESS  read-only
    STATUS      current
    DESCRIPTION
        "When retrieved, this object returns the count of
        bytes the balance group has received."
    ::= { h3cBlgStatsEntry 5 }

h3cBlgGroupCountClear OBJECT-TYPE
    SYNTAX CounterClear
    MAX-ACCESS read-write
    STATUS current
    DESCRIPTION
        "This object is used to reset the counter of the balance group.
        Read operation is meaningless."
    ::= { h3cBlgStatsEntry 6 }

END
