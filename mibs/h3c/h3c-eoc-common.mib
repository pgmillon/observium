-- =================================================================
-- Copyright (c) 2004-2009 by H3C Technologies. All rights reserved.
--
-- Description:
-- Reference:
-- Version: V1.5
-- History:
-- V1.0 created by liujingya.
--     Initial version of the MIB
-- V1.1 2008-1-29 Adjusted the structure of some tables and the value of
--     some objects by liujingya.
-- V1.2 2008-5-19 Added h3cEOCComUniAdminStatus, h3cEOCComCnuSoftwareVersion,
--     modified description of h3cEOCComUniUpLineRate and
--     h3cEOCComUniDownLineRate by liujingya.
-- V1.3 2008-7-30 updated by xujun
--     add h3cEOCComCnuRateDropThr, h3cEOCComCnuTxRate, h3cEOCComCnuRxRate,
--     h3cEOCComCnuTxRateDrop, h3cEOCComCnuRxRateDrop, h3cEOCCnuTxRateDropTrap,
--     h3cEOCCnuTxRateDropRecoverTrap, h3cEOCCnuRxRateDropTrap and
--     h3cEOCCnuRxRateDropRecoverTrap by xujun
-- V1.4 2009-2-13 Added h3cEOCCnuFWDownLoadErrTrap,
--     h3cEOCCnuFWDownLoadErrReTrap, h3cEOCCnuDeviceTypeErrTrap,
--     h3cEOCCnuDeviceTypeErrReTrap, h3cEOCCnuAutoUpdateErrTrap,
--     h3cEOCCnuAutoUpdateSuccTrap and
--     modified MAX-ACCESS of h3cEOCComCnuDeviceType by liujingya.
-- V1.5 2010-1-7 Added h3cEocComCnuTypeIdx, h3cEOCComCnuDescripton,
--     h3cEOCComCltMaxAllowToAccess, h3cEocComCnuNumber by xujun
-- =================================================================
H3C-EOC-COMMON-MIB DEFINITIONS ::= BEGIN

IMPORTS
        h3cCommon
    FROM HUAWEI-3COM-OID-MIB
        ifIndex, ifDescr
    FROM IF-MIB
        Integer32, Unsigned32, TimeTicks, OBJECT-TYPE, MODULE-IDENTITY,
        NOTIFICATION-TYPE, Gauge32
    FROM SNMPv2-SMI
        IANAifType
    FROM IANAifType-MIB
        MacAddress, RowStatus, DisplayString, TruthValue
    FROM SNMPv2-TC
        h3cHPEOCDownLoadCNUFWResult
    FROM H3C-HPEOC-MIB;


h3cEOCCommon MODULE-IDENTITY
    LAST-UPDATED "200709111008Z"
    ORGANIZATION
        "Hangzhou H3C Tech. Co., Ltd."
    CONTACT-INFO
        "SMB EOC Team H3C Technologies Co., Ltd.
        310 Liuhe Road, Zhijiang Science Park, Hangzhou, P.R.China
        http://www.h3c.com
        Zip:310053."
    DESCRIPTION
        "
        The objects in this MIB module are used to manage and
        display common configuration between Ethernet Passive
        Optical Network (EOC) port which are based on the Ethernet
        in the First Mile (EFM) Passive Optical Network(PON) as
        defined in IEEE Draft P802.3ah/D3.0 clause 60, 64, 65..
        and Ethernet Over Cable (EOC) which is based on HomePlug
        AV Specification.
        "
    ::= { h3cCommon 83 }

--
-- h3cEOCCommonSysMan
--
h3cEOCCommonSysMan OBJECT IDENTIFIER ::= { h3cEOCCommon 1 }

h3cEOCCommonSysScalarObjects OBJECT IDENTIFIER ::= { h3cEOCCommonSysMan 1 }

h3cEOCCommonSysVersion OBJECT-TYPE
    SYNTAX     OCTET STRING
    MAX-ACCESS read-only
    STATUS     current
    DESCRIPTION
        "
        Eoc version.  If the object length is
        zero, it means the version is unknown.
        The length is up to 1024.
        "
    ::= { h3cEOCCommonSysScalarObjects 1 }

h3cEOCCommonUpLinkMacAddress OBJECT-TYPE
    SYNTAX     MacAddress
    MAX-ACCESS read-only
    STATUS     current
    DESCRIPTION
        "
        EOC CLT's uplink device's mac address.
        "
    ::= { h3cEOCCommonSysScalarObjects 2 }


--
-- h3cEOCCommonCltMan
--
h3cEOCCommonCltMan OBJECT IDENTIFIER ::= { h3cEOCCommon 2 }

--
-- h3cEOCCommonCltManTable
--
h3cEOCCommonCltManTable OBJECT-TYPE
    SYNTAX     SEQUENCE OF H3cEOCCommonCltManEntry
    MAX-ACCESS not-accessible
    STATUS     current
    DESCRIPTION
        "
        This table defines the primary parameters of the
        CLT configuration.
        "
    ::= { h3cEOCCommonCltMan 1 }

h3cEOCCommonCltManEntry OBJECT-TYPE
    SYNTAX     H3cEOCCommonCltManEntry
    MAX-ACCESS not-accessible
    STATUS     current
    DESCRIPTION
        "
        The entry of the table h3cEOCCommonCltManTable.
        "
    INDEX
        {
            ifIndex
        }
    ::= { h3cEOCCommonCltManTable 1 }

H3cEOCCommonCltManEntry ::= SEQUENCE
    {
        h3cEOCCommonCltAutoAuthorize    TruthValue,
        h3cEOCCommonCltMaxAllowToAccess Integer32
    }

h3cEOCCommonCltAutoAuthorize OBJECT-TYPE
    SYNTAX     TruthValue
    MAX-ACCESS read-write
    STATUS     current
    DESCRIPTION
        "
        This value determines whether software performs
        self-authorization for each Cable Network Unit(CNU)
        registering to the network.  Setting it to false
        means for every CNU registering, software requires
        external authorization, and until it's done the
        CNU is not authenticated.  True value means software
        authorizes each CNU registering to the network
        automatically.
        "
    DEFVAL
        {
            false
        }
    ::= { h3cEOCCommonCltManEntry 1 }

h3cEOCCommonCltMaxAllowToAccess OBJECT-TYPE
    SYNTAX     Integer32
    MAX-ACCESS read-write
    STATUS     current
    DESCRIPTION
         "
         This value determines how many CNU can be bound
         in this CLT. If the number of CNU is more than this
         value , then the rest of CNU should not be allow to
         access.
         "
    DEFVAL
        {
            253
        }
    ::= { h3cEOCCommonCltManEntry 2 }

--
-- h3cEOCComCnuMan
--

h3cEOCComCnuMan OBJECT IDENTIFIER ::= { h3cEOCCommon 3 }

h3cEOCComCnuScalarObjects OBJECT IDENTIFIER ::= { h3cEOCComCnuMan 1 }

h3cEOCComCnuMaxDownBWMinVal OBJECT-TYPE
    SYNTAX     Integer32
    MAX-ACCESS read-only
    STATUS     current
    DESCRIPTION
        "
        The lower limit of total-bandwidth which is confined to
        h3cEOCComCnuMaxDownBW."
    ::= { h3cEOCComCnuScalarObjects 1 }

h3cEOCComCnuMaxDownBWMaxVal OBJECT-TYPE
    SYNTAX     Integer32
    MAX-ACCESS read-only
    STATUS     current
    DESCRIPTION
        "
        The upper limit of total-bandwidth which is confined to
        h3cEOCComCnuMaxDownBW."
    ::= { h3cEOCComCnuScalarObjects 2 }

h3cEOCComCnuSlaHighPriBWMinVal OBJECT-TYPE
    SYNTAX     Integer32
    MAX-ACCESS read-only
    STATUS     current
    DESCRIPTION
        "
        The lower limit of high priority bandwidth which is confined to
        h3cEOCComCnuSlaHighPriBW."
    ::= { h3cEOCComCnuScalarObjects 3 }

h3cEOCComCnuSlaHighPriBWMaxVal OBJECT-TYPE
    SYNTAX     Integer32
    MAX-ACCESS read-only
    STATUS     current
    DESCRIPTION
        "
        The upper limit of high priority bandwidth which is confined to
        h3cEOCComCnuSlaHighPriBW."
    ::= { h3cEOCComCnuScalarObjects 4 }

h3cEOCComCnuMaxUpBWMinVal OBJECT-TYPE
    SYNTAX     Integer32
    MAX-ACCESS read-only
    STATUS     current
    DESCRIPTION
        "
        The lower limit of total-bandwidth which is confined to
        h3cEOCComCnuMaxUpBW."
    ::= { h3cEOCComCnuScalarObjects 5 }

h3cEOCComCnuMaxUpBWMaxVal OBJECT-TYPE
    SYNTAX     Integer32
    MAX-ACCESS read-only
    STATUS     current
    DESCRIPTION
        "
        The upper limit of total-bandwidth which is confined to
        h3cEOCComCnuMaxUpBW."
    ::= { h3cEOCComCnuScalarObjects 6 }

h3cEOCComCnuAttenThrA OBJECT-TYPE
    SYNTAX     Integer32
    MAX-ACCESS read-write
    STATUS     current
    DESCRIPTION
        "
        The value of cnu's average attenuation good level thresholds.
        "
    ::= { h3cEOCComCnuScalarObjects 7 }

h3cEOCComCnuAttenThrB OBJECT-TYPE
    SYNTAX     Integer32
    MAX-ACCESS read-write
    STATUS     current
    DESCRIPTION
        "
        The value of cnu's average attenuation normal level thresholds.
        "
    ::= { h3cEOCComCnuScalarObjects 8 }

h3cEOCComCnuRateDropThr OBJECT-TYPE
    SYNTAX     Integer32
    MAX-ACCESS read-write
    STATUS     current
    DESCRIPTION
        "
        The value of cnu's Tx/Rx rate drop thresholds.
        "
    ::= { h3cEOCComCnuScalarObjects 9 }

--
-- h3cEOCComCnuSysManTable
--

h3cEOCComCnuSysManTable OBJECT-TYPE
    SYNTAX     SEQUENCE OF H3cEOCComCnuSysManEntry
    MAX-ACCESS not-accessible
    STATUS     current
    DESCRIPTION
        "
        This table implements the management of CNUs(Coax Network Unit).
        "
    ::= { h3cEOCComCnuMan 2 }

h3cEOCComCnuSysManEntry OBJECT-TYPE
    SYNTAX     H3cEOCComCnuSysManEntry
    MAX-ACCESS not-accessible
    STATUS     current
    DESCRIPTION
        "
        The entry of the table h3cEOCComCnuSysManTable.
        "
    INDEX
        {
            ifIndex
        }
    ::= { h3cEOCComCnuSysManTable 1 }

H3cEOCComCnuSysManEntry ::= SEQUENCE
    {
        h3cEOCComCnuCableIfindex    Integer32,
        h3cEOCComCnuDeviceType      DisplayString,
        h3cEOCComCnuDeviceAlias     DisplayString,
        h3cEOCComCnuDescr           DisplayString,
        h3cEOCComCnuUpTime          TimeTicks,
        h3cEOCComCnuVLANType        INTEGER,
        h3cEOCComCnuPvid            Integer32,
        h3cEOCComCnuVlanTag         INTEGER,
        h3cEOCComCnuReset           INTEGER,
        h3cEOCComCnuDeregister      INTEGER,
        h3cEOCComCnuSave            INTEGER,
        h3cEOCComCnuAccess          INTEGER
    }

h3cEOCComCnuCableIfindex OBJECT-TYPE
    SYNTAX     Integer32
    MAX-ACCESS read-only
    STATUS     current
    DESCRIPTION
        "
        The index of cable port which uniquely identifies the cable
        port of one device.
        "
    ::= { h3cEOCComCnuSysManEntry 1 }

h3cEOCComCnuDeviceType OBJECT-TYPE
    SYNTAX     DisplayString
    MAX-ACCESS read-write
    STATUS     current
    DESCRIPTION
        "
        The type of the EOC CNU(Coax Network Unit).
        "
    ::= { h3cEOCComCnuSysManEntry 2 }

h3cEOCComCnuDeviceAlias OBJECT-TYPE
    SYNTAX DisplayString
    MAX-ACCESS read-write
    STATUS current
    DESCRIPTION
        "
        EOC CNU's alias which display as the device's name,
        it's recommended to set it uniquely and understandably.
        "
    ::= { h3cEOCComCnuSysManEntry 3 }

h3cEOCComCnuDescr OBJECT-TYPE
    SYNTAX     DisplayString
    MAX-ACCESS read-write
    STATUS     current
    DESCRIPTION
        "
        User's description, including user's address,
        name, telephone number and so on.
        "
    ::= { h3cEOCComCnuSysManEntry 4 }

h3cEOCComCnuUpTime OBJECT-TYPE
    SYNTAX     TimeTicks
    MAX-ACCESS read-only
    STATUS     current
    DESCRIPTION
        "
        The time since the CNU last registered to the network.
        "
    ::= { h3cEOCComCnuSysManEntry 5 }

h3cEOCComCnuVLANType OBJECT-TYPE
    SYNTAX     INTEGER
        {
            vLANTrunk(1),
            access(2),
            hybrid(3),
            fabric(4)
        }
    MAX-ACCESS read-write
    STATUS     current
    DESCRIPTION
        "port vlan types.
        hybrid (3) port can carry multiple VLANs.
        If fabric function is supported, fabric(4) means the port is
        a fabric port."
    ::= { h3cEOCComCnuSysManEntry 6 }

h3cEOCComCnuPvid OBJECT-TYPE
    SYNTAX     Integer32 (1..4094)
    MAX-ACCESS read-write
    STATUS     current
    DESCRIPTION
        "
        The PVID, the VLAN ID assigned to untagged frames or
        Priority-Tagged frames received on cable interface.
        "
    REFERENCE
        "
        IEEE 802.1Q/D11 Section 12.10.1.1
        "
    DEFVAL
        {
            1
        }
    ::= { h3cEOCComCnuSysManEntry 7 }

h3cEOCComCnuVlanTag OBJECT-TYPE
    SYNTAX     INTEGER
        {
            tagged(1),
            untagged(2)
        }
    MAX-ACCESS read-write
    STATUS     current
    DESCRIPTION
        "
        VLAN is set tagged or untagged on cable interface.
        "
    ::= { h3cEOCComCnuSysManEntry 8 }

h3cEOCComCnuReset OBJECT-TYPE
    SYNTAX     INTEGER
        {
            running(1),
            reset(2)
        }
    MAX-ACCESS read-write
    STATUS     current
    DESCRIPTION
        "
        This variable is used to reset the CNU device. The
        interface may be unavailable while the reset occurs and
        data may be lost. During reading operation it returns
        the state of the CNU device. running(1) indicates and
        operates normal operation, reset(2) indicates and
        operates reset mode. Writing can be done all the time.
        "
    ::= { h3cEOCComCnuSysManEntry 9 }

h3cEOCComCnuDeregister OBJECT-TYPE
    SYNTAX     INTEGER
        {
            deregister(1)
        }
    MAX-ACCESS read-write
    STATUS     current
    DESCRIPTION
        "
        deregister CNU.
        "
    ::= { h3cEOCComCnuSysManEntry 10 }

h3cEOCComCnuSave OBJECT-TYPE
    SYNTAX     INTEGER
        {
            save(1),
            running(2)
        }
    MAX-ACCESS read-write
    STATUS     current
    DESCRIPTION
        "
        Save the UNI and CNU related configurations to
        the CNU.
        "
    ::= { h3cEOCComCnuSysManEntry 11 }

h3cEOCComCnuAccess OBJECT-TYPE
    SYNTAX     INTEGER
        {
            access(1),
            notaccess(2)
        }
    MAX-ACCESS read-write
    STATUS     current
    DESCRIPTION
        "
        Control whether the user can access to the network.
        "
    ::= { h3cEOCComCnuSysManEntry 12 }

--
-- h3cEOCComCnuMacTable
--

h3cEOCComCnuMacTable OBJECT-TYPE
    SYNTAX     SEQUENCE OF H3cEOCComCnuMacEntry
    MAX-ACCESS not-accessible
    STATUS     current
    DESCRIPTION
        "
        This table implements the management of CNUs.
        "
    ::= { h3cEOCComCnuMan 3 }

h3cEOCComCnuMacEntry OBJECT-TYPE
    SYNTAX     H3cEOCComCnuMacEntry
    MAX-ACCESS not-accessible
    STATUS     current
    DESCRIPTION
        "
        The entry of the table h3cEOCComCnuMacTable.
        "
    INDEX
        {
            ifIndex
        }
    ::= { h3cEOCComCnuMacTable 1 }

H3cEOCComCnuMacEntry ::= SEQUENCE
    {
        h3cEOCComCnuMacAddress    MacAddress,
        h3cEOCComCnuRowStatus     RowStatus
    }

h3cEOCComCnuMacAddress OBJECT-TYPE
    SYNTAX     MacAddress
    MAX-ACCESS read-create
    STATUS     current
    DESCRIPTION
        "
        EOC CNU's MAC address.
        "
    ::= { h3cEOCComCnuMacEntry 1 }

h3cEOCComCnuRowStatus OBJECT-TYPE
    SYNTAX     RowStatus
    MAX-ACCESS read-create
    STATUS     current
    DESCRIPTION
        "
        Operation status.
        "
    ::= { h3cEOCComCnuMacEntry 2 }

--
-- h3cEOCComCnuInfoTable
--

h3cEOCComCnuInfoTable OBJECT-TYPE
    SYNTAX     SEQUENCE OF H3cEOCComCnuInfoEntry
    MAX-ACCESS not-accessible
    STATUS     current
    DESCRIPTION
        "
        Primary status of the specified CNU.
        There will be one row in this table for each
        information in the system.
        "
    ::= { h3cEOCComCnuMan 4 }

h3cEOCComCnuInfoEntry OBJECT-TYPE
    SYNTAX     H3cEOCComCnuInfoEntry
    MAX-ACCESS not-accessible
    STATUS     current
    DESCRIPTION
        "
        The entry of the h3cEOCComCnuInfoTable.
        "
    INDEX
        {
            ifIndex
        }
    ::= { h3cEOCComCnuInfoTable 1 }

H3cEOCComCnuInfoEntry ::= SEQUENCE
    {
        h3cEOCComCnuHardwareVersion    DisplayString,
        h3cEOCComCnuPCBVersion         OCTET STRING,
        h3cEOCComCnuLinkState          INTEGER,
        h3cEOCComCnuAttenuation        Integer32,
        h3cEOCComCnuSoftwareVersion    DisplayString,
        h3cEOCComCnuTxRate             Integer32,
        h3cEOCComCnuRxRate             Integer32,
        h3cEOCComCnuTxRateDrop         Integer32,
        h3cEOCComCnuRxRateDrop         Integer32
    }

h3cEOCComCnuHardwareVersion OBJECT-TYPE
    SYNTAX     DisplayString
    MAX-ACCESS read-only
    STATUS     current
    DESCRIPTION
        "
        EOC CNU's hardware version.  If the object length is
        zero, it means the version is unknown.
        "
    ::= { h3cEOCComCnuInfoEntry 1 }

h3cEOCComCnuPCBVersion OBJECT-TYPE
    SYNTAX     OCTET STRING (SIZE(0..255))
    MAX-ACCESS read-only
    STATUS     current
    DESCRIPTION
        "
        EOC CNU's PCB version.
        "
    ::= { h3cEOCComCnuInfoEntry 2 }

h3cEOCComCnuLinkState OBJECT-TYPE
    SYNTAX     INTEGER
        {
            physicaldown(1),
            linkdown(2),
            linkup(3)
        }
    MAX-ACCESS read-only
    STATUS     current
    DESCRIPTION
        "
        The cable port's link state.  The physicaldown(1) state indicates
        that the CNU is not powered on.  The linkdown(2) state indicates
        that the CNU is powered on, but registers fail.  The linkup(3)
        state indicates that the CNU is powered on, and registers
        successful.
        "
    ::= { h3cEOCComCnuInfoEntry 3 }

h3cEOCComCnuAttenuation OBJECT-TYPE
    SYNTAX     Integer32
    MAX-ACCESS read-only
    STATUS     current
    DESCRIPTION
        "
        The cnu's average attenuation.
        "
    ::= { h3cEOCComCnuInfoEntry 4 }

h3cEOCComCnuSoftwareVersion OBJECT-TYPE
    SYNTAX     DisplayString
    MAX-ACCESS read-only
    STATUS     current
    DESCRIPTION
        "
        EOC CNU's software version.  If the object length is
        zero, it means the version is unknown.
        "
    ::= { h3cEOCComCnuInfoEntry 5 }

h3cEOCComCnuTxRate OBJECT-TYPE
    SYNTAX     Integer32
    MAX-ACCESS read-only
    STATUS     current
    DESCRIPTION
        "
        The cnu's capability of tx speed in unit of 1Mbps.
        "
    ::= { h3cEOCComCnuInfoEntry 6 }

h3cEOCComCnuRxRate OBJECT-TYPE
    SYNTAX     Integer32
    MAX-ACCESS read-only
    STATUS     current
    DESCRIPTION
        "
        The cnu's capability of rx speed in unit of 1Mbps.
        "
    ::= { h3cEOCComCnuInfoEntry 7 }

h3cEOCComCnuTxRateDrop OBJECT-TYPE
    SYNTAX     Integer32
    MAX-ACCESS read-only
    STATUS     current
    DESCRIPTION
        "
        The cnu's capability droping of tx
        speed from it's history max value in unit of %.
        "
    ::= { h3cEOCComCnuInfoEntry 8 }

h3cEOCComCnuRxRateDrop OBJECT-TYPE
    SYNTAX     Integer32
    MAX-ACCESS read-only
    STATUS     current
    DESCRIPTION
        "
        The cnu's capability droping of rx
        speed from it's history max value in unit of %.
        "
    ::= { h3cEOCComCnuInfoEntry 9 }

--
-- h3cEOCComCnuBandWidthTable
--

h3cEOCComCnuBandWidthTable OBJECT-TYPE
    SYNTAX     SEQUENCE OF H3cEOCComCnuBandWidthEntry
    MAX-ACCESS not-accessible
    STATUS     current
    DESCRIPTION
        "
        Set bandwidth parameters.
        "
    ::= { h3cEOCComCnuMan 5 }

h3cEOCComCnuBandWidthEntry OBJECT-TYPE
    SYNTAX     H3cEOCComCnuBandWidthEntry
    MAX-ACCESS not-accessible
    STATUS     current
    DESCRIPTION
        "
        The entry of table h3cEOCComCnuBandWidthTable.
        It is a pre-configuration.
        "
    INDEX
        {
            ifIndex
        }
    ::= { h3cEOCComCnuBandWidthTable 1 }

H3cEOCComCnuBandWidthEntry ::= SEQUENCE
    {
        h3cEOCComCnuMaxDownBW       Integer32,
        h3cEOCComCnuSlaHighPriBW    Integer32,
        h3cEOCComCnuMaxUpBW         Integer32
    }

h3cEOCComCnuMaxDownBW OBJECT-TYPE
    SYNTAX     Integer32
    MAX-ACCESS read-write
    STATUS     current
    DESCRIPTION
        "
        Maximum bandwidth allowed for the CNU,
        measured in Kbit/s.
        "
    ::= { h3cEOCComCnuBandWidthEntry 1 }

h3cEOCComCnuSlaHighPriBW OBJECT-TYPE
    SYNTAX     Integer32
    MAX-ACCESS read-write
    STATUS     current
    DESCRIPTION
        "
        High priority bandwidth - measured in Kbit/s.
        The value of this object should be the multiple of
        the value of h3cEOCComCnuMaxUpBW.
        The high priority bandwidth should not be larger than the maximum
        bandwidth.
        "
    ::= { h3cEOCComCnuBandWidthEntry 2 }

h3cEOCComCnuMaxUpBW OBJECT-TYPE
    SYNTAX     Integer32
    MAX-ACCESS read-write
    STATUS     current
    DESCRIPTION
        "
        Total bandwidth - measured in Kbit/s.
        The value of this object should be the multiple of
        the value of h3cEOCComCnuSlaHighPriBW.
        The total bandwidth should be larger than the high priority bandwidth.
        "
    ::= { h3cEOCComCnuBandWidthEntry 3 }




--
-- h3cEOCComUniMan
--

h3cEOCComUniMan OBJECT IDENTIFIER ::= { h3cEOCCommon 4 }

h3cEOCComUniManTable OBJECT-TYPE
    SYNTAX     SEQUENCE OF H3cEOCComUniManEntry
    MAX-ACCESS not-accessible
    STATUS     current
    DESCRIPTION
        "
        This table defines several user network interface(UNI) system
        parameters.
        "
    ::= { h3cEOCComUniMan 1 }

h3cEOCComUniManEntry OBJECT-TYPE
    SYNTAX     H3cEOCComUniManEntry
    MAX-ACCESS not-accessible
    STATUS     current
    DESCRIPTION
        "
        The entry of h3cEOCComUniManTable.
        "
    INDEX
        {
            ifIndex,
            h3cEOCUniIndex
        }
    ::= { h3cEOCComUniManTable 1 }

H3cEOCComUniManEntry ::= SEQUENCE
    {
        h3cEOCUniIndex               Unsigned32,
        h3cEOCComUniDescr            DisplayString,
        h3cEOCComUniStatus           INTEGER,
        h3cEOCComUniSpeed            INTEGER,
        h3cEOCComUniDuplex           INTEGER,
        h3cEOCComUniCurrentSpeed     Gauge32,
        h3cEOCComUniCurrentDuplex    INTEGER,
        h3cEOCComUniMdi              INTEGER,
        h3cEOCComUniFlowControl      TruthValue,
        h3cEOCComUniCountReset       INTEGER,
        h3cEOCComUniAlias            DisplayString,
        h3cEOCComUniType             IANAifType,
        h3cEOCComUniVLANType         INTEGER,
        h3cEOCComUniPvid             Integer32,
        h3cEOCComUniVlanTag          INTEGER,
        h3cEOCComUniPriority         Integer32,
        h3cEOCComUniUpLineRate       Unsigned32,
        h3cEOCComUniDownLineRate     Unsigned32,
        h3cEOCComUniAdminStatus      INTEGER
    }

h3cEOCUniIndex OBJECT-TYPE
    SYNTAX     Unsigned32
    MAX-ACCESS not-accessible
    STATUS     current
    DESCRIPTION
        "
        The index value which uniquely identifies the FE(Fast Ethernet)
        interface of the CNU.
        "
    ::= { h3cEOCComUniManEntry 1 }

h3cEOCComUniDescr OBJECT-TYPE
    SYNTAX     DisplayString
    MAX-ACCESS read-only
    STATUS     current
    DESCRIPTION
        "
        A textual string containing information about the interface.  This
        string should include the name of the manufacturer, the product
        name and the version of the interface hardware and software.
        "
    ::= { h3cEOCComUniManEntry 2 }

h3cEOCComUniStatus OBJECT-TYPE
    SYNTAX     INTEGER
        {
            up(1),
            down(2),
            testing(3)
        }
    MAX-ACCESS read-write
    STATUS     current
    DESCRIPTION
        "
        The desired state of the user network interface. When a managed
        system initializes, all user network interfaces start with down
        state. The testing state indicates that no operational packets
        can be passed. As a result of either explicit management action or
        per configuration information retained by the managed system,
        h3cEOCComUniStatus is then changed to either the up or
        testing states (or remains in the down state).
        "
    ::= { h3cEOCComUniManEntry 3 }

h3cEOCComUniSpeed OBJECT-TYPE
    SYNTAX     INTEGER
        {
            auto(1),
            s10M(10),
            s100M(100)
        }
    MAX-ACCESS read-write
    STATUS     current
    DESCRIPTION
        "
        User network interface speed.
        "
    ::= { h3cEOCComUniManEntry 4 }

h3cEOCComUniDuplex OBJECT-TYPE
    SYNTAX     INTEGER
        {
            full(1),
            half(2),
            auto(3)
        }
    MAX-ACCESS read-write
    STATUS     current
    DESCRIPTION
        "
        User network interface mode.
        "
    ::= { h3cEOCComUniManEntry 5 }

h3cEOCComUniCurrentSpeed OBJECT-TYPE
    SYNTAX     Gauge32
    MAX-ACCESS read-only
    STATUS     current
    DESCRIPTION
        "
        An estimate of the interface's current bandwidth in
        bits per second.  For interfaces which do not vary in
        bandwidth or for those where no accurate estimation
        can be made, this object should contain the nominal
        bandwidth.  If the bandwidth of the interface is
        greater than the maximum value reportable by this
        object then this object should report its maximum
        value (4,294,967,295).  For a sub-layer which
        has no concept of bandwidth, this object should be
        zero.
        "
    ::= { h3cEOCComUniManEntry 6 }

h3cEOCComUniCurrentDuplex OBJECT-TYPE
    SYNTAX     INTEGER
        {
            full(1),
            half(2),
            unknown(3)
        }
    MAX-ACCESS read-only
    STATUS     current
    DESCRIPTION
        "
        The current mode of operation of the MAC
        entity.  'unknown' indicates that the current
        duplex mode could not be determined.

        Management control of the duplex mode is
        accomplished through the MAU MIB.  When
        an interface does not support autonegotiation,
        or when autonegotiation is not enabled, the
        duplex mode is controlled using
        ifMauDefaultType.  When autonegotiation is
        supported and enabled, duplex mode is controlled
        using ifMauAutoNegAdvertisedBits.  In either
        case, the currently operating duplex mode is
        reflected both in this object and in ifMauType.

        Note that this object provides redundant
        information with ifMauType.  Normally, redundant
        objects are discouraged.  However, in this
        instance, it allows a management application to
        determine the duplex status of an interface
        without having to know every possible value of
        ifMauType.  This was felt to be sufficiently
        valuable to justify the redundancy.
        "
    REFERENCE
        "
        [IEEE 802.3 Std.], 30.3.1.1.32, aDuplexStatus.
        "
    ::= { h3cEOCComUniManEntry 7 }

h3cEOCComUniMdi OBJECT-TYPE
    SYNTAX     INTEGER
        {
            mdi-ii(1),
            mdi-x(2),
            mdi-auto(3)
        }
    MAX-ACCESS read-write
    STATUS     current
    DESCRIPTION
        "Type of the line connected to UNI interface:
        mdi-ii(straight-through cable),
        mdi-x (crossover cable),
        mdi-auto (auto-sensing)."
    DEFVAL
        {
            mdi-auto
        }
    ::= { h3cEOCComUniManEntry 8 }

h3cEOCComUniFlowControl OBJECT-TYPE
    SYNTAX      TruthValue
    MAX-ACCESS  read-write
    STATUS      current
    DESCRIPTION
        "Flow control status.
        true(1)  - Flow control status enable.
        false(2) - Flow control status disable."
    DEFVAL
        {
            false
        }
    ::= { h3cEOCComUniManEntry 9 }

h3cEOCComUniCountReset OBJECT-TYPE
    SYNTAX      INTEGER
        {
            reset(1)
        }
    MAX-ACCESS  read-write
    STATUS      current
    DESCRIPTION
        "Reset the counter which is about packets of the interface,
        then the counter will change to zero.  There is no sense in
        reading this object."
    ::= { h3cEOCComUniManEntry 10 }

h3cEOCComUniAlias OBJECT-TYPE
    SYNTAX     DisplayString
    MAX-ACCESS read-write
    STATUS     current
    DESCRIPTION
        "
        This object is an 'alias' name for the interface as
        specified by a network manager, and provides a non-
        volatile 'handle' for the interface.

        On the first instantiation of an interface, the value
        of h3cEOCComUniAlias associated with that interface is the
        zero-length string.  As and when a value is written
        into an instance of h3cEOCComUniAlias through a network
        management set operation, then the agent must retain
        the supplied value in the h3cEOCComUniAlias instance associated
        with the same interface for as long as that interface
        remains instantiated, including across all re-
        initializations/reboots of the network management
        system, including those which result in a change of
        the interface's ifIndex and h3cEOCUniIndex value.

        An example of the value which a network manager might
        store in this object for a WAN interface is the
        (Telco's) circuit number/identifier of the interface.

        Some agents may support write-access only for
        interfaces having particular values of h3cEOCComUniType.  An
        agent which supports write access to this object is
        required to keep the value in non-volatile storage,
        but it may limit the length of new values depending on
        how much storage is already occupied by the current
        values for other interfaces.
        "
    ::= { h3cEOCComUniManEntry 11 }

h3cEOCComUniType OBJECT-TYPE
    SYNTAX     IANAifType
    MAX-ACCESS read-only
    STATUS     current
    DESCRIPTION
        "
        The type of interface.  Additional values for h3cEOCComUniType
        are assigned by the Internet Assigned Numbers
        Authority(IANA), through updating the syntax of the
        IANAifType textual convention.
        "
    ::= { h3cEOCComUniManEntry 12 }

h3cEOCComUniVLANType OBJECT-TYPE
    SYNTAX     INTEGER
        {
            vLANTrunk(1),
            access(2),
            hybrid(3),
            fabric(4)
        }
    MAX-ACCESS read-write
    STATUS     current
    DESCRIPTION
        "port vlan types.
        hybrid (3) port can carry multiple VLANs.
        If fabric function is supported, fabric(4) means the port is
        a fabric port."
    ::= { h3cEOCComUniManEntry 13 }

h3cEOCComUniPvid OBJECT-TYPE
    SYNTAX     Integer32 (1..4094)
    MAX-ACCESS read-write
    STATUS     current
    DESCRIPTION
        "
        The PVID, the VLAN ID assigned to untagged frames or
        Priority-Tagged frames received on this port.
        "
    REFERENCE
        "
        IEEE 802.1Q/D11 Section 12.10.1.1
        "
    DEFVAL
        {
            1
        }
    ::= { h3cEOCComUniManEntry 14 }

h3cEOCComUniVlanTag OBJECT-TYPE
    SYNTAX     INTEGER
        {
            tagged(1),
            untagged(2)
        }
    MAX-ACCESS read-write
    STATUS     current
    DESCRIPTION
        "
        VLAN is set tagged or untagged.
        "
    ::= { h3cEOCComUniManEntry 15 }

h3cEOCComUniPriority OBJECT-TYPE
    SYNTAX     Integer32 (0..7)
    MAX-ACCESS read-write
    STATUS     current
    DESCRIPTION
        "
        The default ingress User Priority for this port.  This
        only has effect on media, such as Ethernet, that do not
        support native User Priority.
        "
    ::= { h3cEOCComUniManEntry 16 }

h3cEOCComUniUpLineRate OBJECT-TYPE
    SYNTAX     Unsigned32
    MAX-ACCESS read-write
    STATUS     current
    DESCRIPTION
        "
        The max speed upload in units of 1,000 bits per second
        on this interface.  The value should between 0 and 100Mbps.
        If the value is 0, it means that the upload speed is only
        restricted by the physical line.
        "
    ::= { h3cEOCComUniManEntry 17 }

h3cEOCComUniDownLineRate OBJECT-TYPE
    SYNTAX     Unsigned32
    MAX-ACCESS read-write
    STATUS     current
    DESCRIPTION
        "
        The max speed download in units of 1,000 bits per second
        on this interface.  The value should between 0 and 100Mbps.
        If the value is 0, it means that the download speed is only
        restricted by the physical line.
        "
    ::= { h3cEOCComUniManEntry 18 }

h3cEOCComUniAdminStatus OBJECT-TYPE
    SYNTAX      INTEGER
        {
            up(1),
            down(2)
        }
    MAX-ACCESS  read-write
    STATUS      current
    DESCRIPTION
        "
        Control if open or close the UNI.  If choose up(1), means the UNI is
        opened and packets can pass it.  If choose down(2), means the UNI is
        closed and all packets will be discard.
        "
    ::= { h3cEOCComUniManEntry 19 }

--
-- h3cEOCComUniCountTable
--
h3cEOCComUniCountTable OBJECT-TYPE
    SYNTAX      SEQUENCE OF H3cEOCComUniCountEntry
    MAX-ACCESS  not-accessible
    STATUS      current
    DESCRIPTION
        "A list of interface counter about frames entries."
    ::= { h3cEOCComUniMan 2 }

h3cEOCComUniCountEntry OBJECT-TYPE
    SYNTAX      H3cEOCComUniCountEntry
    MAX-ACCESS  not-accessible
    STATUS      current
    DESCRIPTION
        "An entry containing management information applicable
        to a particular interface."
    INDEX
        {
            ifIndex,
            h3cEOCUniIndex
        }
    ::= { h3cEOCComUniCountTable 1 }

H3cEOCComUniCountEntry ::= SEQUENCE
    {
        h3cEOCUniInPkts                     Unsigned32,
        h3cEOCUniInUPkts                    Unsigned32,
        h3cEOCUniInBPkts                    Unsigned32,
        h3cEOCUniInMPkts                    Unsigned32,
        h3cEOCUniInPausePkts                Unsigned32,
        h3cEOCUniInTotalErrors              Unsigned32,
        h3cEOCUniInCRCErrs                  Unsigned32,
        h3cEOCUniInUndersizePkts            Unsigned32,
        h3cEOCUniInOversizePkts             Unsigned32,
        h3cEOCUniInErrorbyOther             Unsigned32,
        h3cEOCUniInOctets                   Unsigned32,
        h3cEOCUniOutPkts                    Unsigned32,
        h3cEOCUniOutUPkts                   Unsigned32,
        h3cEOCUniOutBPkts                   Unsigned32,
        h3cEOCUniOutMPkts                   Unsigned32,
        h3cEOCUniOutPausePkts               Unsigned32,
        h3cEOCUniOutTotalErrors             Unsigned32,
        h3cEOCUniOutCollisions              Unsigned32,
        h3cEOCUniOutDelayExceedDsds         Unsigned32,
        h3cEOCUniOutErrorbyOther            Unsigned32,
        h3cEOCUniOutDroppedFrames           Unsigned32,
        h3cEOCUniOutOctets                  Unsigned32
    }

h3cEOCUniInPkts OBJECT-TYPE
    SYNTAX     Unsigned32
    MAX-ACCESS read-only
    STATUS     current
    DESCRIPTION
        "The total number of packets (including bad packets,
        broadcast packets, and multicast packets) received."
    ::= { h3cEOCComUniCountEntry 1 }

h3cEOCUniInUPkts  OBJECT-TYPE
    SYNTAX     Unsigned32
    MAX-ACCESS read-only
    STATUS     current
    DESCRIPTION
        "The total number of good packets received that are
        directed to the unicast address.  Note that this
        does not include multicast and broadcast packets."
    ::= { h3cEOCComUniCountEntry 2 }

h3cEOCUniInBPkts  OBJECT-TYPE
    SYNTAX     Unsigned32
    MAX-ACCESS read-only
    STATUS     current
    DESCRIPTION
        "The total number of good packets received that are
        directed to the broadcast address.  Note that this
        does not include multicast packets."
    ::= { h3cEOCComUniCountEntry 3 }

h3cEOCUniInMPkts  OBJECT-TYPE
    SYNTAX     Unsigned32
    MAX-ACCESS read-only
    STATUS     current
    DESCRIPTION
        "The total number of good packets received that are
        directed to a multicast address.  Note that this number
        does not include packets directed to the broadcast address."
    ::= { h3cEOCComUniCountEntry 4 }

h3cEOCUniInPausePkts  OBJECT-TYPE
    SYNTAX     Unsigned32
    MAX-ACCESS read-only
    STATUS     current
    DESCRIPTION
        "A count of MAC Control packets received on this
        interface by the pause(flow control) operation.
        This counter does not increment when the
        interface is in a half-duplex mode.
        Discontinuities in the value of this counter can
        occur at re-initialization of the management
        system."
    ::= { h3cEOCComUniCountEntry 5 }

h3cEOCUniInTotalErrors  OBJECT-TYPE
    SYNTAX     Unsigned32
    MAX-ACCESS read-only
    STATUS     current
    DESCRIPTION
        "Total count of the error packets received on this interface."
    ::= { h3cEOCComUniCountEntry 6 }

h3cEOCUniInCRCErrs  OBJECT-TYPE
    SYNTAX     Unsigned32
    MAX-ACCESS read-only
    STATUS     current
    DESCRIPTION
        "The total number of packets received that
        had a length (excluding framing bits, but
        including FCS octets) of between 64 and 1518
        octets, inclusive, but had either a bad
        Frame Check Sequence (FCS) with an integral
        number of octets (FCS Error) or a bad FCS with
        a non-integral number of octets (Alignment Error)."
    ::= { h3cEOCComUniCountEntry 7 }

h3cEOCUniInUndersizePkts  OBJECT-TYPE
    SYNTAX     Unsigned32
    MAX-ACCESS read-only
    STATUS     current
    DESCRIPTION
        "The total number of packets received that are
        less than 64 octets long (excluding framing bits,
        but including FCS octets) and are otherwise well formed."
    ::= { h3cEOCComUniCountEntry 8 }

h3cEOCUniInOversizePkts  OBJECT-TYPE
    SYNTAX     Unsigned32
    MAX-ACCESS read-only
    STATUS     current
    DESCRIPTION
        "The total number of packets received that are
        longer than 1518 octets (excluding framing bits,
        but including FCS octets) and are otherwise well formed."
    ::= { h3cEOCComUniCountEntry 9 }

h3cEOCUniInErrorbyOther   OBJECT-TYPE
    SYNTAX     Unsigned32
    MAX-ACCESS read-only
    STATUS     current
    DESCRIPTION
        "The total number of other error packets received on this interface."
    ::= { h3cEOCComUniCountEntry 10 }

h3cEOCUniInOctets   OBJECT-TYPE
    SYNTAX     Unsigned32
    MAX-ACCESS read-only
    STATUS     current
    DESCRIPTION
        "The total number of octets received on this interface."
    ::= { h3cEOCComUniCountEntry 11 }

h3cEOCUniOutPkts OBJECT-TYPE
    SYNTAX     Unsigned32
    MAX-ACCESS read-only
    STATUS     current
    DESCRIPTION
        "The total number of packets (including bad packets,
        broadcast packets, and multicast packets) sent."
    ::= { h3cEOCComUniCountEntry 12 }

h3cEOCUniOutUPkts OBJECT-TYPE
    SYNTAX     Unsigned32
    MAX-ACCESS read-only
    STATUS     current
    DESCRIPTION
        "The total number of good packets sent that are
        directed to the unicast address.  Note that this
        does not include multicast and broadcast packets."
    ::= { h3cEOCComUniCountEntry 13 }

h3cEOCUniOutBPkts  OBJECT-TYPE
    SYNTAX     Unsigned32
    MAX-ACCESS read-only
    STATUS     current
    DESCRIPTION
        "The total number of good packets sent that are
        directed to the broadcast address.  Note that this
        does not include multicast packets."
    ::= { h3cEOCComUniCountEntry 14 }

h3cEOCUniOutMPkts  OBJECT-TYPE
    SYNTAX     Unsigned32
    MAX-ACCESS read-only
    STATUS     current
    DESCRIPTION
        "The total number of good packets sent that are
        directed to a multicast address.  Note that this number
        does not include packets directed to the broadcast address."
    ::= { h3cEOCComUniCountEntry 15 }

h3cEOCUniOutPausePkts  OBJECT-TYPE
    SYNTAX     Unsigned32
    MAX-ACCESS read-only
    STATUS     current
    DESCRIPTION
        "The total number of MAC control packets sent on this
        interface by the pause operation.  This counter does
        not increment when the interface is in a half-duplex mode.
        Discontinuities in the value of this counter can
        occur at re-initialization of the management system."
    ::= { h3cEOCComUniCountEntry 16 }

h3cEOCUniOutTotalErrors  OBJECT-TYPE
    SYNTAX     Unsigned32
    MAX-ACCESS read-only
    STATUS     current
    DESCRIPTION
        "The total number of error packets sent on this interface."
    ::= { h3cEOCComUniCountEntry 17 }

h3cEOCUniOutCollisions  OBJECT-TYPE
    SYNTAX     Unsigned32
    MAX-ACCESS read-only
    STATUS     current
    DESCRIPTION
        "The best estimate of the total number of collisions
        on this Ethernet segment.
        The value returned will depend on the location of the
        RMON probe.  Section 8.2.1.3 (10BASE-5) and section
        10.3.1.3 (10BASE-2) of IEEE standard 802.3 states that a
        station must detect a collision, in the receive mode, if
        three or more stations are transmitting simultaneously.  A
        repeater port must detect a collision when two or more
        stations are transmitting simultaneously.  Thus a probe
        placed on a repeater port could record more collisions
        than a probe connected to a station on the same segment
        could.  Probe location plays a much smaller role when considering
        10BASE-T.  14.2.1.4 (10BASE-T) of IEEE standard 802.3
        defines a collision as the simultaneous presence of signals
        on the DO and RD circuits (transmitting and receiving
        at the same time).  A 10BASE-T station can only detect
        collisions when it is transmitting.  Thus probes placed on
        a station and a repeater, should report the same number of
        collisions.  Note also that an RMON probe inside a repeater should
        ideally report collisions between the repeater and one or
        more other hosts (transmit collisions as defined by IEEE
        802.3k) plus receiver collisions observed on any coax
        segments to which the repeater is connected."
    ::= { h3cEOCComUniCountEntry 18 }

h3cEOCUniOutDelayExceedDsds  OBJECT-TYPE
    SYNTAX     Unsigned32
    MAX-ACCESS read-only
    STATUS  current
    DESCRIPTION
        "The number of packets discarded by this port due
        to excessive transit delay through the bridge.  It
        is incremented by both transparent and source route bridges."
    ::= { h3cEOCComUniCountEntry 19 }

h3cEOCUniOutErrorbyOther  OBJECT-TYPE
    SYNTAX     Unsigned32
    MAX-ACCESS read-only
    STATUS     current
    DESCRIPTION
        "The total number of other error packets sent on this interface.
        Other error packets means the error packets out of collision packets
        and excessive delayed packets."
    ::= { h3cEOCComUniCountEntry 20 }

h3cEOCUniOutDroppedFrames OBJECT-TYPE
    SYNTAX     Unsigned32
    MAX-ACCESS read-only
    STATUS     current
    DESCRIPTION
        "The total number of frames dropped because of buffer failure."
    ::= { h3cEOCComUniCountEntry 21 }

h3cEOCUniOutOctets   OBJECT-TYPE
    SYNTAX     Unsigned32
    MAX-ACCESS read-only
    STATUS     current
    DESCRIPTION
        "The total number of octets transmitted out of the interface."
    ::= { h3cEOCComUniCountEntry 22 }

--
-- h3cEOCCommon NOTIFICATION
--

h3cEOCCommonTrap OBJECT IDENTIFIER ::= { h3cEOCCommon 5 }

h3cEOCTrapPrefix OBJECT IDENTIFIER ::= {h3cEOCCommonTrap 0}

h3cEOCCnuRegExcessTrap NOTIFICATION-TYPE
    OBJECTS
        {
            ifIndex,
            ifDescr
        }
    STATUS current
    DESCRIPTION
        "
        A h3cEOCCnuRegExcessTrap notification is sent when the
        number of registered CNUs exceeds the limit.
        "
    ::= { h3cEOCTrapPrefix 1 }

h3cEOCCnuRegExcessRecoverTrap NOTIFICATION-TYPE
    OBJECTS
        {
            ifIndex,
            ifDescr
        }
    STATUS current
    DESCRIPTION
        "
        A h3cEOCCnuRegExcessRecoverTrap notification is sent when
        h3cEOCCnuRegExcessTrap is detected and then recoverd.
        "
    ::= { h3cEOCTrapPrefix 2 }

h3cEOCCnuRegSuccTrap NOTIFICATION-TYPE
    OBJECTS
        {
            ifIndex,
            ifDescr
        }
    STATUS current
    DESCRIPTION
        "
        A h3cEOCCnuRegSuccTrap notification is sent when a
        CNU registers successful.
        "
    ::= { h3cEOCTrapPrefix 3 }

h3cEOCCnuOffLineTrap NOTIFICATION-TYPE
    OBJECTS
        {
            ifIndex,
            ifDescr
        }
    STATUS current
    DESCRIPTION
        "
        A h3cEOCCnuOffLineTrap notification is sent when a
        CNU offline.
        "
    ::= { h3cEOCTrapPrefix 4 }

h3cEOCCnuLinkupTrap NOTIFICATION-TYPE
    OBJECTS
        {
            ifIndex,
            ifDescr
        }
    STATUS current
    DESCRIPTION
        "
        A h3cEOCCnuLinkupTrap notification is sent when a
        CNU linkup.
        "
    ::= { h3cEOCTrapPrefix 5 }

h3cEOCOamDisconnectTrap NOTIFICATION-TYPE
    OBJECTS
        {
            ifIndex,
            ifDescr
        }
    STATUS current
    DESCRIPTION
        "
        A h3cEOCOamDisconnectionTrap notification is sent when
        LLID's OAM link is disconnected.
        "
    ::= { h3cEOCTrapPrefix 6 }

h3cEOCOamDisconnectRecoverTrap NOTIFICATION-TYPE
    OBJECTS
        {
            ifIndex,
            ifDescr
        }
    STATUS current
    DESCRIPTION
        "
        A h3cEOCOamDisconnectionRecoverTrap notification is sent when
        LLID's OAM link is disconnected and then connected.
        "
    ::= { h3cEOCTrapPrefix 7 }


h3cEOCBandwidthNotEnoughTrap NOTIFICATION-TYPE
    OBJECTS
        {
            ifIndex,
            ifDescr
        }
    STATUS current
    DESCRIPTION
        "
        Bandwidth is not enough, cnu can not bind now.
        "
    ::= { h3cEOCTrapPrefix 8 }

h3cEOCCnuAttenuationTrap NOTIFICATION-TYPE
    OBJECTS
        {
            ifIndex,
            ifDescr,
            h3cEOCComCnuMacAddress,
            h3cEOCComCnuAttenuation
        }
    STATUS current
    DESCRIPTION
        "
        A h3cHPEOCCnuAttenuationTrap notification is sent when a
        CNU's attenuation is changing.
        "
    ::= { h3cEOCTrapPrefix 9 }

h3cEOCCnuRegFailTrap NOTIFICATION-TYPE
    OBJECTS
        {
            ifIndex,
            ifDescr
        }
    STATUS current
    DESCRIPTION
        "
        A h3cEOCCnuRegFailTrap notification is sent when a
        CNU registers fail.
        "
    ::= { h3cEOCTrapPrefix 10 }

h3cEOCCLTCablePortErrorTrap NOTIFICATION-TYPE
    OBJECTS
        {
            ifIndex,
            ifDescr
        }
    STATUS current
    DESCRIPTION
        "
        A h3cEOCCLTCablePortErrorTrap notification is sent when the
        hardware of cable port occurs error or CLT's vlan is configged
        error.
        "
    ::= { h3cEOCTrapPrefix 11 }

h3cEOCCLTCablePortErrReTrap NOTIFICATION-TYPE
    OBJECTS
        {
            ifIndex,
            ifDescr
        }
    STATUS current
    DESCRIPTION
        "
        A h3cEOCCLTCablePortErrReTrap notification is sent when cable port
        error and then recovered.
        "
    ::= { h3cEOCTrapPrefix 12 }

h3cEOCCnuTxRateDropTrap NOTIFICATION-TYPE
    OBJECTS
        {
            ifIndex,
            ifDescr,
            h3cEOCComCnuMacAddress,
            h3cEOCComCnuTxRateDrop
        }
    STATUS current
    DESCRIPTION
        "
        A h3cEOCCnuTxRateDropTrap notification is sent when cable port
        rate of TX capability drop exceeded threshold.
        "
    ::= { h3cEOCTrapPrefix 13 }

h3cEOCCnuTxRateDropRecoverTrap NOTIFICATION-TYPE
    OBJECTS
        {
            ifIndex,
            ifDescr,
            h3cEOCComCnuMacAddress,
            h3cEOCComCnuTxRateDrop
        }
    STATUS current
    DESCRIPTION
        "
        A h3cEOCCnuTxRateDropRecoverTrap notification is sent when cable port
        rate of TX capability recover from the recent rate-drop trap.
        "
    ::= { h3cEOCTrapPrefix 14 }

h3cEOCCnuRxRateDropTrap NOTIFICATION-TYPE
    OBJECTS
        {
            ifIndex,
            ifDescr,
            h3cEOCComCnuMacAddress,
            h3cEOCComCnuRxRateDrop
        }
    STATUS current
    DESCRIPTION
        "
        A h3cEOCCnuRxRateDropTrap notification is sent when cable port
        rate of RX capability drop exceeded threshold.
        "
    ::= { h3cEOCTrapPrefix 15 }

h3cEOCCnuRxRateDropRecoverTrap NOTIFICATION-TYPE
    OBJECTS
        {
            ifIndex,
            ifDescr,
            h3cEOCComCnuMacAddress,
            h3cEOCComCnuRxRateDrop
        }
    STATUS current
    DESCRIPTION
        "
        A h3cEOCCnuRxRateDropRecoverTrap notification is sent when cable port
        rate of RX capability recover from the recent rate-drop trap.
        "
    ::= { h3cEOCTrapPrefix 16 }

h3cEOCCnuFWDownLoadErrTrap NOTIFICATION-TYPE
    OBJECTS
        {
            h3cHPEOCDownLoadCNUFWResult
        }
    STATUS current
    DESCRIPTION
        "
        A h3cEOCCnuFWDownLoadErrTrap notification is sent when CLT can't
        download CNU firmware from the server successfully.
        "
    ::= { h3cEOCTrapPrefix 17 }

h3cEOCCnuFWDownLoadErrReTrap NOTIFICATION-TYPE
    STATUS current
    DESCRIPTION
        "
        A h3cEOCCnuFWDownLoadErrReTrap notification is sent when CLT recover
        from the download CNU firmware error.
        "
    ::= { h3cEOCTrapPrefix 18 }

h3cEOCCnuDeviceTypeErrTrap NOTIFICATION-TYPE
    OBJECTS
        {
            ifIndex,
            ifDescr,
            h3cEOCComCnuMacAddress,
            h3cEOCComCnuDeviceType
        }
    STATUS current
    DESCRIPTION
        "
        A h3cEOCCnuDeviceTypeErrTrap notification is sent when the online CNU
        doesn't match the type which user defined earlier.
        "
    ::= { h3cEOCTrapPrefix 19 }

h3cEOCCnuDeviceTypeErrReTrap NOTIFICATION-TYPE
    OBJECTS
        {
            ifIndex,
            ifDescr,
            h3cEOCComCnuMacAddress
        }
    STATUS current
    DESCRIPTION
        "
        A h3cEOCCnuDeviceTypeErrReTrap notification is sent when the online CNU
        doesn't match the type which user defined earlier and then recover.
        "
    ::= { h3cEOCTrapPrefix 20 }

h3cEOCCnuAutoUpdateErrTrap NOTIFICATION-TYPE
    OBJECTS
        {
            ifIndex,
            ifDescr,
            h3cEOCComCnuMacAddress
        }
    STATUS current
    DESCRIPTION
        "
        A h3cEOCCnuAutoUpdateErrTrap notification is sent when the online CNU
        doesn't auto update successfully.
        "
    ::= { h3cEOCTrapPrefix 21 }

h3cEOCCnuAutoUpdateSuccTrap NOTIFICATION-TYPE
    OBJECTS
        {
            ifIndex,
            ifDescr,
            h3cEOCComCnuMacAddress
        }
    STATUS current
    DESCRIPTION
        "
        A h3cEOCCnuAutoUpdateSuccTrap notification is sent when the online CNU
        auto update successfully.
        "
    ::= { h3cEOCTrapPrefix 22 }

--
-- h3cEOCComOnLineCnuMan
--

h3cEOCComOnLineCnuMan OBJECT IDENTIFIER ::= { h3cEOCCommon 6 }
--
-- h3cEOCComCnuTypeTable
--
h3cEOCComCnuTypeTable OBJECT-TYPE
    SYNTAX     SEQUENCE OF H3cEOCComCnuTypeEntry
    MAX-ACCESS not-accessible
    STATUS     current
    DESCRIPTION
        "
        This table defines the description of cnu typ.
        "
    ::= { h3cEOCComOnLineCnuMan 1 }

h3cEOCComCnuTypeEntry OBJECT-TYPE
    SYNTAX     H3cEOCComCnuTypeEntry
    MAX-ACCESS not-accessible
    STATUS     current
    DESCRIPTION
        "
        The entry of the table h3cEOCComCnuTypeTable.
        "
    INDEX
        {
            h3cEOCComCnuTypeIdx
        }
    ::= { h3cEOCComCnuTypeTable 1 }

H3cEOCComCnuTypeEntry ::= SEQUENCE
    {
        h3cEOCComCnuTypeIdx    Unsigned32,
        h3cEOCComCnuDescripton DisplayString
    }

h3cEOCComCnuTypeIdx OBJECT-TYPE
    SYNTAX     Unsigned32
    MAX-ACCESS not-accessible
    STATUS     current
    DESCRIPTION
        "
        A unique value for each cnu types.  Its value
        ranges between 1 and the value of cny typess.
        "
    ::= { h3cEOCComCnuTypeEntry 1 }

h3cEOCComCnuDescripton OBJECT-TYPE
    SYNTAX     DisplayString
    MAX-ACCESS read-only
    STATUS     current
    DESCRIPTION
        "
        The description for unique cnu types.
        "
    ::= { h3cEOCComCnuTypeEntry 2 }

--
-- h3cEOCComCnuNumTable
--

h3cEOCComCnuNumTable OBJECT-TYPE
    SYNTAX     SEQUENCE OF H3cEOCComCnuNumEntry
    MAX-ACCESS not-accessible
    STATUS     current
    DESCRIPTION
        "
        This table defines the number of cnu registered in variable types
        of the CLT .
        "
    ::= { h3cEOCComOnLineCnuMan 2 }

h3cEOCComCnuNumEntry OBJECT-TYPE
    SYNTAX     H3cEOCComCnuNumEntry
    MAX-ACCESS not-accessible
    STATUS     current
    DESCRIPTION
        "
        The entry of the table h3cEOCComCnuNumTable.
        "
    INDEX
        {
            ifIndex,
            h3cEOCComCnuTypeIdx
        }
    ::= { h3cEOCComCnuNumTable 1 }

H3cEOCComCnuNumEntry ::= SEQUENCE
    {
        h3cEOCComCnuNumber     Integer32
    }

h3cEOCComCnuNumber OBJECT-TYPE
    SYNTAX     Integer32
    MAX-ACCESS read-only
    STATUS     current
    DESCRIPTION
        "
        The number of special type of cnu that has been registerd in clt.
        "
    ::= { h3cEOCComCnuNumEntry 1 }

END
