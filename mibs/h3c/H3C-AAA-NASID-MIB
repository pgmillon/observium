-- ==========================================================================
-- Copyright (c) 2004-2011 Hangzhou H3C Tech. Co., Ltd.  All rights reserved.
--
-- Description: AAA Nas-id mib
-- Reference:
-- Version: V1.0
-- History:
--   V1.0 2011-03-09 created by wangbin
-- ==========================================================================
H3C-AAA-NASID-MIB DEFINITIONS ::= BEGIN

IMPORTS
    MODULE-IDENTITY, OBJECT-TYPE
        FROM SNMPv2-SMI
    h3cCommon
        FROM HUAWEI-3COM-OID-MIB;

h3cAAANasId MODULE-IDENTITY
    LAST-UPDATED "201103090945Z"
    ORGANIZATION
        "Hangzhou H3C Technologies Co., Ltd."
    CONTACT-INFO
        "Platform Team H3C Technologies Co., Ltd.
         Hai-Dian District Beijing P.R. China
         http://www.h3c.com
         Zip: 100085"
    DESCRIPTION
        "This MIB contains objects to
        manage configuration for AAA Nas-id feature.
        AAA presents authentication, authorization and accouting.
        NAS acts as the Network Access Server.
        Nas-id is an identifier that contains some strings identifying the NAS."
    REVISION "201103090945Z"
    DESCRIPTION
        "Initial version."
    ::= { h3cCommon 114 }

h3cAAANasIdObjects OBJECT IDENTIFIER ::= { h3cAAANasId 1 }

-- ==========================================================================
-- h3cAAANasIdTable OBJECT
-- ==========================================================================
h3cAAANasIdTable OBJECT-TYPE
    SYNTAX SEQUENCE OF H3cAAANasIdEntry
    MAX-ACCESS not-accessible
    STATUS current
    DESCRIPTION
    "The AAA Nas-id table."
::= { h3cAAANasIdObjects 1 }

h3cAAANasIdEntry OBJECT-TYPE
    SYNTAX H3cAAANasIdEntry
    MAX-ACCESS not-accessible
    STATUS current
    DESCRIPTION
    "The AAA Nas-id entry."
    INDEX { h3cAAANasIdName }
::= { h3cAAANasIdTable 1 }

H3cAAANasIdEntry ::= SEQUENCE {
    h3cAAANasIdName             OCTET STRING }

h3cAAANasIdName OBJECT-TYPE
    SYNTAX      OCTET STRING (SIZE(1..64))
    MAX-ACCESS  read-only
    STATUS      current
    DESCRIPTION
    "The Nas-id name."
::= { h3cAAANasIdEntry 1 }

END
