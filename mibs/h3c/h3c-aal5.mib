-- =============================================================
-- Copyright (C) 2008 by Hangzhou H3C Technologies Co., Ltd. All rights reserved.
--
-- Description: This file describes the huawei mib implementation of ATM
-- Reference:  extension of RFC 1695
-- Version: V1.1
-- History:
--   V1.0 Initial Version  by lizhiyong
--   V1.1 Add node h3cAal5VccState and Trap h3cAal5VccStateChange
-- =============================================================
H3C-AAL5-MIB DEFINITIONS ::= BEGIN

IMPORTS
        MODULE-IDENTITY,
        OBJECT-TYPE,
        Integer32,
        NOTIFICATION-TYPE,
        Counter32
    FROM SNMPv2-SMI
        MODULE-COMPLIANCE,
        OBJECT-GROUP,
        NOTIFICATION-GROUP
    FROM SNMPv2-CONF
        ifIndex
    FROM RFC1213-MIB
        h3cAAL5
    FROM HUAWEI-3COM-OID-MIB;

h3cAAL5MIB  MODULE-IDENTITY
    LAST-UPDATED    "200411041350Z"
    ORGANIZATION
        "Hangzhou H3C Technologies Co., Ltd."
    CONTACT-INFO
        "PLAT Team Hangzhou H3C Technologies Co.,Ltd.
        Shang-Di Information Industry Base,
        Hai-Dian District Beijing P.R. China
        http://www.h3c.com
        Zip:100085"
    DESCRIPTION
        "This MIB file provides AAL5 specific information
        that are excluded by RFC 1695 "
    REVISION        "200411041350Z"
    DESCRIPTION
        "Initial version of this MIB module."
    ::= { h3cAAL5 1 }


h3cAal5MIBObjects OBJECT IDENTIFIER ::= { h3cAAL5MIB 1 }
h3cAal5MIBTraps OBJECT IDENTIFIER ::= { h3cAAL5MIB 0 }

h3cAal5VccTable OBJECT-TYPE
    SYNTAX       SEQUENCE OF H3CAal5VccEntry
    MAX-ACCESS   not-accessible
    STATUS       current
    DESCRIPTION
        "This table extends AAL5 VCC performance
         parameters which definded in aal5VccEntry of RFC1695."
    ::= { h3cAal5MIBObjects 1 }

h3cAal5VccEntry OBJECT-TYPE
    SYNTAX         H3CAal5VccEntry
    MAX-ACCESS     not-accessible
    STATUS         current
    DESCRIPTION
        "This list contains the additional AAL5 VCC performance
         parameters which are not definded in aal5VccEntry
         of RFC1695."
    INDEX { ifIndex, h3cAal5VccVpi, h3cAal5VccVci }
    ::= { h3cAal5VccTable 1 }

H3CAal5VccEntry ::= SEQUENCE  {
    h3cAal5VccVpi        Integer32,
    h3cAal5VccVci        Integer32,
    h3cAal5VccInPkts     Counter32,
    h3cAal5VccOutPkts    Counter32,
    h3cAal5VccInOctets   Counter32,
    h3cAal5VccOutOctets  Counter32,
    h3cAal5VccState      INTEGER
    }

h3cAal5VccVpi              OBJECT-TYPE
    SYNTAX         Integer32  (0..4095)
    MAX-ACCESS     not-accessible
    STATUS         current
    DESCRIPTION
        "The VPI value of the AAL5 VCC."
    ::= { h3cAal5VccEntry 1 }

h3cAal5VccVci             OBJECT-TYPE
    SYNTAX         Integer32  (0..65535)
    MAX-ACCESS     not-accessible
    STATUS         current
    DESCRIPTION
        "The VCI value of the AAL5 VCC."
    ::= { h3cAal5VccEntry 2 }

h3cAal5VccInPkts          OBJECT-TYPE
    SYNTAX          Counter32
    MAX-ACCESS      read-only
    STATUS          current
    DESCRIPTION
        "The number of AAL5 CPCS PDUs received."
    ::= { h3cAal5VccEntry 3 }

h3cAal5VccOutPkts        OBJECT-TYPE
    SYNTAX          Counter32
    MAX-ACCESS      read-only
    STATUS          current
    DESCRIPTION
        "The number of AAL5 CPCS PDUs transmitted."
    ::= { h3cAal5VccEntry 4 }

h3cAal5VccInOctets       OBJECT-TYPE
    SYNTAX          Counter32
    MAX-ACCESS      read-only
    STATUS          current
    DESCRIPTION
        "The number of AAL5 CPCS PDU octets received."
    ::= { h3cAal5VccEntry 5 }

h3cAal5VccOutOctets     OBJECT-TYPE
    SYNTAX          Counter32
    MAX-ACCESS      read-only
    STATUS          current
    DESCRIPTION
        "The number of AAL5 CPCS PDU octets transmitted."
    ::= { h3cAal5VccEntry 6 }

h3cAal5VccState OBJECT-TYPE
    SYNTAX   INTEGER    {
                invalid (1),
                active (2),
                inactive (3)
            }
    MAX-ACCESS   read-only
    STATUS   current
    DESCRIPTION
        "Indicates whether the particular virtual circuit is
        operational. 'Active' indicates the particular virtual
        circuit is operational.  'Inactive' indicates the circuit
        is temporarily disabled.  'Invalid' indicates the circuit
        is deleted"
    DEFVAL { active }
        ::= { h3cAal5VccEntry 7 }

h3cAal5VccStateChange   NOTIFICATION-TYPE
    OBJECTS  { h3cAal5VccState }
    STATUS          current
    DESCRIPTION
        "The status of AAL5 VCC."
    ::= { h3cAal5MIBTraps 1 }


-- Conformance Information

h3cAal5MIBConformance OBJECT IDENTIFIER ::= { h3cAAL5MIB 3 }
h3cAal5MIBCompliances OBJECT IDENTIFIER ::= { h3cAal5MIBConformance 1 }
h3cAal5MIBGroups      OBJECT IDENTIFIER ::= { h3cAal5MIBConformance 2 }

-- Compliance Statement
h3cAal5MIBCompliance MODULE-COMPLIANCE
    STATUS  current
    DESCRIPTION
        "The compliance statement."
    MODULE  -- this module
    MANDATORY-GROUPS { h3cAal5MIBGroup }
    GROUP       h3cAal5NotificationGroup
    DESCRIPTION
        "This optional group defines the asynchronous
        notifications generated by ATM Systems."
    ::= { h3cAal5MIBCompliances 1 }

-- units of conformance:

h3cAal5MIBGroup OBJECT-GROUP
    OBJECTS {
        h3cAal5VccInPkts,
        h3cAal5VccOutPkts,
        h3cAal5VccInOctets,
        h3cAal5VccOutOctets
    }
    STATUS  current
    DESCRIPTION
        "A collection of objects."
    ::= { h3cAal5MIBGroups 1 }

h3cAal5NotificationGroup NOTIFICATION-GROUP
    NOTIFICATIONS { h3cAal5VccStateChange }
    STATUS  current
    DESCRIPTION
        "Traps which may be used to enhance event driven
        management of the interface."
    ::= { h3cAal5MIBGroups 2 }

END
