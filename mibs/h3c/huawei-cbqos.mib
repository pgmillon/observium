-- =========================================================================
-- Copyright (C) 2004 by  HUAWEI TECHNOLOGIES. All rights reserved
--
-- Description:This mib file is used for management of huawei Class Based
--             QoS information.
-- Reference:
-- Version: V1.8
-- History:
--      V1.0 tianli,2004.4.10,publish
--      V1.1 lizhiyong, 2004-9-14
--          modify the hyphens which is not allowed used in SMIv2
--      v1.2 changed by gaolong
--          replace chinese characters in this file with english characters
--          move MODULE-IDENTITY after IMPORTS CLAUSE
--          changed by yangjianjun
--          change description of hwCBQoSMatchRuleIntValue1 and hwCBQoSMatchRuleIntValue2
--          changed by wanghao
--          add an object hwCBQoSQueueCbsRatio
--      v1.3 changed by liguanmin,2004-12-23.
--          added two values in the node hwCBQoSMatchRuleType of the hwCBQoSMatchRuleCfgInfoTable.
--          this two values are typeMatchDe,typeMatchClp.
--      V1.4 2005-04-15 modify description of hwCBQoSMatchRuleStringValue by tangshun.
--      V1.5 2005-05-23 add hwCBQoSFrPvcClassAverageRate, hwCBQoSAtmPvcClassAverageRate,
--          and hwCBQoSIfClassAverageRate by dongjun.
--      V1.6 2005-08-11 add enum value 25 for MatchRuleType,
--          modify description of hwCBQoSMatchRuleType and hwCBQoSMatchRuleStringValue
--          by dongjun.
--          update file format by gaolong
--      V1.7 2006-05-18 modified by haochunbo
--          Add an enumeration unitRemainPercent for QueueBandwidthUnit.
--          Modify the description of hwCBQoSQueueBandwidthUnit and hwCBQoSQueueBandwidthValue.
--      V1.8 2007-05-23 modified by huguohua
--          Add LrCirUnit, hwCBQoSNestPolicyCfgInfoTable, hwCBQoSLrCfgInfoTable,
--              hwCBQoSIfLrRunInfoTable, hwCBQoSAtmPvcLrRunInfoTable, hwCBQoSFrPvcLrRunInfoTable
-- ==========================================================================
HUAWEI-CBQOS-MIB DEFINITIONS ::= BEGIN

IMPORTS
    hwQoS
        FROM HUAWEI-3COM-OID-MIB

    OBJECT-GROUP, MODULE-COMPLIANCE
        FROM SNMPv2-CONF

    IpAddress, Integer32, Counter32, Unsigned32, OBJECT-TYPE, MODULE-IDENTITY,
    Counter64
        FROM SNMPv2-SMI

    TEXTUAL-CONVENTION, RowStatus, DisplayString, MacAddress
        FROM SNMPv2-TC;

        hwCBQoSMIB MODULE-IDENTITY
            LAST-UPDATED "200404100000Z"            -- April 10, 2004 at 00:00 GMT
            ORGANIZATION
                    "Huawei Technologies co.,Ltd."
            CONTACT-INFO
                " R&D BeiJing, Huawei Technologies co.,Ltd.
                Huawei Bld.,NO.3 Xinxi Rd.,
                Shang-Di Information Industry Base,
                Hai-Dian District Beijing P.R. China
                Zip:100085
                Http://www.huawei.com
                E-mail:support@huawei.com "
            DESCRIPTION
                "The HUAWEI-CBQOS-MIB contains objects to
                Manage configuration and Monitor running state
                for Class Based QoS feature.

                    *********************************
                        MIB Tables
                    **********************************
                This MIB consists of the following tables:
                     1 :  hwCBQoSClassifierCfgInfoTable
                     2 :  hwCBQoSMatchRuleCfgInfoTable
                     3 :  hwCBQoSBehaviorCfgInfoTable
                     4 :  hwCBQoSCarCfgInfoTable
                     5 :  hwCBQoSGtsCfgInfoTable
                     6 :  hwCBQoSRemarkCfgInfoTable
                     7 :  hwCBQoSQueueCfgInfoTable
                     8 :  hwCBQoSWredCfgInfoTable
                     9 :  hwCBQoSWredClassCfgInfoTable
                     10:  hwCBQoSPolicyRouteCfgInfoTable
                     11:  hwCBQoSNatCfgInfoTable
                     12:  hwCBQoSFirewallCfgInfoTable
                     13:  hwCBQoSSamplingCfgInfoTable
                     14:  hwCBQoSPolicyCfgInfoTable
                     15:  hwCBQoSPolicyClassCfgInfoTable
                     16:  hwCBQoSIfApplyPolicyTable
                     17:  hwCBQoSAtmPvcApplyPolicyTable
                     18:  hwCBQoSIfVlanApplyPolicyTable
                     19:  hwCBQoSFrClassApplyPolicyTable
                     20:  hwCBQoSFrPvcApplyPolicyTable
                     21:  hwCBQoSIfCbqRunInfoTable
                     22:  hwCBQoSIfClassMatchRunInfoTable
                     23:  hwCBQoSIfCarRunInfoTable
                     24:  hwCBQoSIfGtsRunInfoTable
                     25:  hwCBQoSIfRemarkRunInfoTable
                     26:  hwCBQoSIfQueueRunInfoTable
                     27:  hwCBQoSIfWredRunInfoTable
                     28:  hwCBQoSAtmPvcCbqRunInfoTable
                     29:  hwCBQoSAtmPvcClassMatchRunInfoTable
                     30:  hwCBQoSAtmPvcCarRunInfoTable
                     31:  hwCBQoSAtmPvcGtsRunInfoTable
                     32:  hwCBQoSAtmPvcRemarkRunInfoTable
                     33:  hwCBQoSAtmPvcQueueRunInfoTable
                     34:  hwCBQoSAtmPvcWredRunInfoTable
                     35:  hwCBQoSFrPvcCbqRunInfoTable
                     36:  hwCBQoSFrPvcClassMatchRunInfoTable
                     37:  hwCBQoSFrPvcCarRunInfoTable
                     38:  hwCBQoSFrPvcGtsRunInfoTable
                     39:  hwCBQoSFrPvcRemarkRunInfoTable
                     40:  hwCBQoSFrPvcQueueRunInfoTable
                     41:  hwCBQoSFrPvcWredRunInfoTable
                     42:  hwCBQoSIfVlanClassMatchRunInfoTable

                Software QoS supports the following tables:
                     1 :  hwCBQoSClassifierCfgInfoTable
                     2 :  hwCBQoSMatchRuleCfgInfoTable
                     3 :  hwCBQoSBehaviorCfgInfoTable
                     4 :  hwCBQoSCarCfgInfoTable
                     5 :  hwCBQoSGtsCfgInfoTable
                     6 :  hwCBQoSRemarkCfgInfoTable
                     7 :  hwCBQoSQueueCfgInfoTable
                     8 :  hwCBQoSWredCfgInfoTable
                     9 :  hwCBQoSWredClassCfgInfoTable
                     14:  hwCBQoSPolicyCfgInfoTable
                     15:  hwCBQoSPolicyClassCfgInfoTable
                     16:  hwCBQoSIfApplyPolicyTable
                     17:  hwCBQoSAtmPvcApplyPolicyTable
                     19:  hwCBQoSFrClassApplyPolicyTable
                     20:  hwCBQoSFrPvcApplyPolicyTable
                     21:  hwCBQoSIfCbqRunInfoTable
                     22:  hwCBQoSIfClassMatchRunInfoTable
                     23:  hwCBQoSIfCarRunInfoTable
                     24:  hwCBQoSIfGtsRunInfoTable
                     25:  hwCBQoSIfRemarkRunInfoTable
                     26:  hwCBQoSIfQueueRunInfoTable
                     27:  hwCBQoSIfWredRunInfoTable
                     28:  hwCBQoSAtmPvcCbqRunInfoTable
                     29:  hwCBQoSAtmPvcClassMatchRunInfoTable
                     30:  hwCBQoSAtmPvcCarRunInfoTable
                     31:  hwCBQoSAtmPvcGtsRunInfoTable
                     32:  hwCBQoSAtmPvcRemarkRunInfoTable
                     33:  hwCBQoSAtmPvcQueueRunInfoTable
                     34:  hwCBQoSAtmPvcWredRunInfoTable
                     35:  hwCBQoSFrPvcCbqRunInfoTable
                     36:  hwCBQoSFrPvcClassMatchRunInfoTable
                     37:  hwCBQoSFrPvcCarRunInfoTable
                     38:  hwCBQoSFrPvcGtsRunInfoTable
                     39:  hwCBQoSFrPvcRemarkRunInfoTable
                     40:  hwCBQoSFrPvcQueueRunInfoTable
                     41:  hwCBQoSFrPvcWredRunInfoTable

                Hardware QoS supports the following tables:
                     1 :  hwCBQoSClassifierCfgInfoTable
                     2 :  hwCBQoSMatchRuleCfgInfoTable
                     3 :  hwCBQoSBehaviorCfgInfoTable
                     4 :  hwCBQoSCarCfgInfoTable
                     6 :  hwCBQoSRemarkCfgInfoTable
                     10:  hwCBQoSPolicyRouteCfgInfoTable
                     11:  hwCBQoSNatCfgInfoTable
                     12:  hwCBQoSFirewallCfgInfoTable
                     13:  hwCBQoSSamplingCfgInfoTable
                     14:  hwCBQoSPolicyCfgInfoTable
                     15:  hwCBQoSPolicyClassCfgInfoTable
                     16:  hwCBQoSIfApplyPolicyTable
                     18:  hwCBQoSIfVlanApplyPolicyTable
                     22:  hwCBQoSIfClassMatchRunInfoTable
                     42:  hwCBQoSIfVlanClassMatchRunInfoTable
                "
            ::= { hwQoS 1 }

--
--type definitions in the traffic classifier
--

--MatchRuleType
    MatchRuleType ::= TEXTUAL-CONVENTION
        STATUS  current
        DESCRIPTION
            "Type of Match Rule."
        SYNTAX  INTEGER {
            typeAny(1),
            typeAcl(2),
            typeRtpPort(3),
            typeProtocol(4),
            typeIpPrec(5),
            typeDscp(6),
            typeVlan8021p(7),
            typeMplsExp(8),
            typeSourceMac(9),
            typeDestinationMac(10),
            typeClassifier(11),
            typeInboundInterface(12),
            typeMacGroup(13),
            -- value 14 and 15 are reserved for future use.
            typeMatchDe(16),  -- the match rule is FR DE
            typeMatchClp(17),  -- the match rule is ATM CLP
            -- enum values 18 to 24 are reserved
            typeOutboundInterface(25)
        }

--
--end of type definitions in the traffic classifier
--

--
--type definitions in the traffic behavior
--

--CarAction

    CarAction ::= TEXTUAL-CONVENTION
        STATUS  current
        DESCRIPTION
            "The actions taken when packets conforming or exceeding the configured
            CIR:
                pass (1),
                discard (2),
                remark IP Precedence (3),
                remark DSCP(4),
                remark Mpls Exp(5),
                remark (6)
            "

        SYNTAX  INTEGER {
                pass (1),
                discard (2),
                remarkIpPrec (3),
                remarkDscp(4),
                remarkMplsExp(5),
                remark(6)
        }

--RemarkType
    RemarkType ::= TEXTUAL-CONVENTION
        STATUS  current
        DESCRIPTION
            "typeIpPrec(1)
            typeDscp(2)
            typeMplsExp(3)
            typeVlan8021p(4)
            typeAtmClp(5)
            typeFrDe(6)
            "
        SYNTAX INTEGER {
            typeIpPrec(1),
            typeDscp(2),
            typeMplsExp(3),
            typeVlan8021p(4),
            typeAtmClp(5),
            typeFrDe(6)
        }

--WredType
    WredType ::= TEXTUAL-CONVENTION
        STATUS  current
        DESCRIPTION
            "IpPrec Based (1)
            DSCP Based (2)
            "
        SYNTAX INTEGER {
            typeIpPrecbased (1),
            typeDscpbased (2)
        }

--QueueType
    QueueType ::= TEXTUAL-CONVENTION
        STATUS  current
        DESCRIPTION
            "Queueing Type:
            EF: (1)
            AF: (2)
            WFQ: (3)
            "
        SYNTAX INTEGER {
            ef (1),
            af (2),
            wfq (3)
        }

--QueueBandwidthUnit
    QueueBandwidthUnit ::= TEXTUAL-CONVENTION
        STATUS  current
        DESCRIPTION
            "Bandwidth Unit:
            Absolute, Unit Kbps (1)
            Percent, Unit % (2), means the percentage of the reserved bandwidth besides the part
            configured for RTP queue.
            Remaining percent, Unit % (3), means the percentage of the reserved bandwidth besides
            the parts configured for EF and RTP queue.
            "
        SYNTAX INTEGER {
            unitUnavailable(-1),
            unitAbsolute(1),
            unitPercent(2),
            unitRemainPercent(3)
        }

-- LrCirUnit
        LrCirUnit ::= TEXTUAL-CONVENTION
            STATUS current
            DESCRIPTION
                "CIR Unit:
                Absolute, Unit bps (1)
                Percent, Unit % (2)
                "
            SYNTAX INTEGER
                {
                absoluteUnitBps(1),
                percentUnit(2)
                }

--
--end of type definitions in the traffic behavior
--

--
--type definitions in the policy
--

--Direction

    DirectionType ::= TEXTUAL-CONVENTION
        STATUS  current
        DESCRIPTION
            "The Direction Policy apply on."
        SYNTAX  INTEGER {
            inbound (1),
            outbound (2)
        }

--
--end of type definitions in policy
--




--
-- Node definitions
--

        hwCBQoSObjects OBJECT IDENTIFIER ::= { hwCBQoSMIB 1 }

--hwCBQoSClassifierObjects

hwCBQoSClassifierObjects OBJECT IDENTIFIER ::= { hwCBQoSObjects 1 }

-- Traffic Classifier Next Index
        hwCBQoSClassifierIndexNext OBJECT-TYPE
            SYNTAX Integer32
            MAX-ACCESS read-only
            STATUS current
            DESCRIPTION
                "This object contains an appropriate value to be used for
                 hwCBQoSClassifierIndex when creating rows in the
                 hwCBQoSClassifierCfgInfoTable. Begin with 0."
            ::= { hwCBQoSClassifierObjects 1 }

-- Traffic Classifier
        hwCBQoSClassifierCfgInfoTable OBJECT-TYPE
            SYNTAX SEQUENCE OF HwCBQoSClassifierCfgInfoEntry
            MAX-ACCESS not-accessible
            STATUS current
            DESCRIPTION
                "A table of Traffic Classifier configuration information."
            ::= { hwCBQoSClassifierObjects 2 }

        hwCBQoSClassifierCfgInfoEntry OBJECT-TYPE
            SYNTAX HwCBQoSClassifierCfgInfoEntry
            MAX-ACCESS not-accessible
            STATUS current
            DESCRIPTION
                "Traffic Classifier Configuration Information Entry."
            INDEX { hwCBQoSClassifierIndex }
            ::= { hwCBQoSClassifierCfgInfoTable 1 }

        HwCBQoSClassifierCfgInfoEntry ::=
            SEQUENCE {
                hwCBQoSClassifierIndex
                    Integer32,
                hwCBQoSClassifierName
                    OCTET STRING,
                hwCBQoSClassifierRuleCount
                    Integer32,
                hwCBQoSClassifierOperator
                    INTEGER,
                hwCBQoSClassifierLayer
                    INTEGER,
                hwCBQoSClassifierRowStatus
                    RowStatus
                 }

        hwCBQoSClassifierIndex OBJECT-TYPE
            SYNTAX Integer32
            MAX-ACCESS not-accessible
            STATUS current
            DESCRIPTION
                "Index of Traffic Classifier. Begin with 0."
            ::= { hwCBQoSClassifierCfgInfoEntry 1 }

        hwCBQoSClassifierName OBJECT-TYPE
            SYNTAX OCTET STRING (SIZE (1..31))
            MAX-ACCESS read-create
            STATUS current
            DESCRIPTION
                "Name of Traffic Classifier."
            ::= { hwCBQoSClassifierCfgInfoEntry 2 }

        hwCBQoSClassifierRuleCount OBJECT-TYPE
            SYNTAX Integer32
            MAX-ACCESS read-only
            STATUS current
            DESCRIPTION
                "The count of match rules of Traffic classifier. It can be used
                for hwCBQoSMatchRuleIndex when creating rows in the
                hwCBQoSMatchRuleCfgInfoTable. Begin with 0."
            ::= { hwCBQoSClassifierCfgInfoEntry 3 }

        hwCBQoSClassifierOperator OBJECT-TYPE
            SYNTAX INTEGER {
             and(1),
             or(2)
            }
            MAX-ACCESS read-create
            STATUS current
            DESCRIPTION
                "Operator of the match rules of traffic classifier.
                Software QoS support and,or.
                Hardware QoS support and."
            DEFVAL {and}
            ::= { hwCBQoSClassifierCfgInfoEntry 4 }

        hwCBQoSClassifierLayer OBJECT-TYPE
            SYNTAX INTEGER {
                    unavailable(-1),
                    l2(1),
                    l3(2),
                    both(3)
                }
            MAX-ACCESS read-create
            STATUS current
            DESCRIPTION
                "Configuration layer of traffic classifier.
                Only hardware QoS support it.
                -1(unavailable) is returned only when getting value from software QoS.
                -1(unavailable) can't be set."
            DEFVAL {l3}
            ::= { hwCBQoSClassifierCfgInfoEntry 5 }

        hwCBQoSClassifierRowStatus OBJECT-TYPE
            SYNTAX RowStatus
            MAX-ACCESS read-create
            STATUS current
            DESCRIPTION
                "RowStatus. Three actions are used: active,
                createAndGo, destroy"
            ::= { hwCBQoSClassifierCfgInfoEntry 6 }

-- Match rule
        hwCBQoSMatchRuleCfgInfoTable OBJECT-TYPE
            SYNTAX SEQUENCE OF HwCBQoSMatchRuleCfgInfoEntry
            MAX-ACCESS not-accessible
            STATUS current
            DESCRIPTION
                "A table of Match Rule configuration information."
            ::= { hwCBQoSClassifierObjects 3 }

        hwCBQoSMatchRuleCfgInfoEntry OBJECT-TYPE
            SYNTAX HwCBQoSMatchRuleCfgInfoEntry
            MAX-ACCESS not-accessible
            STATUS current
            DESCRIPTION
                "Match Rule Configuration Information Entry."
            INDEX { hwCBQoSClassifierIndex, hwCBQoSMatchRuleIndex }
            ::= { hwCBQoSMatchRuleCfgInfoTable 1 }


        HwCBQoSMatchRuleCfgInfoEntry ::=
            SEQUENCE {
                hwCBQoSMatchRuleIndex
                    Integer32,
                hwCBQoSMatchRuleIfNot
                    INTEGER,
                hwCBQoSMatchRuleType
                    MatchRuleType,
                hwCBQoSMatchRuleStringValue
                    OCTET STRING,
                hwCBQoSMatchRuleIntValue1
                    Unsigned32,
                hwCBQoSMatchRuleIntValue2
                    Unsigned32,
                hwCBQoSMatchRuleRowStatus
                    RowStatus
                 }

        hwCBQoSMatchRuleIndex OBJECT-TYPE
            SYNTAX Integer32
            MAX-ACCESS not-accessible
            STATUS current
            DESCRIPTION
                "Index of Match Rule."
            ::= { hwCBQoSMatchRuleCfgInfoEntry 1 }

        hwCBQoSMatchRuleIfNot OBJECT-TYPE
            SYNTAX INTEGER {
                match(1),
                match-Not(2)
             }
            MAX-ACCESS read-create
            STATUS current
            DESCRIPTION
                "whether the if-match rule is a Match or Match-Not statement.
                Software QoS support match,match-Not.
                Hardware QoS support match."
            DEFVAL {match}
            ::= { hwCBQoSMatchRuleCfgInfoEntry 2 }

        hwCBQoSMatchRuleType OBJECT-TYPE
            SYNTAX MatchRuleType
            MAX-ACCESS read-create
            STATUS current
            DESCRIPTION
                "Type of Match Rule.
                typeAny(1)
                typeAcl(2),
                typeRtpPort(3),
                typeProtocol(4),
                typeIpPrec(5),
                typeDscp(6),
                typeVlan8021p(7),
                typeMplsExp(8),
                typeSourceMac(9),
                typeDestinationMac(10),
                typeClassifier(11),
                typeInboundInterface(12),
                typeMacGroup(13),
                typeMatchDe(16),  /* the match rule is FR DE   */
                typeMatchClp(17),  /* the match rule is ATM CLP */
                typeOutboundInterface(25)
                Software QoS supports any type except typeMacGroup.
                Hardware QoS supports typeAcl,typeDscp,typeMacGroup.
                "
            ::= { hwCBQoSMatchRuleCfgInfoEntry 3 }

        hwCBQoSMatchRuleStringValue OBJECT-TYPE
            SYNTAX OCTET STRING (SIZE (0..255))
            MAX-ACCESS read-create
            STATUS current
            DESCRIPTION
                "Value of Match Rule.
                 SourceMAC(9): SIZE (12) HHHHHHHHHHHH  for example: 010102020303 means
                               the match rule is 'if-match source-mac 0101-0202-0303'
                 DestinationMAC(10): SIZE (12) HHHHHHHHHHHH for example: 010102020303 means
                               the match rule is 'if-match destination-mac 0101-0202-0303'
                 Classifier(11): SIZE (1..31)
                 InboundInterface(12): SIZE (1..47)
                 typeOutboundInterface(25): SIZE (1..47)
                 other type: Set is not permitted. Zero-length String  will be
                             returned when getting.
                "
            ::= { hwCBQoSMatchRuleCfgInfoEntry 4 }

        hwCBQoSMatchRuleIntValue1 OBJECT-TYPE
            SYNTAX Unsigned32
            MAX-ACCESS read-create
            STATUS current
            DESCRIPTION
                "Value of Match Rule.
                Acl(2):
                      Software QoS: 2000~3999  Hardware Qos: 10000~42767
                RtpPort(3): start-port: 2000~65535
                Protocol(4): 1(Ip)
                IpPrec(5):  value:0~7, up to 8 value can be input. The bit set
                            to 1 of the last 8 bits of hwCBQoSMatchRuleIntValue1
                            is used to indicate the value 0~7.
                            For example: 0x00000053(Binary format is 01010011)
                                         means the match rule is 'if-match ip-prec 0 1 4 6'
                Dscp(6):     value:0~63,up to 8 value can be input.
                             The bit set to 1 of hwCBQoSMatchRuleIntValue1 is
                             used to indicate the value 32~63.
                             The bit set to 1 of hwCBQoSMatchRuleIntValue2 is
                             used to indicate the value 0~31.
                             For example: 0x80000003 means the match rule is
                                          'if-match dscp 32 33 63'
                Vlan8021p(7): value:0~7, up to 8 value can be input. The bit
                              set to 1 of the last 8 bits of hwCBQoSMatchRuleIntValue1
                              is used to indicate the 8 value 0~7.
                              For example: 0x53(Binary format is 01010011) means
                                           the match rule is 'if-match vlan 0 1 4 6'
                MplsExp(8): value:0~7, up to 8 value can be input. The bit set
                            to 1 of the last 8 bits of hwCBQoSMatchRuleIntValue1
                            is used to indicate the 8 value 0~7.
                            For example: 0x53(Binary format is 01010011) means
                            the match rule is 'if-match mpls 0 1 4 6'
                MacGroup(13): 1~63
                other type: Set is not permitted.  0xffffffff will be returned
                            when getting.
                "
            ::= { hwCBQoSMatchRuleCfgInfoEntry 5 }

        hwCBQoSMatchRuleIntValue2 OBJECT-TYPE
            SYNTAX Unsigned32
            MAX-ACCESS read-create
            STATUS current
            DESCRIPTION
                "Value of Match Rule.
                 RtpPort(3): end-port: 2000~65535
                 Dscp(6):  value:0~63,up to 8 value can be input.
                           The bit set to 1 of hwCBQoSMatchRuleIntValue1 is used
                           to indicate the value 32~63.
                           The bit set to 1 of hwCBQoSMatchRuleIntValue2 is used
                           to indicate the value 0~31.
                           for example: 0x80000003 means the match rule is
                                        'if-match dscp 0 1 31'
                 other type: Set is not permitted.  0xffffffff will be returned
                             when getting.
                "
            ::= { hwCBQoSMatchRuleCfgInfoEntry 6 }

        hwCBQoSMatchRuleRowStatus OBJECT-TYPE
            SYNTAX RowStatus
            MAX-ACCESS read-create
            STATUS current
            DESCRIPTION
                "RowStatus for Match Rule Table.
                Three actions are used: active, createAndGo, destroy"
            ::= { hwCBQoSMatchRuleCfgInfoEntry 7 }



--hwCBQoSBehaviorObjects

hwCBQoSBehaviorObjects OBJECT IDENTIFIER ::= { hwCBQoSObjects 2 }

-- Traffic Behavior Next Index
        hwCBQoSBehaviorIndexNext OBJECT-TYPE
            SYNTAX Integer32
            MAX-ACCESS read-only
            STATUS current
            DESCRIPTION
                "This object contains an appropriate value to be used for
                hwCBQoSBehaviorIndex when creating rows in the
                hwCBQoSBehaviorCfgInfoTable. Begin with 0."
            ::= { hwCBQoSBehaviorObjects 1 }

-- Traffic Behavior
        hwCBQoSBehaviorCfgInfoTable OBJECT-TYPE
            SYNTAX SEQUENCE OF HwCBQoSBehaviorCfgInfoEntry
            MAX-ACCESS not-accessible
            STATUS current
            DESCRIPTION
                "A table of Traffic Behavior configuration information."
            ::= { hwCBQoSBehaviorObjects 2 }

        hwCBQoSBehaviorCfgInfoEntry OBJECT-TYPE
            SYNTAX HwCBQoSBehaviorCfgInfoEntry
            MAX-ACCESS not-accessible
            STATUS current
            DESCRIPTION
                "Traffic Behavior Configuration Information Entry."
            INDEX { hwCBQoSBehaviorIndex }
            ::= { hwCBQoSBehaviorCfgInfoTable 1 }


        HwCBQoSBehaviorCfgInfoEntry ::=
            SEQUENCE {
                hwCBQoSBehaviorIndex
                    Integer32,
                hwCBQoSBehaviorName
                    OCTET STRING,
                hwCBQoSBehaviorRowStatus
                    RowStatus
             }
        hwCBQoSBehaviorIndex OBJECT-TYPE
            SYNTAX Integer32
            MAX-ACCESS not-accessible
            STATUS current
            DESCRIPTION
                "Index of Traffic Behavior."
            ::= { hwCBQoSBehaviorCfgInfoEntry 1 }

        hwCBQoSBehaviorName OBJECT-TYPE
            SYNTAX OCTET STRING (SIZE (1..31))
            MAX-ACCESS read-create
            STATUS current
            DESCRIPTION
                "Name of Traffic Behavior."
            ::= { hwCBQoSBehaviorCfgInfoEntry 2 }

        hwCBQoSBehaviorRowStatus OBJECT-TYPE
            SYNTAX RowStatus
            MAX-ACCESS read-create
            STATUS current
            DESCRIPTION
                "RowStatus. Three actions are used: active,
                createAndGo, destroy"
            ::= { hwCBQoSBehaviorCfgInfoEntry 3 }

-- CAR
        hwCBQoSCarCfgInfoTable OBJECT-TYPE
            SYNTAX SEQUENCE OF HwCBQoSCarCfgInfoEntry
            MAX-ACCESS not-accessible
            STATUS current
            DESCRIPTION
                "A table of CAR feature configuration information."
            ::= { hwCBQoSBehaviorObjects 3 }

        hwCBQoSCarCfgInfoEntry OBJECT-TYPE
            SYNTAX HwCBQoSCarCfgInfoEntry
            MAX-ACCESS not-accessible
            STATUS current
            DESCRIPTION
                "CAR Configuration Information Entry."
            INDEX { hwCBQoSBehaviorIndex }
            ::= { hwCBQoSCarCfgInfoTable 1 }

        HwCBQoSCarCfgInfoEntry ::=
            SEQUENCE {
                hwCBQoSCarCir
                    Integer32,
                hwCBQoSCarCbs
                    Integer32,
                hwCBQoSCarEbs
                    Integer32,
                hwCBQoSCarPir
                    Integer32,
                hwCBQoSCarPbs
                    Integer32,
                hwCBQoSCarGreenAction
                    CarAction,
                hwCBQoSCarGreenRemarkValue
                    Integer32,
                hwCBQoSCarYellowAction
                    INTEGER,
                hwCBQoSCarRedAction
                    CarAction,
                hwCBQoSCarRedRemarkValue
                    Integer32,
                hwCBQoSCarRowStatus
                    RowStatus
            }

        hwCBQoSCarCir OBJECT-TYPE
            SYNTAX Integer32 (8..10000000)
            MAX-ACCESS read-create
            STATUS current
            DESCRIPTION
                "Committed Information Rate. Unit: kbps.
                software QoS: 8..155000
                hardware QoS: 100..10000000"
            ::= { hwCBQoSCarCfgInfoEntry 1 }

        hwCBQoSCarCbs OBJECT-TYPE
            SYNTAX Integer32 (64..19375000)
            MAX-ACCESS read-create
            STATUS current
            DESCRIPTION
                "Committed Burst Size. Unit: byte
                 software QoS: 1875..19375000 (default:max(cir*125/2,1875))
                 hardware QoS: 64..131071(default:12288)"
            ::= { hwCBQoSCarCfgInfoEntry 2 }

        hwCBQoSCarEbs OBJECT-TYPE
            SYNTAX Integer32(-1|0..19375000)
            MAX-ACCESS read-create
            STATUS current
            DESCRIPTION
                "Excess Burst Size. Unit: byte. 0..19375000
                Only software QoS support this node.
                -1 is returned only when getting value from hardware QoS.
                -1 can't be set."
            DEFVAL {0}
            ::= { hwCBQoSCarCfgInfoEntry 3 }

        hwCBQoSCarPir OBJECT-TYPE
            SYNTAX Integer32 (-1|100..10000000)
            MAX-ACCESS read-create
            STATUS current
            DESCRIPTION
                "Peak Information Rate. Unit: kbps. 100..10000000
                Only hardware QoS support this node.
                -1 is returned only when getting value from software QoS.
                -1 can't be set."
            ::= { hwCBQoSCarCfgInfoEntry 4 }

        hwCBQoSCarPbs OBJECT-TYPE
            SYNTAX Integer32 (-1|64..4000000)
            MAX-ACCESS read-create
            STATUS current
            DESCRIPTION
                "Peak Burst Size. Unit: byte.
                64..4000000.(default:cbs when Peak Information Rate configured)
                Only hardware QoS support this node.
                -1 is returned only when getting value from software QoS.
                -1 can't be set."
            ::= { hwCBQoSCarCfgInfoEntry 5 }

        hwCBQoSCarGreenAction OBJECT-TYPE
            SYNTAX CarAction
            MAX-ACCESS read-create
            STATUS current
            DESCRIPTION
                "Green Action:
                pass (1)
                discard (2)
                remark IP Precedence (3)
                remark DSCP (4)
                remark MPLS EXP (5)
                remark (6)
                Hardware QoS : pass, discard, remark.
                Software QoS : pass, discard, remark IP Precedence, remark DSCP,
                               remark MPLS EXP.
                "
            DEFVAL {pass}
            ::= { hwCBQoSCarCfgInfoEntry 6 }

        hwCBQoSCarGreenRemarkValue OBJECT-TYPE
            SYNTAX Integer32 (-1|0..63)
            MAX-ACCESS read-create
            STATUS current
            DESCRIPTION
                "The value is to remark When green action is remarking.
                For remarking DSCP, the range is 0~63;
                For remarking IP Precedence and MPLS EXP, the range is 0~7;
                Only software QoS support this node.
                -1 is returned only when getting value from hardware QoS or
                when action being pass, discard of software QoS.
                -1 can't be set."
            ::= { hwCBQoSCarCfgInfoEntry 7 }

        hwCBQoSCarYellowAction OBJECT-TYPE
            SYNTAX INTEGER {
                unavailable(-1),
                pass (1),
                discard (2),
                remarkIpPrec (3),
                remarkDscp(4),
                remarkMplsExp(5),
                remark(6)
            }
            MAX-ACCESS read-create
            STATUS current
            DESCRIPTION
                "Yellow Action:
                unavailable(-1)
                pass (1)
                discard (2)
                remark IP Precedence (3)
                remark DSCP (4)
                remark MPLS EXP (5)
                remark(6)
                Only hardware QoS support this node. Hardware QoS support pass,
                discard, remark.
                -1 is returned only when getting value from software QoS.
                -1 can't be set."
            DEFVAL {remark}
            ::= { hwCBQoSCarCfgInfoEntry 8 }

        hwCBQoSCarRedAction OBJECT-TYPE
            SYNTAX CarAction
            MAX-ACCESS read-create
            STATUS current
            DESCRIPTION
                "Red Action:
                pass (1)
                discard (2)
                remark IP Precedence (3)
                remark DSCP (4)
                remark MPLS EXP (5)
                remark (6)
                Hardware QoS : pass, discard, remark.
                Software QoS : pass, discard, remark IP Precedence, remark DSCP,
                               remark MPLS EXP.
                "
            DEFVAL {discard}
            ::= { hwCBQoSCarCfgInfoEntry 9 }

        hwCBQoSCarRedRemarkValue OBJECT-TYPE
            SYNTAX Integer32 (-1|0..63)
            MAX-ACCESS read-create
            STATUS current
            DESCRIPTION
                "The value is to remark When red action is remarking.
                For remarking DSCP, the range is 0~63;
                For remarking IP Precedence and MPLS EXP, the range is 0~7;
                Only software QoS support this node.
                -1 is returned only when getting value from hardware QoS or
                when action being pass, discard of software QoS.
                -1 can't be set."
            ::= { hwCBQoSCarCfgInfoEntry 10 }

        hwCBQoSCarRowStatus OBJECT-TYPE
            SYNTAX RowStatus
            MAX-ACCESS read-create
            STATUS current
            DESCRIPTION
                "RowStatus. Three actions are used: active,
                createAndGo, destroy"
            ::= { hwCBQoSCarCfgInfoEntry 11 }

-- GTS
        hwCBQoSGtsCfgInfoTable OBJECT-TYPE
            SYNTAX SEQUENCE OF HwCBQoSGtsCfgInfoEntry
            MAX-ACCESS not-accessible
            STATUS current
            DESCRIPTION
                "A table of GTS feature configuration information."
            ::= { hwCBQoSBehaviorObjects 4 }

        hwCBQoSGtsCfgInfoEntry OBJECT-TYPE
            SYNTAX HwCBQoSGtsCfgInfoEntry
            MAX-ACCESS not-accessible
            STATUS current
            DESCRIPTION
                "GTS Configuration Information Entry."
            INDEX { hwCBQoSBehaviorIndex }
            ::= { hwCBQoSGtsCfgInfoTable 1 }

        HwCBQoSGtsCfgInfoEntry ::=
            SEQUENCE {
                hwCBQoSGtsCir
                    Integer32,
                hwCBQoSGtsCbs
                    Integer32,
                hwCBQoSGtsEbs
                    Integer32,
                hwCBQoSGtsQueueLength
                    Integer32,
                hwCBQoSGtsRowStatus
                    RowStatus
            }

        hwCBQoSGtsCir OBJECT-TYPE
            SYNTAX Integer32 (8000..155000000)
            MAX-ACCESS read-create
            STATUS current
            DESCRIPTION
                "Committed Information Rate. Unit: bps"
            ::= { hwCBQoSGtsCfgInfoEntry 1 }

        hwCBQoSGtsCbs OBJECT-TYPE
            SYNTAX Integer32 (15000..155000000)
            MAX-ACCESS read-create
            STATUS current
            DESCRIPTION
                "Committed Burst Size. Unit: bit
                 default: max(cir*1/2,15000)"
            ::= { hwCBQoSGtsCfgInfoEntry 2 }

        hwCBQoSGtsEbs OBJECT-TYPE
            SYNTAX Integer32 (0..155000000)
            MAX-ACCESS read-create
            STATUS current
            DESCRIPTION
                "Excess Burst Size. Unit: bit"
            DEFVAL {0}
            ::= { hwCBQoSGtsCfgInfoEntry 3 }

        hwCBQoSGtsQueueLength OBJECT-TYPE
            SYNTAX Integer32 (1..1024)
            MAX-ACCESS read-create
            STATUS current
            DESCRIPTION
                "The length of GTS buffer."
            DEFVAL {50}
            ::= { hwCBQoSGtsCfgInfoEntry 4 }

        hwCBQoSGtsRowStatus OBJECT-TYPE
            SYNTAX RowStatus
            MAX-ACCESS read-create
            STATUS current
            DESCRIPTION
                "RowStatus. Three actions are used: active,
                createAndGo, destroy"
            ::= { hwCBQoSGtsCfgInfoEntry 5 }

-- REMARK
        hwCBQoSRemarkCfgInfoTable OBJECT-TYPE
            SYNTAX SEQUENCE OF HwCBQoSRemarkCfgInfoEntry
            MAX-ACCESS not-accessible
            STATUS current
            DESCRIPTION
                "A table of Remarking feature configuration information."
            ::= { hwCBQoSBehaviorObjects 5 }

        hwCBQoSRemarkCfgInfoEntry OBJECT-TYPE
            SYNTAX HwCBQoSRemarkCfgInfoEntry
            MAX-ACCESS not-accessible
            STATUS current
            DESCRIPTION
                "Remarking Configuration Information Entry."
            INDEX { hwCBQoSBehaviorIndex, hwCBQoSRemarkType }
            ::= { hwCBQoSRemarkCfgInfoTable 1 }


        HwCBQoSRemarkCfgInfoEntry ::=
            SEQUENCE {
                hwCBQoSRemarkType
                    RemarkType,
                hwCBQoSRemarkValue
                    Integer32,
                hwCBQoSRemarkRowStatus
                    RowStatus
            }

        hwCBQoSRemarkType OBJECT-TYPE
            SYNTAX RemarkType
            MAX-ACCESS not-accessible
            STATUS current
            DESCRIPTION
                "IpPrec(1)
                Dscp(2)
                MplsExp(3)
                Vlan8021p(4)
                AtmClp(5)
                FrDe(6)
                Hardware QoS support IpPrec, Dscp,MplsExp, Vlan8021p.
                Software QoS support each type.
                "
            ::= { hwCBQoSRemarkCfgInfoEntry 1 }

        hwCBQoSRemarkValue OBJECT-TYPE
            SYNTAX Integer32 (0..63)
            MAX-ACCESS read-create
            STATUS current
            DESCRIPTION
                "Value to remark:
                for IpPrec: 0~7;
                for Dscp: 0~63;
                for Vlan8021p: 0~7;
                for AtmClp: 0~1;
                for FrDe: 0~1;
                for MplsExp: 0~7"
            ::= { hwCBQoSRemarkCfgInfoEntry 2 }

        hwCBQoSRemarkRowStatus OBJECT-TYPE
            SYNTAX RowStatus
            MAX-ACCESS read-create
            STATUS current
            DESCRIPTION
                "RowStatus. Three actions are used: active,
                createAndGo, destroy"
            ::= { hwCBQoSRemarkCfgInfoEntry 3 }

-- Queue
        hwCBQoSQueueCfgInfoTable OBJECT-TYPE
            SYNTAX SEQUENCE OF HwCBQoSQueueCfgInfoEntry
            MAX-ACCESS not-accessible
            STATUS current
            DESCRIPTION
                "A table of queueing feature configuration information."
            ::= { hwCBQoSBehaviorObjects 6 }

        hwCBQoSQueueCfgInfoEntry OBJECT-TYPE
            SYNTAX HwCBQoSQueueCfgInfoEntry
            MAX-ACCESS not-accessible
            STATUS current
            DESCRIPTION
                "Queue Configuration Information Entry."
            INDEX { hwCBQoSBehaviorIndex }
            ::= { hwCBQoSQueueCfgInfoTable 1 }

        HwCBQoSQueueCfgInfoEntry ::=
            SEQUENCE {
                hwCBQoSQueueType
                    QueueType,
                hwCBQoSQueueDropType
                    INTEGER,
                hwCBQoSQueueLength
                    Integer32,
                hwCBQoSQueueBandwidthUnit
                    QueueBandwidthUnit,
                hwCBQoSQueueBandwidthValue
                    Integer32,
                hwCBQoSQueueCbs
                    Integer32,
                hwCBQoSQueueQueueNumber
                    INTEGER,
                hwCBQoSQueueRowStatus
                    RowStatus,
                hwCBQoSQueueCbsRatio
                    Integer32
            }

        hwCBQoSQueueType OBJECT-TYPE
            SYNTAX QueueType
            MAX-ACCESS read-create
            STATUS current
            DESCRIPTION
                "Queueing Type:
                EF: (1)
                AF: (2)
                WFQ: (3)"
            ::= { hwCBQoSQueueCfgInfoEntry 1 }

        hwCBQoSQueueDropType OBJECT-TYPE
            SYNTAX INTEGER {
                    typeUnavailable(-1),
                    typeTailDrop(1),
                    typeWred(2)
                }
            MAX-ACCESS read-create
            STATUS current
            DESCRIPTION
                "The drop type of queue. Only valid for AF and WFQ queue.
                -1 is returned only when getting value about EF queue.
                -1 can't be set."
            DEFVAL {typeTailDrop}
            ::= { hwCBQoSQueueCfgInfoEntry 2 }

        hwCBQoSQueueLength OBJECT-TYPE
            SYNTAX Integer32 (-1|1..512)
            MAX-ACCESS read-create
            STATUS current
            DESCRIPTION
                "The length of QueueLength. Only valid for tail-drop type
                of AF and WFQ queue.
                -1 is returned only when getting value about EF queue or
                wred type of AF and WFQ queue.
                -1 can't be set."
            DEFVAL {64}
            ::= { hwCBQoSQueueCfgInfoEntry 3 }

        hwCBQoSQueueBandwidthUnit OBJECT-TYPE
            SYNTAX QueueBandwidthUnit
            MAX-ACCESS read-create
            STATUS current
            DESCRIPTION
                "Bandwidth Unit:
                Absolute, Unit Kbps (1)
                Percent, Unit % (2)
                Remaining percent, Unit % (3)
                Absolute unit and percent unit are valid for EF and AF queue,
                but remaining percent unit is only valid for AF queue.
                -1 is returned only when getting value about WFQ queue.
                -1 can't be set."
            ::= { hwCBQoSQueueCfgInfoEntry 4 }

        hwCBQoSQueueBandwidthValue OBJECT-TYPE
            SYNTAX Integer32 (-1|1..1000000)
            MAX-ACCESS read-create
            STATUS current
            DESCRIPTION
                "Bandwidth value:
                Absolute value: 8~1000000. Unit: Kbps
                Percent value: 1~100.
                Remaining percent value: 1~100.
                Absolute value and percent value are valid for EF and AF queue,
                but remaining percent value is only valid for AF queue.
                -1 is returned only when getting value about WFQ queue.
                -1 can't be set."
            ::= { hwCBQoSQueueCfgInfoEntry 5 }

        hwCBQoSQueueCbs OBJECT-TYPE
            SYNTAX Integer32 (-1|32..2000000)
            MAX-ACCESS read-create
            STATUS current
            DESCRIPTION
                "Committed Burst Size. Unit: byte.
                 Only valid for EF queue.
                 Default:min( Bandwidth*25 , 2000000)
                 -1 is returned only when getting value about AF or WFQ queue.
                 -1 can't be set."
            ::= { hwCBQoSQueueCfgInfoEntry 6 }

        hwCBQoSQueueQueueNumber OBJECT-TYPE
            SYNTAX INTEGER {
                    unavailable(-1),
                    a16(16),
                    a32(32),
                    a64(64),
                    a128(128),
                    a256(256),
                    a512(512),
                    a1024(1024),
                    a2048(2048),
                    a4096(4096)
                }
            MAX-ACCESS read-create
            STATUS current
            DESCRIPTION
                "Max number of hashed queues (a power of 2).
                Only valid for WFQ.
                -1 is returned only when getting value about AF or EF queue.
                -1 can't be set."
            DEFVAL {a256}
            ::= { hwCBQoSQueueCfgInfoEntry 7 }

        hwCBQoSQueueRowStatus OBJECT-TYPE
            SYNTAX RowStatus
            MAX-ACCESS read-create
            STATUS current
            DESCRIPTION
                "RowStatus. Three actions are used: active,
                createAndGo, destroy"
            ::= { hwCBQoSQueueCfgInfoEntry 8 }

        hwCBQoSQueueCbsRatio OBJECT-TYPE
            SYNTAX           Integer32(-1|25..500)
            MAX-ACCESS       read-create
            STATUS           current
            DESCRIPTION
                "Committed Burst Size Ratio. Unit: byte.
                CBS = CBS_Ratio * Bandwidth(kbps)
                Only valid for EF queue.
                -1 is returned only when getting value about AF or WFQ queue.
                -1 can't be set."
            DEFVAL  { 25 }
            ::= { hwCBQoSQueueCfgInfoEntry 9 }

-- WRED
        hwCBQoSWredCfgInfoTable OBJECT-TYPE
            SYNTAX SEQUENCE OF HwCBQoSWredCfgInfoEntry
            MAX-ACCESS not-accessible
            STATUS current
            DESCRIPTION
                "A table of WRED configuration information."
            ::= { hwCBQoSBehaviorObjects 7 }

        hwCBQoSWredCfgInfoEntry OBJECT-TYPE
            SYNTAX HwCBQoSWredCfgInfoEntry
            MAX-ACCESS not-accessible
            STATUS current
            DESCRIPTION
                "WRED Configuration Information Entry."
            INDEX { hwCBQoSBehaviorIndex }
            ::= { hwCBQoSWredCfgInfoTable 1 }

        HwCBQoSWredCfgInfoEntry ::=
            SEQUENCE {
                hwCBQoSWredType
                    WredType,
                hwCBQoSWredWeightConst
                    Integer32
            }

        hwCBQoSWredType OBJECT-TYPE
            SYNTAX WredType
            MAX-ACCESS read-write
            STATUS current
            DESCRIPTION
                "IP-Prec Based (1)
                 DSCP Based (2)"
            DEFVAL {typeIpPrecbased}
            ::= { hwCBQoSWredCfgInfoEntry 1 }

        hwCBQoSWredWeightConst OBJECT-TYPE
            SYNTAX Integer32 (1..16)
            MAX-ACCESS read-write
            STATUS current
            DESCRIPTION
                "Specify weight for calculating mean queue depth."
            DEFVAL {9}
            ::= { hwCBQoSWredCfgInfoEntry 2 }

-- WRED Class
        hwCBQoSWredClassCfgInfoTable OBJECT-TYPE
            SYNTAX SEQUENCE OF HwCBQoSWredClassCfgInfoEntry
            MAX-ACCESS not-accessible
            STATUS current
            DESCRIPTION
                "A table of WRED configuration information."
            ::= { hwCBQoSBehaviorObjects 8 }

        hwCBQoSWredClassCfgInfoEntry OBJECT-TYPE
            SYNTAX HwCBQoSWredClassCfgInfoEntry
            MAX-ACCESS not-accessible
            STATUS current
            DESCRIPTION
                "WRED Class Configuration Information Entry."
            INDEX { hwCBQoSBehaviorIndex, hwCBQoSWredClassValue }
            ::= { hwCBQoSWredClassCfgInfoTable 1 }


        HwCBQoSWredClassCfgInfoEntry ::=
            SEQUENCE {
                hwCBQoSWredClassValue
                    Integer32,
                hwCBQoSWredClassLowLimit
                    Integer32,
                hwCBQoSWredClassHighLimit
                    Integer32,
                hwCBQoSWredClassDiscardProb
                    Integer32
            }

        hwCBQoSWredClassValue OBJECT-TYPE
            SYNTAX Integer32 (0..63)
            MAX-ACCESS not-accessible
            STATUS current
            DESCRIPTION
                "The class value.
                For IP precedence based WRED, the class is IP precedence,
                and range is 0~7.
                For DSCP based WRED, the class is DSCP, and range is 0~63."
            ::= { hwCBQoSWredClassCfgInfoEntry 1 }

        hwCBQoSWredClassLowLimit OBJECT-TYPE
            SYNTAX Integer32 (1..1024)
            MAX-ACCESS read-write
            STATUS current
            DESCRIPTION
                "The low limit of queue depth."
            DEFVAL {10}
            ::= { hwCBQoSWredClassCfgInfoEntry 2 }

        hwCBQoSWredClassHighLimit OBJECT-TYPE
            SYNTAX Integer32 (1..1024)
            MAX-ACCESS read-write
            STATUS current
            DESCRIPTION
                "The high limit of queue depth."
            DEFVAL {30}
            ::= { hwCBQoSWredClassCfgInfoEntry 3 }

        hwCBQoSWredClassDiscardProb OBJECT-TYPE
            SYNTAX Integer32 (1..255)
            MAX-ACCESS read-write
            STATUS current
            DESCRIPTION
                "The discard probability denominator."
            DEFVAL {10}
            ::= { hwCBQoSWredClassCfgInfoEntry 4 }

-- Policy Route
        hwCBQoSPolicyRouteCfgInfoTable OBJECT-TYPE
            SYNTAX SEQUENCE OF HwCBQoSPolicyRouteCfgInfoEntry
            MAX-ACCESS not-accessible
            STATUS current
            DESCRIPTION
                "A table of Policy Routeing configuration information."
            ::= { hwCBQoSBehaviorObjects 9 }

        hwCBQoSPolicyRouteCfgInfoEntry OBJECT-TYPE
            SYNTAX HwCBQoSPolicyRouteCfgInfoEntry
            MAX-ACCESS not-accessible
            STATUS current
            DESCRIPTION
                "Policy Routeing Configuration Information Entry."
            INDEX { hwCBQoSBehaviorIndex }
            ::= { hwCBQoSPolicyRouteCfgInfoTable 1 }

        HwCBQoSPolicyRouteCfgInfoEntry ::=
            SEQUENCE {
                hwCBQoSPolicyRouteNexthop
                    IpAddress,
                hwCBQoSPolicyRouteBackup
                    INTEGER,
                hwCBQoSPolicyRouteRowStatus
                    RowStatus
            }

        hwCBQoSPolicyRouteNexthop OBJECT-TYPE
            SYNTAX IpAddress
            MAX-ACCESS read-create
            STATUS current
            DESCRIPTION
                "The next-hop ip address for redirection"
            ::= { hwCBQoSPolicyRouteCfgInfoEntry 1 }

        hwCBQoSPolicyRouteBackup OBJECT-TYPE
            SYNTAX INTEGER {
                    backup(1),
                    notbackup(2)
                }
            MAX-ACCESS read-create
            STATUS current
            DESCRIPTION
                "Whether forward the packet according to the routing table
                When the next-hop ip address for redirection is not valid.
                Backup means forwarding. NoBackup means not forwarding"
            ::= { hwCBQoSPolicyRouteCfgInfoEntry 2 }

        hwCBQoSPolicyRouteRowStatus OBJECT-TYPE
            SYNTAX RowStatus
            MAX-ACCESS read-create
            STATUS current
            DESCRIPTION
                "RowStatus. Three actions are used: active,
                createAndGo, destroy"
            ::= { hwCBQoSPolicyRouteCfgInfoEntry 3 }

-- NAT
        hwCBQoSNatCfgInfoTable OBJECT-TYPE
            SYNTAX SEQUENCE OF HwCBQoSNatCfgInfoEntry
            MAX-ACCESS not-accessible
            STATUS current
            DESCRIPTION
                "A table of Nat configuration information."
            ::= { hwCBQoSBehaviorObjects 10 }

        hwCBQoSNatCfgInfoEntry OBJECT-TYPE
            SYNTAX HwCBQoSNatCfgInfoEntry
            MAX-ACCESS not-accessible
            STATUS current
            DESCRIPTION
                "Nat Configuration Information Entry."
            INDEX { hwCBQoSBehaviorIndex }
            ::= { hwCBQoSNatCfgInfoTable 1 }

        HwCBQoSNatCfgInfoEntry ::=
            SEQUENCE {
                hwCBQoSNatMainNumber
                    Integer32,
                hwCBQoSNatBackupNumber
                    Integer32,
                hwCBQoSNatServiceClass
                    Integer32,
                hwCBQoSNatRowStatus
                    RowStatus
            }

        hwCBQoSNatMainNumber OBJECT-TYPE
            SYNTAX Integer32 (1..255)
            MAX-ACCESS read-create
            STATUS current
            DESCRIPTION
                "The main ISP number"
            ::= { hwCBQoSNatCfgInfoEntry 1 }

        hwCBQoSNatBackupNumber OBJECT-TYPE
            SYNTAX Integer32 (1..255)
            MAX-ACCESS read-create
            STATUS current
            DESCRIPTION
                "The backup ISP number"
            ::= { hwCBQoSNatCfgInfoEntry 2 }

        hwCBQoSNatServiceClass OBJECT-TYPE
            SYNTAX Integer32 (1..4)
            MAX-ACCESS read-create
            STATUS current
            DESCRIPTION
                "The service class. DEFVAL: 2"
            DEFVAL {2}
            ::= { hwCBQoSNatCfgInfoEntry 3 }

        hwCBQoSNatRowStatus OBJECT-TYPE
            SYNTAX RowStatus
            MAX-ACCESS read-create
            STATUS current
            DESCRIPTION
                "RowStatus. Three actions are used: active,
                createAndGo, destroy"
            ::= { hwCBQoSNatCfgInfoEntry 4 }

-- Firewall
        hwCBQoSFirewallCfgInfoTable OBJECT-TYPE
            SYNTAX SEQUENCE OF HwCBQoSFirewallCfgInfoEntry
            MAX-ACCESS not-accessible
            STATUS current
            DESCRIPTION
                "A table of Firewall configuration information."
            ::= { hwCBQoSBehaviorObjects 11 }

        hwCBQoSFirewallCfgInfoEntry OBJECT-TYPE
            SYNTAX HwCBQoSFirewallCfgInfoEntry
            MAX-ACCESS not-accessible
            STATUS current
            DESCRIPTION
                "Firewall Configuration Information Entry."
            INDEX { hwCBQoSBehaviorIndex }
            ::= { hwCBQoSFirewallCfgInfoTable 1 }

        HwCBQoSFirewallCfgInfoEntry ::=
            SEQUENCE {
                hwCBQoSFirewallAction
                    INTEGER,
                hwCBQoSFirewallRowStatus
                    RowStatus
            }

        hwCBQoSFirewallAction OBJECT-TYPE
            SYNTAX INTEGER {
                    permit(1),
                    deny(2)
                }
            MAX-ACCESS read-create
            STATUS current
            DESCRIPTION
                "The firewall action "
            DEFVAL {permit}
            ::= { hwCBQoSFirewallCfgInfoEntry 1 }

        hwCBQoSFirewallRowStatus OBJECT-TYPE
            SYNTAX RowStatus
            MAX-ACCESS read-create
            STATUS current
            DESCRIPTION
                "RowStatus. Three actions are used: active,
                createAndGo, destroy"
            ::= { hwCBQoSFirewallCfgInfoEntry 2 }

-- Sampling behavior
        hwCBQoSSamplingCfgInfoTable OBJECT-TYPE
            SYNTAX SEQUENCE OF HwCBQoSSamplingCfgInfoEntry
            MAX-ACCESS not-accessible
            STATUS current
            DESCRIPTION
                "A table of Sampling configuration information."
            ::= { hwCBQoSBehaviorObjects 12 }

        hwCBQoSSamplingCfgInfoEntry OBJECT-TYPE
            SYNTAX HwCBQoSSamplingCfgInfoEntry
            MAX-ACCESS not-accessible
            STATUS current
            DESCRIPTION
                "Sampling Configuration Information Entry."
            INDEX { hwCBQoSBehaviorIndex }
            ::= { hwCBQoSSamplingCfgInfoTable 1 }

        HwCBQoSSamplingCfgInfoEntry ::=
            SEQUENCE {
                hwCBQoSSamplingNum
                    Integer32,
                hwCBQoSSamplingRowStatus
                    RowStatus
            }

        hwCBQoSSamplingNum OBJECT-TYPE
            SYNTAX Integer32 (1..16)
            MAX-ACCESS read-create
            STATUS current
            DESCRIPTION
                "The sampling number"
            ::= { hwCBQoSSamplingCfgInfoEntry 1 }

        hwCBQoSSamplingRowStatus OBJECT-TYPE
            SYNTAX RowStatus
            MAX-ACCESS read-create
            STATUS current
            DESCRIPTION
                "RowStatus. Three actions are used: active,
                createAndGo, destroy"
            ::= { hwCBQoSSamplingCfgInfoEntry 2 }

--  LR
        hwCBQoSLrCfgInfoTable OBJECT-TYPE
            SYNTAX SEQUENCE OF HwCBQoSLrCfgInfoEntry
            MAX-ACCESS not-accessible
            STATUS current
            DESCRIPTION
                "A table of Line Rate configuration information."
            ::= { hwCBQoSBehaviorObjects 13 }


        hwCBQoSLrCfgInfoEntry OBJECT-TYPE
            SYNTAX HwCBQoSLrCfgInfoEntry
            MAX-ACCESS not-accessible
            STATUS current
            DESCRIPTION
                "LR Configuration Information Entry."
            INDEX { hwCBQoSBehaviorIndex }
            ::= { hwCBQoSLrCfgInfoTable 1 }


        HwCBQoSLrCfgInfoEntry ::=
            SEQUENCE {
                hwCBQoSLrUnit
                    LrCirUnit,
                hwCBQoSLrCir
                    Integer32,
                hwCBQoSLrCbs
                    Integer32,
                hwCBQoSLrEbs
                    Integer32,
                hwCBQoSLrRowStatus
                    RowStatus
             }

        hwCBQoSLrUnit OBJECT-TYPE
            SYNTAX LrCirUnit
            MAX-ACCESS read-create
            STATUS current
            DESCRIPTION
                "CIR Unit:
                Absolute, Unit bps (1)
                Percent, Unit % (2)"
            ::= { hwCBQoSLrCfgInfoEntry 1 }


        hwCBQoSLrCir OBJECT-TYPE
            SYNTAX Integer32 (1..1000000000)
            MAX-ACCESS read-create
            STATUS current
            DESCRIPTION
                "Committed Information Rate.
                Absolute value: 8000..1000000000. Unit: bps
                Percent value: 1~100."
            ::= { hwCBQoSLrCfgInfoEntry 2 }


        hwCBQoSLrCbs OBJECT-TYPE
            SYNTAX Integer32 (50..1000000000)
            MAX-ACCESS read-create
            STATUS current
            DESCRIPTION
                "Committed Burst Size.
                When CIR is absolute value,
                CBS value: 15000..1000000000,
                default value: max(cir*1/2,15000),
                Unit: bit;
                When CIR is percent value,
                CBS value: 50..2000,
                default value: 500,
                Unit: ms.
                "
            ::= { hwCBQoSLrCfgInfoEntry 3 }


        hwCBQoSLrEbs OBJECT-TYPE
            SYNTAX Integer32 (0..1000000000)
            MAX-ACCESS read-create
            STATUS current
            DESCRIPTION
                "Excess Burst Size.
                When CIR is absolute value,
                EBS value: 0..1000000000, Unit: bit;
                When CIR is percent value,
                EBS value: 0..2000, Unit: ms."
            DEFVAL { 0 }
            ::= { hwCBQoSLrCfgInfoEntry 4 }


        hwCBQoSLrRowStatus OBJECT-TYPE
            SYNTAX RowStatus
            MAX-ACCESS read-create
            STATUS current
            DESCRIPTION
                "RowStatus. Three actions are used: active,
                createAndGo, destroy"
            ::= { hwCBQoSLrCfgInfoEntry 5 }


--  Hierachical Policy
        hwCBQoSNestPolicyCfgInfoTable OBJECT-TYPE
            SYNTAX SEQUENCE OF HwCBQoSNestPolicyCfgInfoEntry
            MAX-ACCESS not-accessible
            STATUS current
            DESCRIPTION
                "A table of Hierachical Policy configuration information."
            ::= { hwCBQoSBehaviorObjects 14 }


        hwCBQoSNestPolicyCfgInfoEntry OBJECT-TYPE
            SYNTAX HwCBQoSNestPolicyCfgInfoEntry
            MAX-ACCESS not-accessible
            STATUS current
            DESCRIPTION
                "Hierachical Policy Configuration Information Entry."
            INDEX { hwCBQoSBehaviorIndex }
            ::= { hwCBQoSNestPolicyCfgInfoTable 1 }


        HwCBQoSNestPolicyCfgInfoEntry ::=
            SEQUENCE {
                hwCBQoSNestPolicyName
                    OCTET STRING,
                hwCBQoSNestPolicyRowStatus
                    RowStatus
             }

        hwCBQoSNestPolicyName OBJECT-TYPE
            SYNTAX OCTET STRING (SIZE (1..31))
            MAX-ACCESS read-create
            STATUS current
            DESCRIPTION
                "Name of hierachical traffic policy."
            ::= { hwCBQoSNestPolicyCfgInfoEntry 1 }


        hwCBQoSNestPolicyRowStatus OBJECT-TYPE
            SYNTAX RowStatus
            MAX-ACCESS read-create
            STATUS current
            DESCRIPTION
                "RowStatus. Three actions are used: active,
                createAndGo, destroy"
            ::= { hwCBQoSNestPolicyCfgInfoEntry 2 }



--hwCBQoSPolicyObjects

hwCBQoSPolicyObjects OBJECT IDENTIFIER ::= { hwCBQoSObjects 3 }

-- Traffic Policy Next Index
        hwCBQoSPolicyIndexNext OBJECT-TYPE
            SYNTAX Integer32
            MAX-ACCESS read-only
            STATUS current
            DESCRIPTION
                "This object contains an appropriate value to be used
                for hwCBQoSPolicyIndex when creating rows in the
                hwCBQoSPolicyCfgInfoTable. Begin with 0."
            ::= { hwCBQoSPolicyObjects 1 }

-- Traffic Policy
        hwCBQoSPolicyCfgInfoTable OBJECT-TYPE
            SYNTAX SEQUENCE OF HwCBQoSPolicyCfgInfoEntry
            MAX-ACCESS not-accessible
            STATUS current
            DESCRIPTION
                "A table of QoS policy configuration information."
            ::= { hwCBQoSPolicyObjects 2 }

        hwCBQoSPolicyCfgInfoEntry OBJECT-TYPE
            SYNTAX HwCBQoSPolicyCfgInfoEntry
            MAX-ACCESS not-accessible
            STATUS current
            DESCRIPTION
                "Traffic Policy Configuration Information Entry."
            INDEX { hwCBQoSPolicyIndex }
            ::= { hwCBQoSPolicyCfgInfoTable 1 }

        HwCBQoSPolicyCfgInfoEntry ::=
            SEQUENCE {
                hwCBQoSPolicyIndex
                    Integer32,
                hwCBQoSPolicyName
                    OCTET STRING,
                hwCBQoSPolicyClassCount
                    Integer32,
                hwCBQoSPolicyConfigMode
                    INTEGER,
                hwCBQoSPolicyRowStatus
                    RowStatus
            }

        hwCBQoSPolicyIndex OBJECT-TYPE
            SYNTAX Integer32
            MAX-ACCESS not-accessible
            STATUS current
            DESCRIPTION
                "Index of Traffic Policy."
            ::= { hwCBQoSPolicyCfgInfoEntry 1 }

        hwCBQoSPolicyName OBJECT-TYPE
            SYNTAX OCTET STRING (SIZE (1..31))
            MAX-ACCESS read-create
            STATUS current
            DESCRIPTION
                "Name of Traffic Policy."
            ::= { hwCBQoSPolicyCfgInfoEntry 2 }

        hwCBQoSPolicyClassCount OBJECT-TYPE
            SYNTAX Integer32
            MAX-ACCESS read-only
            STATUS current
            DESCRIPTION
                "The count of policy classes of policy. It can be used
                for hwCBQoSPolicyClassIndex when creating rows in the
                hwCBQoSPolicyClassCfgInfoTable. Begin with 0."
            ::= { hwCBQoSPolicyCfgInfoEntry 3 }

        hwCBQoSPolicyConfigMode OBJECT-TYPE
            SYNTAX INTEGER {
                    unavailable(-1),
                    config(1),
                    auto(2)
                }
            MAX-ACCESS read-create
            STATUS current
            DESCRIPTION
                "Configuration mode of Traffic Policy.
                Only hardware QoS support this node.
                -1 is returned only when getting value from software QoS.
                -1 can't be set."
            DEFVAL {config}
            ::= { hwCBQoSPolicyCfgInfoEntry 4 }

        hwCBQoSPolicyRowStatus OBJECT-TYPE
            SYNTAX RowStatus
            MAX-ACCESS read-create
            STATUS current
            DESCRIPTION
                "RowStatus. Three actions are used: active,
                createAndGo, destroy"
            ::= { hwCBQoSPolicyCfgInfoEntry 5 }

-- Classifier-Behavior in QoS policy
        hwCBQoSPolicyClassCfgInfoTable OBJECT-TYPE
            SYNTAX SEQUENCE OF HwCBQoSPolicyClassCfgInfoEntry
            MAX-ACCESS not-accessible
            STATUS current
            DESCRIPTION
                "A table of QoS Policy classifier-behavior configuration information."
            ::= { hwCBQoSPolicyObjects 3 }

        hwCBQoSPolicyClassCfgInfoEntry OBJECT-TYPE
            SYNTAX HwCBQoSPolicyClassCfgInfoEntry
            MAX-ACCESS not-accessible
            STATUS current
            DESCRIPTION
                "Traffic Policy classifier-behavior Configuration Information Entry."
            INDEX { hwCBQoSPolicyIndex, hwCBQoSPolicyClassIndex }
            ::= { hwCBQoSPolicyClassCfgInfoTable 1 }

        HwCBQoSPolicyClassCfgInfoEntry ::=
            SEQUENCE {
                hwCBQoSPolicyClassIndex
                    Integer32,
                hwCBQoSPolicyClassClassifierIndex
                    Integer32,
                hwCBQoSPolicyClassClassifierName
                    OCTET STRING,
                hwCBQoSPolicyClassBehaviorIndex
                    Integer32,
                hwCBQoSPolicyClassBehaviorName
                    OCTET STRING,
                hwCBQoSPolicyClassPrecedence
                    Integer32,
                hwCBQoSPolicyClassRowStatus
                    RowStatus
            }

        hwCBQoSPolicyClassIndex OBJECT-TYPE
            SYNTAX Integer32
            MAX-ACCESS not-accessible
            STATUS current
            DESCRIPTION
                "PolicyClass Index in a QoS policy."
            ::= { hwCBQoSPolicyClassCfgInfoEntry 1 }

        hwCBQoSPolicyClassClassifierIndex OBJECT-TYPE
            SYNTAX Integer32
            MAX-ACCESS read-create
            STATUS current
            DESCRIPTION
                "Index of classifier applied by a policy.
                It should exist in hwCBQoSClassifierCfgInfoTable."
            ::= { hwCBQoSPolicyClassCfgInfoEntry 2 }

        hwCBQoSPolicyClassClassifierName OBJECT-TYPE
            SYNTAX OCTET STRING (SIZE (1..31))
            MAX-ACCESS read-only
            STATUS current
            DESCRIPTION
                "Name of classifier applied by a policy.
                It is corresponding to hwCBQoSPolicyClassClassifierIndex."
            ::= { hwCBQoSPolicyClassCfgInfoEntry 3 }

        hwCBQoSPolicyClassBehaviorIndex OBJECT-TYPE
            SYNTAX Integer32
            MAX-ACCESS read-create
            STATUS current
            DESCRIPTION
                "Index of Behavior applied by a policy.
                It should exist in hwCBQoSBehaviorCfgInfoTable."
            ::= { hwCBQoSPolicyClassCfgInfoEntry 4 }

        hwCBQoSPolicyClassBehaviorName OBJECT-TYPE
            SYNTAX OCTET STRING (SIZE (1..31))
            MAX-ACCESS read-only
            STATUS current
            DESCRIPTION
                "Name of Behavior applied by a policy.
                It is corresponding to hwCBQoSPolicyClassBehaviorIndex."
            ::= { hwCBQoSPolicyClassCfgInfoEntry 5 }

        hwCBQoSPolicyClassPrecedence OBJECT-TYPE
            SYNTAX Integer32 (-1|0..16383)
            MAX-ACCESS read-create
            STATUS current
            DESCRIPTION
                "The Precedence of the class in the policy.
                Only hardware QoS support this node.
                -1 is returned only when getting value from software QoS.
                -1 can't be set."
            ::= { hwCBQoSPolicyClassCfgInfoEntry 6 }

        hwCBQoSPolicyClassRowStatus OBJECT-TYPE
            SYNTAX RowStatus
            MAX-ACCESS read-create
            STATUS current
            DESCRIPTION
                "RowStatus. Three actions are used: active,
                createAndGo, destroy"
            ::= { hwCBQoSPolicyClassCfgInfoEntry 7 }


--hwCBQoSApplyPolicyObjects

hwCBQoSApplyPolicyObjects OBJECT IDENTIFIER ::= { hwCBQoSObjects 4 }

-- Policy Instance on interface Table
        hwCBQoSIfApplyPolicyTable OBJECT-TYPE
            SYNTAX SEQUENCE OF HwCBQoSIfApplyPolicyEntry
            MAX-ACCESS not-accessible
            STATUS current
            DESCRIPTION
                "A table of QoS policy instance."
            ::= { hwCBQoSApplyPolicyObjects 1 }

        hwCBQoSIfApplyPolicyEntry OBJECT-TYPE
            SYNTAX HwCBQoSIfApplyPolicyEntry
            MAX-ACCESS not-accessible
            STATUS current
            DESCRIPTION
                "Policy applied on interface Configuration Information Entry."
            INDEX { hwCBQoSIfApplyPolicyIfIndex, hwCBQoSIfApplyPolicyDirection }
            ::= { hwCBQoSIfApplyPolicyTable 1 }

        HwCBQoSIfApplyPolicyEntry ::=
            SEQUENCE {
                hwCBQoSIfApplyPolicyIfIndex
                    Integer32,
                hwCBQoSIfApplyPolicyDirection
                    DirectionType,
                hwCBQoSIfApplyPolicyName
                    OCTET STRING,
                hwCBQoSIfApplyPolicyEnableDynamic
                    INTEGER,
                hwCBQoSIfApplyPolicyRowStatus
                    RowStatus
            }

        hwCBQoSIfApplyPolicyIfIndex OBJECT-TYPE
            SYNTAX Integer32
            MAX-ACCESS not-accessible
            STATUS current
            DESCRIPTION
                "Interface Index, equal to ifIndex."
            ::= { hwCBQoSIfApplyPolicyEntry 1 }

        hwCBQoSIfApplyPolicyDirection OBJECT-TYPE
            SYNTAX DirectionType
            MAX-ACCESS not-accessible
            STATUS current
            DESCRIPTION
                "Policy direction:
                inbound (1)
                outbound (2)"
            ::= { hwCBQoSIfApplyPolicyEntry 2 }

        hwCBQoSIfApplyPolicyName OBJECT-TYPE
            SYNTAX OCTET STRING (SIZE (1..31))
            MAX-ACCESS read-create
            STATUS current
            DESCRIPTION
                "Name of Traffic Policy."
            ::= { hwCBQoSIfApplyPolicyEntry 3 }

        hwCBQoSIfApplyPolicyEnableDynamic OBJECT-TYPE
            SYNTAX INTEGER
                {
                    unavailable(-1),
                    true(1),
                    false(2)
                }
            MAX-ACCESS read-create
            STATUS current
            DESCRIPTION
                "
                  If the value of it is specified 'true', enable dynamic qos policy.
                  -1(unavailable) is returned if device doesn't support dynamic QoS.
                  -1(unavailable) can't be set.
                "
            ::= { hwCBQoSIfApplyPolicyEntry 4 }

        hwCBQoSIfApplyPolicyRowStatus OBJECT-TYPE
            SYNTAX RowStatus
            MAX-ACCESS read-create
            STATUS current
            DESCRIPTION
                "RowStatus. Three actions are used: active,
                createAndGo, destroy"
            ::= { hwCBQoSIfApplyPolicyEntry 5 }

-- Policy Instance on ATM PVC Table
        hwCBQoSAtmPvcApplyPolicyTable OBJECT-TYPE
            SYNTAX SEQUENCE OF HwCBQoSAtmPvcApplyPolicyEntry
            MAX-ACCESS not-accessible
            STATUS current
            DESCRIPTION
                "A table of QoS policy instance."
            ::= { hwCBQoSApplyPolicyObjects 2 }

        hwCBQoSAtmPvcApplyPolicyEntry OBJECT-TYPE
            SYNTAX HwCBQoSAtmPvcApplyPolicyEntry
            MAX-ACCESS not-accessible
            STATUS current
            DESCRIPTION
                "Policy applied on ATM PVC Configuration Information Entry."
            INDEX { hwCBQoSAtmPvcApplyPolicyIfIndex, hwCBQoSAtmPvcApplyPolicyVPI,
                    hwCBQoSAtmPvcApplyPolicyVCI,hwCBQoSAtmPvcApplyPolicyDirection }
            ::= { hwCBQoSAtmPvcApplyPolicyTable 1 }

        HwCBQoSAtmPvcApplyPolicyEntry ::=
            SEQUENCE {
                hwCBQoSAtmPvcApplyPolicyIfIndex
                    Integer32,
                hwCBQoSAtmPvcApplyPolicyVPI
                    Integer32,
                hwCBQoSAtmPvcApplyPolicyVCI
                    Integer32,
                hwCBQoSAtmPvcApplyPolicyDirection
                    DirectionType,
                hwCBQoSAtmPvcApplyPolicyName
                    OCTET STRING,
                hwCBQoSAtmPvcApplyPolicyRowStatus
                    RowStatus
            }

        hwCBQoSAtmPvcApplyPolicyIfIndex OBJECT-TYPE
            SYNTAX Integer32
            MAX-ACCESS not-accessible
            STATUS current
            DESCRIPTION
                "ATM Interface Index, equal to ifIndex."
            ::= { hwCBQoSAtmPvcApplyPolicyEntry 1 }

        hwCBQoSAtmPvcApplyPolicyVPI OBJECT-TYPE
            SYNTAX Integer32
            MAX-ACCESS not-accessible
            STATUS current
            DESCRIPTION
                "VPI value of ATM Interface."
            ::= { hwCBQoSAtmPvcApplyPolicyEntry 2 }

        hwCBQoSAtmPvcApplyPolicyVCI OBJECT-TYPE
            SYNTAX Integer32
            MAX-ACCESS not-accessible
            STATUS current
            DESCRIPTION
                "VCI value of ATM Interface."
            ::= { hwCBQoSAtmPvcApplyPolicyEntry 3 }

        hwCBQoSAtmPvcApplyPolicyDirection OBJECT-TYPE
            SYNTAX DirectionType
            MAX-ACCESS not-accessible
            STATUS current
            DESCRIPTION
                "Policy direction:
                inbound (1)
                outbound (2)"
            ::= { hwCBQoSAtmPvcApplyPolicyEntry 4 }

        hwCBQoSAtmPvcApplyPolicyName OBJECT-TYPE
            SYNTAX OCTET STRING (SIZE (1..31))
            MAX-ACCESS read-create
            STATUS current
            DESCRIPTION
                "Name of Traffic Policy."
            ::= { hwCBQoSAtmPvcApplyPolicyEntry 5 }

        hwCBQoSAtmPvcApplyPolicyRowStatus OBJECT-TYPE
            SYNTAX RowStatus
            MAX-ACCESS read-create
            STATUS current
            DESCRIPTION
                "RowStatus. Three actions are used: active,
                createAndGo, destroy"
            ::= { hwCBQoSAtmPvcApplyPolicyEntry 6 }


-- Policy Instance on vlanid Table
        hwCBQoSIfVlanApplyPolicyTable OBJECT-TYPE
            SYNTAX SEQUENCE OF HwCBQoSIfVlanApplyPolicyEntry
            MAX-ACCESS not-accessible
            STATUS current
            DESCRIPTION
                "A table of QoS policy instance."
            ::= { hwCBQoSApplyPolicyObjects 3 }

        hwCBQoSIfVlanApplyPolicyEntry OBJECT-TYPE
            SYNTAX HwCBQoSIfVlanApplyPolicyEntry
            MAX-ACCESS not-accessible
            STATUS current
            DESCRIPTION
                "Policy applied on Ethernet Vlan Configuration Information Entry."
            INDEX { hwCBQoSIfVlanApplyPolicyIfIndex, hwCBQoSIfVlanApplyPolicyVlanid,
                     hwCBQoSIfVlanApplyPolicyDirection }
            ::= { hwCBQoSIfVlanApplyPolicyTable 1 }

        HwCBQoSIfVlanApplyPolicyEntry ::=
            SEQUENCE {
                hwCBQoSIfVlanApplyPolicyIfIndex
                    Integer32,
                hwCBQoSIfVlanApplyPolicyVlanid
                    Integer32,
                hwCBQoSIfVlanApplyPolicyDirection
                    DirectionType,
                hwCBQoSIfVlanApplyPolicyName
                    OCTET STRING,
                hwCBQoSIfVlanApplyPolicyRowStatus
                    RowStatus
            }

        hwCBQoSIfVlanApplyPolicyIfIndex OBJECT-TYPE
            SYNTAX Integer32
            MAX-ACCESS not-accessible
            STATUS current
            DESCRIPTION
                "Ethernet Interface Index, equal to ifIndex."
            ::= { hwCBQoSIfVlanApplyPolicyEntry 1 }

        hwCBQoSIfVlanApplyPolicyVlanid OBJECT-TYPE
            SYNTAX Integer32
            MAX-ACCESS not-accessible
            STATUS current
            DESCRIPTION
                "Vlan of Ethernet Interface."
            ::= { hwCBQoSIfVlanApplyPolicyEntry 2 }

        hwCBQoSIfVlanApplyPolicyDirection OBJECT-TYPE
            SYNTAX DirectionType
            MAX-ACCESS not-accessible
            STATUS current
            DESCRIPTION
                "Policy direction:
                inbound (1)
                outbound (2)"
            ::= { hwCBQoSIfVlanApplyPolicyEntry 3 }

        hwCBQoSIfVlanApplyPolicyName OBJECT-TYPE
            SYNTAX OCTET STRING (SIZE (1..31))
            MAX-ACCESS read-create
            STATUS current
            DESCRIPTION
                "Name of Traffic Policy."
            ::= { hwCBQoSIfVlanApplyPolicyEntry 4 }

        hwCBQoSIfVlanApplyPolicyRowStatus OBJECT-TYPE
            SYNTAX RowStatus
            MAX-ACCESS read-create
            STATUS current
            DESCRIPTION
                "RowStatus. Three actions are used: active,
                createAndGo, destroy"
            ::= { hwCBQoSIfVlanApplyPolicyEntry 5 }

-- Policy Instance on fr class Table
        hwCBQoSFrClassApplyPolicyTable OBJECT-TYPE
            SYNTAX SEQUENCE OF HwCBQoSFrClassApplyPolicyEntry
            MAX-ACCESS not-accessible
            STATUS current
            DESCRIPTION
                "A table of QoS policy instance."
            ::= { hwCBQoSApplyPolicyObjects 4 }

        hwCBQoSFrClassApplyPolicyEntry OBJECT-TYPE
            SYNTAX HwCBQoSFrClassApplyPolicyEntry
            MAX-ACCESS not-accessible
            STATUS current
            DESCRIPTION
                "Policy applied on fr class Configuration Information Entry."
            INDEX { hwCBQoSFrClassApplyPolicyFrClassName,
                    hwCBQoSFrClassApplyPolicyDirection }
            ::= { hwCBQoSFrClassApplyPolicyTable 1 }

        HwCBQoSFrClassApplyPolicyEntry ::=
            SEQUENCE {
                hwCBQoSFrClassApplyPolicyFrClassName
                    OCTET STRING,
                hwCBQoSFrClassApplyPolicyDirection
                    DirectionType,
                hwCBQoSFrClassApplyPolicyName
                    OCTET STRING,
                hwCBQoSFrClassApplyPolicyRowStatus
                    RowStatus
            }

        hwCBQoSFrClassApplyPolicyFrClassName OBJECT-TYPE
            SYNTAX OCTET STRING (SIZE (1..31))
            MAX-ACCESS not-accessible
            STATUS current
            DESCRIPTION
                "The name of fr class."
            ::= { hwCBQoSFrClassApplyPolicyEntry 1 }

        hwCBQoSFrClassApplyPolicyDirection OBJECT-TYPE
            SYNTAX DirectionType
            MAX-ACCESS not-accessible
            STATUS current
            DESCRIPTION
                "Policy direction:
                inbound (1)
                outbound (2)"
            ::= { hwCBQoSFrClassApplyPolicyEntry 2 }

        hwCBQoSFrClassApplyPolicyName OBJECT-TYPE
            SYNTAX OCTET STRING (SIZE (1..31))
            MAX-ACCESS read-create
            STATUS current
            DESCRIPTION
                "Name of Traffic Policy."
            ::= { hwCBQoSFrClassApplyPolicyEntry 3 }

        hwCBQoSFrClassApplyPolicyRowStatus OBJECT-TYPE
            SYNTAX RowStatus
            MAX-ACCESS read-create
            STATUS current
            DESCRIPTION
                "RowStatus. Three actions are used: active,
                createAndGo, destroy"
            ::= { hwCBQoSFrClassApplyPolicyEntry 4 }

-- Policy Instance on fr pvc Table
        hwCBQoSFrPvcApplyPolicyTable OBJECT-TYPE
            SYNTAX SEQUENCE OF HwCBQoSFrPvcApplyPolicyEntry
            MAX-ACCESS not-accessible
            STATUS current
            DESCRIPTION
                "A table of QoS policy instance."
            ::= { hwCBQoSApplyPolicyObjects 5 }

        hwCBQoSFrPvcApplyPolicyEntry OBJECT-TYPE
            SYNTAX HwCBQoSFrPvcApplyPolicyEntry
            MAX-ACCESS not-accessible
            STATUS current
            DESCRIPTION
                "Policy applied on FR PVC Configuration Information Entry."
            INDEX { hwCBQoSFrPvcApplyPolicyIfIndex,
                    hwCBQoSFrPvcApplyPolicyDlciNum,
                    hwCBQoSFrPvcApplyPolicyDirection }
            ::= { hwCBQoSFrPvcApplyPolicyTable 1 }

        HwCBQoSFrPvcApplyPolicyEntry ::=
            SEQUENCE {
                hwCBQoSFrPvcApplyPolicyIfIndex
                    Integer32,
                hwCBQoSFrPvcApplyPolicyDlciNum
                    Integer32,
                hwCBQoSFrPvcApplyPolicyDirection
                    DirectionType,
                hwCBQoSFrPvcApplyPolicyName
                    OCTET STRING
            }

        hwCBQoSFrPvcApplyPolicyIfIndex OBJECT-TYPE
            SYNTAX Integer32
            MAX-ACCESS not-accessible
            STATUS current
            DESCRIPTION
                "Fr Interface Index, equal to ifIndex."
            ::= { hwCBQoSFrPvcApplyPolicyEntry 1 }

        hwCBQoSFrPvcApplyPolicyDlciNum OBJECT-TYPE
            SYNTAX Integer32 (16..1007)
            MAX-ACCESS not-accessible
            STATUS current
            DESCRIPTION
                "Fr DLCI number."
            ::= { hwCBQoSFrPvcApplyPolicyEntry 2 }

        hwCBQoSFrPvcApplyPolicyDirection OBJECT-TYPE
            SYNTAX DirectionType
            MAX-ACCESS not-accessible
            STATUS current
            DESCRIPTION
                "Policy direction:
                inbound (1)
                outbound (2)"
            ::= { hwCBQoSFrPvcApplyPolicyEntry 3 }

        hwCBQoSFrPvcApplyPolicyName OBJECT-TYPE
            SYNTAX OCTET STRING (SIZE (1..31))
            MAX-ACCESS read-only
            STATUS current
            DESCRIPTION
                "Name of Traffic Policy."
            ::= { hwCBQoSFrPvcApplyPolicyEntry 4 }

-- Running statistics information

hwCBQoSApplyPolicyStaticsObjects OBJECT IDENTIFIER ::= { hwCBQoSObjects 5 }

--- Interface: policy Running statistics information

        hwCBQoSIfStaticsObjects OBJECT IDENTIFIER ::= { hwCBQoSApplyPolicyStaticsObjects 1 }

-- Interface CBQ statistics
        hwCBQoSIfCbqRunInfoTable OBJECT-TYPE
            SYNTAX SEQUENCE OF HwCBQoSIfCbqRunInfoEntry
            MAX-ACCESS not-accessible
            STATUS current
            DESCRIPTION
                "A table of interface CBQ Running statistics. When policy using
                queue behavior is applied on
                interface the interface will using Class Based Queuing."
            ::= { hwCBQoSIfStaticsObjects 1 }

        hwCBQoSIfCbqRunInfoEntry OBJECT-TYPE
            SYNTAX HwCBQoSIfCbqRunInfoEntry
            MAX-ACCESS not-accessible
            STATUS current
            DESCRIPTION
                "Interface CBQ statistics entry."
            INDEX { hwCBQoSIfApplyPolicyIfIndex}
            ::= { hwCBQoSIfCbqRunInfoTable 1 }

        HwCBQoSIfCbqRunInfoEntry ::=
            SEQUENCE {
                hwCBQoSIfCbqQueueSize
                    Integer32,
                hwCBQoSIfCbqDiscard
                    Counter32,
                hwCBQoSIfCbqEfQueueSize
                    Integer32,
                hwCBQoSIfCbqAfQueueSize
                    Integer32,
                hwCBQoSIfCbqBeQueueSize
                    Integer32,
                hwCBQoSIfCbqBeActiveQueueNum
                    Integer32,
                hwCBQoSIfCbqBeMaxActiveQueueNum
                    Integer32,
                hwCBQoSIfCbqBeTotalQueueNum
                    Integer32,
                hwCBQoSIfCbqAfAllocatedQueueNum
                    Integer32
                }

        hwCBQoSIfCbqQueueSize OBJECT-TYPE
            SYNTAX Integer32
            MAX-ACCESS read-only
            STATUS current
            DESCRIPTION
                "Packet number of CBQ queue"
            ::= { hwCBQoSIfCbqRunInfoEntry 1 }

        hwCBQoSIfCbqDiscard OBJECT-TYPE
            SYNTAX Counter32
            MAX-ACCESS read-only
            STATUS current
            DESCRIPTION
                "The number of discarded packets which coundn't be enqueued."
            ::= { hwCBQoSIfCbqRunInfoEntry 2 }

        hwCBQoSIfCbqEfQueueSize OBJECT-TYPE
            SYNTAX Integer32
            MAX-ACCESS read-only
            STATUS current
            DESCRIPTION
                "Packet number of EF queue"
            ::= { hwCBQoSIfCbqRunInfoEntry 3 }

        hwCBQoSIfCbqAfQueueSize OBJECT-TYPE
            SYNTAX Integer32
            MAX-ACCESS read-only
            STATUS current
            DESCRIPTION
                "Packet number of of AF queue"
            ::= { hwCBQoSIfCbqRunInfoEntry 4 }

        hwCBQoSIfCbqBeQueueSize OBJECT-TYPE
            SYNTAX Integer32
            MAX-ACCESS read-only
            STATUS current
            DESCRIPTION
                "Packet number of BE queue"
            ::= { hwCBQoSIfCbqRunInfoEntry 5 }

        hwCBQoSIfCbqBeActiveQueueNum OBJECT-TYPE
            SYNTAX Integer32
            MAX-ACCESS read-only
            STATUS current
            DESCRIPTION
                "the Packet number of Active Be Queue"
            ::= { hwCBQoSIfCbqRunInfoEntry 6 }

        hwCBQoSIfCbqBeMaxActiveQueueNum OBJECT-TYPE
            SYNTAX Integer32
            MAX-ACCESS read-only
            STATUS current
            DESCRIPTION
                "the max Packet number of Active Be Queue"
            ::= { hwCBQoSIfCbqRunInfoEntry 7 }

        hwCBQoSIfCbqBeTotalQueueNum OBJECT-TYPE
            SYNTAX Integer32
            MAX-ACCESS read-only
            STATUS current
            DESCRIPTION
                "the total Packet number of Be Queue"
            ::= { hwCBQoSIfCbqRunInfoEntry 8 }

        hwCBQoSIfCbqAfAllocatedQueueNum OBJECT-TYPE
            SYNTAX Integer32
            MAX-ACCESS read-only
            STATUS current
            DESCRIPTION
                "the Allocated Packet number of Af Queue"
            ::= { hwCBQoSIfCbqRunInfoEntry 9 }

-- Class match statistics
        hwCBQoSIfClassMatchRunInfoTable OBJECT-TYPE
            SYNTAX SEQUENCE OF HwCBQoSIfClassMatchRunInfoEntry
            MAX-ACCESS not-accessible
            STATUS current
            DESCRIPTION
                "A table of Running statistics for matching a classifier
                in a QoS policy applied on the interface."
            ::= { hwCBQoSIfStaticsObjects 2 }

        hwCBQoSIfClassMatchRunInfoEntry OBJECT-TYPE
            SYNTAX HwCBQoSIfClassMatchRunInfoEntry
            MAX-ACCESS not-accessible
            STATUS current
            DESCRIPTION
                "Classifier's matching statistics information entry."
            INDEX { hwCBQoSIfApplyPolicyIfIndex,
                    hwCBQoSIfApplyPolicyDirection,
                    hwCBQoSPolicyClassIndex }
            ::= { hwCBQoSIfClassMatchRunInfoTable 1 }

        HwCBQoSIfClassMatchRunInfoEntry ::=
            SEQUENCE {
                hwCBQoSIfClassMatchedPackets
                    Counter32,
                hwCBQoSIfClassMatchedBytes
                    Counter32,
                hwCBQoSIfClassAverageRate
                    Counter64
            }

        hwCBQoSIfClassMatchedPackets OBJECT-TYPE
            SYNTAX Counter32
            MAX-ACCESS read-only
            STATUS current
            DESCRIPTION
                "Number of packets matching a class in a QoS policy."
            ::= { hwCBQoSIfClassMatchRunInfoEntry 1 }

        hwCBQoSIfClassMatchedBytes OBJECT-TYPE
            SYNTAX Counter32
            MAX-ACCESS read-only
            STATUS current
            DESCRIPTION
                "Number of bytes matching a class in a QoS policy.
                Only software QoS support this node."
            ::= { hwCBQoSIfClassMatchRunInfoEntry 2 }

        hwCBQoSIfClassAverageRate OBJECT-TYPE
            SYNTAX Counter64
            MAX-ACCESS read-only
            STATUS current
            DESCRIPTION
                "Average rate matching a class of the last 5 minutes."
            ::= { hwCBQoSIfClassMatchRunInfoEntry 3 }

-- CAR statistics
        hwCBQoSIfCarRunInfoTable OBJECT-TYPE
            SYNTAX SEQUENCE OF HwCBQoSIfCarRunInfoEntry
            MAX-ACCESS not-accessible
            STATUS current
            DESCRIPTION
                "A table of Running statistics for CAR
                in a QoS policy applied on the interface."
            ::= { hwCBQoSIfStaticsObjects 3 }

        hwCBQoSIfCarRunInfoEntry OBJECT-TYPE
            SYNTAX HwCBQoSIfCarRunInfoEntry
            MAX-ACCESS not-accessible
            STATUS current
            DESCRIPTION
                "CAR statistics information entry."
            INDEX { hwCBQoSIfApplyPolicyIfIndex, hwCBQoSIfApplyPolicyDirection,
                    hwCBQoSPolicyClassIndex }
            ::= { hwCBQoSIfCarRunInfoTable 1 }

        HwCBQoSIfCarRunInfoEntry ::=
            SEQUENCE {
                hwCBQoSIfCarGreenPackets
                    Counter32,
                hwCBQoSIfCarGreenBytes
                    Counter32,
                hwCBQoSIfCarRedPackets
                    Counter32,
                hwCBQoSIfCarRedBytes
                    Counter32
            }

        hwCBQoSIfCarGreenPackets OBJECT-TYPE
            SYNTAX Counter32
            MAX-ACCESS read-only
            STATUS current
            DESCRIPTION
                "Number of packets conforming CIR."
            ::= { hwCBQoSIfCarRunInfoEntry 1 }

        hwCBQoSIfCarGreenBytes OBJECT-TYPE
            SYNTAX Counter32
            MAX-ACCESS read-only
            STATUS current
            DESCRIPTION
                "Number of bytes conforming CIR."
            ::= { hwCBQoSIfCarRunInfoEntry 2 }

        hwCBQoSIfCarRedPackets OBJECT-TYPE
            SYNTAX Counter32
            MAX-ACCESS read-only
            STATUS current
            DESCRIPTION
                "Number of packets exceeding CIR."
            ::= { hwCBQoSIfCarRunInfoEntry 3 }

        hwCBQoSIfCarRedBytes OBJECT-TYPE
            SYNTAX Counter32
            MAX-ACCESS read-only
            STATUS current
            DESCRIPTION
                "Number of bytes exceeding CIR."
            ::= { hwCBQoSIfCarRunInfoEntry 4 }

-- GTS statistics
        hwCBQoSIfGtsRunInfoTable OBJECT-TYPE
            SYNTAX SEQUENCE OF HwCBQoSIfGtsRunInfoEntry
            MAX-ACCESS not-accessible
            STATUS current
            DESCRIPTION
                "A table of Running statistics for GTS
                in a QoS policy applied on the interface."
            ::= { hwCBQoSIfStaticsObjects 4 }

        hwCBQoSIfGtsRunInfoEntry OBJECT-TYPE
            SYNTAX HwCBQoSIfGtsRunInfoEntry
            MAX-ACCESS not-accessible
            STATUS current
            DESCRIPTION
                "GTS statistics entry."
            INDEX { hwCBQoSIfApplyPolicyIfIndex, hwCBQoSIfApplyPolicyDirection,
                    hwCBQoSPolicyClassIndex }
            ::= { hwCBQoSIfGtsRunInfoTable 1 }

        HwCBQoSIfGtsRunInfoEntry ::=
            SEQUENCE {
                hwCBQoSIfGtsPassedPackets
                    Counter32,
                hwCBQoSIfGtsPassedBytes
                    Counter32,
                hwCBQoSIfGtsDiscardedPackets
                    Counter32,
                hwCBQoSIfGtsDiscardedBytes
                    Counter32,
                hwCBQoSIfGtsDelayedPackets
                    Counter32,
                hwCBQoSIfGtsDelayedBytes
                    Counter32,
                hwCBQoSIfGtsQueueSize
                    Integer32
            }

        hwCBQoSIfGtsPassedPackets OBJECT-TYPE
            SYNTAX Counter32
            MAX-ACCESS read-only
            STATUS current
            DESCRIPTION
                "Number of packets passed by GTS."
            ::= { hwCBQoSIfGtsRunInfoEntry 1 }

        hwCBQoSIfGtsPassedBytes OBJECT-TYPE
            SYNTAX Counter32
            MAX-ACCESS read-only
            STATUS current
            DESCRIPTION
                "Number of bytes passed by GTS."
            ::= { hwCBQoSIfGtsRunInfoEntry 2 }

        hwCBQoSIfGtsDiscardedPackets OBJECT-TYPE
            SYNTAX Counter32
            MAX-ACCESS read-only
            STATUS current
            DESCRIPTION
                "Number of packets discarded by GTS."
            ::= { hwCBQoSIfGtsRunInfoEntry 3 }

        hwCBQoSIfGtsDiscardedBytes OBJECT-TYPE
            SYNTAX Counter32
            MAX-ACCESS read-only
            STATUS current
            DESCRIPTION
                "Number of bytes discarded by GTS."
            ::= { hwCBQoSIfGtsRunInfoEntry 4 }

        hwCBQoSIfGtsDelayedPackets OBJECT-TYPE
            SYNTAX Counter32
            MAX-ACCESS read-only
            STATUS current
            DESCRIPTION
                "Number of packets delayed by GTS."
            ::= { hwCBQoSIfGtsRunInfoEntry 5 }

        hwCBQoSIfGtsDelayedBytes OBJECT-TYPE
            SYNTAX Counter32
            MAX-ACCESS read-only
            STATUS current
            DESCRIPTION
                "Number of bytes delayed by GTS."
            ::= { hwCBQoSIfGtsRunInfoEntry 6 }

        hwCBQoSIfGtsQueueSize OBJECT-TYPE
            SYNTAX Integer32
            MAX-ACCESS read-only
            STATUS current
            DESCRIPTION
                "Packet number of GTS queue."
            ::= { hwCBQoSIfGtsRunInfoEntry 7 }

-- Remark statistics
        hwCBQoSIfRemarkRunInfoTable OBJECT-TYPE
            SYNTAX SEQUENCE OF HwCBQoSIfRemarkRunInfoEntry
            MAX-ACCESS not-accessible
            STATUS current
            DESCRIPTION
                "A table of Running statistics for remarking
                in a QoS policy applied on the interface."
            ::= { hwCBQoSIfStaticsObjects 5 }

        hwCBQoSIfRemarkRunInfoEntry OBJECT-TYPE
            SYNTAX HwCBQoSIfRemarkRunInfoEntry
            MAX-ACCESS not-accessible
            STATUS current
            DESCRIPTION
                "Remarking statistics entry."
            INDEX { hwCBQoSIfApplyPolicyIfIndex, hwCBQoSIfApplyPolicyDirection,
                    hwCBQoSPolicyClassIndex }
            ::= { hwCBQoSIfRemarkRunInfoTable 1 }

        HwCBQoSIfRemarkRunInfoEntry ::=
            SEQUENCE {
                hwCBQoSIfRemarkedPackets
                    Counter32
            }

        hwCBQoSIfRemarkedPackets OBJECT-TYPE
            SYNTAX Counter32
            MAX-ACCESS read-only
            STATUS current
            DESCRIPTION
                "Number of packets remarked."
            ::= { hwCBQoSIfRemarkRunInfoEntry 1 }


-- Queue statistics
        hwCBQoSIfQueueRunInfoTable OBJECT-TYPE
            SYNTAX SEQUENCE OF HwCBQoSIfQueueRunInfoEntry
            MAX-ACCESS not-accessible
            STATUS current
            DESCRIPTION
                "A table of Running statistics for queue
                in a QoS policy applied on the interface."
            ::= { hwCBQoSIfStaticsObjects 6 }

        hwCBQoSIfQueueRunInfoEntry OBJECT-TYPE
            SYNTAX HwCBQoSIfQueueRunInfoEntry
            MAX-ACCESS not-accessible
            STATUS current
            DESCRIPTION
                "Queue statistics entry."
            INDEX { hwCBQoSIfApplyPolicyIfIndex, hwCBQoSIfApplyPolicyDirection,
                    hwCBQoSPolicyClassIndex }
            ::= { hwCBQoSIfQueueRunInfoTable     1 }

        HwCBQoSIfQueueRunInfoEntry ::=
            SEQUENCE {
                hwCBQoSIfQueueMatchedPackets
                    Counter32,
                hwCBQoSIfQueueMatchedBytes
                    Counter32,
                hwCBQoSIfQueueEnqueuedPackets
                    Counter32,
                hwCBQoSIfQueueEnqueuedBytes
                    Counter32,
                hwCBQoSIfQueueDiscardedPackets
                    Counter32,
                hwCBQoSIfQueueDiscardedBytes
                    Counter32
            }

        hwCBQoSIfQueueMatchedPackets OBJECT-TYPE
            SYNTAX Counter32
            MAX-ACCESS read-only
            STATUS current
            DESCRIPTION
                "Number of packets matched to enqueue."
            ::= { hwCBQoSIfQueueRunInfoEntry 1 }

        hwCBQoSIfQueueMatchedBytes OBJECT-TYPE
            SYNTAX Counter32
            MAX-ACCESS read-only
            STATUS current
            DESCRIPTION
                "Number of bytes matched to enqueue."
            ::= { hwCBQoSIfQueueRunInfoEntry 2 }

        hwCBQoSIfQueueEnqueuedPackets OBJECT-TYPE
            SYNTAX Counter32
            MAX-ACCESS read-only
            STATUS current
            DESCRIPTION
                "Number of packets enqueued."
            ::= { hwCBQoSIfQueueRunInfoEntry 3 }

        hwCBQoSIfQueueEnqueuedBytes OBJECT-TYPE
            SYNTAX Counter32
            MAX-ACCESS read-only
            STATUS current
            DESCRIPTION
                "Number of bytes enqueued."
            ::= { hwCBQoSIfQueueRunInfoEntry 4 }

        hwCBQoSIfQueueDiscardedPackets OBJECT-TYPE
            SYNTAX Counter32
            MAX-ACCESS read-only
            STATUS current
            DESCRIPTION
                "Number of packets discarded when enqueued by discard method."
            ::= { hwCBQoSIfQueueRunInfoEntry 5 }

        hwCBQoSIfQueueDiscardedBytes OBJECT-TYPE
            SYNTAX Counter32
            MAX-ACCESS read-only
            STATUS current
            DESCRIPTION
                "Number of bytes discarded when enqueued by discard method."
            ::= { hwCBQoSIfQueueRunInfoEntry 6 }

-- WRED statistics
        hwCBQoSIfWredRunInfoTable OBJECT-TYPE
            SYNTAX SEQUENCE OF HwCBQoSIfWredRunInfoEntry
            MAX-ACCESS not-accessible
            STATUS current
            DESCRIPTION
                "A table of Running statistics for WRED
                in a QoS policy applied on the interface."
            ::= { hwCBQoSIfStaticsObjects 7 }

        hwCBQoSIfWredRunInfoEntry OBJECT-TYPE
            SYNTAX HwCBQoSIfWredRunInfoEntry
            MAX-ACCESS not-accessible
            STATUS current
            DESCRIPTION
                "WRED statistics entry."
            INDEX { hwCBQoSIfApplyPolicyIfIndex, hwCBQoSIfApplyPolicyDirection,
                    hwCBQoSPolicyClassIndex, hwCBQoSWredClassValue}
            ::= { hwCBQoSIfWredRunInfoTable 1 }

        HwCBQoSIfWredRunInfoEntry ::=
            SEQUENCE {
                hwCBQoSIfWredRandomDiscardedPackets
                    Counter32,
                hwCBQoSIfWredTailDiscardedPackets
                    Counter32
            }

        hwCBQoSIfWredRandomDiscardedPackets OBJECT-TYPE
            SYNTAX Counter32
            MAX-ACCESS read-only
            STATUS current
            DESCRIPTION
                "Number of packets that random-discarded by WRED."
            ::= { hwCBQoSIfWredRunInfoEntry 1 }

        hwCBQoSIfWredTailDiscardedPackets OBJECT-TYPE
            SYNTAX Counter32
            MAX-ACCESS read-only
            STATUS current
            DESCRIPTION
                "Number of packets that tail-discarded by WRED."
            ::= { hwCBQoSIfWredRunInfoEntry 2 }

--  LR statistics
        hwCBQoSIfLrRunInfoTable OBJECT-TYPE
            SYNTAX SEQUENCE OF HwCBQoSIfLrRunInfoEntry
            MAX-ACCESS not-accessible
            STATUS current
            DESCRIPTION
                "A table of Running statistics for LR
                in a QoS policy applied on the interface."
            ::= { hwCBQoSIfStaticsObjects 8 }


        hwCBQoSIfLrRunInfoEntry OBJECT-TYPE
            SYNTAX HwCBQoSIfLrRunInfoEntry
            MAX-ACCESS not-accessible
            STATUS current
            DESCRIPTION
                "LR statistics entry."
            INDEX { hwCBQoSIfApplyPolicyIfIndex, hwCBQoSIfApplyPolicyDirection, hwCBQoSPolicyClassIndex }
            ::= { hwCBQoSIfLrRunInfoTable 1 }


        HwCBQoSIfLrRunInfoEntry ::=
            SEQUENCE {
                hwCBQoSIfLrPassedPackets
                    Counter32,
                hwCBQoSIfLrPassedBytes
                    Counter32,
                hwCBQoSIfLrDiscardedPackets
                    Counter32,
                hwCBQoSIfLrDiscardedBytes
                    Counter32,
                hwCBQoSIfLrDelayedPackets
                    Counter32,
                hwCBQoSIfLrDelayedBytes
                    Counter32,
                hwCBQoSIfLrQueueSize
                    Integer32
             }

        hwCBQoSIfLrPassedPackets OBJECT-TYPE
            SYNTAX Counter32
            MAX-ACCESS read-only
            STATUS current
            DESCRIPTION
                "Number of packets passed by LR."
            ::= { hwCBQoSIfLrRunInfoEntry 1 }


        hwCBQoSIfLrPassedBytes OBJECT-TYPE
            SYNTAX Counter32
            MAX-ACCESS read-only
            STATUS current
            DESCRIPTION
                "Number of bytes passed by LR."
            ::= { hwCBQoSIfLrRunInfoEntry 2 }


        hwCBQoSIfLrDiscardedPackets OBJECT-TYPE
            SYNTAX Counter32
            MAX-ACCESS read-only
            STATUS current
            DESCRIPTION
                "Number of packets discarded by LR."
            ::= { hwCBQoSIfLrRunInfoEntry 3 }


        hwCBQoSIfLrDiscardedBytes OBJECT-TYPE
            SYNTAX Counter32
            MAX-ACCESS read-only
            STATUS current
            DESCRIPTION
                "Number of bytes discarded by LR."
            ::= { hwCBQoSIfLrRunInfoEntry 4 }


        hwCBQoSIfLrDelayedPackets OBJECT-TYPE
            SYNTAX Counter32
            MAX-ACCESS read-only
            STATUS current
            DESCRIPTION
                "Number of packets delayed by LR."
            ::= { hwCBQoSIfLrRunInfoEntry 5 }


        hwCBQoSIfLrDelayedBytes OBJECT-TYPE
            SYNTAX Counter32
            MAX-ACCESS read-only
            STATUS current
            DESCRIPTION
                "Number of bytes delayed by LR."
            ::= { hwCBQoSIfLrRunInfoEntry 6 }

        hwCBQoSIfLrQueueSize OBJECT-TYPE
            SYNTAX Integer32
            MAX-ACCESS read-only
            STATUS current
            DESCRIPTION
                "Packet number of LR queue"
            ::= { hwCBQoSIfLrRunInfoEntry 7 }


-- ATM Interface PVC: policy Running statistics information

        hwCBQoSAtmPvcStaticsObjects OBJECT IDENTIFIER ::= { hwCBQoSApplyPolicyStaticsObjects 2 }

-- ATM PVC CBQ statistics
        hwCBQoSAtmPvcCbqRunInfoTable OBJECT-TYPE
            SYNTAX SEQUENCE OF HwCBQoSAtmPvcCbqRunInfoEntry
            MAX-ACCESS not-accessible
            STATUS current
            DESCRIPTION
                "A table of atm pvc CBQ Running statistics. When policy using
                queue behavior is applied on
                atm pvc atm pvc will using Class Based Queuing."
            ::= { hwCBQoSAtmPvcStaticsObjects 1 }

        hwCBQoSAtmPvcCbqRunInfoEntry OBJECT-TYPE
            SYNTAX HwCBQoSAtmPvcCbqRunInfoEntry
            MAX-ACCESS not-accessible
            STATUS current
            DESCRIPTION
                "FR PVC CBQ statistics entry."
            INDEX { hwCBQoSAtmPvcApplyPolicyIfIndex,
                    hwCBQoSAtmPvcApplyPolicyVPI,
                    hwCBQoSAtmPvcApplyPolicyVCI }
            ::= { hwCBQoSAtmPvcCbqRunInfoTable 1 }

        HwCBQoSAtmPvcCbqRunInfoEntry ::=
            SEQUENCE {
                hwCBQoSAtmPvcCbqQueueSize
                    Integer32,
                hwCBQoSAtmPvcCbqDiscard
                    Counter32,
                hwCBQoSAtmPvcCbqEfQueueSize
                    Integer32,
                hwCBQoSAtmPvcCbqAfQueueSize
                    Integer32,
                hwCBQoSAtmPvcCbqBeQueueSize
                    Integer32,
                hwCBQoSAtmPvcCbqBeActiveQueueNum
                    Integer32,
                hwCBQoSAtmPvcCbqBeMaxActiveQueueNum
                    Integer32,
                hwCBQoSAtmPvcCbqBeTotalQueueNum
                    Integer32,
                hwCBQoSAtmPvcCbqAfAllocatedQueueNum
                    Integer32
                }

        hwCBQoSAtmPvcCbqQueueSize OBJECT-TYPE
            SYNTAX Integer32
            MAX-ACCESS read-only
            STATUS current
            DESCRIPTION
                "Packet number of CBQ queue"
            ::= { hwCBQoSAtmPvcCbqRunInfoEntry 1 }

        hwCBQoSAtmPvcCbqDiscard OBJECT-TYPE
            SYNTAX Counter32
            MAX-ACCESS read-only
            STATUS current
            DESCRIPTION
                "The number of discarded packets which coundn't be enqueued."
            ::= { hwCBQoSAtmPvcCbqRunInfoEntry 2 }

        hwCBQoSAtmPvcCbqEfQueueSize OBJECT-TYPE
            SYNTAX Integer32
            MAX-ACCESS read-only
            STATUS current
            DESCRIPTION
                "Packet number of EF queue"
            ::= { hwCBQoSAtmPvcCbqRunInfoEntry 3 }

        hwCBQoSAtmPvcCbqAfQueueSize OBJECT-TYPE
            SYNTAX Integer32
            MAX-ACCESS read-only
            STATUS current
            DESCRIPTION
                "Packet number of AF queue"
            ::= { hwCBQoSAtmPvcCbqRunInfoEntry 4 }

        hwCBQoSAtmPvcCbqBeQueueSize OBJECT-TYPE
            SYNTAX Integer32
            MAX-ACCESS read-only
            STATUS current
            DESCRIPTION
                "Packet number of BE queue"
            ::= { hwCBQoSAtmPvcCbqRunInfoEntry 5 }

        hwCBQoSAtmPvcCbqBeActiveQueueNum OBJECT-TYPE
            SYNTAX Integer32
            MAX-ACCESS read-only
            STATUS current
            DESCRIPTION
                "the packet number of Active Be Queue"
            ::= { hwCBQoSAtmPvcCbqRunInfoEntry 6 }

        hwCBQoSAtmPvcCbqBeMaxActiveQueueNum OBJECT-TYPE
            SYNTAX Integer32
            MAX-ACCESS read-only
            STATUS current
            DESCRIPTION
                "the max packet number of Active Be Queue"
            ::= { hwCBQoSAtmPvcCbqRunInfoEntry 7 }

        hwCBQoSAtmPvcCbqBeTotalQueueNum OBJECT-TYPE
            SYNTAX Integer32
            MAX-ACCESS read-only
            STATUS current
            DESCRIPTION
                "the total packet number of Be Queue"
            ::= { hwCBQoSAtmPvcCbqRunInfoEntry 8 }

        hwCBQoSAtmPvcCbqAfAllocatedQueueNum OBJECT-TYPE
            SYNTAX Integer32
            MAX-ACCESS read-only
            STATUS current
            DESCRIPTION
                "the Allocated packet number of Af Queue"
            ::= { hwCBQoSAtmPvcCbqRunInfoEntry 9 }

-- Class match statistics

        hwCBQoSAtmPvcClassMatchRunInfoTable OBJECT-TYPE
            SYNTAX SEQUENCE OF HwCBQoSAtmPvcClassMatchRunInfoEntry
            MAX-ACCESS not-accessible
            STATUS current
            DESCRIPTION
                "A table of Running statistics for matching a classifier
                in a QoS policy applied on ATM PVC."
            ::= { hwCBQoSAtmPvcStaticsObjects 2 }

        hwCBQoSAtmPvcClassMatchRunInfoEntry OBJECT-TYPE
            SYNTAX HwCBQoSAtmPvcClassMatchRunInfoEntry
            MAX-ACCESS not-accessible
            STATUS current
            DESCRIPTION
                "Classifier matching statistics entry."
            INDEX { hwCBQoSAtmPvcApplyPolicyIfIndex, hwCBQoSAtmPvcApplyPolicyVPI,
                    hwCBQoSAtmPvcApplyPolicyVCI, hwCBQoSAtmPvcApplyPolicyDirection,
                    hwCBQoSPolicyClassIndex }
            ::= { hwCBQoSAtmPvcClassMatchRunInfoTable 1 }

        HwCBQoSAtmPvcClassMatchRunInfoEntry ::=
            SEQUENCE {
                hwCBQoSAtmPvcClassMatchPackets
                    Counter32,
                hwCBQoSAtmPvcClassMatchBytes
                    Counter32,
                hwCBQoSAtmPvcClassAverageRate
                    Counter64
            }

        hwCBQoSAtmPvcClassMatchPackets OBJECT-TYPE
            SYNTAX Counter32
            MAX-ACCESS read-only
            STATUS current
            DESCRIPTION
                "Number of packets matching a class in a QoS policy."
            ::= { hwCBQoSAtmPvcClassMatchRunInfoEntry 1 }

        hwCBQoSAtmPvcClassMatchBytes OBJECT-TYPE
            SYNTAX Counter32
            MAX-ACCESS read-only
            STATUS current
            DESCRIPTION
                "Number of bytes matching a class in a QoS policy."
            ::= { hwCBQoSAtmPvcClassMatchRunInfoEntry 2 }

        hwCBQoSAtmPvcClassAverageRate OBJECT-TYPE
            SYNTAX Counter64
            MAX-ACCESS read-only
            STATUS current
            DESCRIPTION
                "Average rate matching a class in the last 5 minutes."
            ::= { hwCBQoSAtmPvcClassMatchRunInfoEntry 3 }

-- CAR statistics
        hwCBQoSAtmPvcCarRunInfoTable OBJECT-TYPE
            SYNTAX SEQUENCE OF HwCBQoSAtmPvcCarRunInfoEntry
            MAX-ACCESS not-accessible
            STATUS current
            DESCRIPTION
                "A table of Running statistics for CAR
                in a QoS policy applied on ATM PVC."
            ::= { hwCBQoSAtmPvcStaticsObjects 3 }

        hwCBQoSAtmPvcCarRunInfoEntry OBJECT-TYPE
            SYNTAX HwCBQoSAtmPvcCarRunInfoEntry
            MAX-ACCESS not-accessible
            STATUS current
            DESCRIPTION
                "CAR statistics entry."
            INDEX { hwCBQoSAtmPvcApplyPolicyIfIndex, hwCBQoSAtmPvcApplyPolicyVPI,
                    hwCBQoSAtmPvcApplyPolicyVCI,hwCBQoSAtmPvcApplyPolicyDirection,
                    hwCBQoSPolicyClassIndex }
            ::= { hwCBQoSAtmPvcCarRunInfoTable 1 }

        HwCBQoSAtmPvcCarRunInfoEntry ::=
            SEQUENCE {
                hwCBQoSAtmPvcCarConformPackets
                    Counter32,
                hwCBQoSAtmPvcCarConformBytes
                    Counter32,
                hwCBQoSAtmPvcCarExceedPackets
                    Counter32,
                hwCBQoSAtmPvcCarExceedBytes
                    Counter32
            }

        hwCBQoSAtmPvcCarConformPackets OBJECT-TYPE
            SYNTAX Counter32
            MAX-ACCESS read-only
            STATUS current
            DESCRIPTION
                "Number of packets that conforming specified CIR."
            ::= { hwCBQoSAtmPvcCarRunInfoEntry 1 }

        hwCBQoSAtmPvcCarConformBytes OBJECT-TYPE
            SYNTAX Counter32
            MAX-ACCESS read-only
            STATUS current
            DESCRIPTION
                "Number of bytes that conforming specified CIR."
            ::= { hwCBQoSAtmPvcCarRunInfoEntry 2 }

        hwCBQoSAtmPvcCarExceedPackets OBJECT-TYPE
            SYNTAX Counter32
            MAX-ACCESS read-only
            STATUS current
            DESCRIPTION
                "Number of packets exceeded CIR."
            ::= { hwCBQoSAtmPvcCarRunInfoEntry 3 }

        hwCBQoSAtmPvcCarExceedBytes OBJECT-TYPE
            SYNTAX Counter32
            MAX-ACCESS read-only
            STATUS current
            DESCRIPTION
                "Number of bytes exceeded CIR."
            ::= { hwCBQoSAtmPvcCarRunInfoEntry 4 }

-- GTS statistics
        hwCBQoSAtmPvcGtsRunInfoTable OBJECT-TYPE
            SYNTAX SEQUENCE OF HwCBQoSAtmPvcGtsRunInfoEntry
            MAX-ACCESS not-accessible
            STATUS current
            DESCRIPTION
                "A table of Running statistics for GTS
                in a QoS policy applied on ATM PVC."
            ::= { hwCBQoSAtmPvcStaticsObjects 4 }

        hwCBQoSAtmPvcGtsRunInfoEntry OBJECT-TYPE
            SYNTAX HwCBQoSAtmPvcGtsRunInfoEntry
            MAX-ACCESS not-accessible
            STATUS current
            DESCRIPTION
                "GTS statistics entry."
            INDEX { hwCBQoSAtmPvcApplyPolicyIfIndex, hwCBQoSAtmPvcApplyPolicyVPI,
                    hwCBQoSAtmPvcApplyPolicyVCI, hwCBQoSAtmPvcApplyPolicyDirection,
                    hwCBQoSPolicyClassIndex }
            ::= { hwCBQoSAtmPvcGtsRunInfoTable 1 }

        HwCBQoSAtmPvcGtsRunInfoEntry ::=
            SEQUENCE {
                hwCBQoSAtmPvcGtsPassedPackets
                    Counter32,
                hwCBQoSAtmPvcGtsPassedBytes
                    Counter32,
                hwCBQoSAtmPvcGtsDiscardedPackets
                    Counter32,
                hwCBQoSAtmPvcGtsDiscardedBytes
                    Counter32,
                hwCBQoSAtmPvcGtsDelayedPackets
                    Counter32,
                hwCBQoSAtmPvcGtsDelayedBytes
                    Counter32,
                hwCBQoSAtmPvcGtsQueueSize
                    Integer32
            }

        hwCBQoSAtmPvcGtsPassedPackets OBJECT-TYPE
            SYNTAX Counter32
            MAX-ACCESS read-only
            STATUS current
            DESCRIPTION
                "Number of packets passed by GTS."
            ::= { hwCBQoSAtmPvcGtsRunInfoEntry 1 }

        hwCBQoSAtmPvcGtsPassedBytes OBJECT-TYPE
            SYNTAX Counter32
            MAX-ACCESS read-only
            STATUS current
            DESCRIPTION
                "Number of bytes passed by GTS."
            ::= { hwCBQoSAtmPvcGtsRunInfoEntry 2 }

        hwCBQoSAtmPvcGtsDiscardedPackets OBJECT-TYPE
            SYNTAX Counter32
            MAX-ACCESS read-only
            STATUS current
            DESCRIPTION
                "Number of packets discarded by GTS."
            ::= { hwCBQoSAtmPvcGtsRunInfoEntry 3 }

        hwCBQoSAtmPvcGtsDiscardedBytes OBJECT-TYPE
            SYNTAX Counter32
            MAX-ACCESS read-only
            STATUS current
            DESCRIPTION
                "Number of bytes discarded by GTS."
            ::= { hwCBQoSAtmPvcGtsRunInfoEntry 4 }

        hwCBQoSAtmPvcGtsDelayedPackets OBJECT-TYPE
            SYNTAX Counter32
            MAX-ACCESS read-only
            STATUS current
            DESCRIPTION
                "Number of packets delayed by GTS."
            ::= { hwCBQoSAtmPvcGtsRunInfoEntry 5 }

        hwCBQoSAtmPvcGtsDelayedBytes OBJECT-TYPE
            SYNTAX Counter32
            MAX-ACCESS read-only
            STATUS current
            DESCRIPTION
                "Number of bytes delayed by GTS."
            ::= { hwCBQoSAtmPvcGtsRunInfoEntry 6 }

        hwCBQoSAtmPvcGtsQueueSize OBJECT-TYPE
            SYNTAX Integer32
            MAX-ACCESS read-only
            STATUS current
            DESCRIPTION
                "packet number of GTS queue."
            ::= { hwCBQoSAtmPvcGtsRunInfoEntry 7 }

-- Remark statistics
        hwCBQoSAtmPvcRemarkRunInfoTable OBJECT-TYPE
            SYNTAX SEQUENCE OF HwCBQoSAtmPvcRemarkRunInfoEntry
            MAX-ACCESS not-accessible
            STATUS current
            DESCRIPTION
                "A table of Running statistics for remarking
                in a QoS policy applied on ATM PVC."
            ::= { hwCBQoSAtmPvcStaticsObjects 5 }

        hwCBQoSAtmPvcRemarkRunInfoEntry OBJECT-TYPE
            SYNTAX HwCBQoSAtmPvcRemarkRunInfoEntry
            MAX-ACCESS not-accessible
            STATUS current
            DESCRIPTION
                "Remarking statistics entry."
            INDEX { hwCBQoSAtmPvcApplyPolicyIfIndex, hwCBQoSAtmPvcApplyPolicyVPI,
                    hwCBQoSAtmPvcApplyPolicyVCI, hwCBQoSAtmPvcApplyPolicyDirection,
                    hwCBQoSPolicyClassIndex }
            ::= { hwCBQoSAtmPvcRemarkRunInfoTable 1 }

        HwCBQoSAtmPvcRemarkRunInfoEntry ::=
            SEQUENCE {
                hwCBQoSAtmPvcRemarkedPackets
                    Counter32
            }

        hwCBQoSAtmPvcRemarkedPackets OBJECT-TYPE
            SYNTAX Counter32
            MAX-ACCESS read-only
            STATUS current
            DESCRIPTION
                "Number of packets remarked."
            ::= { hwCBQoSAtmPvcRemarkRunInfoEntry 1 }

-- Queue statistics
        hwCBQoSAtmPvcQueueRunInfoTable OBJECT-TYPE
            SYNTAX SEQUENCE OF HwCBQoSAtmPvcQueueRunInfoEntry
            MAX-ACCESS not-accessible
            STATUS current
            DESCRIPTION
                "A table of Running statistics for queue
                in a QoS policy applied on ATM PVC."
            ::= { hwCBQoSAtmPvcStaticsObjects 6 }

        hwCBQoSAtmPvcQueueRunInfoEntry OBJECT-TYPE
            SYNTAX HwCBQoSAtmPvcQueueRunInfoEntry
            MAX-ACCESS not-accessible
            STATUS current
            DESCRIPTION
                "Queue statistics entry."
            INDEX { hwCBQoSAtmPvcApplyPolicyIfIndex, hwCBQoSAtmPvcApplyPolicyVPI,
                    hwCBQoSAtmPvcApplyPolicyVCI, hwCBQoSAtmPvcApplyPolicyDirection,
                    hwCBQoSPolicyClassIndex }
            ::= { hwCBQoSAtmPvcQueueRunInfoTable 1}

        HwCBQoSAtmPvcQueueRunInfoEntry ::=
            SEQUENCE {
                hwCBQoSAtmPvcQueueMatchedPackets
                    Counter32,
                hwCBQoSAtmPvcQueueMatchedBytes
                    Counter32,
                hwCBQoSAtmPvcQueueEnqueuedPackets
                    Counter32,
                hwCBQoSAtmPvcQueueEnqueuedBytes
                    Counter32,
                hwCBQoSAtmPvcQueueDiscardedPackets
                    Counter32,
                hwCBQoSAtmPvcQueueDiscardedBytes
                    Counter32
            }

        hwCBQoSAtmPvcQueueMatchedPackets OBJECT-TYPE
            SYNTAX Counter32
            MAX-ACCESS read-only
            STATUS current
            DESCRIPTION
                "Number of packets matched to enqueue."
            ::= { hwCBQoSAtmPvcQueueRunInfoEntry 1 }

        hwCBQoSAtmPvcQueueMatchedBytes OBJECT-TYPE
            SYNTAX Counter32
            MAX-ACCESS read-only
            STATUS current
            DESCRIPTION
                "Number of bytes matched to enqueue."
            ::= { hwCBQoSAtmPvcQueueRunInfoEntry 2 }

        hwCBQoSAtmPvcQueueEnqueuedPackets OBJECT-TYPE
            SYNTAX Counter32
            MAX-ACCESS read-only
            STATUS current
            DESCRIPTION
                "Number of packets enqueued."
            ::= { hwCBQoSAtmPvcQueueRunInfoEntry 3 }

        hwCBQoSAtmPvcQueueEnqueuedBytes OBJECT-TYPE
            SYNTAX Counter32
            MAX-ACCESS read-only
            STATUS current
            DESCRIPTION
                "Number of bytes enqueued."
            ::= { hwCBQoSAtmPvcQueueRunInfoEntry 4 }

        hwCBQoSAtmPvcQueueDiscardedPackets OBJECT-TYPE
            SYNTAX Counter32
            MAX-ACCESS read-only
            STATUS current
            DESCRIPTION
                "Number of packets discard when enqueued by discard method."
            ::= { hwCBQoSAtmPvcQueueRunInfoEntry 5 }

        hwCBQoSAtmPvcQueueDiscardedBytes OBJECT-TYPE
            SYNTAX Counter32
            MAX-ACCESS read-only
            STATUS current
            DESCRIPTION
                "Number of bytes discard when enqueued by discard method."
            ::= { hwCBQoSAtmPvcQueueRunInfoEntry 6 }

-- WRED statistics
        hwCBQoSAtmPvcWredRunInfoTable OBJECT-TYPE
            SYNTAX SEQUENCE OF HwCBQoSAtmPvcWredRunInfoEntry
            MAX-ACCESS not-accessible
            STATUS current
            DESCRIPTION
                "A table of Running statistics for WRED
                in a QoS policy applied on ATM PVC."
            ::= { hwCBQoSAtmPvcStaticsObjects 7 }

        hwCBQoSAtmPvcWredRunInfoEntry OBJECT-TYPE
            SYNTAX HwCBQoSAtmPvcWredRunInfoEntry
            MAX-ACCESS not-accessible
            STATUS current
            DESCRIPTION
                "WRED statistics entry."
            INDEX { hwCBQoSAtmPvcApplyPolicyIfIndex, hwCBQoSAtmPvcApplyPolicyVPI,
                    hwCBQoSAtmPvcApplyPolicyVCI,hwCBQoSAtmPvcApplyPolicyDirection,
                    hwCBQoSPolicyClassIndex, hwCBQoSWredClassValue}
            ::= { hwCBQoSAtmPvcWredRunInfoTable 1 }

        HwCBQoSAtmPvcWredRunInfoEntry ::=
            SEQUENCE {
                hwCBQoSAtmPvcWredRandomDiscardedPackets
                    Counter32,
                hwCBQoSAtmPvcWredTailDiscardedPackets
                    Counter32
            }

        hwCBQoSAtmPvcWredRandomDiscardedPackets OBJECT-TYPE
            SYNTAX Counter32
            MAX-ACCESS read-only
            STATUS current
            DESCRIPTION
                "Number of packets randomly discarded by WRED."
            ::= { hwCBQoSAtmPvcWredRunInfoEntry 1 }

        hwCBQoSAtmPvcWredTailDiscardedPackets OBJECT-TYPE
            SYNTAX Counter32
            MAX-ACCESS read-only
            STATUS current
            DESCRIPTION
                "Number of packets tail-discarded by WRED."
            ::= { hwCBQoSAtmPvcWredRunInfoEntry 2 }

--  LR statistics
        hwCBQoSAtmPvcLrRunInfoTable OBJECT-TYPE
            SYNTAX SEQUENCE OF HwCBQoSAtmPvcLrRunInfoEntry
            MAX-ACCESS not-accessible
            STATUS current
            DESCRIPTION
                "A table of Running statistics for LR
                in a QoS policy applied on ATM PVC."
            ::= { hwCBQoSAtmPvcStaticsObjects 8 }


        hwCBQoSAtmPvcLrRunInfoEntry OBJECT-TYPE
            SYNTAX HwCBQoSAtmPvcLrRunInfoEntry
            MAX-ACCESS not-accessible
            STATUS current
            DESCRIPTION
                "LR statistics entry."
            INDEX { hwCBQoSAtmPvcApplyPolicyIfIndex, hwCBQoSAtmPvcApplyPolicyVPI, hwCBQoSAtmPvcApplyPolicyVCI, hwCBQoSAtmPvcApplyPolicyDirection, hwCBQoSPolicyClassIndex
                 }
            ::= { hwCBQoSAtmPvcLrRunInfoTable 1 }


        HwCBQoSAtmPvcLrRunInfoEntry ::=
            SEQUENCE {
                hwCBQoSAtmPvcLrPassedPackets
                    Counter32,
                hwCBQoSAtmPvcLrPassedBytes
                    Counter32,
                hwCBQoSAtmPvcLrDiscardedPackets
                    Counter32,
                hwCBQoSAtmPvcLrDiscardedBytes
                    Counter32,
                hwCBQoSAtmPvcLrDelayedPackets
                    Counter32,
                hwCBQoSAtmPvcLrDelayedBytes
                    Counter32,
                hwCBQoSAtmPvcLrQueueSize
                    Integer32
             }

        hwCBQoSAtmPvcLrPassedPackets OBJECT-TYPE
            SYNTAX Counter32
            MAX-ACCESS read-only
            STATUS current
            DESCRIPTION
                "Number of packets passed by LR."
            ::= { hwCBQoSAtmPvcLrRunInfoEntry 1 }


        hwCBQoSAtmPvcLrPassedBytes OBJECT-TYPE
            SYNTAX Counter32
            MAX-ACCESS read-only
            STATUS current
            DESCRIPTION
                "Number of bytes passed by LR."
            ::= { hwCBQoSAtmPvcLrRunInfoEntry 2 }


        hwCBQoSAtmPvcLrDiscardedPackets OBJECT-TYPE
            SYNTAX Counter32
            MAX-ACCESS read-only
            STATUS current
            DESCRIPTION
                "Number of packets discarded by LR."
            ::= { hwCBQoSAtmPvcLrRunInfoEntry 3 }


        hwCBQoSAtmPvcLrDiscardedBytes OBJECT-TYPE
            SYNTAX Counter32
            MAX-ACCESS read-only
            STATUS current
            DESCRIPTION
                "Number of bytes discarded by LR."
            ::= { hwCBQoSAtmPvcLrRunInfoEntry 4 }


        hwCBQoSAtmPvcLrDelayedPackets OBJECT-TYPE
            SYNTAX Counter32
            MAX-ACCESS read-only
            STATUS current
            DESCRIPTION
                "Number of packets delayed by LR."
            ::= { hwCBQoSAtmPvcLrRunInfoEntry 5 }


        hwCBQoSAtmPvcLrDelayedBytes OBJECT-TYPE
            SYNTAX Counter32
            MAX-ACCESS read-only
            STATUS current
            DESCRIPTION
                "Number of bytes delayed by LR."
            ::= { hwCBQoSAtmPvcLrRunInfoEntry 6 }

        hwCBQoSAtmPvcLrQueueSize OBJECT-TYPE
            SYNTAX Integer32
            MAX-ACCESS read-only
            STATUS current
            DESCRIPTION
                "Packet number of LR queue"
            ::= { hwCBQoSAtmPvcLrRunInfoEntry 7 }


-- FR Interface PVC: policy Running statistics information

        hwCBQoSFrPvcStaticsObjects OBJECT IDENTIFIER ::= { hwCBQoSApplyPolicyStaticsObjects 3 }

-- FR PVC CBQ statistics
        hwCBQoSFrPvcCbqRunInfoTable OBJECT-TYPE
            SYNTAX SEQUENCE OF HwCBQoSFrPvcCbqRunInfoEntry
            MAX-ACCESS not-accessible
            STATUS current
            DESCRIPTION
                "A table of fr pvc CBQ Running statistics. When policy using
                queue behavior is applied on
                fr pvc fr pvc will using Class Based Queuing."
            ::= { hwCBQoSFrPvcStaticsObjects 1 }

        hwCBQoSFrPvcCbqRunInfoEntry OBJECT-TYPE
            SYNTAX HwCBQoSFrPvcCbqRunInfoEntry
            MAX-ACCESS not-accessible
            STATUS current
            DESCRIPTION
                "FR PVC CBQ statistics entry."
            INDEX { hwCBQoSFrPvcApplyPolicyIfIndex, hwCBQoSFrPvcApplyPolicyDlciNum }
            ::= { hwCBQoSFrPvcCbqRunInfoTable 1 }

        HwCBQoSFrPvcCbqRunInfoEntry ::=
            SEQUENCE {
                hwCBQoSFrPvcCbqQueueSize
                    Integer32,
                hwCBQoSFrPvcCbqDiscard
                    Counter32,
                hwCBQoSFrPvcCbqEfQueueSize
                    Integer32,
                hwCBQoSFrPvcCbqAfQueueSize
                    Integer32,
                hwCBQoSFrPvcCbqBeQueueSize
                    Integer32,
                hwCBQoSFrPvcCbqBeActiveQueueNum
                    Integer32,
                hwCBQoSFrPvcCbqBeMaxActiveQueueNum
                    Integer32,
                hwCBQoSFrPvcCbqBeTotalQueueNum
                    Integer32,
                hwCBQoSFrPvcCbqAfAllocatedQueueNum
                    Integer32
                }

        hwCBQoSFrPvcCbqQueueSize OBJECT-TYPE
            SYNTAX Integer32
            MAX-ACCESS read-only
            STATUS current
            DESCRIPTION
                "packet number of CBQ queue"
            ::= { hwCBQoSFrPvcCbqRunInfoEntry 1 }

        hwCBQoSFrPvcCbqDiscard OBJECT-TYPE
            SYNTAX Counter32
            MAX-ACCESS read-only
            STATUS current
            DESCRIPTION
                "The number of discarded packets which coundn't be enqueued."
            ::= { hwCBQoSFrPvcCbqRunInfoEntry 2 }

        hwCBQoSFrPvcCbqEfQueueSize OBJECT-TYPE
            SYNTAX Integer32
            MAX-ACCESS read-only
            STATUS current
            DESCRIPTION
                "packet number of EF queue"
            ::= { hwCBQoSFrPvcCbqRunInfoEntry 3 }

        hwCBQoSFrPvcCbqAfQueueSize OBJECT-TYPE
            SYNTAX Integer32
            MAX-ACCESS read-only
            STATUS current
            DESCRIPTION
                "packet number of AF queue"
            ::= { hwCBQoSFrPvcCbqRunInfoEntry 4 }

        hwCBQoSFrPvcCbqBeQueueSize OBJECT-TYPE
            SYNTAX Integer32
            MAX-ACCESS read-only
            STATUS current
            DESCRIPTION
                "packet number of BE queue"
            ::= { hwCBQoSFrPvcCbqRunInfoEntry 5 }

        hwCBQoSFrPvcCbqBeActiveQueueNum OBJECT-TYPE
            SYNTAX Integer32
            MAX-ACCESS read-only
            STATUS current
            DESCRIPTION
                "the packet number of Active Be Queue"
            ::= { hwCBQoSFrPvcCbqRunInfoEntry 6 }

        hwCBQoSFrPvcCbqBeMaxActiveQueueNum OBJECT-TYPE
            SYNTAX Integer32
            MAX-ACCESS read-only
            STATUS current
            DESCRIPTION
                "the max packet number of Active Be Queue"
            ::= { hwCBQoSFrPvcCbqRunInfoEntry 7 }

        hwCBQoSFrPvcCbqBeTotalQueueNum OBJECT-TYPE
            SYNTAX Integer32
            MAX-ACCESS read-only
            STATUS current
            DESCRIPTION
                "the total packet number of Be Queue"
            ::= { hwCBQoSFrPvcCbqRunInfoEntry 8 }

        hwCBQoSFrPvcCbqAfAllocatedQueueNum OBJECT-TYPE
            SYNTAX Integer32
            MAX-ACCESS read-only
            STATUS current
            DESCRIPTION
                "the Allocated packet number of Af Queue"
            ::= { hwCBQoSFrPvcCbqRunInfoEntry 9 }

-- Class match statistics

        hwCBQoSFrPvcClassMatchRunInfoTable OBJECT-TYPE
            SYNTAX SEQUENCE OF HwCBQoSFrPvcClassMatchRunInfoEntry
            MAX-ACCESS not-accessible
            STATUS current
            DESCRIPTION
                "A table of Running statistics for matching a classifier
                in a QoS policy applied on FR PVC."
            ::= { hwCBQoSFrPvcStaticsObjects 2 }

        hwCBQoSFrPvcClassMatchRunInfoEntry OBJECT-TYPE
            SYNTAX HwCBQoSFrPvcClassMatchRunInfoEntry
            MAX-ACCESS not-accessible
            STATUS current
            DESCRIPTION
                "Classifier matching statistics entry."
            INDEX { hwCBQoSFrPvcApplyPolicyIfIndex, hwCBQoSFrPvcApplyPolicyDlciNum,
                    hwCBQoSFrPvcApplyPolicyDirection, hwCBQoSPolicyClassIndex }
            ::= { hwCBQoSFrPvcClassMatchRunInfoTable 1 }

        HwCBQoSFrPvcClassMatchRunInfoEntry ::=
            SEQUENCE {
                hwCBQoSFrPvcClassMatchedPackets
                    Counter32,
                hwCBQoSFrPvcClassMatchedBytes
                    Counter32,
                hwCBQoSFrPvcClassAverageRate
                    Counter64
             }

        hwCBQoSFrPvcClassMatchedPackets OBJECT-TYPE
            SYNTAX Counter32
            MAX-ACCESS read-only
            STATUS current
            DESCRIPTION
                "Number of packets matching a class in a QoS policy."
            ::= { hwCBQoSFrPvcClassMatchRunInfoEntry 1 }

        hwCBQoSFrPvcClassMatchedBytes OBJECT-TYPE
            SYNTAX Counter32
            MAX-ACCESS read-only
            STATUS current
            DESCRIPTION
                "Number of bytes matching a class in a QoS policy."
            ::= { hwCBQoSFrPvcClassMatchRunInfoEntry 2 }

        hwCBQoSFrPvcClassAverageRate OBJECT-TYPE
            SYNTAX Counter64
            MAX-ACCESS read-only
            STATUS current
            DESCRIPTION
                "Average rate matching a class of the last 5 minutes."
            ::= { hwCBQoSFrPvcClassMatchRunInfoEntry 3 }

-- CAR statistics
        hwCBQoSFrPvcCarRunInfoTable OBJECT-TYPE
            SYNTAX SEQUENCE OF HwCBQoSFrPvcCarRunInfoEntry
            MAX-ACCESS not-accessible
            STATUS current
            DESCRIPTION
                "A table of Running statistics for CAR
                in a QoS policy applied on FR PVC."
            ::= { hwCBQoSFrPvcStaticsObjects 3 }

        hwCBQoSFrPvcCarRunInfoEntry OBJECT-TYPE
            SYNTAX HwCBQoSFrPvcCarRunInfoEntry
            MAX-ACCESS not-accessible
            STATUS current
            DESCRIPTION
                "CAR statistics entry."
            INDEX { hwCBQoSFrPvcApplyPolicyIfIndex, hwCBQoSFrPvcApplyPolicyDlciNum,
                    hwCBQoSFrPvcApplyPolicyDirection, hwCBQoSPolicyClassIndex }
            ::= { hwCBQoSFrPvcCarRunInfoTable 1 }

        HwCBQoSFrPvcCarRunInfoEntry ::=
            SEQUENCE {
                hwCBQoSFrPvcCarConformPackets
                    Counter32,
                hwCBQoSFrPvcCarConformBytes
                    Counter32,
                hwCBQoSFrPvcCarExceedPackets
                    Counter32,
                hwCBQoSFrPvcCarExceedBytes
                    Counter32
            }

        hwCBQoSFrPvcCarConformPackets OBJECT-TYPE
            SYNTAX Counter32
            MAX-ACCESS read-only
            STATUS current
            DESCRIPTION
                "Number of packets conform CIR."
            ::= { hwCBQoSFrPvcCarRunInfoEntry 1 }

        hwCBQoSFrPvcCarConformBytes OBJECT-TYPE
            SYNTAX Counter32
            MAX-ACCESS read-only
            STATUS current
            DESCRIPTION
                "Number of bytes conform CIR."
            ::= { hwCBQoSFrPvcCarRunInfoEntry 2 }

        hwCBQoSFrPvcCarExceedPackets OBJECT-TYPE
            SYNTAX Counter32
            MAX-ACCESS read-only
            STATUS current
            DESCRIPTION
                "Number of packets exceed CIR."
            ::= { hwCBQoSFrPvcCarRunInfoEntry 3 }

        hwCBQoSFrPvcCarExceedBytes OBJECT-TYPE
            SYNTAX Counter32
            MAX-ACCESS read-only
            STATUS current
            DESCRIPTION
                "Number of bytes exceed CIR."
            ::= { hwCBQoSFrPvcCarRunInfoEntry 4 }

-- GTS statistics
        hwCBQoSFrPvcGtsRunInfoTable OBJECT-TYPE
            SYNTAX SEQUENCE OF HwCBQoSFrPvcGtsRunInfoEntry
            MAX-ACCESS not-accessible
            STATUS current
            DESCRIPTION
                "A table of Running statistics for GTS
                in a QoS policy applied on FR PVC."
            ::= { hwCBQoSFrPvcStaticsObjects 4 }

        hwCBQoSFrPvcGtsRunInfoEntry OBJECT-TYPE
            SYNTAX HwCBQoSFrPvcGtsRunInfoEntry
            MAX-ACCESS not-accessible
            STATUS current
            DESCRIPTION
                "GTS statistics entry."
            INDEX { hwCBQoSFrPvcApplyPolicyIfIndex, hwCBQoSFrPvcApplyPolicyDlciNum,
                    hwCBQoSFrPvcApplyPolicyDirection, hwCBQoSPolicyClassIndex }
            ::= { hwCBQoSFrPvcGtsRunInfoTable 1 }

        HwCBQoSFrPvcGtsRunInfoEntry ::=
            SEQUENCE {
                hwCBQoSFrPvcGtsPassedPackets
                    Counter32,
                hwCBQoSFrPvcGtsPassedBytes
                    Counter32,
                hwCBQoSFrPvcGtsDiscardedPackets
                    Counter32,
                hwCBQoSFrPvcGtsDiscardedBytes
                    Counter32,
                hwCBQoSFrPvcGtsDelayedPackets
                    Counter32,
                hwCBQoSFrPvcGtsDelayedBytes
                    Counter32,
                hwCBQoSFrPvcGtsQueueSize
                    Integer32
            }

        hwCBQoSFrPvcGtsPassedPackets OBJECT-TYPE
            SYNTAX Counter32
            MAX-ACCESS read-only
            STATUS current
            DESCRIPTION
                "Number of packets passed by GTS."
            ::= { hwCBQoSFrPvcGtsRunInfoEntry 1 }

        hwCBQoSFrPvcGtsPassedBytes OBJECT-TYPE
            SYNTAX Counter32
            MAX-ACCESS read-only
            STATUS current
            DESCRIPTION
                "Number of bytes passed by GTS."
            ::= { hwCBQoSFrPvcGtsRunInfoEntry 2 }

        hwCBQoSFrPvcGtsDiscardedPackets OBJECT-TYPE
            SYNTAX Counter32
            MAX-ACCESS read-only
            STATUS current
            DESCRIPTION
                "Number of packets discarded by GTS."
            ::= { hwCBQoSFrPvcGtsRunInfoEntry 3 }

        hwCBQoSFrPvcGtsDiscardedBytes OBJECT-TYPE
            SYNTAX Counter32
            MAX-ACCESS read-only
            STATUS current
            DESCRIPTION
                "Number of bytes discarded by GTS."
            ::= { hwCBQoSFrPvcGtsRunInfoEntry 4 }

        hwCBQoSFrPvcGtsDelayedPackets OBJECT-TYPE
            SYNTAX Counter32
            MAX-ACCESS read-only
            STATUS current
            DESCRIPTION
                "Number of packets delayed by GTS."
            ::= { hwCBQoSFrPvcGtsRunInfoEntry 5 }

        hwCBQoSFrPvcGtsDelayedBytes OBJECT-TYPE
            SYNTAX Counter32
            MAX-ACCESS read-only
            STATUS current
            DESCRIPTION
                "Number of bytes delayed by GTS."
            ::= { hwCBQoSFrPvcGtsRunInfoEntry 6 }

        hwCBQoSFrPvcGtsQueueSize OBJECT-TYPE
            SYNTAX Integer32
            MAX-ACCESS read-only
            STATUS current
            DESCRIPTION
                "packet number of GTS queue."
            ::= { hwCBQoSFrPvcGtsRunInfoEntry 7 }

-- Remark statistics
        hwCBQoSFrPvcRemarkRunInfoTable OBJECT-TYPE
            SYNTAX SEQUENCE OF HwCBQoSFrPvcRemarkRunInfoEntry
            MAX-ACCESS not-accessible
            STATUS current
            DESCRIPTION
                "A table of Running statistics for remarking
                in a QoS policy applied on FR PVC."
            ::= { hwCBQoSFrPvcStaticsObjects 5 }

        hwCBQoSFrPvcRemarkRunInfoEntry OBJECT-TYPE
            SYNTAX HwCBQoSFrPvcRemarkRunInfoEntry
            MAX-ACCESS not-accessible
            STATUS current
            DESCRIPTION
                "Remarking statistics entry."
            INDEX { hwCBQoSFrPvcApplyPolicyIfIndex, hwCBQoSFrPvcApplyPolicyDlciNum,
                    hwCBQoSFrPvcApplyPolicyDirection, hwCBQoSPolicyClassIndex }
            ::= { hwCBQoSFrPvcRemarkRunInfoTable 1 }

        HwCBQoSFrPvcRemarkRunInfoEntry ::=
            SEQUENCE {
                hwCBQoSFrPvcRemarkedPackets
                    Counter32
            }

        hwCBQoSFrPvcRemarkedPackets OBJECT-TYPE
            SYNTAX Counter32
            MAX-ACCESS read-only
            STATUS current
            DESCRIPTION
                "Number of packets remarked."
            ::= { hwCBQoSFrPvcRemarkRunInfoEntry 1 }

-- Queue statistics
        hwCBQoSFrPvcQueueRunInfoTable OBJECT-TYPE
            SYNTAX SEQUENCE OF HwCBQoSFrPvcQueueRunInfoEntry
            MAX-ACCESS not-accessible
            STATUS current
            DESCRIPTION
                "A table of Running statistics for queue
                in a QoS policy applied on FR PVC."
            ::= { hwCBQoSFrPvcStaticsObjects 6 }

        hwCBQoSFrPvcQueueRunInfoEntry OBJECT-TYPE
            SYNTAX HwCBQoSFrPvcQueueRunInfoEntry
            MAX-ACCESS not-accessible
            STATUS current
            DESCRIPTION
                "Queue statistics entry."
            INDEX { hwCBQoSFrPvcApplyPolicyIfIndex, hwCBQoSFrPvcApplyPolicyDlciNum,
                    hwCBQoSFrPvcApplyPolicyDirection, hwCBQoSPolicyClassIndex }
            ::= { hwCBQoSFrPvcQueueRunInfoTable 1 }

        HwCBQoSFrPvcQueueRunInfoEntry ::=
            SEQUENCE {
                hwCBQoSFrPvcQueueMatchedPackets
                    Counter32,
                hwCBQoSFrPvcQueueMatchedBytes
                    Counter32,
                hwCBQoSFrPvcQueueEnqueuedPackets
                    Counter32,
                hwCBQoSFrPvcQueueEnqueuedBytes
                    Counter32,
                hwCBQoSFrPvcQueueDiscardedPackets
                    Counter32,
                hwCBQoSFrPvcQueueDiscardedBytes
                    Counter32
            }

        hwCBQoSFrPvcQueueMatchedPackets OBJECT-TYPE
            SYNTAX Counter32
            MAX-ACCESS read-only
            STATUS current
            DESCRIPTION
                "Number of packets matched to enqueue."
            ::= { hwCBQoSFrPvcQueueRunInfoEntry 1 }

        hwCBQoSFrPvcQueueMatchedBytes OBJECT-TYPE
            SYNTAX Counter32
            MAX-ACCESS read-only
            STATUS current
            DESCRIPTION
                "Number of bytes matched to enqueue."
            ::= { hwCBQoSFrPvcQueueRunInfoEntry 2 }

        hwCBQoSFrPvcQueueEnqueuedPackets OBJECT-TYPE
            SYNTAX Counter32
            MAX-ACCESS read-only
            STATUS current
            DESCRIPTION
                "Number of packets enqueued."
            ::= { hwCBQoSFrPvcQueueRunInfoEntry 3 }

        hwCBQoSFrPvcQueueEnqueuedBytes OBJECT-TYPE
            SYNTAX Counter32
            MAX-ACCESS read-only
            STATUS current
            DESCRIPTION
                "Number of bytes enqueued."
            ::= { hwCBQoSFrPvcQueueRunInfoEntry 4 }

        hwCBQoSFrPvcQueueDiscardedPackets OBJECT-TYPE
            SYNTAX Counter32
            MAX-ACCESS read-only
            STATUS current
            DESCRIPTION
                "Number of packets discarded when enqueued by discard method."
            ::= { hwCBQoSFrPvcQueueRunInfoEntry 5 }

        hwCBQoSFrPvcQueueDiscardedBytes OBJECT-TYPE
            SYNTAX Counter32
            MAX-ACCESS read-only
            STATUS current
            DESCRIPTION
                "Number of bytes discarded when enqueued by discard method."
            ::= { hwCBQoSFrPvcQueueRunInfoEntry 6 }

-- WRED statistics
        hwCBQoSFrPvcWredRunInfoTable OBJECT-TYPE
            SYNTAX SEQUENCE OF HwCBQoSFrPvcWredRunInfoEntry
            MAX-ACCESS not-accessible
            STATUS current
            DESCRIPTION
                "A table of Running statistics for WRED
                in a QoS policy applied on FR PVC."
            ::= { hwCBQoSFrPvcStaticsObjects 7 }

        hwCBQoSFrPvcWredRunInfoEntry OBJECT-TYPE
            SYNTAX HwCBQoSFrPvcWredRunInfoEntry
            MAX-ACCESS not-accessible
            STATUS current
            DESCRIPTION
                "WRED statistics entry."
            INDEX { hwCBQoSFrPvcApplyPolicyIfIndex, hwCBQoSFrPvcApplyPolicyDlciNum,
                    hwCBQoSFrPvcApplyPolicyDirection, hwCBQoSPolicyClassIndex,
                    hwCBQoSWredClassValue}
            ::= { hwCBQoSFrPvcWredRunInfoTable 1 }

        HwCBQoSFrPvcWredRunInfoEntry ::=
            SEQUENCE {
                hwCBQoSFrPvcWredRandomDiscardedPackets
                    Counter32,
                hwCBQoSFrPvcWredTailDiscardedPackets
                    Counter32
             }

        hwCBQoSFrPvcWredRandomDiscardedPackets OBJECT-TYPE
            SYNTAX Counter32
            MAX-ACCESS read-only
            STATUS current
            DESCRIPTION
                "Number of packets randomly discarded by WRED."
            ::= { hwCBQoSFrPvcWredRunInfoEntry 1 }

        hwCBQoSFrPvcWredTailDiscardedPackets OBJECT-TYPE
            SYNTAX Counter32
            MAX-ACCESS read-only
            STATUS current
            DESCRIPTION
                "Number of packets tail-discarded by WRED."
            ::= { hwCBQoSFrPvcWredRunInfoEntry 2 }


--  LR statistics
        hwCBQoSFrPvcLrRunInfoTable OBJECT-TYPE
            SYNTAX SEQUENCE OF HwCBQoSFrPvcLrRunInfoEntry
            MAX-ACCESS not-accessible
            STATUS current
            DESCRIPTION
                "A table of Running statistics for LR
                in a QoS policy applied on FR PVC."
            ::= { hwCBQoSFrPvcStaticsObjects 8 }


        hwCBQoSFrPvcLrRunInfoEntry OBJECT-TYPE
            SYNTAX HwCBQoSFrPvcLrRunInfoEntry
            MAX-ACCESS not-accessible
            STATUS current
            DESCRIPTION
                "LR statistics entry."
            INDEX { hwCBQoSFrPvcApplyPolicyIfIndex, hwCBQoSFrPvcApplyPolicyDlciNum, hwCBQoSFrPvcApplyPolicyDirection, hwCBQoSPolicyClassIndex }
            ::= { hwCBQoSFrPvcLrRunInfoTable 1 }


        HwCBQoSFrPvcLrRunInfoEntry ::=
            SEQUENCE {
                hwCBQoSFrPvcLrPassedPackets
                    Counter32,
                hwCBQoSFrPvcLrPassedBytes
                    Counter32,
                hwCBQoSFrPvcLrDiscardedPackets
                    Counter32,
                hwCBQoSFrPvcLrDiscardedBytes
                    Counter32,
                hwCBQoSFrPvcLrDelayedPackets
                    Counter32,
                hwCBQoSFrPvcLrDelayedBytes
                    Counter32,
                hwCBQoSFrPvcLrQueueSize
                    Integer32
             }

        hwCBQoSFrPvcLrPassedPackets OBJECT-TYPE
            SYNTAX Counter32
            MAX-ACCESS read-only
            STATUS current
            DESCRIPTION
                "Number of packets passed by LR."
            ::= { hwCBQoSFrPvcLrRunInfoEntry 1 }


        hwCBQoSFrPvcLrPassedBytes OBJECT-TYPE
            SYNTAX Counter32
            MAX-ACCESS read-only
            STATUS current
            DESCRIPTION
                "Number of bytes passed by LR."
            ::= { hwCBQoSFrPvcLrRunInfoEntry 2 }


        hwCBQoSFrPvcLrDiscardedPackets OBJECT-TYPE
            SYNTAX Counter32
            MAX-ACCESS read-only
            STATUS current
            DESCRIPTION
                "Number of packets discarded by LR."
            ::= { hwCBQoSFrPvcLrRunInfoEntry 3 }


        hwCBQoSFrPvcLrDiscardedBytes OBJECT-TYPE
            SYNTAX Counter32
            MAX-ACCESS read-only
            STATUS current
            DESCRIPTION
                "Number of bytes discarded by LR."
            ::= { hwCBQoSFrPvcLrRunInfoEntry 4 }


        hwCBQoSFrPvcLrDelayedPackets OBJECT-TYPE
            SYNTAX Counter32
            MAX-ACCESS read-only
            STATUS current
            DESCRIPTION
                "Number of packets delayed by LR."
            ::= { hwCBQoSFrPvcLrRunInfoEntry 5 }


        hwCBQoSFrPvcLrDelayedBytes OBJECT-TYPE
            SYNTAX Counter32
            MAX-ACCESS read-only
            STATUS current
            DESCRIPTION
                "Number of bytes delayed by LR."
            ::= { hwCBQoSFrPvcLrRunInfoEntry 6 }

        hwCBQoSFrPvcLrQueueSize OBJECT-TYPE
            SYNTAX Integer32
            MAX-ACCESS read-only
            STATUS current
            DESCRIPTION
                "Packet number of LR queue"
            ::= { hwCBQoSFrPvcLrRunInfoEntry 7 }


-- Ethernet Interface VLAN: policy Running statistics information

        hwCBQoSIfVlanStaticsObjects OBJECT IDENTIFIER ::= { hwCBQoSApplyPolicyStaticsObjects 4 }

-- Class match statistics
        hwCBQoSIfVlanClassMatchRunInfoTable OBJECT-TYPE
            SYNTAX SEQUENCE OF HwCBQoSIfVlanClassMatchRunInfoEntry
            MAX-ACCESS not-accessible
            STATUS current
            DESCRIPTION
                "A table of Running statistics for matching a classifier
                in a QoS policy applied on ethernet vlan."
            ::= { hwCBQoSIfVlanStaticsObjects 1 }

        hwCBQoSIfVlanClassMatchRunInfoEntry OBJECT-TYPE
            SYNTAX HwCBQoSIfVlanClassMatchRunInfoEntry
            MAX-ACCESS not-accessible
            STATUS current
            DESCRIPTION
                "Classifier matching statistics entry."
            INDEX { hwCBQoSIfVlanApplyPolicyIfIndex, hwCBQoSIfVlanApplyPolicyVlanid,
                    hwCBQoSIfVlanApplyPolicyDirection, hwCBQoSPolicyClassIndex }
            ::= { hwCBQoSIfVlanClassMatchRunInfoTable 1 }

        HwCBQoSIfVlanClassMatchRunInfoEntry ::=
            SEQUENCE {
                hwCBQoSIfVlanClassMatchedPackets
                    Counter32
             }

        hwCBQoSIfVlanClassMatchedPackets OBJECT-TYPE
            SYNTAX Counter32
            MAX-ACCESS read-only
            STATUS current
            DESCRIPTION
                "Number of packets matching a class in a QoS policy."
            ::= { hwCBQoSIfVlanClassMatchRunInfoEntry 1 }

END
