-- ============================================================================
-- Copyright (C) 2005 by  HUAWEI 3COM TECHNOLOGIES.  All rights reserved.
-- Description:  This mib is used for configuration of ATM-DXI.
--               include :1.ATM-DXI PVC
--                        2.ATM-DXI MAP
-- Reference:
-- Version: V1.0
-- History:
--   V1.0 2005/04/14 created by Liguanmin
-- ============================================================================
H3C-ATM-DXI-MIB DEFINITIONS ::= BEGIN

      IMPORTS
                h3cCommon
                    FROM HUAWEI-3COM-OID-MIB
                ifIndex
                    FROM RFC1213-MIB
                OBJECT-GROUP,MODULE-COMPLIANCE
                    FROM SNMPv2-CONF
                Integer32, OBJECT-TYPE, MODULE-IDENTITY
                    FROM SNMPv2-SMI
                InetAddressType,InetAddress
                    FROM INET-ADDRESS-MIB
                RowStatus
                    FROM SNMPv2-TC;

      h3cAtmDxi MODULE-IDENTITY
                LAST-UPDATED "200504141518Z"            -- 14 April, 2005 at 15:18 GMT
                ORGANIZATION
                        "Huawei-3Com Technologies Co., Ltd."
                CONTACT-INFO
                        "Platform Team Huawei 3Com Technologies Co., Ltd.
                         Hai-Dian District Beijing P.R. China
                         http://www.huawei-3com.com
                         Zip:100085"
                DESCRIPTION
                        "This MIB contains objects to manage configuration of ATM-DXI.
                         There are no constraints on this MIB."
                REVISION "200504141518Z"                -- 14 April, 2005 at 15:18 GMT
                DESCRIPTION
                        "The initial revision of this MIB module."
                ::= { h3cCommon 49 }

--
-- Node definitions
--
        h3cAtmDxiScalarGroup OBJECT IDENTIFIER ::= { h3cAtmDxi 1 }

        h3cAtmDxiConfMode OBJECT-TYPE
                SYNTAX INTEGER
                        {
                        mode1a(1),
                        mode1b(2),
                        mode2(3)
                        }
                MAX-ACCESS read-only
                STATUS current
                DESCRIPTION
                        "This node identifies the ATM-DXI mode being
                        used at the ATM-DXI port."
                ::= { h3cAtmDxiScalarGroup 1 }


        h3cAtmDxiIfObjects OBJECT IDENTIFIER ::= { h3cAtmDxi 2 }


        h3cAtmDxiPvcTable OBJECT-TYPE
                SYNTAX SEQUENCE OF H3cAtmDxiPvcEntry
                MAX-ACCESS not-accessible
                STATUS current
                DESCRIPTION
                        "This table describes information of PVC in ATM-DXI interface."
                ::= { h3cAtmDxiIfObjects 1 }


        h3cAtmDxiPvcEntry OBJECT-TYPE
                SYNTAX H3cAtmDxiPvcEntry
                MAX-ACCESS not-accessible
                STATUS current
                DESCRIPTION
                        "The entry of h3cAtmDxiPvcTable."
                INDEX { ifIndex, h3cAtmDxiPvcVpi, h3cAtmDxiPvcVci }
                ::= { h3cAtmDxiPvcTable 1 }


        H3cAtmDxiPvcEntry ::=
                SEQUENCE {
                        h3cAtmDxiPvcVpi
                                Integer32,
                        h3cAtmDxiPvcVci
                                Integer32,
                        h3cAtmDxiPvcDFA
                                Integer32,
                        h3cAtmDxiPvcEncType
                                INTEGER,
                        h3cAtmDxiPvcMapCount
                                Integer32,
                        h3cAtmDxiPvcRowStatus
                                RowStatus
                 }


        h3cAtmDxiPvcVpi OBJECT-TYPE
                SYNTAX Integer32 (0..15)
                MAX-ACCESS not-accessible
                STATUS current
                DESCRIPTION
                        "The value of VPI.  It can't be 0 if h3cAtmDxiPvcVci is 0."
                ::= { h3cAtmDxiPvcEntry 1 }


        h3cAtmDxiPvcVci OBJECT-TYPE
                SYNTAX Integer32 (0..63)
                MAX-ACCESS not-accessible
                STATUS current
                DESCRIPTION
                        "The value of VCI.  It can't be 0 if h3cAtmDxiPvcVpi is 0."
                ::= { h3cAtmDxiPvcEntry 2 }


        h3cAtmDxiPvcDFA OBJECT-TYPE
                SYNTAX Integer32
                MAX-ACCESS read-create
                STATUS current
                DESCRIPTION
                        "The index of PVC.  It is equal with vci and VPI.  And this node value
                        is correlate with h3cAtmDxiPvcVpi and h3cAtmDxiPvcVci. "
                ::= { h3cAtmDxiPvcEntry 3 }


        h3cAtmDxiPvcEncType OBJECT-TYPE
                SYNTAX INTEGER
                        {
                        snap(1),
                        nlpid(2),
                        mux(3)
                        }
                MAX-ACCESS read-create
                STATUS current
                DESCRIPTION
                        "Encapsulation type of the frame."
                DEFVAL { snap }
                ::= { h3cAtmDxiPvcEntry 4 }


        h3cAtmDxiPvcMapCount OBJECT-TYPE
                SYNTAX Integer32 (0..32)
                MAX-ACCESS read-create
                STATUS current
                DESCRIPTION
                        "The number of map.  One map can only associate with one PVC, but
                        one PVC can associate with 32 maps.  This node is the map count
                        which one PVC associated with."
                ::= { h3cAtmDxiPvcEntry 5 }


        h3cAtmDxiPvcRowStatus OBJECT-TYPE
                SYNTAX RowStatus
                MAX-ACCESS read-create
                STATUS current
                DESCRIPTION
                        "Only support 'destroy' 'createAndGo' and 'active'."
                ::= { h3cAtmDxiPvcEntry 6 }


        h3cAtmDxiMapTable OBJECT-TYPE
                SYNTAX SEQUENCE OF H3cAtmDxiMapEntry
                MAX-ACCESS not-accessible
                STATUS current
                DESCRIPTION
                        "This table describes PVC map information."
                ::= { h3cAtmDxiIfObjects 2 }


        h3cAtmDxiMapEntry OBJECT-TYPE
                SYNTAX H3cAtmDxiMapEntry
                MAX-ACCESS not-accessible
                STATUS current
                DESCRIPTION
                        "The entry of h3cAtmDxiMapTable."
                INDEX { ifIndex,
                        h3cAtmDxiMapPeerIpType,
                        h3cAtmDxiMapPeerIp,
                        h3cAtmDxiMapPvcVpi,
                        h3cAtmDxiMapPvcVci,
                        h3cAtmDxiMapType
                      }
                ::= { h3cAtmDxiMapTable 1 }


        H3cAtmDxiMapEntry ::=
                SEQUENCE {
                        h3cAtmDxiMapPeerIpType
                                InetAddressType,
                        h3cAtmDxiMapPeerIp
                                InetAddress,
                        h3cAtmDxiMapPvcVpi
                                Integer32,
                        h3cAtmDxiMapPvcVci
                                Integer32,
                        h3cAtmDxiMapType
                                INTEGER,
                        h3cAtmDxiMapInarpTime
                                Integer32,
                        h3cAtmDxiMapBroEnable
                                INTEGER,
                        h3cAtmDxiMapRowStatus
                                RowStatus
                 }

        h3cAtmDxiMapPeerIpType OBJECT-TYPE
                SYNTAX InetAddressType
                MAX-ACCESS not-accessible
                STATUS current
                DESCRIPTION
                        "The type of ip address: IPv4 or IPv6."
                ::= { h3cAtmDxiMapEntry 1 }

        h3cAtmDxiMapPeerIp OBJECT-TYPE
                SYNTAX InetAddress
                MAX-ACCESS not-accessible
                STATUS current
                DESCRIPTION
                        "The peer ip address.  This ip address is the peer ip
                        address which the frame will arrive."
                ::= { h3cAtmDxiMapEntry 2 }

        h3cAtmDxiMapPvcVpi OBJECT-TYPE
                SYNTAX Integer32 (0..15)
                MAX-ACCESS not-accessible
                STATUS current
                DESCRIPTION
                        "The VPI of PVC.  It can't be 0 if h3cAtmDxiMapPvcVci is 0."
                ::= { h3cAtmDxiMapEntry 3 }

        h3cAtmDxiMapPvcVci OBJECT-TYPE
                SYNTAX Integer32 (0..63)
                MAX-ACCESS not-accessible
                STATUS current
                DESCRIPTION
                        "The VCI of PVC.  It can't be 0 if h3cAtmDxiMapPvcVpi is 0."
                ::= { h3cAtmDxiMapEntry 4 }

        h3cAtmDxiMapType OBJECT-TYPE
                SYNTAX INTEGER
                        {
                        address(1),
                        inarp(2),
                        default(3)
                        }
                MAX-ACCESS not-accessible
                STATUS current
                DESCRIPTION
                        "Pvc map type."
                ::= { h3cAtmDxiMapEntry 5 }

        h3cAtmDxiMapInarpTime OBJECT-TYPE
                SYNTAX Integer32 (0 | 5..10)
                MAX-ACCESS read-create
                STATUS current
                DESCRIPTION
                        "The interval time of inarp request.  This node describes
                        the interval time inarp request frame sent.  If the h3cAtmDxiMapType
                        isn't inarp, this value is 0.  Its unit is minute."
                DEFVAL { 10 }
                ::= { h3cAtmDxiMapEntry 6 }

        h3cAtmDxiMapBroEnable OBJECT-TYPE
                SYNTAX INTEGER
                        {
                        enable(1),
                        disable(2)
                        }
                MAX-ACCESS read-create
                STATUS current
                DESCRIPTION
                        "Whether ATM-DXI map enable broadcast or not."
                DEFVAL { 2 }
                ::= { h3cAtmDxiMapEntry 7 }

        h3cAtmDxiMapRowStatus OBJECT-TYPE
                SYNTAX RowStatus
                MAX-ACCESS read-create
                STATUS current
                DESCRIPTION
                        "Only support 'destroy', 'createAndGo' and 'active'."
                ::= { h3cAtmDxiMapEntry 8 }


        h3cAtmDxiConformance OBJECT IDENTIFIER ::= { h3cAtmDxi 3 }

        h3cAtmDxiCompliances OBJECT IDENTIFIER ::= { h3cAtmDxiConformance 1 }

        h3cAtmDxiCompliance MODULE-COMPLIANCE
               STATUS current
               DESCRIPTION
                       "The compliance statement."
               MODULE
               MANDATORY-GROUPS { h3cPVCMAPGroup }
               GROUP h3cAtmDxiGeneralGroup
               DESCRIPTION
                       "If ATM-DXI protocol supports other ATM-DXI modes,
                       this group must be supported."
               ::= { h3cAtmDxiCompliances 1 }

        h3cAtmDxiGroup OBJECT IDENTIFIER ::= { h3cAtmDxiConformance 2 }

        h3cPVCMAPGroup OBJECT-GROUP
                OBJECTS { h3cAtmDxiPvcDFA, h3cAtmDxiPvcEncType, h3cAtmDxiPvcMapCount,
                          h3cAtmDxiPvcRowStatus, h3cAtmDxiMapBroEnable, h3cAtmDxiMapInarpTime,
                          h3cAtmDxiMapRowStatus }
                STATUS current
                DESCRIPTION
                        "This group includes nodes which are associated with interface."
                ::= { h3cAtmDxiGroup 1 }

        h3cAtmDxiGeneralGroup OBJECT-GROUP
                OBJECTS { h3cAtmDxiConfMode }
                STATUS current
                DESCRIPTION
                        "This group includes the general nodes about ATM-DXI."
                ::= { h3cAtmDxiGroup 2 }

END
