-- =============================================================================
-- Copyright (C) 2002-2003 by  HUAWEI TECHNOLOGIES. All rights reserved.
--
-- Description:MPLS-BGP-VPN-MIB 
-- Reference:This mib was extracted from Draft-ietf-mpls-ldp-mib-01
-- Version: V1.6
-- History:
--  VERSION    AUTHOR/          Change Description
--  OLD/NEW     DATE
--                                                  
--  #/1.1     Lingesh M        + Initial create. 
--             27/08/99
--  #/1.2     27/09/99         + Replaced the MIB objects
--                                  - hwMplsLdpLsrMaxIngressCrlspTnls
--                                  - hwMplsLdpLsrMaxInbetwnCrlspTnls
--                               with hwMplsLdpLsrMaxCrlspTnls
--  1.2/1.3   19/10/99         + Added hwMplsLdpPeerType in Peer Table.
--            04/10/99         + Added hwMplsLdpEntityIfTable.
--  1.3/1.4   23/11/99         + Added mib object for Hello Hold Time in Entity
--                               Table, modified Cr-lsp Tnl index of type
--                               read-create to not-accessible.
--                             + Removed hwMplsLdpSessionRowStatus mib-object.
--  
--   1.1      03/01/2k         + Huawei MPLS Release 1.0.0.0
--             Naren             
-- 
--   1.2      27/01/2k         + Modified for MPLS Implementation for Huawei
--             Naren             Following objects are added in the Incarnation table
--                                 hwMplsLdpLsrMaxVcmCapability                  
--                                 hwMplsLdpLsrVcmPathVecInAllLblMapPresent      
--                                 hwMplsLdpLsrRequestRetrytimerValue            
--                                 hwMplsLdpLsrNumOfRequestRetryAttempts         
--                               Following Notifications are added
--                                 hwMplsLdpIncarnUpEventFailure
--                                 hwMplsLdpIncarnDownEventFailure
--                                 hwMplsLdpEntityUpEventFailure
--                                 hwMplsLdpEntityDownEventFailure
-- 
--   1.3      03/04/2k         + Changed FS related identification to hw 
--             David             related identification.	
--   1.4      03/14/2003       add hwMplsLdpSessionUpEventFailure and hwMplsLdpSessionDownEventFailure
--   V1.5 2004-10-12 updated by gaolong
--        Change SYNTAX clause value from INTEGER to Unsigned because the value range is (1..4294967295).
--        Change MAX-ACCESS clause value of hwMplsLdpCrlspTnlIndex to accessible-for-notify
--        because this index node is used when sending notification.
--   V1.6 2004-11-5  updated by liuxiaolong
--        Change DEFVAL clause value of hwMplsLdpLsrHopCountLimit to 32.
-- ====================================================================================
--
-- Full Copyright Notice of the mib that was extracted from Draft-ietf-mpls-ldp-mib-01 as follows：
--
--Copyright (C) The Internet Society (1999). All Rights Reserved.
--
--
--   This document and translations of it may be copied and furnished to
--   others, and derivative works that comment on or otherwise explain it
--   or assist in its implementation may be prepared, copied, published
--   and distributed, in whole or in part, without restriction of any
--   kind, provided that the above copyright notice and this paragraph are
--   included on all such copies and derivative works.  However, this
--   document itself may not be modified in any way, such as by removing
--   the copyright notice or references to the Internet Society or other
--   Internet organizations, except as needed for the  purpose of
--   developing Internet standards in which case the procedures for
--   copyrights defined in the Internet Standards process must be
--   followed, or as required to translate it into languages other than
--   English.
--
--   The limited permissions granted above are perpetual and will not be
--   revoked by the Internet Society or its successors or assigns.
--
--   This document and the information contained herein is provided on an
--   "AS IS" basis and THE INTERNET SOCIETY AND THE INTERNET ENGINEERING
--   TASK FORCE DISCLAIMS ALL WARRANTIES, EXPRESS OR IMPLIED, INCLUDING
--   BUT NOT LIMITED TO ANY WARRANTY THAT THE USE OF THE INFORMATION
--   HEREIN WILL NOT INFRINGE ANY RIGHTS OR ANY IMPLIED WARRANTIES OF
--   MERCHANTABILITY OR FITNESS FOR A PARTICULAR PURPOSE.
--
--  HuaweiMPLS Label Distribution Protocol MIB Definitions
HUAWEI-MPLS-LDP-MIB DEFINITIONS ::= BEGIN

     IMPORTS                  
         huaweiMgmt,hwMpls
             FROM HUAWEI-3COM-OID-MIB
         OBJECT-TYPE, MODULE-IDENTITY, NOTIFICATION-TYPE,
         Integer32, Counter32, Unsigned32,IpAddress
             FROM SNMPv2-SMI
         MODULE-COMPLIANCE, OBJECT-GROUP, NOTIFICATION-GROUP
             FROM SNMPv2-CONF
         TEXTUAL-CONVENTION, TruthValue, RowStatus, TimeInterval
             FROM SNMPv2-TC;
             
     hwMplsLdp MODULE-IDENTITY
         LAST-UPDATED "9906301200Z"     -- June 30, 1999 at 12:00 GMT
         ORGANIZATION "HuaweiMPLS Working Group"
         CONTACT-INFO "S. Manikantan,
                       Huawei Software Pvt. Ltd.,
                       481, Mount Road,
                       Nandanam. CHENNAI-35
                       INDIA
                       manis@Huawei.futsoft.com"
         DESCRIPTION  "All rights reserved"
         REVISION     "9611082155Z"
         DESCRIPTION  "The MIB for HuaweiMPLS LDP module.
                       This MIB has been derived from the MPLS Working 
                       group LDP MIB <drst-ietf-mpls-ldp-mib-01.txt> and
                       MPLS Working group TE MIB <draft-ietf-mpls-te-mib
                       -01.txt>."

         ::= { hwMpls 2 }

     --********************************************************************
     -- MPLS LDP Textual Conventions
     --********************************************************************
     --

           DisplayString ::=
               OCTET STRING
          -- This data type is used to model textual information taken
          -- from the NVT ASCII character set.  By convention, objects
          -- with this syntax are declared as having
          --
                (SIZE (0..255))

           PhysAddress ::=
               OCTET STRING
          -- This data type is used to model media addresses.  For many
          -- types of media, this will be in a binary representation.
          -- For example, an ethernet address would be represented as
          -- a string of 6 octets.

	BitRate ::= INTEGER
	
	BurstSize ::= INTEGER
	
	
     MplsLsrIdentifier ::= TEXTUAL-CONVENTION
         STATUS      current
         DESCRIPTION
             "The Label Switch Router (LSR) identifier
             is the first 4 bytes or the IP Address component
             of the Label Distribution Protocol (LDP) identifier."
         SYNTAX      OCTET STRING (SIZE (4))

     MplsLdpGenAddr ::= TEXTUAL-CONVENTION
         STATUS      current
         DESCRIPTION
             "The value of an network layer or data link layer address."
         SYNTAX      OCTET STRING (SIZE (0..64))

     MplsLdpIdentifier ::= TEXTUAL-CONVENTION
         STATUS      current
         DESCRIPTION
             "The LDP identifier is a six octet quantity
             which is used to identify an Label Switch Router
             (LSR) label space.

             The first four octets encode an IP address
             assigned to the LSR, and the last two octets
             identify a specific label space within the LSR."
         SYNTAX      OCTET STRING (SIZE (6))

     AtmVpIdentifier ::= TEXTUAL-CONVENTION
          STATUS      current
          DESCRIPTION
              "The VPI value for a VPL. The value VPI=0 is not
              used for a VPL not associated with a VCL. For ATM
              UNIs supporting VPCs the VPI value ranges from 1
              to 255. For ATM UNIs supporting VCCs the VPI value
              ranges from 0 to 255.  The maximum VPI value
              cannot exceed the value allowable by
              atmInterfaceMaxVpiBits defined in ATM-MIB."
          SYNTAX INTEGER (0..4095)

     AtmVcIdentifier ::= TEXTUAL-CONVENTION
          STATUS      current
          DESCRIPTION
              "The VCI value for a VCL. The maximum VCI value
              cannot exceed the value allowable by
              atmInterfaceMaxVciBits defined in ATM-MIB."
          SYNTAX INTEGER (0..65535)

     AddressFamilyNumbers ::= TEXTUAL-CONVENTION
        STATUS        current
        DESCRIPTION
            "An address family.  Values are defined in RFC 1700 -
             Assigned Numbers.  All values may not be relevant in
             all contexts when used in this MIB, but are included
             for completeness."
        REFERENCE
            "RFC  1700   Assigned Numbers, Reynolds and  Postel,
             Oct. 1994"
        SYNTAX        INTEGER {
                        other(0),
                         ipv4(1),
                         ipv6(2),
                         nsap(3),
                         hdlc(4),
                         bbn1822(5),
                         ieee802(6),
                         e163(7),
                         e164(8),
                         f69(9),
                         x121(10),
                         ipx(11),
                         appleTalk(12),
                         decnetIV(13),
                         banyanVines(14),
                         e164WithNsap(15)
                     }


     MplsLabel ::= TEXTUAL-CONVENTION
        STATUS        current
        DESCRIPTION
            "Represents an MPLS label.  Note that the contents of
             a  label  field are interpreted in an interface-type
             specific fashion.  For example, the label carried in
             the MPLS shim header is 20 bits wide and the top  12
             bits  must  be zero.  The frame relay label  can  be
             either 10, 17 or 23 bits wide depending on the  size
             of the DLCI field size and the top 22, 15, or 9 bits
             must  be  zero, respectively.  For an ATM interface,
             the  lowermost 16 bits are interpreted as  the  VCI,
             the  next  8 bits as the VPI and the remaining  bits
             must  be  zero.   Also  note the  permissible  label
             values  are  also a function of the interface  type.
             For  example,  the value 3 has special semantics  in
             the  control plane for an MPLS shim header label and
             is not a valid label value in the datapath."
        REFERENCE
            "1.  MPLS  Label Stack Encoding, Rosen et al,  draft-
             ietf-mpls-label-encaps-04.txt, April 1999.
            2.  Use  of  Label Switching on Frame Relay Networks,
             Conta et al, draft-ietf-mpls-fr-03.txt, Nov. 1998."
        SYNTAX INTEGER
     
     MplsTunnelIndex ::= TEXTUAL-CONVENTION
        STATUS        current
        DESCRIPTION
            "Index into mplsTunnelTable."
        SYNTAX        INTEGER (0..65535)
     
     hwMplsLdpObjects       OBJECT IDENTIFIER ::= { hwMplsLdp 1 }
     hwMplsLdpNotifications OBJECT IDENTIFIER ::= { hwMplsLdp 2 }

     --****************************************************************
     -- MPLS LDP Objects
     --****************************************************************

     hwMplsLdpLsrObjects            OBJECT IDENTIFIER ::= { hwMplsLdpObjects 1 }
     hwMplsLdpEntityObjects         OBJECT IDENTIFIER ::= { hwMplsLdpObjects 2 }
     hwMplsLdpPeerObjects           OBJECT IDENTIFIER ::= { hwMplsLdpObjects 3 }
     hwMplsLdpSessionObjects        OBJECT IDENTIFIER ::= { hwMplsLdpObjects 4 }
     hwMplsLdpHelloAdjacencyObjects OBJECT IDENTIFIER ::= { hwMplsLdpObjects 5 }
     hwMplsLdpCrlspTnlObjects       OBJECT IDENTIFIER ::= { hwMplsLdpObjects 6 }

     --
     -- The MPLS Label Distribution Protocol Label Switch Router Objects
     --
     hwMplsLdpLsrIncarnTable OBJECT-TYPE
         SYNTAX      SEQUENCE OF HwMplsLdpLsrIncarnEntry
         MAX-ACCESS  not-accessible
         STATUS      current
         DESCRIPTION
             "HuaweiMPLS provides support for multiple incarnations of the 
              MPLS Stack in a target. The LSR defined in the standard <IETF
              DRAFT> MIB is treated as an incarnation in this MIB. Using a
              local policy the Network administrator must group the LDP Entities
              that should be placed in an incarnation."
         ::= { hwMplsLdpLsrObjects 1 }

     hwMplsLdpLsrIncarnEntry OBJECT-TYPE
         SYNTAX      HwMplsLdpLsrIncarnEntry
         MAX-ACCESS  not-accessible
         STATUS      current
         DESCRIPTION
             "An entry in this table represents an LSR incarnation.
              All the entries in this table are created initially when the 
              LDP is initiated. The row status of each entry will be in 
              'notInService' state initially. The row status must be set to
              'active' after the necessary configurations are complete with
              respect to an incarnation.

              Currenlty the LSR ID of the incarnation is the only mandatory
              parameter that must be set before the rowStatus is set to 
              'active'.

              An LSR Incarnation Entity is uniquely indexed by its Incarnation
              Identifier."
         INDEX       {  hwMplsLdpLsrIncarnID }
         ::= { hwMplsLdpLsrIncarnTable 1 }

     HwMplsLdpLsrIncarnEntry ::= SEQUENCE {
         hwMplsLdpLsrID                                MplsLsrIdentifier,
         hwMplsLdpLsrLoopDetectionPresent              TruthValue,
         hwMplsLdpLsrLoopDetectionAdminStatus          INTEGER,
         hwMplsLdpLsrPathVectorLimit                   INTEGER,
         hwMplsLdpLsrHopCountLimit                     INTEGER,
         hwMplsLdpLsrLoopPreventionPresent             TruthValue,
         hwMplsLdpLsrLoopPreventionAdminStatus         INTEGER,
         hwMplsLdpLsrLabelRetentionMode                INTEGER,
         hwMplsLdpLsrIncarnID                          INTEGER,
         hwMplsLdpLsrMaxLdpEntities                    INTEGER,
         hwMplsLdpLsrMaxLocalPeers                     INTEGER,
         hwMplsLdpLsrMaxRemotePeers                    INTEGER,
         hwMplsLdpLsrMaxIfaces                         INTEGER,
         hwMplsLdpLsrMaxLsps                           INTEGER,
         hwMplsLdpLsrMaxCrlspTnls                      INTEGER,
         hwMplsLdpLsrMaxErhopPerCrlspTnl               INTEGER,
         hwMplsLdpLsrRowStatus                         RowStatus,
         hwMplsLdpLsrMaxVcmCapability                  INTEGER,  
         hwMplsLdpLsrVcmPathVecInAllLblMapPresent      TruthValue,
         hwMplsLdpLsrRequestRetrytimerValue            INTEGER,
         hwMplsLdpLsrNumOfRequestRetryAttempts         INTEGER
    }

     hwMplsLdpLsrID OBJECT-TYPE
         SYNTAX      MplsLsrIdentifier
         MAX-ACCESS  read-write   
         STATUS      current
         DESCRIPTION
             "The LSR's Identifier."
         ::= { hwMplsLdpLsrIncarnEntry 1 }

     hwMplsLdpLsrLoopDetectionPresent OBJECT-TYPE
         SYNTAX      TruthValue
         MAX-ACCESS  read-only
         STATUS      current
         DESCRIPTION
             "A indication of whether this LSR supports loop detection.  A 
             value of 'true' indicates this LSR does support loop detection.  
             A value of 'false' indicates this LSR does not support
             loop detection."
         DEFVAL  { true }
         ::= { hwMplsLdpLsrIncarnEntry 2 }

     hwMplsLdpLsrLoopDetectionAdminStatus OBJECT-TYPE
         SYNTAX      INTEGER {
                         enabled(1),
                         disabled(2)
                     }
         MAX-ACCESS  read-write
         STATUS      current
         DESCRIPTION
             "To enable loop detection the value of this object should be 
             'enabled(1)'.  Otherwise, to turn off loop detection, set this 
             value to 'disabled(2)'."
         DEFVAL  { enabled }
         ::= { hwMplsLdpLsrIncarnEntry 3 }

     hwMplsLdpLsrPathVectorLimit OBJECT-TYPE
         SYNTAX      INTEGER
         MAX-ACCESS  read-write
         STATUS      current
         DESCRIPTION
             "This object only has meaning if hwMplsLdpLsrLoopDetectionPresent 
             has the value of 'true'.

             The value of this object represents the limit of path vectors which
             this LSR uses to treat the message as if it had traversed a loop."
         DEFVAL  { 32 }
         ::= { hwMplsLdpLsrIncarnEntry 4 }

     hwMplsLdpLsrHopCountLimit OBJECT-TYPE
         SYNTAX      INTEGER
         MAX-ACCESS  read-write
         STATUS      current
         DESCRIPTION
             "This object only has meaning if hwMplsLdpLsrLoopDetectionPresent 
             has the value of 'true'.

             The value of this object represents the limit on the Hop Count 
             which this LSR uses to treat the message as if it had traversed a 
             loop."
         DEFVAL  { 32 }
         ::= { hwMplsLdpLsrIncarnEntry 5 }

     hwMplsLdpLsrLoopPreventionPresent OBJECT-TYPE
         SYNTAX      TruthValue
         MAX-ACCESS  read-only
         STATUS      current
         DESCRIPTION
             "A indication of whether this LSR supports loop prevention.  A 
             value of 'true' indicates this LSR does support loop prevention.  
             A value of 'false' indicates this LSR does not support loop 
             prevention.

             Current release of HuaweiMPLS does not provide support to assign
             this MIB object with a value 'true'."
         DEFVAL  { false }
         ::= { hwMplsLdpLsrIncarnEntry 6 }

     hwMplsLdpLsrLoopPreventionAdminStatus OBJECT-TYPE
         SYNTAX      INTEGER {
                         enabled(1),
                         disabled(2)
                     }
         MAX-ACCESS  read-write
         STATUS      current
         DESCRIPTION
             "To enable loop prevention the value of this object should be 
             'enabled(1)'.  Otherwise, to turn off loop prevention, set this 
             value to 'disabled(2)'.

             Current release of HuaweiMPLS does not provide support to assign
             this MIB object with a value 'enabled'."
         DEFVAL  { disabled }
         ::= { hwMplsLdpLsrIncarnEntry 7 }

     hwMplsLdpLsrLabelRetentionMode OBJECT-TYPE
         SYNTAX      INTEGER {
                         conservative(1),
                         liberal(2)
                     }
         MAX-ACCESS  read-write
         STATUS      current
         DESCRIPTION
             "The LSR can be configured to use either conservative or liberal 
              label retention mode.

             If the value of this object is conservative(1) then advertized 
             label mappings are retained only if they will be used to forward 
             packets, i.e. if label came from a valid next hop.  If the value of
             this object is liberal(2) then all advertized label mappings are 
             retained whether they are from a valid next hop or not.

             Current release of HuaweiMPLS does not provide support to assign
             this MIB object with a value 'liberal'."
         DEFVAL  { conservative }
         ::= { hwMplsLdpLsrIncarnEntry 8 }

     hwMplsLdpLsrIncarnID   OBJECT-TYPE
         SYNTAX     INTEGER
         MAX-ACCESS read-only
         STATUS     current
         DESCRIPTION 
             "The incarnation acts as index to all the elements in this
              table."
         ::= { hwMplsLdpLsrIncarnEntry  9 }
 
     hwMplsLdpLsrMaxLdpEntities OBJECT-TYPE
         SYNTAX      INTEGER (1..1024)
         MAX-ACCESS  read-write
         STATUS      current
         DESCRIPTION
             "The maximum number of LDP entities that can be supported by this
              Incarnation."
         ::= { hwMplsLdpLsrIncarnEntry 10 }

     hwMplsLdpLsrMaxLocalPeers OBJECT-TYPE
         SYNTAX      INTEGER (1..1024)
         MAX-ACCESS  read-write
         STATUS      current
         DESCRIPTION
             "The maximum number of Local LDP peers that can be supported by 
              this Incarnation."
         ::= { hwMplsLdpLsrIncarnEntry 11 }

     hwMplsLdpLsrMaxRemotePeers OBJECT-TYPE
         SYNTAX      INTEGER (1..1024)
         MAX-ACCESS  read-write
         STATUS      current
         DESCRIPTION
             "The maximum number of Remote LDP peers that can be supported by 
              this Incarnation."
         ::= { hwMplsLdpLsrIncarnEntry 12 }

     hwMplsLdpLsrMaxIfaces OBJECT-TYPE
         SYNTAX      INTEGER
         MAX-ACCESS  read-write
         STATUS      current
         DESCRIPTION
             "The maximum number of Label enabled Interfaces that can be 
              supported by this Incarnation."
         ::= { hwMplsLdpLsrIncarnEntry 13 }

     hwMplsLdpLsrMaxLsps OBJECT-TYPE
         SYNTAX      INTEGER
         MAX-ACCESS  read-write
         STATUS      current
         DESCRIPTION
             "The maximum number of Label Switched Paths that can be 
              supported by this Incarnation."
         ::= { hwMplsLdpLsrIncarnEntry 14 }

     hwMplsLdpLsrMaxCrlspTnls OBJECT-TYPE
         SYNTAX      INTEGER
         MAX-ACCESS  read-write
         STATUS      current
         DESCRIPTION
             "The maximum number of CRLSPs that can be supported by this
             Incarnation."
         ::= { hwMplsLdpLsrIncarnEntry 15 }


     hwMplsLdpLsrMaxErhopPerCrlspTnl OBJECT-TYPE
         SYNTAX      INTEGER
         MAX-ACCESS  read-write
         STATUS      current
         DESCRIPTION
             " The maximum number of ER-Hops that can be supported in a 
              CRLSP tunnel."
         ::= { hwMplsLdpLsrIncarnEntry 16 }

     hwMplsLdpLsrRowStatus OBJECT-TYPE
         SYNTAX      RowStatus
         MAX-ACCESS  read-create
         STATUS      current
              DESCRIPTION
                  "An object that allows entries in this table to
                  be created and deleted using the
                  RowStatus convention."
         ::= { hwMplsLdpLsrIncarnEntry 17 }

     hwMplsLdpLsrMaxVcmCapability OBJECT-TYPE
         SYNTAX      INTEGER
         MAX-ACCESS  read-write
         STATUS      current
         DESCRIPTION
                  "  "
         ::= { hwMplsLdpLsrIncarnEntry 18 }

     hwMplsLdpLsrVcmPathVecInAllLblMapPresent OBJECT-TYPE
         SYNTAX      TruthValue
         MAX-ACCESS  read-write
         STATUS      current
         DESCRIPTION
                  "  "
         ::= { hwMplsLdpLsrIncarnEntry 19 }

     hwMplsLdpLsrRequestRetrytimerValue  OBJECT-TYPE
         SYNTAX      INTEGER
         MAX-ACCESS  read-write
         STATUS      current
         DESCRIPTION
                  "  "
         ::= { hwMplsLdpLsrIncarnEntry 20 }

     hwMplsLdpLsrNumOfRequestRetryAttempts OBJECT-TYPE
         SYNTAX      INTEGER
         MAX-ACCESS  read-write
         STATUS      current
         DESCRIPTION
                  "  "
         ::= { hwMplsLdpLsrIncarnEntry 21 }


     --
     -- The MPLS Label Distribution Protocol Entity Table
     --

     hwMplsLdpEntityTable OBJECT-TYPE
         SYNTAX      SEQUENCE OF HwMplsLdpEntityEntry
         MAX-ACCESS  not-accessible
         STATUS      current
         DESCRIPTION
             "This table contains information about the
             MPLS Label Distribution Protocol Entities which
             exist on this Label Switch Router (LSR)."
         ::= { hwMplsLdpEntityObjects 1 }

     hwMplsLdpEntityEntry OBJECT-TYPE
         SYNTAX      HwMplsLdpEntityEntry
         MAX-ACCESS  not-accessible
         STATUS      current
         DESCRIPTION
             "An entry in this table represents an LDP entity.
             An entry can be created by a network administrator
             or by an SNMP agent as instructed by LDP.

             An LPD Entity is uniquely indexed by its LPD
             Identifier."
         INDEX       {   hwMplsLdpLsrIncarnID, hwMplsLdpEntityIfIndex  }
         ::= { hwMplsLdpEntityTable 1 }

     HwMplsLdpEntityEntry ::= SEQUENCE {
         hwMplsLdpEntityID                            MplsLdpIdentifier,
         hwMplsLdpEntityLabelSpaceType                INTEGER,
         hwMplsLdpEntityDefVpi                        AtmVpIdentifier,
         hwMplsLdpEntityDefVci                        AtmVcIdentifier,
         hwMplsLdpEntityUnlabTrafVpi                  AtmVpIdentifier,
         hwMplsLdpEntityUnlabTrafVci                  AtmVcIdentifier,
         hwMplsLdpEntityMergeCapability               INTEGER,
         hwMplsLdpEntityVcDirectionality              INTEGER,
         hwMplsLdpEntityWellKnownDiscoveryPort        INTEGER,
         hwMplsLdpEntityMtu                           INTEGER,
         hwMplsLdpEntityKeepAliveHoldTimer            INTEGER,
         hwMplsLdpEntityFailedInitSessionThreshold    INTEGER,
         hwMplsLdpEntityLabelDistributionMethod       INTEGER,
         hwMplsLdpEntityLabelAllocationMethod         INTEGER,
         hwMplsLdpEntityHelloHoldTimer                INTEGER,
         hwMplsLdpEntityRowStatus                     RowStatus
     }

     hwMplsLdpEntityID OBJECT-TYPE
         SYNTAX      MplsLdpIdentifier
         MAX-ACCESS  accessible-for-notify
         STATUS      current
         DESCRIPTION
             "The LDP identifier which uniquely identifies
             the LDP Entity.  This is s six octet quantity
             which is used to identify an Label Switch Router
             (LSR) label space.

             The first four octets encode an IP address
             assigned to the LSR, and the last two octets
             identify a specific label space within the
             LSR."
         REFERENCE
             "LDP Specification, Section on LDP Identifiers."
         ::= { hwMplsLdpEntityEntry 1 }


     hwMplsLdpEntityLabelSpaceType OBJECT-TYPE
         SYNTAX      INTEGER {
                         unknown(1),
                         perInterface(2),
                         perPlatform(3)
                         }
         MAX-ACCESS  read-create
         STATUS      current
         DESCRIPTION
             "The type of label spaces associated with this
             LDP Entity.  The values are

                'unknown(1)'        The type of label space is
                                    not known.

                'perInterface(2)'   The type of label space is
                                    tied to an interface.
                'perPlatform(3)'    The type of label space is
                                    tied to the platform."
         REFERENCE
             "LDP Specification, Section on Label Spaces."
         ::= { hwMplsLdpEntityEntry 2 }

     hwMplsLdpEntityDefVpi OBJECT-TYPE
         SYNTAX      AtmVpIdentifier
         MAX-ACCESS  read-create
         STATUS      current
         DESCRIPTION
             "The Default VPI value used in the label for the default
             VPI."
         ::= { hwMplsLdpEntityEntry 3 }

     hwMplsLdpEntityDefVci OBJECT-TYPE
         SYNTAX      AtmVcIdentifier
         MAX-ACCESS  read-create
         STATUS      current
         DESCRIPTION
             "The Default VCI value used in the label for the default
             VCI."
         ::= { hwMplsLdpEntityEntry  4 }

     hwMplsLdpEntityUnlabTrafVpi OBJECT-TYPE
         SYNTAX      AtmVpIdentifier
         MAX-ACCESS  read-create
         STATUS      current
         DESCRIPTION
             "VPI value of the VCC supporting unlabeled traffic."
         DEFVAL  { 0 }
         ::= { hwMplsLdpEntityEntry 5 }

     hwMplsLdpEntityUnlabTrafVci OBJECT-TYPE
         SYNTAX      AtmVcIdentifier
         MAX-ACCESS  read-create
         STATUS      current
         DESCRIPTION
             "VCI value of the VCC supporting unlabeled traffic."
         DEFVAL  { 32 }
         ::= { hwMplsLdpEntityEntry 6 }

     hwMplsLdpEntityMergeCapability OBJECT-TYPE
         SYNTAX      INTEGER {
                         noMerge(0),
                         vpMerge(1),
                         vcMerge(2),
                         vpVcMerge(3)
                      }
         MAX-ACCESS  read-create
         STATUS      current
         DESCRIPTION
             "Sets the merge capability for this LDP entity.

              Current Release of HuaweiMPLS does not provide support for
              any kind of Merge."
         REFERENCE
             "draft-ietf-mpls-ldp-04.txt, Section 3.5.3"
         ::= { hwMplsLdpEntityEntry 7 }

     hwMplsLdpEntityVcDirectionality OBJECT-TYPE
         SYNTAX      INTEGER {
                         bidirectional(1),
                         unidirectional(2)
                     }
         MAX-ACCESS  read-create
         STATUS      current
         DESCRIPTION
             "Sets the VC directionality for this LDP entity."
         REFERENCE
             "draft-ietf-mpls-ldp-04.txt, Section 3.5.3"
         ::= { hwMplsLdpEntityEntry 8 }

     hwMplsLdpEntityWellKnownDiscoveryPort OBJECT-TYPE
         SYNTAX      INTEGER
         MAX-ACCESS  read-create
         STATUS      current
         DESCRIPTION
             "The well known LDP Discovery Port."
         ::= { hwMplsLdpEntityEntry 9 }

     hwMplsLdpEntityMtu OBJECT-TYPE
         SYNTAX      INTEGER (0..65535)
         MAX-ACCESS  read-create
         STATUS      current
         DESCRIPTION
             "The maximum transmission unit (MTU) that was configured
             for this entity."
         ::= { hwMplsLdpEntityEntry 10 }

     hwMplsLdpEntityKeepAliveHoldTimer OBJECT-TYPE
         SYNTAX      INTEGER (1..65535)
         UNITS       "seconds"
         MAX-ACCESS  read-create
         STATUS      current
         DESCRIPTION
             "The two octet value which is the proposed keep alive hold
             timer for this LDP Entity."
         ::= { hwMplsLdpEntityEntry 11 }

     hwMplsLdpEntityFailedInitSessionThreshold OBJECT-TYPE
         SYNTAX      INTEGER
         MAX-ACCESS  read-create
         STATUS      current
         DESCRIPTION
             "When attempting to establish a session with a
             given Peer, the given LDP Entity should
             send out a notification when exceeding this threshold.
             A value of 0 (zero) for this object
             indicates that the threshold is infinity.
             In other words, a notification will not
             be sent if the value of this object is 0 (zero)."
         ::= { hwMplsLdpEntityEntry 12 }


     hwMplsLdpEntityLabelDistributionMethod OBJECT-TYPE
         SYNTAX      INTEGER {
                        downstreamOnDemand(1),
                        downstreamUnsolicited(2)
                     }
         MAX-ACCESS  read-create
         STATUS      current
         DESCRIPTION
             "For any given LDP session, the method of
             label distribution must be specified.
 
             Current release of HuaweiMPLS does not provide support for
             'downstreamUnsolicited'."
         REFERENCE
             "draft-ietf-mpls-arch-04.txt [20]."
         ::= { hwMplsLdpEntityEntry 13 }

     hwMplsLdpEntityLabelAllocationMethod OBJECT-TYPE
         SYNTAX      INTEGER {
                        ordered(1),
                        independent(2)
                     }
         MAX-ACCESS  read-create
         STATUS      current
         DESCRIPTION
             "For any given LDP session, the method of
             label allocation must be specified. Label can be allocated
             in either ordered mode or in the independent mode."
         DEFVAL  { ordered }
         ::= { hwMplsLdpEntityEntry 14 }

     hwMplsLdpEntityHelloHoldTimer OBJECT-TYPE
         SYNTAX      INTEGER (1..65535)
         UNITS       "seconds"
         MAX-ACCESS  read-create
         STATUS      current
         DESCRIPTION
             "The two octet value which is the proposed hello hold
             timer for this LDP Entity."
         ::= { hwMplsLdpEntityEntry 15 }
     
     hwMplsLdpEntityRowStatus OBJECT-TYPE
         SYNTAX      RowStatus
         MAX-ACCESS  read-create
         STATUS      current
              DESCRIPTION
                  "An object that allows entries in this table to
                  be created and deleted using the
                  RowStatus convention."
         ::= { hwMplsLdpEntityEntry 16 }

     --
     -- The MPLS LDP Entity Interface Table
     --

     hwMplsLdpEntityIfTable OBJECT-TYPE
         SYNTAX      SEQUENCE OF HwMplsLdpEntityIfEntry
         MAX-ACCESS  not-accessible
         STATUS      current
         DESCRIPTION
             "This table contains information about the
             interfaces that are associated with an LDP Entity.
             There should be atleast one interface associated with
             each LDP Entity. If the LDP Entity supports 'per interface
             based label space' label type then, atmost one interface can be 
             associated with the LDP entity. If the LDP Entity supports
             'per platform based label space' label type then, more than one
             interface can be associated with the LDP Entity."
         ::= { hwMplsLdpEntityObjects 2 }

     hwMplsLdpEntityIfEntry OBJECT-TYPE
         SYNTAX      HwMplsLdpEntityIfEntry
         MAX-ACCESS  not-accessible
         STATUS      current
         DESCRIPTION
             "An entry in this table represents an Interface that is
             associated with a LDP entity.

             An entry can be created by a network administrator
             or by an SNMP agent as instructed by LDP.

             An interface (row in this table) can be created/deleted only when 
             the associted LDP Entity row status has the value notInService 
             or notReady."
         INDEX       {   hwMplsLdpLsrIncarnID, hwMplsLdpEntityIfIndex }
         ::= { hwMplsLdpEntityIfTable 1 }

     HwMplsLdpEntityIfEntry ::= SEQUENCE {
         hwMplsLdpEntityIfIndex                       Unsigned32,
         hwMplsLdpEntityIfIpv4Address                 IpAddress,
         hwMplsLdpEntityIfRowStatus                   RowStatus
     }

     hwMplsLdpEntityIfIndex OBJECT-TYPE
         SYNTAX      Unsigned32 (1..4294967295)
         MAX-ACCESS  not-accessible
         STATUS      current
         DESCRIPTION
             "Identifier that uniquely identifies the Interface with 
             respect to an LDP Entity.
             
             The ifIndex value corresponds to the IfIndex value of the
             MIB-II"
         ::= { hwMplsLdpEntityIfEntry 1 }

     hwMplsLdpEntityIfIpv4Address OBJECT-TYPE
        SYNTAX        IpAddress
        MAX-ACCESS    read-create
        STATUS        current
        DESCRIPTION
            "The IPv4 address associated with the interface."
        ::= { hwMplsLdpEntityIfEntry 2 }

     hwMplsLdpEntityIfRowStatus OBJECT-TYPE
         SYNTAX      RowStatus
         MAX-ACCESS  read-create
         STATUS      current
              DESCRIPTION
                  "An object that allows entries in this table to
                  be created and deleted using the
                  RowStatus convention."
         ::= { hwMplsLdpEntityIfEntry 3 }

     --
     -- The MPLS LDP Entity Configurable ATM Label Range Table
     --

     hwMplsLdpEntityConfAtmLabelRangeTable OBJECT-TYPE
         SYNTAX SEQUENCE OF HwMplsLdpEntityConfAtmLabelRangeEntry
         MAX-ACCESS not-accessible
         STATUS current
         DESCRIPTION
             "The MPLS LDP Entity Configurable ATM Label Range Table.
             The purpose of this table is to provide a mechanism
             for specifying a contiguous range of vpi's
             with a contiguous range of vci's, or a 'label range'
             for LDP Entities.

             LDP Entities which use ATM must have at least one
             entry in this table."
         ::= { hwMplsLdpEntityObjects 3 }

     hwMplsLdpEntityConfAtmLabelRangeEntry OBJECT-TYPE
         SYNTAX HwMplsLdpEntityConfAtmLabelRangeEntry
         MAX-ACCESS not-accessible
         STATUS current
         DESCRIPTION
             "A row in the LDP Entity Configurable ATM Label
             Range Table.  One entry in this table contains
             information on a single range of labels
             represented by the configured Upper and Lower
             Bounds VPI/VCI pairs.
             NOTE:  The ranges for a specific LDP Entity
             are UNIQUE and non-overlapping.  For example,
             for a specific LDP Entity index, there could
             be one entry having ConfLowerBound vpi/vci == 0/32, and
             ConfUpperBound vpi/vci == 0/100, and a second entry for this
             same interface with ConfLowerBound vpi/vci == 0/101 and
             ConfUpperBound vpi/vci == 0/200.  However, there could not be
             a third entry with ConfLowerBound vpi/vci == 0/200 and
             ConfUpperBound vpi/vci == 0/300 because this label range overlaps
             with the second entry (i.e. both entries now have 0/200).

             A row will not be created unless a unique and non-overlapping
             range is specified.  Thus, row creation implies a one-shot
             row creation of LDP EntityID and ConfLowerBound vpi/vci and
             ConfUpperBound vpi/vci.  At least one label range entry
             for a specific LDP Entity MUST include the default VPI/VCI
             values denoted in the LDP Entity Table."
         INDEX { hwMplsLdpLsrIncarnID, hwMplsLdpEntityIfIndex,
                 hwMplsLdpEntityConfAtmLabelRangeLowerBoundVPI,
                 hwMplsLdpEntityConfAtmLabelRangeLowerBoundVCI  }
         ::= { hwMplsLdpEntityConfAtmLabelRangeTable 1 }

     HwMplsLdpEntityConfAtmLabelRangeEntry ::= SEQUENCE {
         hwMplsLdpEntityConfAtmLabelRangeLowerBoundVPI  AtmVpIdentifier,
         hwMplsLdpEntityConfAtmLabelRangeLowerBoundVCI  AtmVcIdentifier,
         hwMplsLdpEntityConfAtmLabelRangeUpperBoundVPI  AtmVpIdentifier,
         hwMplsLdpEntityConfAtmLabelRangeUpperBoundVCI  AtmVcIdentifier,
         hwMplsLdpEntityConfAtmLabelRangeRowStatus      RowStatus
     }

     hwMplsLdpEntityConfAtmLabelRangeLowerBoundVPI OBJECT-TYPE
         SYNTAX AtmVpIdentifier
         MAX-ACCESS not-accessible
         STATUS current
         DESCRIPTION
             "The minimum VPI number configured for this range."
         ::= { hwMplsLdpEntityConfAtmLabelRangeEntry 1 }

     hwMplsLdpEntityConfAtmLabelRangeLowerBoundVCI OBJECT-TYPE
         SYNTAX AtmVcIdentifier
         MAX-ACCESS not-accessible
         STATUS current
         DESCRIPTION
             "The minimum VCI number configured for this range."
         ::= { hwMplsLdpEntityConfAtmLabelRangeEntry 2 }

     hwMplsLdpEntityConfAtmLabelRangeUpperBoundVPI OBJECT-TYPE
         SYNTAX AtmVpIdentifier
         MAX-ACCESS read-create
         STATUS current
         DESCRIPTION
             "The maximum VPI number configured for this range."
         ::= { hwMplsLdpEntityConfAtmLabelRangeEntry 3 }

     hwMplsLdpEntityConfAtmLabelRangeUpperBoundVCI OBJECT-TYPE
         SYNTAX AtmVcIdentifier
         MAX-ACCESS read-create
         STATUS current
         DESCRIPTION
             "The maximum VCI number configured for this range."
        ::= { hwMplsLdpEntityConfAtmLabelRangeEntry 4 }

     hwMplsLdpEntityConfAtmLabelRangeRowStatus OBJECT-TYPE
         SYNTAX RowStatus
         MAX-ACCESS read-create
         STATUS current
              DESCRIPTION
                  "An object that allows entries in this
                  table to be created and deleted using
                  the RowStatus convention."
         ::= { hwMplsLdpEntityConfAtmLabelRangeEntry 5 }


     --
     -- The MPLS LDP Entity Statistics Table
     --

     hwMplsLdpEntityStatsTable OBJECT-TYPE
         SYNTAX      SEQUENCE OF HwMplsLdpEntityStatsEntry
         MAX-ACCESS  not-accessible
         STATUS      current
         DESCRIPTION
             "This table is a read-only table which augments
             the MplsLdpConfEntityTable.  The purpose of this
             table is to keep statistical information about
             the LDP Entities on the LSR."
         ::= { hwMplsLdpEntityObjects 4 }

     hwMplsLdpEntityStatsEntry OBJECT-TYPE
         SYNTAX      HwMplsLdpEntityStatsEntry
         MAX-ACCESS  not-accessible
         STATUS      current
         DESCRIPTION
             "A row in this table contains statistical information
             about an LDP Entity."
         AUGMENTS       {   hwMplsLdpEntityEntry  }
         ::= { hwMplsLdpEntityStatsTable 1 }

     HwMplsLdpEntityStatsEntry ::= SEQUENCE {
         hwMplsLdpAttemptedSessions      Counter32
     }

     hwMplsLdpAttemptedSessions OBJECT-TYPE
         SYNTAX      Counter32
         MAX-ACCESS  read-only
         STATUS      current
         DESCRIPTION
             "A count of the total attempted sessions for
             this LDP Entity."
         ::= { hwMplsLdpEntityStatsEntry 1 }


     --
     -- The MPLS LDP Peer Table
     --


     hwMplsLdpPeerTable OBJECT-TYPE
         SYNTAX      SEQUENCE OF HwMplsLdpPeerEntry
         MAX-ACCESS  not-accessible
         STATUS      current
         DESCRIPTION
             "Information about LDP peers which have been discovered
             by the LDP Entities that are managed by this agent."
         ::= { hwMplsLdpPeerObjects 1 }

     hwMplsLdpPeerEntry OBJECT-TYPE
         SYNTAX      HwMplsLdpPeerEntry
         MAX-ACCESS  not-accessible
         STATUS      current
         DESCRIPTION
             "Information about a single Peer."
         INDEX       { hwMplsLdpLsrIncarnID, hwMplsLdpEntityIfIndex,
                       hwMplsLdpPeerIndex }
         ::= { hwMplsLdpPeerTable 1 }

     HwMplsLdpPeerEntry ::= SEQUENCE {
         hwMplsLdpPeerIndex                      Unsigned32,
         hwMplsLdpPeerID                         MplsLdpIdentifier,
         hwMplsLdpPeerInternetworkAddrType       AddressFamilyNumbers,
         hwMplsLdpPeerInternetworkAddr           MplsLdpGenAddr,
         hwMplsLdpPeerDefaultMtu                 INTEGER,
         hwMplsLdpPeerKeepAliveHoldTimer         INTEGER,
         hwMplsLdpPeerLabelDistributionMethod    INTEGER,
         hwMplsLdpPeerType                       INTEGER,
         hwMplsLdpPeerRowStatus                  RowStatus
     }

     hwMplsLdpPeerIndex OBJECT-TYPE
         SYNTAX      Unsigned32 (1..4294967295)
         MAX-ACCESS  not-accessible
         STATUS      current
         DESCRIPTION
             "An identifier for the LDP peer that is unique within the
              scope of this agent."
         ::= { hwMplsLdpPeerEntry 1 }

     hwMplsLdpPeerID OBJECT-TYPE
         SYNTAX      MplsLdpIdentifier
         MAX-ACCESS  read-create
         STATUS      current
         DESCRIPTION
             "The LDP identifier of this LDP Peer."
         ::= { hwMplsLdpPeerEntry 2 }

     hwMplsLdpPeerInternetworkAddrType OBJECT-TYPE
         SYNTAX      AddressFamilyNumbers
         MAX-ACCESS  read-create
         STATUS      current
         DESCRIPTION
             "The type of the internetwork layer address of this
             LDP peer. This object indicates how the value of
             hwMplsLdpPeerInternetworkAddr is to be interpreted."
         ::= { hwMplsLdpPeerEntry 3 }

     hwMplsLdpPeerInternetworkAddr OBJECT-TYPE
         SYNTAX      MplsLdpGenAddr
         MAX-ACCESS  read-create
         STATUS      current
         DESCRIPTION
             "The value of the internetwork layer address of this LDP peer."
         ::= { hwMplsLdpPeerEntry 4 }

     hwMplsLdpPeerDefaultMtu OBJECT-TYPE
         SYNTAX      INTEGER (0..65535)
         MAX-ACCESS  read-create
         STATUS      current
         DESCRIPTION
             "The default maximum transmission unit (MTU) of the
             LDP Peer."
         DEFVAL      { 9180 }
         ::= { hwMplsLdpPeerEntry 5 }

     hwMplsLdpPeerKeepAliveHoldTimer OBJECT-TYPE
         SYNTAX      INTEGER (1..65535)
         UNITS       "seconds"
         MAX-ACCESS  read-create
         STATUS      current
         DESCRIPTION
             "The two octet unsigned non zero INTEGER that indicates
             the number of seconds that this Peer proposes for the
             value of the KeepAlive Interval."
         ::= { hwMplsLdpPeerEntry 6 }

     hwMplsLdpPeerLabelDistributionMethod OBJECT-TYPE
         SYNTAX      INTEGER {
                        downstreamOnDemand(1),
                        downstreamUnsolicited(2)
                     }
         MAX-ACCESS  read-create
         STATUS      current
         DESCRIPTION
             "For any given LDP session, the method of
             label distribution must be specified."
         REFERENCE
             "draft-ietf-mpls-arch-05.txt [20]."
         ::= { hwMplsLdpPeerEntry 7 }

     hwMplsLdpPeerType OBJECT-TYPE
         SYNTAX      INTEGER {
                        local(1),
                        remote(2)
                     }
         MAX-ACCESS  read-create
         STATUS      current
         DESCRIPTION
             "Indicates whether a peer is a local peer or a remote peer"
         ::= { hwMplsLdpPeerEntry 8 } 
     
     hwMplsLdpPeerRowStatus OBJECT-TYPE
         SYNTAX      RowStatus
         MAX-ACCESS  read-create
         STATUS      current
         DESCRIPTION
             "An object that allows entries in this table to be created
             and deleted using the RowStatus convention."
         ::= { hwMplsLdpPeerEntry 9 }

     --
     -- The MPLS LDP Peer Configurable ATM Label Range Table
     --

     hwMplsLdpPeerConfAtmLabelRangeTable OBJECT-TYPE
         SYNTAX SEQUENCE OF HwMplsLdpPeerConfAtmLabelRangeEntry
         MAX-ACCESS not-accessible
         STATUS current
         DESCRIPTION
             "The MPLS LDP Peer Configurable ATM Label Range Table.
             The purpose of this table is to provide a mechanism
             for specifying a contiguous range of vpi's with a contiguous
             range of vci's, or a 'label range' for LDP Peers.
             LDP Peers which use ATM must have at least one
             entry in this table."
         ::= { hwMplsLdpPeerObjects 2 }

     hwMplsLdpPeerConfAtmLabelRangeEntry OBJECT-TYPE
         SYNTAX HwMplsLdpPeerConfAtmLabelRangeEntry
         MAX-ACCESS not-accessible
         STATUS current
         DESCRIPTION
             "A row in the LDP Peer Configurable ATM Label Range Table.
             One entry in this table contains information
             on a single range of labels represented by
             the configured Upper and Lower Bounds VPI/VCI pairs.

             NOTE:  The ranges for a specific LDP Peer
             are UNIQUE and non-overlapping.  For example,
             for a specific LDP Peer index, there could
             be one entry having ConfLowerBound vpi/vci == 0/32, and
             ConfUpperBound vpi/vci == 0/100, and a second entry for this
             same interface with ConfLowerBound vpi/vci == 0/101 and
             ConfUpperBound vpi/vci == 0/200.  However, there could not be
             a third entry with ConfLowerBound vpi/vci == 0/200 and
             ConfUpperBound vpi/vci == 0/300 because this label range overlaps
             with the second entry (i.e. both entries now have 0/200).

             A row will not be created unless a unique and non-overlapping
             range is specified.  Thus, row creation implies a one-shot
             row creation of LDP PeerIndex and ConfLowerBound vpi/vci and
             ConfUpperBound vpi/vci.  At least one label range entry
             for a specific LDP Peer MUST include the default VPI/VCI
             values denoted in the LDP Peer Table."
         INDEX { hwMplsLdpLsrIncarnID, hwMplsLdpEntityIfIndex,
                 hwMplsLdpPeerIndex,
                 hwMplsLdpPeerConfAtmLabelRangeLowerBoundVPI,
                 hwMplsLdpPeerConfAtmLabelRangeLowerBoundVCI  }
         ::= { hwMplsLdpPeerConfAtmLabelRangeTable 1 }

     HwMplsLdpPeerConfAtmLabelRangeEntry ::= SEQUENCE {
         hwMplsLdpPeerConfAtmLabelRangeLowerBoundVPI      AtmVpIdentifier,
         hwMplsLdpPeerConfAtmLabelRangeLowerBoundVCI      AtmVcIdentifier,
         hwMplsLdpPeerConfAtmLabelRangeUpperBoundVPI      AtmVpIdentifier,
         hwMplsLdpPeerConfAtmLabelRangeUpperBoundVCI      AtmVcIdentifier
     }

     hwMplsLdpPeerConfAtmLabelRangeLowerBoundVPI OBJECT-TYPE
         SYNTAX AtmVpIdentifier
         MAX-ACCESS not-accessible
         STATUS current
         DESCRIPTION
             "The minimum VPI number configured for this range."
         ::= { hwMplsLdpPeerConfAtmLabelRangeEntry 1 }

     hwMplsLdpPeerConfAtmLabelRangeLowerBoundVCI OBJECT-TYPE
         SYNTAX AtmVcIdentifier
         MAX-ACCESS not-accessible
         STATUS current
         DESCRIPTION
             "The minimum VCI number configured for this range."
         ::= { hwMplsLdpPeerConfAtmLabelRangeEntry 2 }

     hwMplsLdpPeerConfAtmLabelRangeUpperBoundVPI OBJECT-TYPE
         SYNTAX AtmVpIdentifier
         MAX-ACCESS read-only  
         STATUS current
         DESCRIPTION
             "The maximum VPI number configured for this range."
         ::= { hwMplsLdpPeerConfAtmLabelRangeEntry 3 }

     hwMplsLdpPeerConfAtmLabelRangeUpperBoundVCI OBJECT-TYPE
         SYNTAX AtmVcIdentifier
         MAX-ACCESS read-only  
         STATUS current
         DESCRIPTION
             "The maximum VCI number configured for this range."
        ::= { hwMplsLdpPeerConfAtmLabelRangeEntry 4 }

     --
     -- The MPLS LDP Sessions Table
     --


     hwMplsLdpSessionTable OBJECT-TYPE
         SYNTAX      SEQUENCE OF HwMplsLdpSessionEntry
         MAX-ACCESS  not-accessible
         STATUS      current
         DESCRIPTION
             "A table of Sessions between the LDP Entities and
             LDP Peers."
         ::= { hwMplsLdpSessionObjects 1 }

     hwMplsLdpSessionEntry OBJECT-TYPE
         SYNTAX      HwMplsLdpSessionEntry
         MAX-ACCESS  not-accessible
         STATUS      current
         DESCRIPTION
             "An entry in this table represents information on a
             single session between an LDP Entity and LDP Peer."
         INDEX       { hwMplsLdpLsrIncarnID,
                       hwMplsLdpEntityIfIndex,
                       hwMplsLdpPeerIndex,
                       hwMplsLdpSessionIndex
                     }
         ::= { hwMplsLdpSessionTable 1 }

     HwMplsLdpSessionEntry ::= SEQUENCE {
         hwMplsLdpSessionIndex                          Unsigned32,
         hwMplsLdpSessionID                             MplsLdpIdentifier,
         hwMplsLdpSessionProtocolVersion                INTEGER,
         hwMplsLdpSessionKeepAliveHoldTimeRemaining     TimeInterval,
         hwMplsLdpSessionRole                           INTEGER,
         hwMplsLdpSessionState                          INTEGER,
         hwMplsLdpSessionAtmLabelRangeLowerBoundVPI     AtmVpIdentifier,
         hwMplsLdpSessionAtmLabelRangeLowerBoundVCI     AtmVcIdentifier,
         hwMplsLdpSessionAtmLabelRangeUpperBoundVPI     AtmVpIdentifier,
         hwMplsLdpSessionAtmLabelRangeUpperBoundVCI     AtmVcIdentifier
     }

     hwMplsLdpSessionIndex OBJECT-TYPE
         SYNTAX      Unsigned32 (1..4294967295)
         MAX-ACCESS  not-accessible
         STATUS      current
         DESCRIPTION
             "An unique identifier for this entry such that it
             identifies a specific LDP Session."
         ::= { hwMplsLdpSessionEntry 1 }

     hwMplsLdpSessionID OBJECT-TYPE
         SYNTAX      MplsLdpIdentifier
         MAX-ACCESS  read-only
         STATUS      current
         DESCRIPTION
             "The LDP Session identifier."
         ::= { hwMplsLdpSessionEntry 2 }

     hwMplsLdpSessionProtocolVersion OBJECT-TYPE
              SYNTAX      INTEGER(0..65535)
              MAX-ACCESS  read-only
              STATUS      current
              DESCRIPTION
                  "The version of the LDP Protocol which
                  this session is using."
              ::= { hwMplsLdpSessionEntry 3 }

     hwMplsLdpSessionKeepAliveHoldTimeRemaining OBJECT-TYPE
         SYNTAX      TimeInterval
         MAX-ACCESS  read-only
         STATUS      current
         DESCRIPTION
             "The keep alive hold time remaining for this session."
         ::= { hwMplsLdpSessionEntry 4 }

     hwMplsLdpSessionRole OBJECT-TYPE
         SYNTAX      INTEGER {
                        active(1),
                        passive(2)
                     }
         MAX-ACCESS  read-only
         STATUS      current
         DESCRIPTION
             "An indication of whether the LDP Entity associated with
             this session is acting in an 'active' role or
             a 'passive' role."
         ::= { hwMplsLdpSessionEntry 5 }

     hwMplsLdpSessionState OBJECT-TYPE
         SYNTAX      INTEGER {
                        nonexistent(1),
                        initialized(2),
                        openrec(3),
                        opensent(4),
                        operational(5)
                     }
         MAX-ACCESS  read-only
         STATUS      current
         DESCRIPTION
             "The current state of the session, all of the
             states 1 - 5 are based on the state machine for
             session negotiation behavior."
         ::= { hwMplsLdpSessionEntry 6 }

     hwMplsLdpSessionAtmLabelRangeLowerBoundVPI OBJECT-TYPE
         SYNTAX AtmVpIdentifier
         MAX-ACCESS read-only
         STATUS current
         DESCRIPTION
             "The minimum VPI number for this range."
         ::= { hwMplsLdpSessionEntry 7 }

     hwMplsLdpSessionAtmLabelRangeLowerBoundVCI OBJECT-TYPE
         SYNTAX AtmVcIdentifier
         MAX-ACCESS read-only
         STATUS current
         DESCRIPTION
             "The minimum VCI number for this range."
         ::= { hwMplsLdpSessionEntry 8 }

     hwMplsLdpSessionAtmLabelRangeUpperBoundVPI OBJECT-TYPE
         SYNTAX AtmVpIdentifier
         MAX-ACCESS read-only
         STATUS current
         DESCRIPTION
             "The maximum VPI number for this range."
         ::= { hwMplsLdpSessionEntry 9 }

     hwMplsLdpSessionAtmLabelRangeUpperBoundVCI OBJECT-TYPE
         SYNTAX AtmVcIdentifier
         MAX-ACCESS read-only
         STATUS current
         DESCRIPTION
             "The maximum VCI number for this range."
         ::= { hwMplsLdpSessionEntry 10 }



     --
     -- The MPLS LDP Hello Adjacency Table
     --


     hwMplsLdpHelloAdjacencyTable OBJECT-TYPE
         SYNTAX      SEQUENCE OF HwMplsLdpHelloAdjacencyEntry
         MAX-ACCESS  not-accessible
         STATUS      current
         DESCRIPTION
             "A table of Hello Adjacencies for Sessions."
         ::= { hwMplsLdpHelloAdjacencyObjects 1 }

     hwMplsLdpHelloAdjacencyEntry OBJECT-TYPE
         SYNTAX      HwMplsLdpHelloAdjacencyEntry
         MAX-ACCESS  not-accessible
         STATUS      current
         DESCRIPTION
             "Each row represents a single LDP Hello Adjacency.
             An LDP Session can have one or more Hello adjacencies."
         INDEX       { hwMplsLdpLsrIncarnID,
                       hwMplsLdpEntityIfIndex, 
                       hwMplsLdpPeerIndex,
                       hwMplsLdpSessionIndex,
                       hwMplsLdpHelloAdjacencyIndex }
         ::= { hwMplsLdpHelloAdjacencyTable 1 }

     HwMplsLdpHelloAdjacencyEntry ::= SEQUENCE {
         hwMplsLdpHelloAdjacencyIndex                  Unsigned32,
         hwMplsLdpHelloAdjacencyHoldTimeRemaining      TimeInterval
     }

     hwMplsLdpHelloAdjacencyIndex OBJECT-TYPE
         SYNTAX      Unsigned32 (1..4294967295)
         MAX-ACCESS  not-accessible
         STATUS      current
         DESCRIPTION
             "An identifier for the adjacency."
         ::= { hwMplsLdpHelloAdjacencyEntry 1 }

     hwMplsLdpHelloAdjacencyHoldTimeRemaining OBJECT-TYPE
         SYNTAX      TimeInterval
         MAX-ACCESS  read-only
         STATUS      current
         DESCRIPTION
             "The time remaining for this Hello Adjacency."
         ::= { hwMplsLdpHelloAdjacencyEntry 2 }

     --
     -- FSMPLS- CRLSP Table
     --

     hwMplsLdpCrlspTnlTable OBJECT-TYPE
        SYNTAX        SEQUENCE OF HwMplsLdpCrlspTnlEntry
        MAX-ACCESS    not-accessible
        STATUS        current
        DESCRIPTION
            "The hwMplsLdpCrlspTnlTable allows new CRLSP MPLS tunnels
             to be created. The ER hops associated with a CRLSP tunnel
             are to be configured using the hwMplsLdpCrlspErHopTable."
        ::= { hwMplsLdpCrlspTnlObjects 1 }
     
     hwMplsLdpCrlspTnlEntry OBJECT-TYPE
        SYNTAX        HwMplsLdpCrlspTnlEntry
        MAX-ACCESS    not-accessible
        STATUS        current
        DESCRIPTION
            "An  entry  in this table represents an CRLSP MPLS  tunnel.
             An  entry  can be created by a network administrator."
        INDEX  {  hwMplsLdpLsrIncarnID,  hwMplsLdpCrlspTnlIndex  }
           ::= { hwMplsLdpCrlspTnlTable 1 }
     
     HwMplsLdpCrlspTnlEntry ::= SEQUENCE {
           hwMplsLdpCrlspTnlIndex                 MplsTunnelIndex,
           hwMplsLdpCrlspTnlName                  DisplayString,
           hwMplsLdpCrlspTnlDirection             INTEGER,
           hwMplsLdpCrlspTnlSignallingProto       INTEGER,
           hwMplsLdpCrlspTnlSetupPrio             INTEGER,
           hwMplsLdpCrlspTnlHoldingPrio           INTEGER,
           hwMplsLdpCrlspTnlPeakDataRate          BitRate,
           hwMplsLdpCrlspTnlPeakBurstSize         BurstSize,
           hwMplsLdpCrlspTnlCommittedDataRate     BitRate,
           hwMplsLdpCrlspTnlCommittedBurstSize    BurstSize,
           hwMplsLdpCrlspTnlExcessBurstSize       BurstSize,
           hwMplsLdpCrlspTnlIsPinned              TruthValue,
           hwMplsLdpCrlspTnlFrequency             INTEGER,
           hwMplsLdpCrlspTnlWeight                INTEGER,
           hwMplsLdpCrlspTnlRowStatus             RowStatus
        }
     
     hwMplsLdpCrlspTnlIndex OBJECT-TYPE
        SYNTAX        MplsTunnelIndex
        MAX-ACCESS    accessible-for-notify
        STATUS        current
        DESCRIPTION
            "Uniquely identifies this row."
        ::= { hwMplsLdpCrlspTnlEntry 1 }
     
     hwMplsLdpCrlspTnlName OBJECT-TYPE
        SYNTAX        DisplayString
        MAX-ACCESS    read-create
        STATUS        current
        DESCRIPTION
            "The 'canonical' name assigned to the tunnel that can
             be  used  to refer to it on the 'console' port."
        ::= { hwMplsLdpCrlspTnlEntry 2 }
     
     
     hwMplsLdpCrlspTnlDirection OBJECT-TYPE
        SYNTAX        INTEGER { in(1), out(2), inOut(3) }
        MAX-ACCESS    read-create
        STATUS        current
        DESCRIPTION
            "Whether   this  tunnel  is  unidirectional-incoming,
             unidirectional-outgoing, or bidirectional."
        ::= { hwMplsLdpCrlspTnlEntry 3 }
     
     
     hwMplsLdpCrlspTnlSignallingProto OBJECT-TYPE
        SYNTAX        INTEGER { none(1), ldp(2), rsvp(3) }
        MAX-ACCESS    read-create
        STATUS        current
        DESCRIPTION
            "The  signaling protocol, if any, that  set  up  this
             tunnel."
        DEFVAL        { none }
        ::= { hwMplsLdpCrlspTnlEntry 4 }
     
     hwMplsLdpCrlspTnlSetupPrio OBJECT-TYPE
        SYNTAX        INTEGER (0..7)
        MAX-ACCESS    read-create
        STATUS        current
        DESCRIPTION
            "The setup priority of this tunnel."
        REFERENCE
            "Extensions to RSVP for LSP Tunnels, Awduche  et  al,
             Internet  Draft <draft-mpls-rsvp-lsp-tunnel-02.txt>,
             March  1999., Constraint-Based LSP Setup using  LDP,
             Jamoussi,  Internet  Draft  <draft-ietf-mpls-cr-ldp-
             01.txt>, Feb. 1999."
        ::= { hwMplsLdpCrlspTnlEntry 5 }
     
     hwMplsLdpCrlspTnlHoldingPrio OBJECT-TYPE
        SYNTAX        INTEGER (0..7)
        MAX-ACCESS    read-create
        STATUS        current
        DESCRIPTION
            "The holding priority for this tunnel."
        REFERENCE
            "  Extensions to RSVP for LSP Tunnels, Awduche et al,
             Internet  Draft <draft-mpls-rsvp-lsp-tunnel-02.txt>,
             March  1999., Constraint-Based LSP Setup using  LDP,
             Jamoussi,  Internet  Draft  <draft-ietf-mpls-cr-ldp-
             01.txt>, Feb. 1999."
        ::= { hwMplsLdpCrlspTnlEntry 6 }
     
     hwMplsLdpCrlspTnlPeakDataRate OBJECT-TYPE
        SYNTAX        BitRate
        UNITS         "bits per second"
        MAX-ACCESS    read-create
        STATUS        current
        DESCRIPTION
            "The peak rate - the maximum rate at which traffic will be sent on the
             CRLSP."
        REFERENCE
            "Section 4.3.1.2, Constraint-Based LSP Setup using LDP, Jamoussi, et.
             al, <draft-ietf-mpls-crldp-02.txt>, August 1999."
        DEFVAL        { 0 }
        ::= { hwMplsLdpCrlspTnlEntry 7 }
     
     hwMplsLdpCrlspTnlPeakBurstSize OBJECT-TYPE
        SYNTAX        BurstSize
        UNITS         "bytes"
        MAX-ACCESS    read-create
        STATUS        current
        DESCRIPTION
            "The peak burst size - the maximum burst size of the traffic that can 
             occur in the established CRLSP."
        REFERENCE
            "Section 4.3, Constraint-Based LSP Setup using LDP, Jamoussi, et.
             al, <draft-ietf-mpls-crldp-02.txt>, August 1999."
        DEFVAL        { 0 }
        ::= { hwMplsLdpCrlspTnlEntry 8 }
     
     hwMplsLdpCrlspTnlCommittedDataRate OBJECT-TYPE
        SYNTAX        BitRate
        UNITS         "bits per second"
        MAX-ACCESS    read-create
        STATUS        current
        DESCRIPTION
            "The committed rate - the committed rate at which traffic will be sent on the
             CRLSP."
        REFERENCE
            "Section 4.3.1.3, Constraint-Based LSP Setup using LDP, Jamoussi, et.
             al, <draft-ietf-mpls-crldp-02.txt>, August 1999."
        DEFVAL        { 0 }
        ::= { hwMplsLdpCrlspTnlEntry 9 }
     
     hwMplsLdpCrlspTnlCommittedBurstSize OBJECT-TYPE
        SYNTAX        BurstSize
        UNITS         "bytes"
        MAX-ACCESS    read-create
        STATUS        current
        DESCRIPTION
            "The committed burst size - the committed burst size of the traffic 
             that will be handled in the established CRLSP."
        REFERENCE
            "Section 4.3, Constraint-Based LSP Setup using LDP, Jamoussi, et.
             al, <draft-ietf-mpls-crldp-02.txt>, August 1999."
        DEFVAL        { 0 }
        ::= { hwMplsLdpCrlspTnlEntry 10 }
     
     hwMplsLdpCrlspTnlExcessBurstSize OBJECT-TYPE
        SYNTAX        BurstSize
        UNITS         "bytes"
        MAX-ACCESS    read-create
        STATUS        current
        DESCRIPTION
            "The Excess burst size - the excess burst size limit to be used
             for traffic conditioning at the ingress of the CRLSP."
        REFERENCE
            "Section 4.3.1.4, Constraint-Based LSP Setup using LDP, Jamoussi, et.
             al, <draft-ietf-mpls-crldp-02.txt>, August 1999."
        DEFVAL        { 0 }
        ::= { hwMplsLdpCrlspTnlEntry 11 }
     
     hwMplsLdpCrlspTnlIsPinned OBJECT-TYPE
        SYNTAX        TruthValue
        MAX-ACCESS    read-create
        STATUS        current
        DESCRIPTION
            "Indicates  whether  the loose-routed  hops  of  this
             tunnel are to be pinned."
        DEFVAL        { false }
        ::= { hwMplsLdpCrlspTnlEntry 12 }
     
     hwMplsLdpCrlspTnlFrequency OBJECT-TYPE
        SYNTAX        INTEGER (0..2)
        MAX-ACCESS    read-create
        STATUS        current
        DESCRIPTION
            "Indicates the frequency of usage of the established CRLSP."
        REFERENCE
            "Section 4.3.1.1, Constraint-Based LSP Setup using LDP, Jamoussi, et.
             al, <draft-ietf-mpls-crldp-02.txt>, August 1999."
        ::= { hwMplsLdpCrlspTnlEntry 13 }
     
     hwMplsLdpCrlspTnlWeight OBJECT-TYPE
        SYNTAX        INTEGER (0..255)
        MAX-ACCESS    read-create
        STATUS        current
        DESCRIPTION
            "Indicates the weight that is the established CRLSP."
        REFERENCE
            "Section 4.3, Constraint-Based LSP Setup using LDP, Jamoussi, et.
             al, <draft-ietf-mpls-crldp-02.txt>, August 1999."
        ::= { hwMplsLdpCrlspTnlEntry 14 }
     
     hwMplsLdpCrlspTnlRowStatus OBJECT-TYPE
        SYNTAX        RowStatus
        MAX-ACCESS    read-create
        STATUS        current
        DESCRIPTION
            "For controlling the state of this row.
             The status can be set to 'active' only when atleast one ERHOP
             is created in the hwMplsLdpErHopTable, associated with this
             tunnel."
        ::= { hwMplsLdpCrlspTnlEntry 15 }

    -- 
    -- Er-Hop Table
    --

     hwMplsLdpCrlspErHopTable  OBJECT-TYPE
        SYNTAX        SEQUENCE OF HwMplsLdpCrlspErHopEntry
        MAX-ACCESS    not-accessible
        STATUS        current
        DESCRIPTION
            "The hwMplsLdpCrlspErHopTable is used to indicate the hops,
             strict  or  loose,  for an MPLS  CRLSP tunnel  defined  in
             hwMplsLdpCrlspTnlTable. 
     
             There must be atleast one entry in this table for each CRLSP tunnel 
             that is supported in the hwMplsLdpCrlspTnlTable.
             
             The first row in the table  is  the
             first hop after the origination point of the tunnel."
        ::= { hwMplsLdpCrlspTnlObjects 2 }
     
     hwMplsLdpCrlspErHopEntry  OBJECT-TYPE
        SYNTAX        HwMplsLdpCrlspErHopEntry
        MAX-ACCESS    not-accessible
        STATUS        current
        DESCRIPTION
            "An  entry in this table represents a tunnel hop.  An
             entry  is  created  by a network  administrator  for
             signalled ERLSP set up by LDP or RSVP."
        INDEX  {  hwMplsLdpLsrIncarnID, 
                  hwMplsLdpCrlspTnlIndex, hwMplsLdpCrlspErHopIndex  }
           ::= { hwMplsLdpCrlspErHopTable 1 }
     
     HwMplsLdpCrlspErHopEntry ::= SEQUENCE {
           hwMplsLdpCrlspErHopIndex              INTEGER,
           hwMplsLdpCrlspErHopAddrType           INTEGER,
           hwMplsLdpCrlspErHopIpv4Addr           IpAddress,
           hwMplsLdpCrlspErHopIpv4PrefixLen      INTEGER,
           hwMplsLdpCrlspErHopStrictOrLoose      INTEGER,
           hwMplsLdpCrlspErHopRowStatus          RowStatus
        }
     
     hwMplsLdpCrlspErHopIndex OBJECT-TYPE
        SYNTAX        INTEGER
        MAX-ACCESS    not-accessible
        STATUS        current
        DESCRIPTION
            "Secondary  index  into  this table  identifying  the
             particular hop."
        ::= { hwMplsLdpCrlspErHopEntry 1 }
     
     hwMplsLdpCrlspErHopAddrType OBJECT-TYPE
        SYNTAX        INTEGER { ipV4(1) }
        MAX-ACCESS    read-create
        STATUS        current
        DESCRIPTION
            "Address type of this hop."
        DEFVAL        { ipV4 }
        ::= { hwMplsLdpCrlspErHopEntry 2 }
     
     hwMplsLdpCrlspErHopIpv4Addr OBJECT-TYPE
        SYNTAX        IpAddress
        MAX-ACCESS    read-create
        STATUS        current
        DESCRIPTION
            "If hwMplsLdpCrlspErHopAddrType is ipV4(1), IPv4 address of
             this  hop.  This object is not significant otherwise
             and should return a value of 0."
        ::= { hwMplsLdpCrlspErHopEntry 3 }
     
     hwMplsLdpCrlspErHopIpv4PrefixLen OBJECT-TYPE
        SYNTAX        INTEGER (1..32)
        MAX-ACCESS    read-create
        STATUS        current
        DESCRIPTION
            "If  hwMplsLdpCrlspErHopAddrType is ipV4(1), prefix  length
             for  this  hop's IPv4 address.  This object  is  not
             significant otherwise and should return a  value  of
             0."
        ::= { hwMplsLdpCrlspErHopEntry 4 }
     
     hwMplsLdpCrlspErHopStrictOrLoose OBJECT-TYPE
        SYNTAX        INTEGER { strict(1), loose(2) }
        MAX-ACCESS    read-create
        STATUS        current
        DESCRIPTION
            "Whether this is a strict or loose hop."
        ::= { hwMplsLdpCrlspErHopEntry 5 }
     
     hwMplsLdpCrlspErHopRowStatus OBJECT-TYPE
        SYNTAX        RowStatus
        MAX-ACCESS    read-create
        STATUS        current
        DESCRIPTION
            "For creating, modifying and deleting this row."
        ::= { hwMplsLdpCrlspErHopEntry 6 }

     ---
     --- Notifications
     ---

     hwMplsLdpNotificationPrefix   OBJECT IDENTIFIER ::=
                                      { hwMplsLdpNotifications 0 }

     hwMplsLdpFailedInitSessionThresholdExceeded NOTIFICATION-TYPE
     OBJECTS     {
			hwMplsLdpLsrIncarnID, hwMplsLdpEntityID,
                        hwMplsLdpEntityFailedInitSessionThreshold
                 }
     STATUS      current
   DESCRIPTION   "This notification is generated whenever the value
             of hwMplsLdpEntityFailedInitSessionThreshold is
             exceeded."
   ::= { hwMplsLdpNotificationPrefix 1 }

--          OBJECTS     { hwMplsLdpLsrIncarnID, hwMplsLdpEntityID,
--                        hwMplsLdpEntityFailedInitSessionThreshold
--                      }
--          STATUS      current
--          DESCRIPTION
--             "This notification is generated whenever the value
--             of hwMplsLdpEntityFailedInitSessionThreshold is
--             exceeded."
--          ::= { hwMplsLdpNotificationPrefix 1 }

     hwMplsLdpCrlspTunnelUp NOTIFICATION-TYPE
     OBJECTS     {
			hwMplsLdpLsrIncarnID, hwMplsLdpEntityID,
                  hwMplsLdpCrlspTnlIndex 
                 }
        STATUS      current
        DESCRIPTION
            "This notification is generated by the Ingress LSR of the CRLSP tunnel
             on the receipt of Label mapping message from the downstream LSR for
             the LAbel request sent for the CRLSP tunnel."
        ::= { hwMplsLdpNotificationPrefix 2 }
  
     hwMplsLdpCrlspTunnelDown NOTIFICATION-TYPE
     OBJECTS     {
		hwMplsLdpLsrIncarnID, hwMplsLdpEntityID,
                  hwMplsLdpCrlspTnlIndex }
        STATUS      current
        DESCRIPTION
            "This notification is generated when a CRLSP Row status is modified
             to destroy the CRLSP tunnel.  - due to pre-emption etc.,"
        ::= { hwMplsLdpNotificationPrefix 3 }
     
     hwMplsLdpCrlspTunnelSetupFailure NOTIFICATION-TYPE
     OBJECTS     { hwMplsLdpLsrIncarnID, hwMplsLdpEntityID,
                  hwMplsLdpCrlspTnlIndex }
        STATUS      current
        DESCRIPTION
            "This notification is generated by the Ingress LSR of the CRLSP tunnel
             on the receipt of Nak message from the downstream LSR for
             the Label request sent for the CRLSP tunnel. This can occur due to
             improper ER hop values being set, or Traffic resources not available
             etc.,"
        ::=  { hwMplsLdpNotificationPrefix 4 } 


     hwMplsLdpIncarnUpEventFailure  NOTIFICATION-TYPE
     OBJECTS     { hwMplsLdpLsrIncarnID}
        STATUS      current
        DESCRIPTION
            "This notification is generated by LDP to notify 
             the Incarnation UP Event failure"
        ::= { hwMplsLdpNotificationPrefix 11 } 

     hwMplsLdpIncarnDownEventFailure NOTIFICATION-TYPE
     OBJECTS     { hwMplsLdpLsrIncarnID }
        STATUS      current
        DESCRIPTION
            "This notification is generated by LDP to notify 
             the Incarnation DOWN Event failure"
        ::= { hwMplsLdpNotificationPrefix 12 } 

     hwMplsLdpEntityUpEventFailure NOTIFICATION-TYPE
     OBJECTS     { hwMplsLdpLsrIncarnID, hwMplsLdpEntityID }
        STATUS      current
        DESCRIPTION
            "This notification is generated by LDP to notify 
             the ENTITY UP Event failure"
        ::= { hwMplsLdpNotificationPrefix 13 }


     hwMplsLdpEntityDownEventFailure NOTIFICATION-TYPE
     OBJECTS     { hwMplsLdpLsrIncarnID, hwMplsLdpEntityID }
        STATUS      current
        DESCRIPTION
            "This notification is generated by LDP to notify 
             the ENTITY  DOWN Event failure"
        ::= { hwMplsLdpNotificationPrefix 14 }
        hwMplsLdpSessionUpEventFailure NOTIFICATION-TYPE
     OBJECTS     { hwMplsLdpSessionID, hwMplsLdpSessionState }
        STATUS      current
        DESCRIPTION
            "Generation of this trap occurs when the 
            value of 'hwMplsLdpSessionState' enters
             the 'operational(5)' state."
        ::= { hwMplsLdpNotificationPrefix 15 }  
        
     hwMplsLdpSessionDownEventFailure NOTIFICATION-TYPE
     OBJECTS     { hwMplsLdpSessionID, hwMplsLdpSessionState }
        STATUS      current
        DESCRIPTION
            "Generation of this trap occurs when the 
            value of 'hwMplsLdpSessionState' leaves 
            the 'operational(5)' state."
        ::= { hwMplsLdpNotificationPrefix 16 }      

-- End of notifications.
END
