-- MIB created 08/25/2005 15:29:57, by
-- ATEN International Co., Ltd.
-- 20050915 created to form a basic frame of SN0116A
-- this file can return SNMP manager a full MIB tree when using snmpwalk.

ATEN-SN0116A-SMI DEFINITIONS ::= BEGIN

IMPORTS
    sn3101
          FROM ATEN-PRODUCTS-MIB;

rs232	OBJECT IDENTIFIER ::= {sn3101 1}
usrcfg	OBJECT IDENTIFIER ::= {sn3101 2}
session	OBJECT IDENTIFIER ::= {sn3101 3}
imageCurrentVersion	OBJECT IDENTIFIER ::= {sn3101 4}
imageNewVersion	OBJECT IDENTIFIER ::= {sn3101 5}
portAlert	OBJECT IDENTIFIER ::= {sn3101 6}

END
