-- MIB created 08/25/2005 15:29:57, by


ATEN-SMI DEFINITIONS ::= BEGIN

IMPORTS
    enterprises
            FROM SNMPv2-SMI;

aten OBJECT IDENTIFIER ::= { enterprises 21317 }
-- MODULE-IDENTITY
--  LastUpdated
--    200508250000Z
--  OrgName
--    ATEN International Co., Ltd.
--  Descr
--  The Structure of Management Information for the
--    ATEN enterprise.

atenProducts OBJECT IDENTIFIER ::= { aten 1 }
-- OBJECT-IDENTITY
--  Status
--    mandatory
--  Descr
--    atenProducts is the root OBJECT IDENTIFIER from
--    which sysObjectID values are assigned.  Actual
--    values are defined in ATEN-PRODUCTS-MIB.

otherEnterprises OBJECT IDENTIFIER ::= { aten 2 }
-- OBJECT-IDENTITY
--  Status
--    mandatory
--  Descr
--    otherEnterprises provides a root object identifier
--    from which mibs produced by other companies may be
--    placed.  mibs produced by other enterprises are
--    typicially implemented with the object identifiers
--    as defined in the mib

atenExperiment OBJECT IDENTIFIER ::= { aten 3 }
-- OBJECT-IDENTITY
--  Status
--    mandatory
--  Descr
--    atenExperiment provides a root object identifier
--    from which experimental mibs may be temporarily
--    based.

END
