-- MIB created 08/25/2005 15:29:57, by
-- ATEN International Co., Ltd.
-- 20050913 modified to form a basic frame
-- this file only provides a product-level description, no product-specific allowed
-- if want to know the details of certain products, refer to other documents

ATEN-PRODUCTS-MIB DEFINITIONS ::= BEGIN

IMPORTS
    atenProducts
          FROM ATEN-SMI;

--products layer begins
public 		OBJECT IDENTIFIER ::= { atenProducts 1 }
software 	OBJECT IDENTIFIER ::= { atenProducts 2 }
overip    	OBJECT IDENTIFIER ::= { atenProducts 3 }
kvm 		OBJECT IDENTIFIER ::= { atenProducts 4 }
video    	OBJECT IDENTIFIER ::= { atenProducts 5 }
usb  		OBJECT IDENTIFIER ::= { atenProducts 6 }
firewire    OBJECT IDENTIFIER ::= { atenProducts 7 }
--products layer ends

--overip layer begins
kvmoverip		OBJECT IDENTIFIER ::= { overip 1}
poweroverip		OBJECT IDENTIFIER ::= { overip 2}
serialoverip 	OBJECT IDENTIFIER ::= { overip 3}
--overip layers ends

--poweroverip layers begins
pn9108			OBJECT IDENTIFIER ::= {poweroverip 1}
--poweroverip layers ends

--serialoverip layers begins
sn0116a  OBJECT IDENTIFIER ::= {serialoverip 1}
sn3101   OBJECT IDENTIFIER ::= {serialoverip 2}
--serialoverip layers ends

END
