LANTRONIX-SLC-MIB DEFINITIONS ::= BEGIN

-- This MIB defines the management information for Lantronix SecureLinx
-- Console Managers.  

IMPORTS
    MODULE-IDENTITY, OBJECT-TYPE, IpAddress, NOTIFICATION-TYPE
        FROM SNMPv2-SMI
    TEXTUAL-CONVENTION
        FROM SNMPv2-TC
    Ipv6Address
        FROM IPV6-TC
    products
        FROM LANTRONIX-MIB;

slc MODULE-IDENTITY
    LAST-UPDATED "200912090000Z"
    ORGANIZATION "Lantronix, Inc."
    CONTACT-INFO "Lantronix Technical Support
                  15353 Barranca Parkway
                  Irvine, CA 92618 USA
                  +1 800 422-7044
                  snmp@lantronix.com"
    DESCRIPTION  "MIB module for managing Lantronix SecureLinx Console Managers"

    -- revision history

    REVISION     "200912090000Z"  -- December 9, 2009
    DESCRIPTION  "Added slcNetEthIfMTU, slcNetEthIPv6, slcNetEthBonding, 
                  slcServTelnetTelnetOut, slcServWebTermDeployment, 
                  slcServWebTermBufSize, slcServSMTPSender, 
                  slcAuthLocalAllowReuse, slcAuthLocalReuseHistory, 
                  slcAuthLocalPasswordLifetime, slcAuthLocalWarningPeriod, 
                  slcAuthLocalMaxLoginAttempts, slcAuthLocalLockoutPeriod, 
                  slcAuthLocalMultipleSysadminLogins,
                  slcAuthLocalSysadminConsoleOnly, slcAuthNISDialback, 
                  slcAuthNISDialbackNum, slcAuthLDAPBindWithLogin, 
                  slcAuthLDAPUseLDAPSchema, slcAuthLDAPDialback, 
                  slcAuthLDAPDialbackNum, slcAuthRADIUSDialback, 
                  slcAuthRADIUSDialbackNum, slcAuthKerbDialback, 
                  slcAuthKerbDialbackNum, slcAuthTACACSDialback, 
                  slcAuthTACACSDialbackNum, slcAuthRemoteUserMenu, 
                  slcAuthRemoteUserLocked, slcAuthRemoteUserDialback, 
                  slcAuthRemoteUserDialbackNum, slcDevConNumberShowLines, 
                  slcDevPortCfgNumberShowLines, slcDevPortCfgViewPortLog, 
                  slcDevPortCfgPortLogSeq, slcDevPortCfgMaxDirectConnects, 
                  slcDevPortCfgTelnetTimeout, slcDevPortCfgSSHTimeout,
                  slcDevPortCfgTCPTimeout, slcDevPortCfgCBCPClientType,
                  slcDevPortCfgCBCPServerAllowNoCallback,
                  slcDevPortCfgDialbackDelay, slcPCCardCfgCBCPClientType, 
                  slcPCCardCfgCBCPServerAllowNoCallback,
                  slcPCCardCfgDialbackDelay, slcSystemSSHPreAuthBanner, 
                  slcSystemSiteRackRow, slcSystemSiteRackCluster, 
                  slcSystemSiteRack, slcSystemLCDScreens, 
                  slcSystemLCDUserStrLine1, slcSystemLCDUserStrLine2, 
                  slcSystemLCDScrolling, slcSystemLCDScrollDelay, 
                  slcSystemLCDIdleDelay, slcSystemInternalTemp, 
                  slcSystemWebProtocol, slcSystemWebCipher, 
                  slcEventPCCardAction and slcEventSLCInternalTemp."

    REVISION     "200801090000Z"  -- January 9, 2008
    DESCRIPTION  "Added slcServSNMPv3ReadWriteUser, slcServSNMPv3Security, 
                  slcServSNMPv3Authentication, slcServSNMPv3Encryption, 
                  slcServHostList objects, slcAuthNISEscapeSeq, 
                  slcAuthNISBreakSeq, slcAuthLDAPEscapeSeq, 
                  slcAuthLDAPBreakSeq, slcAuthRADIUSEscapeSeq, 
                  slcAuthRADIUSBreakSeq, slcAuthKerbEscapeSeq, 
                  slcAuthKerbBreakSeq, slcAuthTACACSEscapeSeq, 
                  slcAuthTACACSBreakSeq, slcAuthRemoteUserEscapeSeq, 
                  slcAuthRemoteUserBreakSeq, slcDevConShowLines, 
                  slcDevPortCfgHostList, slcPCCardCfgHostList, 
                  slcDevPortCfgDevLowTemp, slcDevPortCfgDevHighTemp, 
                  slcDevPortCfgDevTemperature, slcDevPortCfgDevLowHumidity, 
                  slcDevPortCfgDevHighHumidity, slcDevPortCfgDevHumidity, 
                  slcDevPortCfgDevTraps, slcDevPortCfgShowLines, 
                  slcSystemWebGadget, slcSystemAction, 
                  slcEventDevicePortDevice* notifications."

    REVISION     "200706250000Z"  -- June 25, 2007
    DESCRIPTION  "Added slcNetEthAlternateGateway, slcNetEthPingIPAddress, 
                  slcNetEthPingInterface, slcNetEthPingDelay, 
                  slcNetEthPingFailed, slcServSNMPTrapCommunity, 
                  slcServSNMPAlarmDelay, slcServPhoneHome section,
                  slcDevPortCfgWebColumns, slcDevPortCfgWebRows and 
                  slcDevPortCfgSyslogState."

    REVISION     "200702200000Z"  -- February 20, 2007
    DESCRIPTION  "Added slcDevPortCfgSLMLoggingState, slcDevPortCfgSLMNMS, 
                  slcDevPortCfgSLMByteThresh and slcDevPortCfgSLMTimeFrame."

    REVISION     "200702070000Z"  -- February 7, 2007
    DESCRIPTION  "Added slcNetEthIfIPv6Addr and slcNetEthIfIPv6PrefixLength."

    REVISION     "200610200000Z"  -- October 20, 2006
    DESCRIPTION  "Added slcNetFirewallRuleset* objects, slcNetFirewallMapping* 
                  objects, slcAuthLDAPEncrypt, slcAuthTACACSServer2, 
                  slcAuthTACACSServer3, slcDevPortCfgDODAuth, 
                  slcDevPortCfgDODCHAPHost, slcPCCardCfgDODAuth, and 
                  slcPCCardCfgDODCHAPHost.  Obsoleted slcNetFirewallReject, 
                  slcNetFirewallPing, slcNetFirewallSSH, slcNetFirewallTelnet, 
                  slcNetFirewallHTTP, slcNetFirewallHTTPS and 
                  slcNetFirewallSMBCIFS.  Added dialinAndDialondemand(6) to 
                  slcDevPortCfgModemState and slcPCCardCfgModemState."

    REVISION     "200607140000Z"  -- July 14, 2006
    DESCRIPTION  "Added slcServSysRemoteServer2, slcServAuditInSystemLog, 
                  slcAuthLocalState, slcAuthLocalOrder, 
                  slcAuthLocalComplexPasswords, slcAuthLocalUseNextMethod, 
                  slcAuthRemoteUserListenPorts, slcAuthRemoteUserDataPorts, 
                  slcAuthRemoteUserClearPorts, slcAuthRemoteAuthListOnly, 
                  slcDevPortCfgIdleTimeout, slcDevPortCfgRestartDelay, 
                  slcDevPortCfgCallerIdLogging, slcDevPortCfgCallerIdATCmd, 
                  slcPCCardCfgIdleTimeout, slcPCCardCfgRestartDelay, 
                  slcPCCardCfgCallerIdLogging, slcPCCardCfgCallerIdATCmd. 
                  Added dialondemand(5) to slcDevPortCfgModemState and 
                  slcPCCardCfgModemState."

    REVISION     "200605120000Z"  -- May 12, 2006
    DESCRIPTION  "Added slcNetEthDomain, slcServNTPLocalServer2, 
                  slcServNTPLocalServer3, slcServSSHV1Incoming, 
                  slcAuthNISSlave4, slcAuthNISSlave5, 
                  slcPCCardCfgGSMPPPCompression, slcPCCardCfgGSMAutoAcquireDNS,
                  slcPCCardCfgGSMDialoutMode, slcPCCardCfgGSMContextID, 
                  slcPCCardCfgGSMBearerService.  Obsoleted 
                  slcPCCardCfgGSMNetworkName."

    REVISION     "200602130000Z"  -- February 13, 2006
    DESCRIPTION  "Added SLCAuthRemote group.  Added slcServAuditIncludeCLI, 
                  slcAuthLocalUserGroup, slcAuthLocalUserRights, 
                  slcAuthNISGroup, slcAuthNISRights, slcAuthNISMenu, 
                  slcAuthNISListenPorts, slcAuthNISDataPorts, 
                  slcAuthNISClearPorts, slcAuthLDAPGroup, slcAuthLDAPRights, 
                  slcAuthLDAPMenu, slcAuthLDAPListenPorts, 
                  slcAuthLDAPDataPorts, slcAuthLDAPClearPorts, 
                  slcAuthRADIUSGroup, slcAuthRADIUSRights, slcAuthRADIUSMenu, 
                  slcAuthRADIUSListenPorts, slcAuthRADIUSDataPorts, 
                  slcAuthRADIUSClearPorts, slcAuthKerbGroup, slcAuthKerbRights, 
                  slcAuthKerbMenu, slcAuthKerbListenPorts, 
                  slcAuthKerbDataPorts, slcAuthKerbClearPorts, 
                  slcAuthTACACSGroup, slcAuthTACACSRights, slcAuthTACACSMenu, 
                  slcAuthTACACSListenPorts, slcAuthTACACSDataPorts, 
                  slcAuthTACACSClearPorts, slcDevGlobalMaxDirect, 
                  slcSystemWebTimeout, slcPCCardCfgTelnetState, 
                  slcPCCardCfgTelnetPort, slcPCCardCfgTelnetAuth, 
                  slcPCCardCfgSSHState, slcPCCardCfgSSHPort, 
                  slcPCCardCfgSSHAuth, slcPCCardCfgTCPState, 
                  slcPCCardCfgTCPPort, slcPCCardCfgTCPAuth, slcPCCardCfgGSMPIN, 
                  slcPCCardCfgGSMNetworkName.  Added slcEventDevicePortSLMData 
                  and slcEventDevicePortSLMConfig traps.  Added Textual 
                  Convention UserGroup and UserRights.  Obsoleted 
                  slcDevGlobalListenPorts, slcDevGlobalDataPorts and
                  slcDevGlobalClearPorts."

    REVISION     "200510030000Z"  -- October 3, 2005
    DESCRIPTION  "Added slcServSSHPort."

    REVISION     "200506090000Z"  -- June 9, 2005
    DESCRIPTION  "Added slcServSSHTimeout, slcServSSHWebSSH, 
                  slcServSNMPReadOnlyCommunity, slcServSNMPReadWriteCommunity, 
                  slcDevPortCfgAction, slcDevPortCfgEmailSend, 
                  slcDevPortCfgBanner, slcPCCardCfgISDNChannel, 
                  slcPCCardCfgISDNChannelNum, slcConnDurationStr, slcConnIdle,
                  slcConnIdleStr, slcConnSourceIP, slcSystemWelcomeBanner, 
                  slcSystemLoginBanner, slcSystemLogoutBanner. 
                  Added sftp(3) to slcSystemLoadVia."

    REVISION     "200412130000Z"  -- December 13, 2004
    DESCRIPTION  "Initial version."

    ::= { products 1 }


-- Textual Conventions

EnabledState ::= TEXTUAL-CONVENTION
    STATUS      current
    DESCRIPTION "The enabled/disabled state of an SLC feature."
    SYNTAX INTEGER {
        disabled(1),
        enabled(2)
    }

AuthOrder ::= TEXTUAL-CONVENTION
    STATUS      current
    DESCRIPTION "Authentication order for a remote authentication method.  
                If the authentication method is disabled, AuthOrder = 0."
    SYNTAX      Integer32 (0..6)

SyslogLevel ::= TEXTUAL-CONVENTION
    STATUS      current
    DESCRIPTION "Syslog logging levels"
    SYNTAX      INTEGER { 
        off(1), 
        info(2), 
        warning(3), 
        error(4), 
        debug(5) 
    }

UserGroup ::= TEXTUAL-CONVENTION
    STATUS      current
    DESCRIPTION "The group assigned to a user.  Each group has a set of user 
                 rights associated with it."
    SYNTAX      INTEGER {
        default(1),
        power(2),
        administrators(3)
    }

UserRights ::= TEXTUAL-CONVENTION
    STATUS      current
    DESCRIPTION "The rights assigned to a user.  Each group has a set of user 
                 rights associated with it.  The string is a comma-separated 
                 list of rights:
                   ad - full administrative rights
                   dp - configure Device Ports
                   dr - Diagnostics and Reports
                   dt - configure Date and Time
                   fc - manage Firmware and Configurations
                   lu - configure Local Users
                   nt - configure Networking
                   pc - configure PC Card
                   ra - configure Remote Authentication
                   rs - Reboot or Shutdown the SLC
                   sk - configure SSH Keys
                   sn - configure SLC Network
                   sv - configure Services
                   um - configure User Menus
                   wb - Web Access"
    SYNTAX      OCTET STRING (SIZE (0..255))


-- Groups in slc

slcNetwork          OBJECT IDENTIFIER ::= { slc 1 }
slcServices         OBJECT IDENTIFIER ::= { slc 2 }
slcAuth             OBJECT IDENTIFIER ::= { slc 3 }
slcDevices          OBJECT IDENTIFIER ::= { slc 4 }
slcConnections      OBJECT IDENTIFIER ::= { slc 5 }
slcSystem           OBJECT IDENTIFIER ::= { slc 6 }


--
-- Network Group
--

slcNetEth           OBJECT IDENTIFIER ::= { slcNetwork 1 }

slcNetEthIfNumber OBJECT-TYPE
    SYNTAX      Integer32 (1..2)
    MAX-ACCESS  read-only
    STATUS      current
    DESCRIPTION 
        "The number of entries in the Ethernet interface table."
    ::= { slcNetEth 1 }

-- Ethernet interface table

slcNetEthIfTable OBJECT-TYPE
    SYNTAX      SEQUENCE OF SlcNetEthIfEntry
    MAX-ACCESS  not-accessible
    STATUS      current
    DESCRIPTION "Table of Ethernet network entries.  The number of entries is 
                 given by the value of slcNetEthIfNumber."
    ::= { slcNetEth 2 }

slcNetEthIfEntry OBJECT-TYPE
    SYNTAX      SlcNetEthIfEntry
    MAX-ACCESS  not-accessible
    STATUS      current
    DESCRIPTION 
        "An entry with the attributes for each Ethernet interface."
    INDEX       { slcNetEthIfIndex }
    ::= { slcNetEthIfTable 1 }

SlcNetEthIfEntry ::= SEQUENCE {
    slcNetEthIfIndex            Integer32,
    slcNetEthIfSource           INTEGER,
    slcNetEthIfMode             INTEGER,
    slcNetEthIfIPv6Addr         Ipv6Address,
    slcNetEthIfIPv6PrefixLength INTEGER (0..128),
    slcNetEthIfMTU              Integer32
}

slcNetEthIfIndex OBJECT-TYPE
    SYNTAX      Integer32 (1..2)
    MAX-ACCESS  read-only
    STATUS      current
    DESCRIPTION "Reference index for each Ethernet interface."
    ::= { slcNetEthIfEntry 1 }

slcNetEthIfSource OBJECT-TYPE
    SYNTAX      INTEGER { disabled(1), dhcp(2), bootp(3), static(4) }
    MAX-ACCESS  read-only
    STATUS      current
    DESCRIPTION "The state/source for the IP Address and subnet mask for the 
                 Ethernet interface."
    ::= { slcNetEthIfEntry 2 }

slcNetEthIfMode OBJECT-TYPE
    SYNTAX      INTEGER { autoNegotiate(1), 
                          10mbitHalfDuplex(2), 
                          10mbitFullDuplex(3), 
                          100mbitHalfDuplex(4),
                          100mbitFullDuplex(5)
                        }
    MAX-ACCESS  read-only
    STATUS      current
    DESCRIPTION "The speed and duplex for the Ethernet interface."
    ::= { slcNetEthIfEntry 3 }

slcNetEthIfIPv6Addr OBJECT-TYPE
    SYNTAX      Ipv6Address
    MAX-ACCESS  read-only
    STATUS      current
    DESCRIPTION "The IPv6 Address for each Ethernet interface."
    ::= { slcNetEthIfEntry 4 }

slcNetEthIfIPv6PrefixLength OBJECT-TYPE
    SYNTAX      INTEGER (0..128)
    MAX-ACCESS  not-accessible
    STATUS      current
    DESCRIPTION "The length of the prefix for slcNetEthIfIPv6Addr (in bits)."
    ::= { slcNetEthIfEntry 5 }

slcNetEthIfMTU OBJECT-TYPE
    SYNTAX      Integer32
    MAX-ACCESS  read-only
    STATUS      current
    DESCRIPTION "The Maximum Transmission Unit for the Ethernet interface."
    ::= { slcNetEthIfEntry 6 }

slcNetEthGateway OBJECT-TYPE
    SYNTAX      IpAddress
    MAX-ACCESS  read-only
    STATUS      current
    DESCRIPTION "The gateway for routing non-Eth1 and non-Eth2 network traffic."
    ::= { slcNetEth 3 }

slcNetEthGatewayPrecedence OBJECT-TYPE
    SYNTAX      INTEGER { dhcp(1), default(2), gprs(3) }
    MAX-ACCESS  read-only
    STATUS      current
    DESCRIPTION "The gateway to give precedence to, if both a static gateway 
                 is set, and a gateway is acquired via DHCP or a GPRS Modem."
    ::= { slcNetEth 4 }

slcNetEthKeepaliveStartProbes OBJECT-TYPE
    SYNTAX      Integer32 (1..99999)
    MAX-ACCESS  read-only
    STATUS      current
    DESCRIPTION "TCP keepalive timer: number of seconds to wait before sending 
                 out the initial probe."
    ::= { slcNetEth 5 }

slcNetEthKeepaliveNumberOfProbes OBJECT-TYPE
    SYNTAX      Integer32 (1..20)
    MAX-ACCESS  read-only
    STATUS      current
    DESCRIPTION "TCP keepalive timer: number of probes to send out after the 
                 initial probe."
    ::= { slcNetEth 6 }

slcNetEthKeepaliveInterval OBJECT-TYPE
    SYNTAX      Integer32 (1..9999)
    MAX-ACCESS  read-only
    STATUS      current
    DESCRIPTION "TCP keepalive timer: number of seconds between probes."
    ::= { slcNetEth 7 }

slcNetEthIPForwarding OBJECT-TYPE
    SYNTAX      EnabledState
    MAX-ACCESS  read-only
    STATUS      current
    DESCRIPTION "If enabled, IP forwarding is used."
    ::= { slcNetEth 8 }

slcNetEthDNS1 OBJECT-TYPE
    SYNTAX      IpAddress
    MAX-ACCESS  read-only
    STATUS      current
    DESCRIPTION "The IP Address of DNS server #1."
    ::= { slcNetEth 9 }

slcNetEthDNS2 OBJECT-TYPE
    SYNTAX      IpAddress
    MAX-ACCESS  read-only
    STATUS      current
    DESCRIPTION "The IP Address of DNS server #2."
    ::= { slcNetEth 10 }

slcNetEthDNS3 OBJECT-TYPE
    SYNTAX      IpAddress
    MAX-ACCESS  read-only
    STATUS      current
    DESCRIPTION "The IP Address of DNS server #3."
    ::= { slcNetEth 11 }

slcNetEthDomain OBJECT-TYPE
    SYNTAX      OCTET STRING
    MAX-ACCESS  read-only
    STATUS      current
    DESCRIPTION "The SLC domain name."
    ::= { slcNetEth 12 }

slcNetEthAlternateGateway OBJECT-TYPE
    SYNTAX      IpAddress
    MAX-ACCESS  read-only
    STATUS      current
    DESCRIPTION "The alternate gateway for routing non-Eth1 and non-Eth2 
                 network traffic.  The alternate gateway is used if an 
                 IP Address usually accessible through the default gateway 
                 fails to return one or more pings."
    ::= { slcNetEth 13 }

slcNetEthPingIPAddress OBJECT-TYPE
    SYNTAX      IpAddress
    MAX-ACCESS  read-only
    STATUS      current
    DESCRIPTION "The IP Address to ping to determine if the alternate gateway 
                 should be used."
    ::= { slcNetEth 14 }

slcNetEthPingInterface OBJECT-TYPE
    SYNTAX      INTEGER { ethernet1(1), ethernet(2) }
    MAX-ACCESS  read-only
    STATUS      current
    DESCRIPTION "The Ethernet interface used to determine if the alternate 
                 gateway should be used."
    ::= { slcNetEth 15 }

slcNetEthPingDelay OBJECT-TYPE
    SYNTAX      Integer32 (1..250)
    MAX-ACCESS  read-only
    STATUS      current
    DESCRIPTION "The delay, in seconds, between pings used to determine if the 
                 alternate gateway should be used."
    ::= { slcNetEth 16 }

slcNetEthPingFailed OBJECT-TYPE
    SYNTAX      Integer32 (1..250)
    MAX-ACCESS  read-only
    STATUS      current
    DESCRIPTION "The number of pings with no response required for the 
                 alternate gateway to be used."
    ::= { slcNetEth 17 }

slcNetEthBonding OBJECT-TYPE
    SYNTAX      INTEGER { disabled(1), 
                          activeBackup(2),
                          8023adLayer2(3), 
                          8023adLayer34(4), 
                          adaptiveLoadBalancing(5) }
    MAX-ACCESS  read-only
    STATUS      current
    DESCRIPTION "The Ethernet network redundancy/load balancing setting."
    ::= { slcNetEth 18 }

slcNetEthIPv6 OBJECT-TYPE
    SYNTAX      EnabledState
    MAX-ACCESS  read-only
    STATUS      current
    DESCRIPTION "If enabled, IPv6 is enabled."
    ::= { slcNetEth 19 }


slcNetFirewall      OBJECT IDENTIFIER ::= { slcNetwork 2 }

slcNetFirewallState OBJECT-TYPE
    SYNTAX      EnabledState
    MAX-ACCESS  read-only
    STATUS      current
    DESCRIPTION "If enabled, network traffic is filtered."
    ::= { slcNetFirewall 1 }

slcNetFirewallReject OBJECT-TYPE
    SYNTAX      INTEGER { return(1), ignore(2) }
    MAX-ACCESS  read-only
    STATUS      obsolete
    DESCRIPTION "If enabled, returns a 'connection denied' message on blocked 
                 ports.  If disabled, ignores attempts to connect to a blocked 
                 port."
    ::= { slcNetFirewall 2 }

slcNetFirewallPing OBJECT-TYPE
    SYNTAX      EnabledState
    MAX-ACCESS  read-only
    STATUS      obsolete
    DESCRIPTION "If enabled, the SLC is invisible to pings."
    ::= { slcNetFirewall 3 }

slcNetFirewallSSH OBJECT-TYPE
    SYNTAX      EnabledState
    MAX-ACCESS  read-only
    STATUS      obsolete
    DESCRIPTION "If enabled, the SSH port is open.  If disabled, the SSH 
                 port is blocked to network traffic."
    ::= { slcNetFirewall 4 }

slcNetFirewallTelnet OBJECT-TYPE
    SYNTAX      EnabledState
    MAX-ACCESS  read-only
    STATUS      obsolete
    DESCRIPTION "If enabled, the Telnet port is open.  If disabled, the Telnet 
                 port is blocked to network traffic."
    ::= { slcNetFirewall 5 }

slcNetFirewallHTTP OBJECT-TYPE
    SYNTAX      EnabledState
    MAX-ACCESS  read-only
    STATUS      obsolete
    DESCRIPTION "If enabled, the HTTP port is open.  If disabled, the HTTP 
                 port is blocked to network traffic."
    ::= { slcNetFirewall 6 }

slcNetFirewallHTTPS OBJECT-TYPE
    SYNTAX      EnabledState
    MAX-ACCESS  read-only
    STATUS      obsolete
    DESCRIPTION "If enabled, the HTTPS port is open.  If disabled, the HTTPS 
                 port is blocked to network traffic."
    ::= { slcNetFirewall 7 }

slcNetFirewallSMBCIFS OBJECT-TYPE
    SYNTAX      EnabledState
    MAX-ACCESS  read-only
    STATUS      obsolete
    DESCRIPTION "If enabled, the SMBCIFS port is open.  If disabled, the 
                 SMBCIFS port is blocked to network traffic."
    ::= { slcNetFirewall 8 }

slcNetFirewallRulesetNumber OBJECT-TYPE
    SYNTAX      Integer32 (0..64)
    MAX-ACCESS  read-only
    STATUS      current
    DESCRIPTION "The number of entries in the IP Filter Ruleset table."
    ::= { slcNetFirewall 9 }

-- IP Filter Ruleset table

slcNetFirewallRulesetTable OBJECT-TYPE
    SYNTAX      SEQUENCE OF SlcNetFirewallRulesetEntry
    MAX-ACCESS  not-accessible
    STATUS      current
    DESCRIPTION "Table of IP Filter Rulesets.  The number of entries is 
                 given by the value of slcNetFirewallRulesetNumber."
    ::= { slcNetFirewall 10 }

slcNetFirewallRulesetEntry OBJECT-TYPE
    SYNTAX      SlcNetFirewallRulesetEntry
    MAX-ACCESS  not-accessible
    STATUS      current
    DESCRIPTION "An entry with all the attributes, including the rules, for 
                 an IP Filter Ruleset."
    INDEX       { slcNetFirewallRulesetIndex }
    ::= { slcNetFirewallRulesetTable 1 }

SlcNetFirewallRulesetEntry ::= SEQUENCE {
    slcNetFirewallRulesetIndex        Integer32,
    slcNetFirewallRulesetName         OCTET STRING,
    slcNetFirewallRulesetNumRules     Integer32,
    slcNetFirewallRulesetRules        OCTET STRING
}

slcNetFirewallRulesetIndex OBJECT-TYPE
    SYNTAX      Integer32 (1..64)
    MAX-ACCESS  read-only
    STATUS      current
    DESCRIPTION "Reference index for each IP Filter Ruleset."
    ::= { slcNetFirewallRulesetEntry 1 }

slcNetFirewallRulesetName OBJECT-TYPE
    SYNTAX      OCTET STRING
    MAX-ACCESS  read-only
    STATUS      current
    DESCRIPTION "The name assigned to the IP Filter Ruleset."
    ::= { slcNetFirewallRulesetEntry 2 }

slcNetFirewallRulesetNumRules OBJECT-TYPE
    SYNTAX      Integer32 (1..32)
    MAX-ACCESS  read-only
    STATUS      current
    DESCRIPTION "The number of rules in the slcNetFirewallRulesetRules string."
    ::= { slcNetFirewallRulesetEntry 3 }

slcNetFirewallRulesetRules OBJECT-TYPE
    SYNTAX      OCTET STRING
    MAX-ACCESS  read-only
    STATUS      current
    DESCRIPTION "The IP Filter rules that are defined for the Ruleset.  The 
                 rule format is <IP>/<Mask Bits>;<Protocol>;<Ports>;<Action> 
                 and rules are separated by a colon.  If the string is 
                 truncated because of system limitations, the string will be 
                 terminated with two colons."
    ::= { slcNetFirewallRulesetEntry 4 }

slcNetFirewallMappingNumber OBJECT-TYPE
    SYNTAX      Integer32 
    MAX-ACCESS  read-only
    STATUS      current
    DESCRIPTION "The number of entries in the IP Filter Mapping table."
    ::= { slcNetFirewall 11 }

-- IP Filter Mapping table

slcNetFirewallMappingTable OBJECT-TYPE
    SYNTAX      SEQUENCE OF SlcNetFirewallMappingEntry
    MAX-ACCESS  not-accessible
    STATUS      current
    DESCRIPTION "Table of mappings between IP Filter Rulesets and interfaces.  
                 The number of entries is given by the value of 
                 slcNetFirewallMappingNumber."
    ::= { slcNetFirewall 12 }

slcNetFirewallMappingEntry OBJECT-TYPE
    SYNTAX      SlcNetFirewallMappingEntry
    MAX-ACCESS  not-accessible
    STATUS      current
    DESCRIPTION "An entry defining an interface that has an IP Filter Ruleset 
                 assigned to it.  The interface can be either an Ethernet 
                 interface or a PC Card or Device Port modem."
    INDEX       { slcNetFirewallMappingIndex }
    ::= { slcNetFirewallMappingTable 1 }

SlcNetFirewallMappingEntry ::= SEQUENCE {
    slcNetFirewallMappingIndex        Integer32,
    slcNetFirewallMappingIfac         INTEGER,
    slcNetFirewallMappingIfacId       Integer32,
    slcNetFirewallMappingRuleset      OCTET STRING
}

slcNetFirewallMappingIndex OBJECT-TYPE
    SYNTAX      Integer32 (1..64)
    MAX-ACCESS  read-only
    STATUS      current
    DESCRIPTION "Reference index for each IP Filter mapping."
    ::= { slcNetFirewallMappingEntry 1 }

slcNetFirewallMappingIfac OBJECT-TYPE
    SYNTAX      INTEGER { ethernet1(1), 
                          ethernet2(2), 
                          upperPCCard(3),
                          lowerPCCard(4),
                          devicePort(5) }
    MAX-ACCESS  read-only
    STATUS      current
    DESCRIPTION "The interface which has an IP Filter Ruleset assigned to it.  
                 If the interface is devicePort, slcNetFirewallMappingIfacId 
                 defines which Device Port (with an attached modem) the Ruleset 
                 is assigned to."
    ::= { slcNetFirewallMappingEntry 2 }

slcNetFirewallMappingIfacId OBJECT-TYPE
    SYNTAX      Integer32 (0..48)
    MAX-ACCESS  read-only
    STATUS      current
    DESCRIPTION "The identifier for a Device Port, if slcNetFirewallMappingIfac 
                 equals devicePort(5).  Otherwise equals zero."
    ::= { slcNetFirewallMappingEntry 3 }

slcNetFirewallMappingRuleset OBJECT-TYPE
    SYNTAX      OCTET STRING
    MAX-ACCESS  read-only
    STATUS      current
    DESCRIPTION "The name of the IP Filter Ruleset assigned to the interface."
    ::= { slcNetFirewallMappingEntry 4 }


slcNetRouting       OBJECT IDENTIFIER ::= { slcNetwork 3 }

slcNetRouteRIPState OBJECT-TYPE
    SYNTAX      EnabledState
    MAX-ACCESS  read-only
    STATUS      current
    DESCRIPTION "If enabled, the Routing Information Protocol (RIP) is used."
    ::= { slcNetRouting 1 }

slcNetRouteRIPVersion OBJECT-TYPE
    SYNTAX      INTEGER { one(1), two(2), oneAndTwo(3) }
    MAX-ACCESS  read-only
    STATUS      current
    DESCRIPTION "The version of RIP being used."
    ::= { slcNetRouting 2 }

slcNetRouteStaticState OBJECT-TYPE
    SYNTAX      EnabledState
    MAX-ACCESS  read-only
    STATUS      current
    DESCRIPTION "If enabled, static routing is used."
    ::= { slcNetRouting 3 }

slcNetRouteStaticNumber OBJECT-TYPE
    SYNTAX      Integer32 (0..64)
    MAX-ACCESS  read-only
    STATUS      current
    DESCRIPTION 
        "The number of entries in the Static Routes table."
    ::= { slcNetRouting 4 }

-- Static Routes table

slcNetRouteStaticTable OBJECT-TYPE
    SYNTAX      SEQUENCE OF SlcNetRouteStaticEntry
    MAX-ACCESS  not-accessible
    STATUS      current
    DESCRIPTION "Table of static route entries.  The number of entries is 
                 given by the value of slcNetRouteStaticNumber."
    ::= { slcNetRouting 5 }

slcNetRouteStaticEntry OBJECT-TYPE
    SYNTAX      SlcNetRouteStaticEntry
    MAX-ACCESS  not-accessible
    STATUS      current
    DESCRIPTION "An entry with the IP Address, subnet mask, and gateway 
                 for a static route."
    INDEX       { slcNetRouteStaticIndex }
    ::= { slcNetRouteStaticTable 1 }

SlcNetRouteStaticEntry ::= SEQUENCE {
    slcNetRouteStaticIndex    Integer32,
    slcNetRouteStaticIP       IpAddress,
    slcNetRouteStaticMask     IpAddress,
    slcNetRouteStaticGateway  IpAddress
}

slcNetRouteStaticIndex OBJECT-TYPE
    SYNTAX      Integer32 (1..64)
    MAX-ACCESS  read-only
    STATUS      current
    DESCRIPTION "Reference index for each static route."
    ::= { slcNetRouteStaticEntry 1 }

slcNetRouteStaticIP OBJECT-TYPE
    SYNTAX      IpAddress
    MAX-ACCESS  read-only
    STATUS      current
    DESCRIPTION "The IP Address for the static route."
    ::= { slcNetRouteStaticEntry 2 }

slcNetRouteStaticMask OBJECT-TYPE
    SYNTAX      IpAddress
    MAX-ACCESS  read-only
    STATUS      current
    DESCRIPTION "The subnet mask for the static route."
    ::= { slcNetRouteStaticEntry 3 }

slcNetRouteStaticGateway OBJECT-TYPE
    SYNTAX      IpAddress
    MAX-ACCESS  read-only
    STATUS      current
    DESCRIPTION "The gateway for the static route."
    ::= { slcNetRouteStaticEntry 4 }


-- 
-- Services Group
--

slcServNTP          OBJECT IDENTIFIER ::= { slcServices 1 }

slcServNTPState OBJECT-TYPE
    SYNTAX      EnabledState
    MAX-ACCESS  read-only
    STATUS      current
    DESCRIPTION "If enabled, NTP is used to synchronize SLC time with a 
                 network time server."
    ::= { slcServNTP 1 }

slcServNTPSynchronize OBJECT-TYPE
    SYNTAX      INTEGER { broadcast(1), poll(2) }
    MAX-ACCESS  read-only
    STATUS      current
    DESCRIPTION "The method used by the SLC to synchronize time: receive 
                 broadcasts from the NTP server, or poll the NTP server."
    ::= { slcServNTP 2 }

slcServNTPPoll OBJECT-TYPE
    SYNTAX      INTEGER { local(1), public(2) }
    MAX-ACCESS  read-only
    STATUS      current
    DESCRIPTION "If slcServNTPSynchronize is set to poll, indicates whether 
                 a local server or a public server is used as the NTP server."
    ::= { slcServNTP 3 }

slcServNTPServer OBJECT-TYPE
    SYNTAX      IpAddress
    MAX-ACCESS  read-only
    STATUS      current
    DESCRIPTION "The IP Address of the local or public NTP server."
    ::= { slcServNTP 4 }

slcServNTPLocalServer2 OBJECT-TYPE
    SYNTAX      IpAddress
    MAX-ACCESS  read-only
    STATUS      current
    DESCRIPTION "The IP Address of the 2nd local NTP server, if slcServNTPPoll 
                 is set to local."
    ::= { slcServNTP 5 }

slcServNTPLocalServer3 OBJECT-TYPE
    SYNTAX      IpAddress
    MAX-ACCESS  read-only
    STATUS      current
    DESCRIPTION "The IP Address of the 3rd local NTP server, if slcServNTPPoll 
                 is set to local."
    ::= { slcServNTP 6 }


slcServSyslog       OBJECT IDENTIFIER ::= { slcServices 2 }

slcServSysNetworkLevel OBJECT-TYPE
    SYNTAX      SyslogLevel
    MAX-ACCESS  read-only
    STATUS      current
    DESCRIPTION "The logging level for Network messages."
    ::= { slcServSyslog 1 }

slcServSysServicesLevel OBJECT-TYPE
    SYNTAX      SyslogLevel
    MAX-ACCESS  read-only
    STATUS      current
    DESCRIPTION "The logging level for Services messages."
    ::= { slcServSyslog 2 }

slcServSysAuthLevel OBJECT-TYPE
    SYNTAX      SyslogLevel
    MAX-ACCESS  read-only
    STATUS      current
    DESCRIPTION "The logging level for Authentication messages."
    ::= { slcServSyslog 3 }

slcServSysDevPortLevel OBJECT-TYPE
    SYNTAX      SyslogLevel
    MAX-ACCESS  read-only
    STATUS      current
    DESCRIPTION "The logging level for Device Port messages."
    ::= { slcServSyslog 4 }

slcServSysDiagLevel OBJECT-TYPE
    SYNTAX      SyslogLevel
    MAX-ACCESS  read-only
    STATUS      current
    DESCRIPTION "The logging level for Diagnostic messages."
    ::= { slcServSyslog 5 }

slcServSysGeneralLevel OBJECT-TYPE
    SYNTAX      SyslogLevel
    MAX-ACCESS  read-only
    STATUS      current
    DESCRIPTION "The logging level for General system messages."
    ::= { slcServSyslog 6 }

slcServSysRemoteServer OBJECT-TYPE
    SYNTAX      IpAddress
    MAX-ACCESS  read-only
    STATUS      current
    DESCRIPTION "The IP Address of the remote Syslog Server."
    ::= { slcServSyslog 7 }

slcServSysRemoteServer2 OBJECT-TYPE
    SYNTAX      IpAddress
    MAX-ACCESS  read-only
    STATUS      current
    DESCRIPTION "The IP Address of the secondary remote Syslog Server."
    ::= { slcServSyslog 8 }

slcServAuditLog     OBJECT IDENTIFIER ::= { slcServices 3 }

slcServAuditState OBJECT-TYPE
    SYNTAX      EnabledState
    MAX-ACCESS  read-only
    STATUS      current
    DESCRIPTION "If enabled, logs all configuration changes to an audit log."
    ::= { slcServAuditLog 1 }

slcServAuditSize OBJECT-TYPE
    SYNTAX      Integer32 (5..500)
    MAX-ACCESS  read-only
    STATUS      current
    DESCRIPTION "The maximum size of the audit login in Kilobytes."
    ::= { slcServAuditLog 2 }

slcServAuditIncludeCLI OBJECT-TYPE
    SYNTAX      EnabledState
    MAX-ACCESS  read-only
    STATUS      current
    DESCRIPTION "If enabled, all CLI commands are included in the audit log in 
                 addition to a description of the configuration change."
    ::= { slcServAuditLog 3 }

slcServAuditInSystemLog OBJECT-TYPE
    SYNTAX      EnabledState
    MAX-ACCESS  read-only
    STATUS      current
    DESCRIPTION "If enabled, all audit log entries are also sent to the system 
                 log."
    ::= { slcServAuditLog 4 }


slcServSSH          OBJECT IDENTIFIER ::= { slcServices 4 }

slcServSSHState OBJECT-TYPE
    SYNTAX      EnabledState
    MAX-ACCESS  read-only
    STATUS      current
    DESCRIPTION "If enabled, allows logins to the SLC CLI via SSH."
    ::= { slcServSSH 1 }

slcServSSHTimeout OBJECT-TYPE
    SYNTAX      Integer32 (0..30)
    MAX-ACCESS  read-only
    STATUS      current
    DESCRIPTION "The timeout (in minutes) for SSH connections.  A value 
                 of 0 indicates that timeouts are disabled."
    ::= { slcServSSH 2 }

slcServSSHWebSSH OBJECT-TYPE
    SYNTAX      EnabledState
    MAX-ACCESS  read-only
    STATUS      current
    DESCRIPTION "If enabled, allows Web SSH access to the CLI and the 
                 Device Ports."
    ::= { slcServSSH 3 }

slcServSSHPort OBJECT-TYPE
    SYNTAX      Integer32 (0..65535)
    MAX-ACCESS  read-only
    STATUS      current
    DESCRIPTION "The TCP Port number for incoming SSH sessions to the SLC CLI."
    ::= { slcServSSH 4 }

slcServSSHV1Incoming OBJECT-TYPE
    SYNTAX      EnabledState
    MAX-ACCESS  read-only
    STATUS      current
    DESCRIPTION "If enabled, incoming SSH version 1 connections are allowed."
    ::= { slcServSSH 5 }


slcServTelnet       OBJECT IDENTIFIER ::= { slcServices 5 }

slcServTelnetState OBJECT-TYPE
    SYNTAX      EnabledState
    MAX-ACCESS  read-only
    STATUS      current
    DESCRIPTION "If enabled, allows logins to the SLC CLI via Telnet."
    ::= { slcServTelnet 1 }

slcServTelnetTimeout OBJECT-TYPE
    SYNTAX      Integer32 (0..30)
    MAX-ACCESS  read-only
    STATUS      current
    DESCRIPTION "The timeout (in minutes) for Telnet connections.  A value 
                 of 0 indicates that timeouts are disabled."
    ::= { slcServTelnet 2 }

slcServTelnetWebTelnet OBJECT-TYPE
    SYNTAX      EnabledState
    MAX-ACCESS  read-only
    STATUS      current
    DESCRIPTION "If enabled, allows Web Telnet access to the CLI and the 
                 Device Ports."
    ::= { slcServTelnet 3 }

slcServTelnetTelnetOut OBJECT-TYPE
    SYNTAX      EnabledState
    MAX-ACCESS  read-only
    STATUS      current
    DESCRIPTION "If enabled, allows outgoing Telnet connections."
    ::= { slcServTelnet 4 }


slcServSNMP         OBJECT IDENTIFIER ::= { slcServices 6 }

slcServSNMPState OBJECT-TYPE
    SYNTAX      EnabledState
    MAX-ACCESS  read-only
    STATUS      current
    DESCRIPTION "Enables the SNMP agent on the SLC."
    ::= { slcServSNMP 1 }

slcServSNMPTraps OBJECT-TYPE
    SYNTAX      EnabledState
    MAX-ACCESS  read-only
    STATUS      current
    DESCRIPTION "If enabled, the SLC sends traps for key events."
    ::= { slcServSNMP 2 }

slcServSNMPNMS OBJECT-TYPE
    SYNTAX      IpAddress
    MAX-ACCESS  read-only
    STATUS      current
    DESCRIPTION "The IP Address of the Network Management System (NMS)."
    ::= { slcServSNMP 3 }

slcServSNMPLocation OBJECT-TYPE
    SYNTAX      OCTET STRING
    MAX-ACCESS  read-only
    STATUS      current
    DESCRIPTION "The SNMP location for the SLC."
    ::= { slcServSNMP 4 }

slcServSNMPContact OBJECT-TYPE
    SYNTAX      OCTET STRING
    MAX-ACCESS  read-only
    STATUS      current
    DESCRIPTION "The SNMP contact for the SLC."
    ::= { slcServSNMP 5 }

slcServSNMPv3User OBJECT-TYPE
    SYNTAX      OCTET STRING (SIZE(1..32))
    MAX-ACCESS  read-only
    STATUS      current
    DESCRIPTION "The user name for read-only access to the SLC via SNMP v3."
    ::= { slcServSNMP 6 }

slcServSNMPReadOnlyCommunity OBJECT-TYPE
    SYNTAX      OCTET STRING
    MAX-ACCESS  read-only
    STATUS      current
    DESCRIPTION "The SNMP read-only community for SNMP versions 1 and 2."
    ::= { slcServSNMP 7 }

slcServSNMPReadWriteCommunity OBJECT-TYPE
    SYNTAX      OCTET STRING
    MAX-ACCESS  read-only
    STATUS      current
    DESCRIPTION "The SNMP read-write community for SNMP versions 1 and 2."
    ::= { slcServSNMP 8 }

slcServSNMPTrapCommunity OBJECT-TYPE
    SYNTAX      OCTET STRING
    MAX-ACCESS  read-only
    STATUS      current
    DESCRIPTION "The SNMP trap community for SNMP versions 1 and 2."
    ::= { slcServSNMP 9 }

slcServSNMPAlarmDelay OBJECT-TYPE
    SYNTAX      Integer32
    MAX-ACCESS  read-only
    STATUS      current
    DESCRIPTION "The delay, in seconds, between traps that are sent out for 
                 alarm conditions."
    ::= { slcServSNMP 10 }

slcServSNMPv3ReadWriteUser OBJECT-TYPE
    SYNTAX      OCTET STRING (SIZE(1..32))
    MAX-ACCESS  read-only
    STATUS      current
    DESCRIPTION "The user name for read-write access to the SLC via SNMP v3."
    ::= { slcServSNMP 11 }

slcServSNMPv3Security OBJECT-TYPE
    SYNTAX      INTEGER { noAuthNoEncrypt(1), authNoEncrypt(2), authEncrypt(3) }
    MAX-ACCESS  read-only
    STATUS      current
    DESCRIPTION "The security model used for SNMP v3: insecure authentication 
                 and no packet encryption, secure authentication and no packet 
                 encryption, secure authentication and packet encryption."
    ::= { slcServSNMP 12 }

slcServSNMPv3Authentication OBJECT-TYPE
    SYNTAX      INTEGER { MD5(1), SHA(2) }
    MAX-ACCESS  read-only
    STATUS      current
    DESCRIPTION "When slcServSNMPv3Security is set to authNoEncrypt or 
                 authEncrypt, the type of authentication used."
    ::= { slcServSNMP 13 }

slcServSNMPv3Encryption OBJECT-TYPE
    SYNTAX      INTEGER { DES(1), AES(2) }
    MAX-ACCESS  read-only
    STATUS      current
    DESCRIPTION "When slcServSNMPv3Security is set to authEncrypt, the type 
                 of encryption used."
    ::= { slcServSNMP 14 }


slcServSMTP         OBJECT IDENTIFIER ::= { slcServices 7 }

slcServSMTPServer OBJECT-TYPE
    SYNTAX      IpAddress
    MAX-ACCESS  read-only
    STATUS      current
    DESCRIPTION "The IP Address of the SMTP (email) server."
    ::= { slcServSMTP 1 }

slcServSMTPSender OBJECT-TYPE
    SYNTAX      OCTET STRING
    MAX-ACCESS  read-only
    STATUS      current
    DESCRIPTION "The sender's email address for emails sent from the SLC."
    ::= { slcServSMTP 2 }


slcServNFS          OBJECT IDENTIFIER ::= { slcServices 8 }

-- NFS Mounts table

slcServNFSMountTable OBJECT-TYPE
    SYNTAX      SEQUENCE OF SlcServNFSMountEntry
    MAX-ACCESS  not-accessible
    STATUS      current
    DESCRIPTION "Table of NFS Mounts."
    ::= { slcServNFS 1 }

slcServNFSMountEntry OBJECT-TYPE
    SYNTAX      SlcServNFSMountEntry
    MAX-ACCESS  not-accessible
    STATUS      current
    DESCRIPTION "An entry containing a NFS Mount and it's attributes."
    INDEX       { slcServNFSMountIndex }
    ::= { slcServNFSMountTable 1 }

SlcServNFSMountEntry ::= SEQUENCE {
    slcServNFSMountIndex        Integer32,
    slcServNFSMountRemoteDir    OCTET STRING,
    slcServNFSMountLocalDir     OCTET STRING,
    slcServNFSMountReadWrite    EnabledState,
    slcServNFSMountMount        EnabledState
}

slcServNFSMountIndex OBJECT-TYPE
    SYNTAX      Integer32 (1..3)
    MAX-ACCESS  read-only
    STATUS      current
    DESCRIPTION "Reference index for each NFS Mount."
    ::= { slcServNFSMountEntry 1 }

slcServNFSMountRemoteDir OBJECT-TYPE
    SYNTAX      OCTET STRING
    MAX-ACCESS  read-only
    STATUS      current
    DESCRIPTION "The remote directory of the NFS Mount, in the format 
                 <remote server>:/<remote directory>."
    ::= { slcServNFSMountEntry 2 }

slcServNFSMountLocalDir OBJECT-TYPE
    SYNTAX      OCTET STRING
    MAX-ACCESS  read-only
    STATUS      current
    DESCRIPTION "The directory in the SLC on which the remote directory is 
                 mounted."
    ::= { slcServNFSMountEntry 3 }

slcServNFSMountReadWrite OBJECT-TYPE
    SYNTAX      EnabledState
    MAX-ACCESS  read-only
    STATUS      current
    DESCRIPTION "If enabled, the remote NFS directory is mounted read-write. 
                 If disabled, the remote NFS directory is mounted read-only."
    ::= { slcServNFSMountEntry 4 }

slcServNFSMountMount OBJECT-TYPE
    SYNTAX      EnabledState
    MAX-ACCESS  read-only
    STATUS      current
    DESCRIPTION "If enabled, the remote NFS directory is configured to be 
                 mounted.  If disabled, the remote NFS directory will not be 
                 mounted, or will be unmounted if is is mounted."
    ::= { slcServNFSMountEntry 5 }


slcServCIFS         OBJECT IDENTIFIER ::= { slcServices 9 }

slcServCIFSState OBJECT-TYPE
    SYNTAX      EnabledState
    MAX-ACCESS  read-only
    STATUS      current
    DESCRIPTION "If enabled, the SLC exports a CIFS share containing system 
                 logs, Device Port logs, and saved SLC configurations."
    ::= { slcServCIFS 1 }

slcServCIFSEth1 OBJECT-TYPE
    SYNTAX      EnabledState
    MAX-ACCESS  read-only
    STATUS      current
    DESCRIPTION "If enabled, the CIFS share is exported on the Eth1 interface."
    ::= { slcServCIFS 2 }

slcServCIFSEth2 OBJECT-TYPE
    SYNTAX      EnabledState
    MAX-ACCESS  read-only
    STATUS      current
    DESCRIPTION "If enabled, the CIFS share is exported on the Eth2 interface."
    ::= { slcServCIFS 3 }

slcServCIFSWorkgroup OBJECT-TYPE
    SYNTAX      OCTET STRING (SIZE(0..15))
    MAX-ACCESS  read-only
    STATUS      current
    DESCRIPTION "The SMB/CIFS workgroup that the CIFS share is associated with."
    ::= { slcServCIFS 4 }


slcServSLCNetwork   OBJECT IDENTIFIER ::= { slcServices 10 }

slcServSLCNetSearch OBJECT-TYPE
    SYNTAX      INTEGER { both(1), subnet(2), manual(3) }
    MAX-ACCESS  read-only
    STATUS      current
    DESCRIPTION "Indicates how to search for SLCs on the network: by searching 
                 a list of manually entered IP Addresses, by broadcasting on 
                 the local subnet, or both."
    ::= { slcServSLCNetwork 1 }

slcServSLCNetNumber OBJECT-TYPE
    SYNTAX      Integer32 (0..200)
    MAX-ACCESS  read-only
    STATUS      current
    DESCRIPTION 
        "The number of entries in the SLC Network Manual IP Address table."
    ::= { slcServSLCNetwork 2 }

-- SLC Network Manual IP Address table

slcServSLCNetTable OBJECT-TYPE
    SYNTAX      SEQUENCE OF SlcServSLCNetEntry
    MAX-ACCESS  not-accessible
    STATUS      current
    DESCRIPTION "Table of manually entered IP Address entries.  The number of 
                 entries is given by the value of slcServSLCNetNumber."
    ::= { slcServSLCNetwork 3 }

slcServSLCNetEntry OBJECT-TYPE
    SYNTAX      SlcServSLCNetEntry
    MAX-ACCESS  not-accessible
    STATUS      current
    DESCRIPTION 
        "An entry containing an IP Address for searching the SLC Network."
    INDEX       { slcServSLCNetIndex }
    ::= { slcServSLCNetTable 1 }

SlcServSLCNetEntry ::= SEQUENCE {
    slcServSLCNetIndex  Integer32,
    slcServSLCNetIP     IpAddress
}

slcServSLCNetIndex OBJECT-TYPE
    SYNTAX      Integer32 (1..200)
    MAX-ACCESS  read-only
    STATUS      current
    DESCRIPTION "Reference index for each manual IP Address."
    ::= { slcServSLCNetEntry 1 }

slcServSLCNetIP OBJECT-TYPE
    SYNTAX      IpAddress
    MAX-ACCESS  read-only
    STATUS      current
    DESCRIPTION "The IP Address to search for in the SLC Network."
    ::= { slcServSLCNetEntry 2 }


slcServPhoneHome    OBJECT IDENTIFIER ::= { slcServices 11 }

slcServPhoneHomeState OBJECT-TYPE
    SYNTAX      EnabledState
    MAX-ACCESS  read-only
    STATUS      current
    DESCRIPTION "Enables the Phone Home feature."
    ::= { slcServPhoneHome 1 }

slcServPhoneHomeIP OBJECT-TYPE
    SYNTAX      IpAddress
    MAX-ACCESS  read-only
    STATUS      current
    DESCRIPTION "The IP Address used for Phone Home communication."
    ::= { slcServPhoneHome 2 }


slcServHostList    OBJECT IDENTIFIER ::= { slcServices 12 }

slcServHostListNumber OBJECT-TYPE
    SYNTAX      Integer32 (0..50)
    MAX-ACCESS  read-only
    STATUS      current
    DESCRIPTION "The number of entries in the Host List table."
    ::= { slcServHostList 1 }

-- Host List table

slcServHostListTable OBJECT-TYPE
    SYNTAX      SEQUENCE OF SlcServHostListEntry
    MAX-ACCESS  not-accessible
    STATUS      current
    DESCRIPTION "Table of Host Lists.  The number of entries is given by the 
                 value of slcServHostListNumber."
    ::= { slcServHostList 2 }

slcServHostListEntry OBJECT-TYPE
    SYNTAX      SlcServHostListEntry
    MAX-ACCESS  not-accessible
    STATUS      current
    DESCRIPTION "An entry containing a Host List, used for Dial-in connections 
                 on a Device Port or PC Card modem."
    INDEX       { slcServHostListIndex }
    ::= { slcServHostListTable 1 }

SlcServHostListEntry ::= SEQUENCE {
    slcServHostListIndex        Integer32,
    slcServHostListName         OCTET STRING,
    slcServHostListRetryCount   Integer32,
    slcServHostListAuth         EnabledState,
    slcServHostListNumHosts     Integer32,
    slcServHostListHosts        OCTET STRING
}

slcServHostListIndex OBJECT-TYPE
    SYNTAX      Integer32 (1..50)
    MAX-ACCESS  read-only
    STATUS      current
    DESCRIPTION "Reference index for each Host List."
    ::= { slcServHostListEntry 1 }

slcServHostListName OBJECT-TYPE
    SYNTAX      OCTET STRING
    MAX-ACCESS  read-only
    STATUS      current
    DESCRIPTION "The unique name assigned to the Host List."
    ::= { slcServHostListEntry 2 }

slcServHostListRetryCount OBJECT-TYPE
    SYNTAX      Integer32
    MAX-ACCESS  read-only
    STATUS      current
    DESCRIPTION "The number of times to retry connections to an individual host 
                 within the Host List."
    ::= { slcServHostListEntry 3 }

slcServHostListAuth OBJECT-TYPE
    SYNTAX      EnabledState
    MAX-ACCESS  read-only
    STATUS      current
    DESCRIPTION "If enabled, authentication is enabled for the hosts in the 
                 Host List."
    ::= { slcServHostListEntry 4 }

slcServHostListNumHosts OBJECT-TYPE
    SYNTAX      Integer32 (0..10)
    MAX-ACCESS  read-only
    STATUS      current
    DESCRIPTION "The number of individual hosts in the Host List."
    ::= { slcServHostListEntry 5 }

slcServHostListHosts OBJECT-TYPE
    SYNTAX      OCTET STRING
    MAX-ACCESS  read-only
    STATUS      current
    DESCRIPTION "A string containing all hosts in the Host List; the entry for 
                 each host is separated by a ';'.  Each host entry is formatted 
                 as follows: '<Host>,<Protocol>,<TCP Port>,<Escape Sequence>;'."
    ::= { slcServHostListEntry 6 }


slcServWebTerm    OBJECT IDENTIFIER ::= { slcServices 13 }

slcServWebTermDeployment OBJECT-TYPE
    SYNTAX      INTEGER { javaWebStart(1), applet(2) }
    MAX-ACCESS  read-only
    STATUS      current
    DESCRIPTION "The method used to launch the Java Terminal for Web SSH and 
                 Web Telnet."
    ::= { slcServWebTerm 1 }

slcServWebTermBufSize OBJECT-TYPE
    SYNTAX      Integer32 (24..5000)
    MAX-ACCESS  read-only
    STATUS      current
    DESCRIPTION "The number of lines in the Java Terminal buffer."
    ::= { slcServWebTerm 2 }


--
-- Auth Group
--

slcAuthLocal    OBJECT IDENTIFIER ::= { slcAuth 1 }

slcAuthLocalNumber OBJECT-TYPE
    SYNTAX      Integer32 (1..128)
    MAX-ACCESS  read-only
    STATUS      current
    DESCRIPTION "The number of entries in the Local Users table."
    ::= { slcAuthLocal 1 }

-- Local Users table

slcAuthLocalUsersTable OBJECT-TYPE
    SYNTAX      SEQUENCE OF SlcAuthLocalUserEntry
    MAX-ACCESS  not-accessible
    STATUS      current
    DESCRIPTION "Table of Local Users entries.  The number of entries 
                 is given by the value of slcAuthLocalNumber."
    ::= { slcAuthLocal 2 }

slcAuthLocalUserEntry OBJECT-TYPE
    SYNTAX      SlcAuthLocalUserEntry
    MAX-ACCESS  not-accessible
    STATUS      current
    DESCRIPTION "An entry containing a Local Users and it's attributes."
    INDEX       { slcAuthLocalUserIndex }
    ::= { slcAuthLocalUsersTable 1 }

SlcAuthLocalUserEntry ::= SEQUENCE {
    slcAuthLocalUserIndex   Integer32,
    slcAuthLocalUserLogin   OCTET STRING (SIZE(0..32)),
    slcAuthLocalUserUID     Unsigned32,
    slcAuthLocalUserListenPorts OCTET STRING,
    slcAuthLocalUserDataPorts   OCTET STRING,
    slcAuthLocalUserClearPorts  OCTET STRING,
    slcAuthLocalUserEscapeSeq   OCTET STRING,
    slcAuthLocalUserBreakSeq    OCTET STRING,
    slcAuthLocalUserMenu        OCTET STRING,
    slcAuthLocalUserDialback    EnabledState,
    slcAuthLocalUserDialbackNum OCTET STRING
    slcAuthLocalUserGroup       UserGroup,
    slcAuthLocalUserRights      UserRights,
    slcAuthLocalUserPwdExpires  EnabledState,
    slcAuthLocalUserChangePwd   EnabledState,
    slcAuthLocalUserChangePwdNextLogin  EnabledState
}

slcAuthLocalUserIndex OBJECT-TYPE
    SYNTAX      Integer32 (1..128)
    MAX-ACCESS  read-only
    STATUS      current
    DESCRIPTION "Reference index for each Local User."
    ::= { slcAuthLocalUserEntry 1 }

slcAuthLocalUserLogin OBJECT-TYPE
    SYNTAX      OCTET STRING (SIZE(0..33))
    MAX-ACCESS  read-only
    STATUS      current
    DESCRIPTION "The login for the Local User.  If the user account is locked 
                 (cannot login), the login is appended with a '*' character."
    ::= { slcAuthLocalUserEntry 2 }

slcAuthLocalUserUID OBJECT-TYPE
    SYNTAX      Unsigned32
    MAX-ACCESS  read-only
    STATUS      current
    DESCRIPTION "The unique user identifier number for the Local User."
    ::= { slcAuthLocalUserEntry 3 }

slcAuthLocalUserListenPorts OBJECT-TYPE
    SYNTAX      OCTET STRING
    MAX-ACCESS  read-only
    STATUS      current
    DESCRIPTION "The Device Ports and PC Card slots which the Local User has 
                 permission to access via 'connect listen'."
    ::= { slcAuthLocalUserEntry 4 }

slcAuthLocalUserDataPorts OBJECT-TYPE
    SYNTAX      OCTET STRING
    MAX-ACCESS  read-only
    STATUS      current
    DESCRIPTION "The Device Ports and PC Card slots which the Local User has 
                 permission to access via 'connect direct'."
    ::= { slcAuthLocalUserEntry 5 }

slcAuthLocalUserClearPorts OBJECT-TYPE
    SYNTAX      OCTET STRING
    MAX-ACCESS  read-only
    STATUS      current
    DESCRIPTION "The Device Ports and PC Card slots which the Local User has 
                 permission to clear."
    ::= { slcAuthLocalUserEntry 6 }

slcAuthLocalUserEscapeSeq OBJECT-TYPE
    SYNTAX      OCTET STRING
    MAX-ACCESS  read-only
    STATUS      current
    DESCRIPTION "The character sequence which the Local User uses to terminate 
                 connections to Device Ports."
    ::= { slcAuthLocalUserEntry 7 }

slcAuthLocalUserBreakSeq OBJECT-TYPE
    SYNTAX      OCTET STRING
    MAX-ACCESS  read-only
    STATUS      current
    DESCRIPTION "The character sequence which the Local User uses to send a 
                 break sequence."
    ::= { slcAuthLocalUserEntry 8 }

slcAuthLocalUserMenu OBJECT-TYPE
    SYNTAX      OCTET STRING
    MAX-ACCESS  read-only
    STATUS      current
    DESCRIPTION "The custom user menu defined for the Local User.  If this is 
                 empty, there is no menu defined for the Local User.  The menu 
                 name is followed by a slash '/' character and either a 'y' if 
                 the menu is automatically displayed at login, or a 'n' if it 
                 is not automatically displayed at login."
    ::= { slcAuthLocalUserEntry 9 }

slcAuthLocalUserDialback OBJECT-TYPE
    SYNTAX      EnabledState
    MAX-ACCESS  read-only
    STATUS      current
    DESCRIPTION 
        "If enabled, the Local User has permission to use modem dialback."
    ::= { slcAuthLocalUserEntry 10 }

slcAuthLocalUserDialbackNum OBJECT-TYPE
    SYNTAX      OCTET STRING
    MAX-ACCESS  read-only
    STATUS      current
    DESCRIPTION "The dialback number defined for the Local User." 
    ::= { slcAuthLocalUserEntry 11 }

slcAuthLocalUserGroup OBJECT-TYPE
    SYNTAX      UserGroup
    MAX-ACCESS  read-only
    STATUS      current
    DESCRIPTION "The group assigned to the Local User."
    ::= { slcAuthLocalUserEntry 12 }

slcAuthLocalUserRights OBJECT-TYPE
    SYNTAX      UserRights
    MAX-ACCESS  read-only
    STATUS      current
    DESCRIPTION "The rights assigned to the Local User."
    ::= { slcAuthLocalUserEntry 13 }

slcAuthLocalUserPwdExpires OBJECT-TYPE
    SYNTAX      EnabledState
    MAX-ACCESS  read-only
    STATUS      current
    DESCRIPTION "If enabled, the local user's password will expire."
    ::= { slcAuthLocalUserEntry 14 }

slcAuthLocalUserChangePwd OBJECT-TYPE
    SYNTAX      EnabledState
    MAX-ACCESS  read-only
    STATUS      current
    DESCRIPTION "If enabled, the local user can change their password."
    ::= { slcAuthLocalUserEntry 15 }

slcAuthLocalUserChangePwdNextLogin OBJECT-TYPE
    SYNTAX      EnabledState
    MAX-ACCESS  read-only
    STATUS      current
    DESCRIPTION "If enabled, the local user must change their password at 
                 their next login."
    ::= { slcAuthLocalUserEntry 16 }

slcAuthLocalState OBJECT-TYPE
    SYNTAX      EnabledState
    MAX-ACCESS  read-only
    STATUS      current
    DESCRIPTION "If enabled, Local Users are used for authentication."
    ::= { slcAuthLocal 3 }

slcAuthLocalOrder OBJECT-TYPE
    SYNTAX      AuthOrder
    MAX-ACCESS  read-only
    STATUS      current
    DESCRIPTION "The authentication order of Local Users in authentication 
                 methods."
    ::= { slcAuthLocal 4 }

slcAuthLocalComplexPasswords OBJECT-TYPE
    SYNTAX      EnabledState
    MAX-ACCESS  read-only
    STATUS      current
    DESCRIPTION "If enabled, Local Users are required to use complex passwords 
                 that are at least 8 characters long and contain at least one 
                 uppercase character, one lowercase character, one digit, and 
                 one non-alphanumeric character."
    ::= { slcAuthLocal 5 }

slcAuthLocalUseNextMethod OBJECT-TYPE
    SYNTAX      EnabledState
    MAX-ACCESS  read-only
    STATUS      current
    DESCRIPTION "This object applies to all authentication methods, not just 
                 Local Users.  If enabled, authentication will occur using 
                 all methods, in the order of their precedence, until a 
                 successful authentication occurs.  If disabled, only the 
                 first authentication method that responds will be used."
    ::= { slcAuthLocal 6 }

slcAuthLocalAllowReuse OBJECT-TYPE
    SYNTAX      EnabledState
    MAX-ACCESS  read-only
    STATUS      current
    DESCRIPTION "If enabled, local users can reuse old passwords."
    ::= { slcAuthLocal 7 }

slcAuthLocalReuseHistory OBJECT-TYPE
    SYNTAX      Integer32 (0..8)
    MAX-ACCESS  read-only
    STATUS      current
    DESCRIPTION "The number of passwords a local user must use before reusing 
                 an old password."
    ::= { slcAuthLocal 8 }

slcAuthLocalPasswordLifetime OBJECT-TYPE
    SYNTAX      Integer32 (1..365)
    MAX-ACCESS  read-only
    STATUS      current
    DESCRIPTION "The number of days until a password expires."
    ::= { slcAuthLocal 9 }

slcAuthLocalWarningPeriod OBJECT-TYPE
    SYNTAX      Integer32 (0..90)
    MAX-ACCESS  read-only
    STATUS      current
    DESCRIPTION "The number of days before a password expires that a local 
                 user is warned about the expiring password.  A value of 0 
                 indicates that this feature is disabled."
    ::= { slcAuthLocal 10 }

slcAuthLocalMaxLoginAttempts OBJECT-TYPE
    SYNTAX      Integer32 (0..8)
    MAX-ACCESS  read-only
    STATUS      current
    DESCRIPTION "The number of times a local user can attempt to log in 
                 unsuccessfully before the SLC locks the user out.  A value 
                 of 0 indicates that this feature is disabled."
    ::= { slcAuthLocal 11 }

slcAuthLocalLockoutPeriod OBJECT-TYPE
    SYNTAX      Integer32 (0..90)
    MAX-ACCESS  read-only
    STATUS      current
    DESCRIPTION "The number of minutes the locked-out user must wait before 
                 trying to log in to to the SLC again.  A value of 0 indicates 
                 that this feature is disabled."
    ::= { slcAuthLocal 12 }

slcAuthLocalMultipleSysadminLogins OBJECT-TYPE
    SYNTAX      EnabledState
    MAX-ACCESS  read-only
    STATUS      current
    DESCRIPTION "If enabled, multiple sysadmin logins to the web are allowed."
    ::= { slcAuthLocal 13 }

slcAuthLocalSysadminConsoleOnly OBJECT-TYPE
    SYNTAX      EnabledState
    MAX-ACCESS  read-only
    STATUS      current
    DESCRIPTION "If enabled, the sysadmin can only access the SLC via the 
                 Console Port."
    ::= { slcAuthLocal 14 }


slcAuthNIS      OBJECT IDENTIFIER ::= { slcAuth 2 }

slcAuthNISState OBJECT-TYPE
    SYNTAX      EnabledState
    MAX-ACCESS  read-only
    STATUS      current
    DESCRIPTION "If enabled, NIS is used for authentication."
    ::= { slcAuthNIS 1 }

slcAuthNISOrder OBJECT-TYPE
    SYNTAX      AuthOrder
    MAX-ACCESS  read-only
    STATUS      current
    DESCRIPTION 
        "The authentication order of NIS in remote authentication methods."
    ::= { slcAuthNIS 2 }

slcAuthNISDomain OBJECT-TYPE
    SYNTAX      OCTET STRING (SIZE(0..80))
    MAX-ACCESS  read-only
    STATUS      current
    DESCRIPTION "The NIS domain."
    ::= { slcAuthNIS 3 }

slcAuthNISBroadcast OBJECT-TYPE
    SYNTAX      EnabledState
    MAX-ACCESS  read-only
    STATUS      current
    DESCRIPTION "If enabled, the SLC broadcasts for the NIS server."
    ::= { slcAuthNIS 4 }

slcAuthNISMaster OBJECT-TYPE
    SYNTAX      IpAddress
    MAX-ACCESS  read-only
    STATUS      current
    DESCRIPTION "The IP Address of the NIS master server."
    ::= { slcAuthNIS 5 }

slcAuthNISSlave1 OBJECT-TYPE
    SYNTAX      IpAddress
    MAX-ACCESS  read-only
    STATUS      current
    DESCRIPTION "The IP Address of the NIS slave server #1."
    ::= { slcAuthNIS 6 }

slcAuthNISSlave2 OBJECT-TYPE
    SYNTAX      IpAddress
    MAX-ACCESS  read-only
    STATUS      current
    DESCRIPTION "The IP Address of the NIS slave server #2."
    ::= { slcAuthNIS 7 }

slcAuthNISSlave3 OBJECT-TYPE
    SYNTAX      IpAddress
    MAX-ACCESS  read-only
    STATUS      current
    DESCRIPTION "The IP Address of the NIS slave server #3."
    ::= { slcAuthNIS 8 }

slcAuthNISGroup OBJECT-TYPE
    SYNTAX      UserGroup
    MAX-ACCESS  read-only
    STATUS      current
    DESCRIPTION "The group assigned to NIS users who login to the SLC and 
                 do not have group/rights defined in the Remote User database."
    ::= { slcAuthNIS 9 }

slcAuthNISRights OBJECT-TYPE
    SYNTAX      UserRights
    MAX-ACCESS  read-only
    STATUS      current
    DESCRIPTION "The rights assigned to NIS users who login to the SLC and 
                 do not have group/rights defined in the Remote User database."
    ::= { slcAuthNIS 10 }

slcAuthNISMenu OBJECT-TYPE
    SYNTAX      OCTET STRING
    MAX-ACCESS  read-only
    STATUS      current
    DESCRIPTION "The custom user menu defined for all NIS users who login 
                 to the SLC.  If this is empty, there is no menu defined for 
                 NIS Users."
    ::= { slcAuthNIS 11 }

slcAuthNISListenPorts OBJECT-TYPE
    SYNTAX      OCTET STRING
    MAX-ACCESS  read-only
    STATUS      current
    DESCRIPTION "The Device Ports and PC Card slots which users authenticated 
                 via NIS have permission to access via 'connect listen'."
    ::= { slcAuthNIS 12 }

slcAuthNISDataPorts OBJECT-TYPE
    SYNTAX      OCTET STRING
    MAX-ACCESS  read-only
    STATUS      current
    DESCRIPTION "The Device Ports and PC Card slots which users authenticated 
                 via NIS have permission to access via 'connect direct'."
    ::= { slcAuthNIS 13 }

slcAuthNISClearPorts OBJECT-TYPE
    SYNTAX      OCTET STRING
    MAX-ACCESS  read-only
    STATUS      current
    DESCRIPTION "The Device Ports and PC Card slots which users authenticated 
                 via NIS have permission to clear."
    ::= { slcAuthNIS 14 }

slcAuthNISSlave4 OBJECT-TYPE
    SYNTAX      IpAddress
    MAX-ACCESS  read-only
    STATUS      current
    DESCRIPTION "The IP Address of the NIS slave server #4."
    ::= { slcAuthNIS 15 }

slcAuthNISSlave5 OBJECT-TYPE
    SYNTAX      IpAddress
    MAX-ACCESS  read-only
    STATUS      current
    DESCRIPTION "The IP Address of the NIS slave server #5."
    ::= { slcAuthNIS 16 }

slcAuthNISEscapeSeq OBJECT-TYPE
    SYNTAX      OCTET STRING
    MAX-ACCESS  read-only
    STATUS      current
    DESCRIPTION "The character sequence which the NIS user uses to terminate 
                 connections to Device Ports."
    ::= { slcAuthNIS 17 }

slcAuthNISBreakSeq OBJECT-TYPE
    SYNTAX      OCTET STRING
    MAX-ACCESS  read-only
    STATUS      current
    DESCRIPTION "The character sequence which the NIS user uses to send a 
                 break sequence."
    ::= { slcAuthNIS 18 }

slcAuthNISDialback OBJECT-TYPE
    SYNTAX      EnabledState
    MAX-ACCESS  read-only
    STATUS      current
    DESCRIPTION "If enabled, NIS users have permission to use modem dialback."
    ::= { slcAuthNIS 19 }

slcAuthNISDialbackNum OBJECT-TYPE
    SYNTAX      OCTET STRING
    MAX-ACCESS  read-only
    STATUS      current
    DESCRIPTION "The dialback number defined for NIS users." 
    ::= { slcAuthNIS 20 }


slcAuthLDAP     OBJECT IDENTIFIER ::= { slcAuth 3 }

slcAuthLDAPState OBJECT-TYPE
    SYNTAX      EnabledState
    MAX-ACCESS  read-only
    STATUS      current
    DESCRIPTION "If enabled, LDAP is used for authentication."
    ::= { slcAuthLDAP 1 }

slcAuthLDAPOrder OBJECT-TYPE
    SYNTAX      AuthOrder
    MAX-ACCESS  read-only
    STATUS      current
    DESCRIPTION 
        "The authentication order of LDAP in remote authentication methods."
    ::= { slcAuthLDAP 2 }

slcAuthLDAPServer OBJECT-TYPE
    SYNTAX      IpAddress
    MAX-ACCESS  read-only
    STATUS      current
    DESCRIPTION "The IP Address of the LDAP server."
    ::= { slcAuthLDAP 3 }

slcAuthLDAPBase OBJECT-TYPE
    SYNTAX      OCTET STRING (SIZE(0..80))
    MAX-ACCESS  read-only
    STATUS      current
    DESCRIPTION "The LDAP Base."
    ::= { slcAuthLDAP 4 }

slcAuthLDAPBindName OBJECT-TYPE
    SYNTAX      OCTET STRING (SIZE(0..80))
    MAX-ACCESS  read-only
    STATUS      current
    DESCRIPTION "The LDAP Bind Name."
    ::= { slcAuthLDAP 5 }

slcAuthLDAPPort OBJECT-TYPE
    SYNTAX      Integer32 (0..65535)
    MAX-ACCESS  read-only
    STATUS      current
    DESCRIPTION "The LDAP TCP Port Number."
    ::= { slcAuthLDAP 6 }

slcAuthLDAPADSupport OBJECT-TYPE
    SYNTAX      EnabledState
    MAX-ACCESS  read-only
    STATUS      current
    DESCRIPTION "If enabled, Active Directory support is enabled for LDAP."
    ::= { slcAuthLDAP 7 }

slcAuthLDAPGroup OBJECT-TYPE
    SYNTAX      UserGroup
    MAX-ACCESS  read-only
    STATUS      current
    DESCRIPTION "The group assigned to LDAP users who login to the SLC and 
                 do not have group/rights defined in the Remote User database."
    ::= { slcAuthLDAP 8 }

slcAuthLDAPRights OBJECT-TYPE
    SYNTAX      UserRights
    MAX-ACCESS  read-only
    STATUS      current
    DESCRIPTION "The rights assigned to LDAP users who login to the SLC and 
                 do not have group/rights defined in the Remote User database."
    ::= { slcAuthLDAP 9 }

slcAuthLDAPMenu OBJECT-TYPE
    SYNTAX      OCTET STRING
    MAX-ACCESS  read-only
    STATUS      current
    DESCRIPTION "The custom user menu defined for all LDAP users who login 
                 to the SLC.  If this is empty, there is no menu defined for 
                 LDAP Users."
    ::= { slcAuthLDAP 10 }

slcAuthLDAPListenPorts OBJECT-TYPE
    SYNTAX      OCTET STRING
    MAX-ACCESS  read-only
    STATUS      current
    DESCRIPTION "The Device Ports and PC Card slots which users authenticated 
                 via LDAP have permission to access via 'connect listen'."
    ::= { slcAuthLDAP 11 }

slcAuthLDAPDataPorts OBJECT-TYPE
    SYNTAX      OCTET STRING
    MAX-ACCESS  read-only
    STATUS      current
    DESCRIPTION "The Device Ports and PC Card slots which users authenticated 
                 via LDAP have permission to access via 'connect direct'."
    ::= { slcAuthLDAP 12 }

slcAuthLDAPClearPorts OBJECT-TYPE
    SYNTAX      OCTET STRING
    MAX-ACCESS  read-only
    STATUS      current
    DESCRIPTION "The Device Ports and PC Card slots which users authenticated 
                 via LDAP have permission to clear."
    ::= { slcAuthLDAP 13 }

slcAuthLDAPEncrypt OBJECT-TYPE
    SYNTAX      EnabledState
    MAX-ACCESS  read-only
    STATUS      current
    DESCRIPTION "If enabled, encrypt messages between the SLC and the LDAP 
                 server."
    ::= { slcAuthLDAP 14 }

slcAuthLDAPEscapeSeq OBJECT-TYPE
    SYNTAX      OCTET STRING
    MAX-ACCESS  read-only
    STATUS      current
    DESCRIPTION "The character sequence which the LDAP user uses to terminate 
                 connections to Device Ports."
    ::= { slcAuthLDAP 15 }

slcAuthLDAPBreakSeq OBJECT-TYPE
    SYNTAX      OCTET STRING
    MAX-ACCESS  read-only
    STATUS      current
    DESCRIPTION "The character sequence which the LDAP user uses to send a 
                 break sequence."
    ::= { slcAuthLDAP 16 }

slcAuthLDAPBindWithLogin OBJECT-TYPE
    SYNTAX      EnabledState
    MAX-ACCESS  read-only
    STATUS      current
    DESCRIPTION "If enabled, bind to the LDAP server using the current login 
                 and password.  The $login token in slcAuthLDAPBindName will 
                 be replaced with the current login."
    ::= { slcAuthLDAP 17 }

slcAuthLDAPUseLDAPSchema OBJECT-TYPE
    SYNTAX      EnabledState
    MAX-ACCESS  read-only
    STATUS      current
    DESCRIPTION "If enabled, attributes and permissions for remote users are 
                 retrieved from an LDAP server."
    ::= { slcAuthLDAP 18 }

slcAuthLDAPDialback OBJECT-TYPE
    SYNTAX      EnabledState
    MAX-ACCESS  read-only
    STATUS      current
    DESCRIPTION "If enabled, LDAP users have permission to use modem dialback."
    ::= { slcAuthLDAP 19 }

slcAuthLDAPDialbackNum OBJECT-TYPE
    SYNTAX      OCTET STRING
    MAX-ACCESS  read-only
    STATUS      current
    DESCRIPTION "The dialback number defined for LDAP users." 
    ::= { slcAuthLDAP 20 }


slcAuthRADIUS   OBJECT IDENTIFIER ::= { slcAuth 4 }

slcAuthRADIUSState OBJECT-TYPE
    SYNTAX      EnabledState
    MAX-ACCESS  read-only
    STATUS      current
    DESCRIPTION "If enabled, RADIUS is used for authentication."
    ::= { slcAuthRADIUS 1 }

slcAuthRADIUSOrder OBJECT-TYPE
    SYNTAX      AuthOrder
    MAX-ACCESS  read-only
    STATUS      current
    DESCRIPTION 
        "The authentication order of RADIUS in remote authentication methods."
    ::= { slcAuthRADIUS 2 }

slcAuthRADIUSTimeout OBJECT-TYPE
    SYNTAX      Integer32 (0..30)
    MAX-ACCESS  read-only
    STATUS      current
    DESCRIPTION "The RADIUS Timeout in seconds.  A value of 0 indicates 
                 that timeouts are disabled."
    ::= { slcAuthRADIUS 3 }

-- RADIUS Servers table

slcAuthRADIUSServerTable OBJECT-TYPE
    SYNTAX      SEQUENCE OF SlcAuthRADIUSServerEntry
    MAX-ACCESS  not-accessible
    STATUS      current
    DESCRIPTION "Table of RADIUS servers."
    ::= { slcAuthRADIUS 4 }

slcAuthRADIUSServerEntry OBJECT-TYPE
    SYNTAX      SlcAuthRADIUSServerEntry
    MAX-ACCESS  not-accessible
    STATUS      current
    DESCRIPTION "An entry containing a RADIUS server and it's parameters."
    INDEX       { slcAuthRADIUSServerIndex }
    ::= { slcAuthRADIUSServerTable 1 }

SlcAuthRADIUSServerEntry ::= SEQUENCE {
    slcAuthRADIUSServerIndex    Integer32,
    slcAuthRADIUSServer         IpAddress,
    slcAuthRADIUSPort           Integer32 (0..65535)
}

slcAuthRADIUSServerIndex OBJECT-TYPE
    SYNTAX      Integer32 (1..2)
    MAX-ACCESS  read-only
    STATUS      current
    DESCRIPTION "Reference index for each RADIUS server."
    ::= { slcAuthRADIUSServerEntry 1 }

slcAuthRADIUSServer OBJECT-TYPE
    SYNTAX      IpAddress
    MAX-ACCESS  read-only
    STATUS      current
    DESCRIPTION "The IP Address of the RADIUS server."
    ::= { slcAuthRADIUSServerEntry 2 }

slcAuthRADIUSPort OBJECT-TYPE
    SYNTAX      Integer32 (0..65535)
    MAX-ACCESS  read-only
    STATUS      current
    DESCRIPTION "The RADIUS Server TCP Port Number."
    ::= { slcAuthRADIUSServerEntry 3 }

slcAuthRADIUSGroup OBJECT-TYPE
    SYNTAX      UserGroup
    MAX-ACCESS  read-only
    STATUS      current
    DESCRIPTION "The group assigned to RADIUS users who login to the SLC and 
                 do not have group/rights defined in the Remote User database."
    ::= { slcAuthRADIUS 5 }

slcAuthRADIUSRights OBJECT-TYPE
    SYNTAX      UserRights
    MAX-ACCESS  read-only
    STATUS      current
    DESCRIPTION "The rights assigned to RADIUS users who login to the SLC and 
                 do not have group/rights defined in the Remote User database."
    ::= { slcAuthRADIUS 6 }

slcAuthRADIUSMenu OBJECT-TYPE
    SYNTAX      OCTET STRING
    MAX-ACCESS  read-only
    STATUS      current
    DESCRIPTION "The custom user menu defined for all RADIUS users who login 
                 to the SLC.  If this is empty, there is no menu defined for 
                 RADIUS Users."
    ::= { slcAuthRADIUS 7 }

slcAuthRADIUSListenPorts OBJECT-TYPE
    SYNTAX      OCTET STRING
    MAX-ACCESS  read-only
    STATUS      current
    DESCRIPTION "The Device Ports and PC Card slots which users authenticated 
                 via RADIUS have permission to access via 'connect listen'."
    ::= { slcAuthRADIUS 8 }

slcAuthRADIUSDataPorts OBJECT-TYPE
    SYNTAX      OCTET STRING
    MAX-ACCESS  read-only
    STATUS      current
    DESCRIPTION "The Device Ports and PC Card slots which users authenticated 
                 via RADIUS have permission to access via 'connect direct'."
    ::= { slcAuthRADIUS 9 }

slcAuthRADIUSClearPorts OBJECT-TYPE
    SYNTAX      OCTET STRING
    MAX-ACCESS  read-only
    STATUS      current
    DESCRIPTION "The Device Ports and PC Card slots which users authenticated 
                 via RADIUS have permission to clear."
    ::= { slcAuthRADIUS 10 }

slcAuthRADIUSEscapeSeq OBJECT-TYPE
    SYNTAX      OCTET STRING
    MAX-ACCESS  read-only
    STATUS      current
    DESCRIPTION "The character sequence which the RADIUS user uses to terminate 
                 connections to Device Ports."
    ::= { slcAuthRADIUS 11 }

slcAuthRADIUSBreakSeq OBJECT-TYPE
    SYNTAX      OCTET STRING
    MAX-ACCESS  read-only
    STATUS      current
    DESCRIPTION "The character sequence which the RADIUS user uses to send a 
                 break sequence."
    ::= { slcAuthRADIUS 12 }

slcAuthRADIUSDialback OBJECT-TYPE
    SYNTAX      EnabledState
    MAX-ACCESS  read-only
    STATUS      current
    DESCRIPTION 
        "If enabled, RADIUS users have permission to use modem dialback."
    ::= { slcAuthRADIUS 13 }

slcAuthRADIUSDialbackNum OBJECT-TYPE
    SYNTAX      OCTET STRING
    MAX-ACCESS  read-only
    STATUS      current
    DESCRIPTION "The dialback number defined for RADIUS users." 
    ::= { slcAuthRADIUS 14 }


slcAuthKerberos OBJECT IDENTIFIER ::= { slcAuth 5 }

slcAuthKerbState OBJECT-TYPE
    SYNTAX      EnabledState
    MAX-ACCESS  read-only
    STATUS      current
    DESCRIPTION "If enabled, Kerberos is used for authentication."
    ::= { slcAuthKerberos 1 }

slcAuthKerbOrder OBJECT-TYPE
    SYNTAX      AuthOrder
    MAX-ACCESS  read-only
    STATUS      current
    DESCRIPTION 
        "The authentication order of Kerberos in remote authentication methods."
    ::= { slcAuthKerberos 2 }

slcAuthKerbRealm OBJECT-TYPE
    SYNTAX      OCTET STRING (SIZE(0..256))
    MAX-ACCESS  read-only
    STATUS      current
    DESCRIPTION "The Kerberos Realm."
    ::= { slcAuthKerberos 3 }

slcAuthKerbKDC OBJECT-TYPE
    SYNTAX      OCTET STRING (SIZE(0..256))
    MAX-ACCESS  read-only
    STATUS      current
    DESCRIPTION "The Kerberos KDC."
    ::= { slcAuthKerberos 4 }

slcAuthKerbKDCIP OBJECT-TYPE
    SYNTAX      IpAddress
    MAX-ACCESS  read-only
    STATUS      current
    DESCRIPTION "The IP Address of the Kerberos Key Distribution Server."
    ::= { slcAuthKerberos 5 }

slcAuthKerbKDCPort OBJECT-TYPE
    SYNTAX      Integer32 (0..65535)
    MAX-ACCESS  read-only
    STATUS      current
    DESCRIPTION "The Kerberos KDC Port Number."
    ::= { slcAuthKerberos 6 }

slcAuthKerbUseLDAP OBJECT-TYPE
    SYNTAX      EnabledState
    MAX-ACCESS  read-only
    STATUS      current
    DESCRIPTION "If enabled, LDAP is used for lookups."
    ::= { slcAuthKerberos 7 }

slcAuthKerbGroup OBJECT-TYPE
    SYNTAX      UserGroup
    MAX-ACCESS  read-only
    STATUS      current
    DESCRIPTION "The group assigned to Kerberos users who login to the SLC and 
                 do not have group/rights defined in the Remote User database."
    ::= { slcAuthKerberos 8 }

slcAuthKerbRights OBJECT-TYPE
    SYNTAX      UserRights
    MAX-ACCESS  read-only
    STATUS      current
    DESCRIPTION "The rights assigned to Kerberos users who login to the SLC and 
                 do not have group/rights defined in the Remote User database."
    ::= { slcAuthKerberos 9 }

slcAuthKerbMenu OBJECT-TYPE
    SYNTAX      OCTET STRING
    MAX-ACCESS  read-only
    STATUS      current
    DESCRIPTION "The custom user menu defined for all Kerberos users who login 
                 to the SLC.  If this is empty, there is no menu defined for 
                 Kerberos Users."
    ::= { slcAuthKerberos 10 }

slcAuthKerbListenPorts OBJECT-TYPE
    SYNTAX      OCTET STRING
    MAX-ACCESS  read-only
    STATUS      current
    DESCRIPTION "The Device Ports and PC Card slots which users authenticated 
                 via Kerberos have permission to access via 'connect listen'."
    ::= { slcAuthKerberos 11 }

slcAuthKerbDataPorts OBJECT-TYPE
    SYNTAX      OCTET STRING
    MAX-ACCESS  read-only
    STATUS      current
    DESCRIPTION "The Device Ports and PC Card slots which users authenticated 
                 via Kerberos have permission to access via 'connect direct'."
    ::= { slcAuthKerberos 12 }

slcAuthKerbClearPorts OBJECT-TYPE
    SYNTAX      OCTET STRING
    MAX-ACCESS  read-only
    STATUS      current
    DESCRIPTION "The Device Ports and PC Card slots which users authenticated 
                 via Kerberos have permission to clear."
    ::= { slcAuthKerberos 13 }

slcAuthKerbEscapeSeq OBJECT-TYPE
    SYNTAX      OCTET STRING
    MAX-ACCESS  read-only
    STATUS      current
    DESCRIPTION "The character sequence which the Kerberos user uses to 
                 terminate connections to Device Ports."
    ::= { slcAuthKerberos 14 }

slcAuthKerbBreakSeq OBJECT-TYPE
    SYNTAX      OCTET STRING
    MAX-ACCESS  read-only
    STATUS      current
    DESCRIPTION "The character sequence which the Kerberos user uses to send a 
                 break sequence."
    ::= { slcAuthKerberos 15 }

slcAuthKerbDialback OBJECT-TYPE
    SYNTAX      EnabledState
    MAX-ACCESS  read-only
    STATUS      current
    DESCRIPTION 
        "If enabled, Kerberos users have permission to use modem dialback."
    ::= { slcAuthKerberos 16 }

slcAuthKerbDialbackNum OBJECT-TYPE
    SYNTAX      OCTET STRING
    MAX-ACCESS  read-only
    STATUS      current
    DESCRIPTION "The dialback number defined for Kerberos users." 
    ::= { slcAuthKerberos 17 }


slcAuthTACACS   OBJECT IDENTIFIER ::= { slcAuth 6 }

slcAuthTACACSState OBJECT-TYPE
    SYNTAX      EnabledState
    MAX-ACCESS  read-only
    STATUS      current
    DESCRIPTION "If enabled, TACACS is used for authentication."
    ::= { slcAuthTACACS 1 }

slcAuthTACACSOrder OBJECT-TYPE
    SYNTAX      AuthOrder
    MAX-ACCESS  read-only
    STATUS      current
    DESCRIPTION 
        "The authentication order of TACACS in remote authentication methods."
    ::= { slcAuthTACACS 2 }

slcAuthTACACSServer OBJECT-TYPE
    SYNTAX      IpAddress
    MAX-ACCESS  read-only
    STATUS      current
    DESCRIPTION "The IP Address of the first TACACS server."
    ::= { slcAuthTACACS 3 }

slcAuthTACACSEncrypt OBJECT-TYPE
    SYNTAX      EnabledState
    MAX-ACCESS  read-only
    STATUS      current
    DESCRIPTION 
        "If enabled, encrypt messages between the SLC and the TACACS server."
    ::= { slcAuthTACACS 4 }

slcAuthTACACSGroup OBJECT-TYPE
    SYNTAX      UserGroup
    MAX-ACCESS  read-only
    STATUS      current
    DESCRIPTION "The group assigned to TACACS users who login to the SLC and 
                 do not have group/rights defined in the Remote User database."
    ::= { slcAuthTACACS 5 }

slcAuthTACACSRights OBJECT-TYPE
    SYNTAX      UserRights
    MAX-ACCESS  read-only
    STATUS      current
    DESCRIPTION "The rights assigned to TACACS users who login to the SLC and 
                 do not have group/rights defined in the Remote User database."
    ::= { slcAuthTACACS 6 }

slcAuthTACACSMenu OBJECT-TYPE
    SYNTAX      OCTET STRING
    MAX-ACCESS  read-only
    STATUS      current
    DESCRIPTION "The custom user menu defined for all TACACS users who login 
                 to the SLC.  If this is empty, there is no menu defined for 
                 TACACS Users."
    ::= { slcAuthTACACS 7 }

slcAuthTACACSListenPorts OBJECT-TYPE
    SYNTAX      OCTET STRING
    MAX-ACCESS  read-only
    STATUS      current
    DESCRIPTION "The Device Ports and PC Card slots which users authenticated 
                 via TACACS have permission to access via 'connect listen'."
    ::= { slcAuthTACACS 8 }

slcAuthTACACSDataPorts OBJECT-TYPE
    SYNTAX      OCTET STRING
    MAX-ACCESS  read-only
    STATUS      current
    DESCRIPTION "The Device Ports and PC Card slots which users authenticated 
                 via TACACS have permission to access via 'connect direct'."
    ::= { slcAuthTACACS 9 }

slcAuthTACACSClearPorts OBJECT-TYPE
    SYNTAX      OCTET STRING
    MAX-ACCESS  read-only
    STATUS      current
    DESCRIPTION "The Device Ports and PC Card slots which users authenticated 
                 via TACACS have permission to clear."
    ::= { slcAuthTACACS 10 }

slcAuthTACACSServer2 OBJECT-TYPE
    SYNTAX      IpAddress
    MAX-ACCESS  read-only
    STATUS      current
    DESCRIPTION "The IP Address of the second TACACS server."
    ::= { slcAuthTACACS 11 }

slcAuthTACACSServer3 OBJECT-TYPE
    SYNTAX      IpAddress
    MAX-ACCESS  read-only
    STATUS      current
    DESCRIPTION "The IP Address of the third TACACS server."
    ::= { slcAuthTACACS 12 }

slcAuthTACACSEscapeSeq OBJECT-TYPE
    SYNTAX      OCTET STRING
    MAX-ACCESS  read-only
    STATUS      current
    DESCRIPTION "The character sequence which the TACACS user uses to terminate 
                 connections to Device Ports."
    ::= { slcAuthTACACS 13 }

slcAuthTACACSBreakSeq OBJECT-TYPE
    SYNTAX      OCTET STRING
    MAX-ACCESS  read-only
    STATUS      current
    DESCRIPTION "The character sequence which the TACACS user uses to send a 
                 break sequence."
    ::= { slcAuthTACACS 14 }

slcAuthTACACSDialback OBJECT-TYPE
    SYNTAX      EnabledState
    MAX-ACCESS  read-only
    STATUS      current
    DESCRIPTION 
        "If enabled, TACACS users have permission to use modem dialback."
    ::= { slcAuthTACACS 15 }

slcAuthTACACSDialbackNum OBJECT-TYPE
    SYNTAX      OCTET STRING
    MAX-ACCESS  read-only
    STATUS      current
    DESCRIPTION "The dialback number defined for TACACS users." 
    ::= { slcAuthTACACS 16 }


slcAuthRemote   OBJECT IDENTIFIER ::= { slcAuth 7 }

slcAuthRemoteNumber OBJECT-TYPE
    SYNTAX      Integer32 (0..128)
    MAX-ACCESS  read-only
    STATUS      current
    DESCRIPTION "The number of entries in the Remote Users table."
    ::= { slcAuthRemote 1 }

-- Remote Users table

slcAuthRemoteUsersTable OBJECT-TYPE
    SYNTAX      SEQUENCE OF SlcAuthRemoteUserEntry
    MAX-ACCESS  not-accessible
    STATUS      current
    DESCRIPTION "Table of Remote Users entries.  The number of entries 
                 is given by the value of slcAuthRemoteNumber."
    ::= { slcAuthRemote 2 }

slcAuthRemoteUserEntry OBJECT-TYPE
    SYNTAX      SlcAuthRemoteUserEntry
    MAX-ACCESS  not-accessible
    STATUS      current
    DESCRIPTION "An entry containing a Remote User and its attributes."
    INDEX       { slcAuthRemoteUserIndex }
    ::= { slcAuthRemoteUsersTable 1 }

SlcAuthRemoteUserEntry ::= SEQUENCE {
    slcAuthRemoteUserIndex    Integer32,
    slcAuthRemoteUserLogin    OCTET STRING (SIZE(0..32)),
    slcAuthRemoteUserGroup    UserGroup,
    slcAuthRemoteUserRights   UserRights,
    slcAuthRemoteUserListenPorts OCTET STRING,
    slcAuthRemoteUserDataPorts   OCTET STRING,
    slcAuthRemoteUserClearPorts  OCTET STRING,
    slcAuthRemoteUserEscapeSeq   OCTET STRING,
    slcAuthRemoteUserBreakSeq    OCTET STRING,
    slcAuthRemoteUserMenu        OCTET STRING,
    slcAuthRemoteUserLocked      EnabledState,
    slcAuthRemoteUserDialback    EnabledState,
    slcAuthRemoteUserDialbackNum OCTET STRING
}

slcAuthRemoteUserIndex OBJECT-TYPE
    SYNTAX      Integer32 (1..128)
    MAX-ACCESS  read-only
    STATUS      current
    DESCRIPTION "Reference index for each Remote User."
    ::= { slcAuthRemoteUserEntry 1 }

slcAuthRemoteUserLogin OBJECT-TYPE
    SYNTAX      OCTET STRING (SIZE(0..32))
    MAX-ACCESS  read-only
    STATUS      current
    DESCRIPTION "The login for the Remote User."
    ::= { slcAuthRemoteUserEntry 2 }

slcAuthRemoteUserGroup OBJECT-TYPE
    SYNTAX      UserGroup
    MAX-ACCESS  read-only
    STATUS      current
    DESCRIPTION "The group assigned to the Remote User."
    ::= { slcAuthRemoteUserEntry 3 }

slcAuthRemoteUserRights OBJECT-TYPE
    SYNTAX      UserRights
    MAX-ACCESS  read-only
    STATUS      current
    DESCRIPTION "The rights assigned to the Remote User."
    ::= { slcAuthRemoteUserEntry 4 }

slcAuthRemoteUserListenPorts OBJECT-TYPE
    SYNTAX      OCTET STRING
    MAX-ACCESS  read-only
    STATUS      current
    DESCRIPTION "The Device Ports and PC Card slots which the Remote User has 
                 permission to access via 'connect listen'."
    ::= { slcAuthRemoteUserEntry 5 }

slcAuthRemoteUserDataPorts OBJECT-TYPE
    SYNTAX      OCTET STRING
    MAX-ACCESS  read-only
    STATUS      current
    DESCRIPTION "The Device Ports and PC Card slots which the Remote User has 
                 permission to access via 'connect direct'."
    ::= { slcAuthRemoteUserEntry 6 }

slcAuthRemoteUserClearPorts OBJECT-TYPE
    SYNTAX      OCTET STRING
    MAX-ACCESS  read-only
    STATUS      current
    DESCRIPTION "The Device Ports and PC Card slots which the Remote User has 
                 permission to clear."
    ::= { slcAuthRemoteUserEntry 7 }

slcAuthRemoteUserEscapeSeq OBJECT-TYPE
    SYNTAX      OCTET STRING
    MAX-ACCESS  read-only
    STATUS      current
    DESCRIPTION "The character sequence which the Remote User uses to terminate 
                 connections to Device Ports."
    ::= { slcAuthRemoteUserEntry 8 }

slcAuthRemoteUserBreakSeq OBJECT-TYPE
    SYNTAX      OCTET STRING
    MAX-ACCESS  read-only
    STATUS      current
    DESCRIPTION "The character sequence which the Remote User uses to send a 
                 break sequence."
    ::= { slcAuthRemoteUserEntry 9 }

slcAuthRemoteUserMenu OBJECT-TYPE
    SYNTAX      OCTET STRING
    MAX-ACCESS  read-only
    STATUS      current
    DESCRIPTION "The custom user menu defined for the Remote User.  If this is 
                 empty, there is no menu defined for the Remote User.  The menu 
                 name is followed by a slash '/' character and either a 'y' if 
                 the menu is automatically displayed at login, or a 'n' if it 
                 is not automatically displayed at login."
    ::= { slcAuthRemoteUserEntry 10 }

slcAuthRemoteUserLocked OBJECT-TYPE
    SYNTAX      EnabledState
    MAX-ACCESS  read-only
    STATUS      current
    DESCRIPTION "If enabled, the Remote User's account is locked (blocked)."
    ::= { slcAuthRemoteUserEntry 11 }

slcAuthRemoteUserDialback OBJECT-TYPE
    SYNTAX      EnabledState
    MAX-ACCESS  read-only
    STATUS      current
    DESCRIPTION 
        "If enabled, the Remote User has permission to use modem dialback."
    ::= { slcAuthRemoteUserEntry 12 }

slcAuthRemoteUserDialbackNum OBJECT-TYPE
    SYNTAX      OCTET STRING
    MAX-ACCESS  read-only
    STATUS      current
    DESCRIPTION "The dialback number defined for the Remote User." 
    ::= { slcAuthRemoteUserEntry 13 }

slcAuthRemoteAuthListOnly OBJECT-TYPE
    SYNTAX      EnabledState
    MAX-ACCESS  read-only
    STATUS      current
    DESCRIPTION "If enabled, remote users who log into the SLC will only be 
                 authenticated if they are listed in the remote user list."
    ::= { slcAuthRemote 3 }


--
-- Devices Group
--

slcDevConsolePort   OBJECT IDENTIFIER ::= { slcDevices 1 }

slcDevConBaud OBJECT-TYPE
    SYNTAX      Integer32 
                ( 300 | 600 | 1200 | 2400 | 4800 | 
                  9600 | 19200 | 38400 | 57600 | 115200 )
    MAX-ACCESS  read-only
    STATUS      current
    DESCRIPTION "The baud rate of the Console Port."
    ::= { slcDevConsolePort 1 }

slcDevConDataBits OBJECT-TYPE
    SYNTAX      Integer32 ( 7 | 8 )
    MAX-ACCESS  read-only
    STATUS      current
    DESCRIPTION "The data bits of the Console Port."
    ::= { slcDevConsolePort 2 }

slcDevConStopBits OBJECT-TYPE
    SYNTAX      Integer32 ( 1 | 2 )
    MAX-ACCESS  read-only
    STATUS      current
    DESCRIPTION "The stop bits of the Console Port."
    ::= { slcDevConsolePort 3 }

slcDevConParity OBJECT-TYPE
    SYNTAX      INTEGER { none(1), odd(2), even(3) }
    MAX-ACCESS  read-only
    STATUS      current
    DESCRIPTION "The parity of the Console Port."
    ::= { slcDevConsolePort 4 }

slcDevConFlowControl OBJECT-TYPE
    SYNTAX      INTEGER { none(1), xonxoff(2), rtscts(3) }
    MAX-ACCESS  read-only
    STATUS      current
    DESCRIPTION "The flow control of the Console Port."
    ::= { slcDevConsolePort 5 }

slcDevConTimeout OBJECT-TYPE
    SYNTAX      Integer32 (0..30)
    MAX-ACCESS  read-only
    STATUS      current
    DESCRIPTION "The timeout (in minutes) for logins to the Console Port.  
                 A value of 0 indicates that timeouts are disabled."
    ::= { slcDevConsolePort 6 }

slcDevConShowLines OBJECT-TYPE
    SYNTAX      EnabledState
    MAX-ACCESS  read-only
    STATUS      current
    DESCRIPTION "If enabled, upon connecting to the Console Port, a series of 
                 characters (or lines) output to the Console Port before it 
                 was connected to are displayed."
    ::= { slcDevConsolePort 7 }

slcDevConNumberShowLines OBJECT-TYPE
    SYNTAX      Integer32 (1..50)
    MAX-ACCESS  read-only
    STATUS      current
    DESCRIPTION "If slcDevConShowLines is enabled, the number of lines that 
                 are displayed upon connecting to the Console Port."
    ::= { slcDevConsolePort 8 }


slcDevDevicePorts   OBJECT IDENTIFIER ::= { slcDevices 2 }

slcDevPortGlobal    OBJECT IDENTIFIER ::= { slcDevDevicePorts 1 }

slcDevGlobalListenPorts OBJECT-TYPE
    SYNTAX      OCTET STRING
    MAX-ACCESS  read-only
    STATUS      obsolete
    DESCRIPTION "The Device Ports which remotely authenticated users have 
                 permission to access via 'connect listen'.  This object has 
                 been replaced by permissions for each remote authentication 
                 method: slcAuthNISListenPorts, slcAuthLDAPListenPorts, 
                 slcAuthRADIUSListenPorts, slcAuthKerbListenPorts, 
                 slcAuthTACACSListenPorts."
    ::= { slcDevPortGlobal 1 }

slcDevGlobalDataPorts OBJECT-TYPE
    SYNTAX      OCTET STRING
    MAX-ACCESS  read-only
    STATUS      obsolete
    DESCRIPTION "The Device Ports which remotely authenticated users have 
                 permission to access via 'connect direct'.  This object has 
                 been replaced by permissions for each remote authentication 
                 method: slcAuthNISDataPorts, slcAuthLDAPDataPorts, 
                 slcAuthRADIUSDataPorts, slcAuthKerbDataPorts, 
                 slcAuthTACACSDataPorts."
    ::= { slcDevPortGlobal 2 }

slcDevGlobalClearPorts OBJECT-TYPE
    SYNTAX      OCTET STRING
    MAX-ACCESS  read-only
    STATUS      obsolete
    DESCRIPTION "The Device Ports which remotely authenticated users have 
                 permission to clear.  This object has been replaced by 
                 permissions for each remote authentication method: 
                 slcAuthNISClearPorts, slcAuthLDAPClearPorts, 
                 slcAuthRADIUSClearPorts, slcAuthKerbClearPorts, 
                 slcAuthTACACSClearPorts."
    ::= { slcDevPortGlobal 3 }

slcDevGlobalStartTelnetPort OBJECT-TYPE
    SYNTAX      Integer32 (0..65535)
    MAX-ACCESS  read-only
    STATUS      current
    DESCRIPTION "The starting TCP port for Telnet in connections 
                 to Device Ports."
    ::= { slcDevPortGlobal 4 }

slcDevGlobalStartSSHPort OBJECT-TYPE
    SYNTAX      Integer32 (0..65535)
    MAX-ACCESS  read-only
    STATUS      current
    DESCRIPTION "The starting TCP port for SSH in connections 
                 to Device Ports."
    ::= { slcDevPortGlobal 5 }

slcDevGlobalStartTCPPort OBJECT-TYPE
    SYNTAX      Integer32 (0..65535)
    MAX-ACCESS  read-only
    STATUS      current
    DESCRIPTION "The starting TCP port for TCP in connections 
                 to Device Ports."
    ::= { slcDevPortGlobal 6 }

slcDevGlobalMaxDirect OBJECT-TYPE
    SYNTAX      Integer32 (0..10)
    MAX-ACCESS  read-only
    STATUS      obsolete
    DESCRIPTION "The maximum number of direct connects allowed for each 
                 Device Port."
    ::= { slcDevPortGlobal 7 }


slcDevPortConfig    OBJECT IDENTIFIER ::= { slcDevDevicePorts 2 }

slcDevPortCfgNumber OBJECT-TYPE
    SYNTAX      Integer32 ( 8 | 16 | 32 | 48 )
    MAX-ACCESS  read-only
    STATUS      current
    DESCRIPTION 
        "The number of entries in the Device Port Configuration table."
    ::= { slcDevPortConfig 1 }

-- Device Port Configuration table.

slcDevPortCfgTable OBJECT-TYPE
    SYNTAX      SEQUENCE OF SlcDevPortCfgEntry
    MAX-ACCESS  not-accessible
    STATUS      current
    DESCRIPTION "Table for managing Device Port configuration.  The number of 
                 entries is given by the value of slcDevPortCfgNumber."
    ::= { slcDevPortConfig 2 }

slcDevPortCfgEntry OBJECT-TYPE
    SYNTAX      SlcDevPortCfgEntry
    MAX-ACCESS  not-accessible
    STATUS      current
    DESCRIPTION 
        "An entry containing all configuration settings for a Device Port."
    INDEX       { slcDevPortId }
    ::= { slcDevPortCfgTable 1 }

SlcDevPortCfgEntry ::= SEQUENCE {
    slcDevPortId                    Integer32,
-- General settings
    slcDevPortCfgName               OCTET STRING,
    slcDevPortCfgDevice             INTEGER,
    slcDevPortCfgDevLogin           OCTET STRING,
    slcDevPortCfgBreakSeq           OCTET STRING,
-- IP settings
    slcDevPortCfgTelnetState        EnabledState,
    slcDevPortCfgTelnetPort         Integer32,
    slcDevPortCfgTelnetAuth         EnabledState,
    slcDevPortCfgSSHState           EnabledState,
    slcDevPortCfgSSHPort            Integer32,
    slcDevPortCfgSSHAuth            EnabledState,
    slcDevPortCfgTCPState           EnabledState,
    slcDevPortCfgTCPPort            Integer32,
    slcDevPortCfgTCPAuth            EnabledState,
    slcDevPortCfgIP                 IpAddress,
-- Data (serial) settings
    slcDevPortCfgBaud               Integer32,
    slcDevPortCfgDataBits           INTEGER,
    slcDevPortCfgStopBits           INTEGER,
    slcDevPortCfgParity             INTEGER,
    slcDevPortCfgFlowControl        INTEGER,
    slcDevPortCfgLogins             EnabledState,
    slcDevPortCfgConnectDSR         EnabledState,
    slcDevPortCfgDisconnectDSR      EnabledState,
-- Modem settings
    slcDevPortCfgModemState         INTEGER,
    slcDevPortCfgModemMode          INTEGER,
    slcDevPortCfgLocalIP            IpAddress,
    slcDevPortCfgRemoteIP           IpAddress,
    slcDevPortCfgAuth               INTEGER,
    slcDevPortCfgCHAPHost           OCTET STRING,
    slcDevPortCfgInitScript         OCTET STRING,
    slcDevPortCfgTimeout            Integer32,
    slcDevPortCfgInitScript         OCTET STRING,
    slcDevPortCfgDialoutNum         OCTET STRING,
    slcDevPortCfgDialoutLogin       OCTET STRING,
    slcDevPortCfgDialbackMode       INTEGER,     
    slcDevPortCfgDialbackNum        OCTET STRING,     
    slcDevPortCfgNATState           EnabledState,
-- Logging settings
    slcDevPortCfgLocalState         EnabledState,
    slcDevPortCfgNFSFileState       EnabledState,
    slcDevPortCfgNFSDir             OCTET STRING,     
    slcDevPortCfgNFSMaxFiles        Integer32,
    slcDevPortCfgNFSMaxSize         Integer32,
    slcDevPortCfgEmailState         EnabledState,
    slcDevPortCfgEmailTrigger       INTEGER,     
    slcDevPortCfgEmailByteThresh    Integer32,     
    slcDevPortCfgEmailDelay         Integer32,     
    slcDevPortCfgEmailRestartDelay  Integer32,     
    slcDevPortCfgEmailTextString    OCTET STRING,     
    slcDevPortCfgEmailTo            OCTET STRING,     
    slcDevPortCfgEmailSubject       OCTET STRING,     
    slcDevPortCfgPCCardState        EnabledState,
    slcDevPortCfgPCCardLogTo        INTEGER,     
    slcDevPortCfgPCCardMaxFiles     Integer32,
    slcDevPortCfgPCCardMaxSize      Integer32,
-- Actions to control Device Port
    slcDevPortCfgAction             INTEGER,
-- Additional Settings
    slcDevPortCfgEmailSend          INTEGER,     
    slcDevPortCfgBanner             OCTET STRING,
    slcDevPortCfgIdleTimeout        Integer32,
    slcDevPortCfgRestartDelay       Integer32,
    slcDevPortCfgCallerIdLogging    EnabledState,
    slcDevPortCfgCallerIdATCmd      OCTET STRING,
    slcDevPortCfgDODAuth            INTEGER,
    slcDevPortCfgDODCHAPHost        OCTET STRING,
    slcDevPortCfgSLMLoggingState    EnabledState,
    slcDevPortCfgSLMNMS             OCTET STRING,
    slcDevPortCfgSLMByteThresh      Integer32,
    slcDevPortCfgSLMTimeFrame       Integer32,
    slcDevPortCfgWebColumns         Integer32,
    slcDevPortCfgWebRows            Integer32,
    slcDevPortCfgSyslogState        EnabledState,
    slcDevPortCfgHostList           OCTET STRING,
    slcDevPortCfgDevLowTemp         Integer32,
    slcDevPortCfgDevHighTemp        Integer32,
    slcDevPortCfgDevTemperature     OCTET STRING,
    slcDevPortCfgDevLowHumidity     Integer32,
    slcDevPortCfgDevHighHumidity    Integer32,
    slcDevPortCfgDevHumidity        OCTET STRING,
    slcDevPortCfgDevTraps           EnabledState,
    slcDevPortCfgShowLines          EnabledState,
    slcDevPortCfgNumberShowLines    Integer32,
    slcDevPortCfgViewPortLog        EnabledState,
    slcDevPortCfgPortLogSeq         OCTET STRING,
    slcDevPortCfgMaxDirectConnects  Integer32,
    slcDevPortCfgTelnetTimeout      Integer32,
    slcDevPortCfgSSHTimeout         Integer32,
    slcDevPortCfgTCPTimeout         Integer32,
    slcDevPortCfgCBCPClientType     INTEGER,
    slcDevPortCfgCBCPServerAllowNoCallback EnabledState,
    slcDevPortCfgDialbackDelay      Integer32
}

slcDevPortId OBJECT-TYPE
    SYNTAX      Integer32 (1..48)
    MAX-ACCESS  read-only
    STATUS      current
    DESCRIPTION "The identifier for a Device Port."
    ::= { slcDevPortCfgEntry 1 }

slcDevPortCfgName OBJECT-TYPE
    SYNTAX      OCTET STRING (SIZE(1..30))
    MAX-ACCESS  read-only
    STATUS      current
    DESCRIPTION "The name of the Device Port."
    ::= { slcDevPortCfgEntry 2 }

slcDevPortCfgDevice OBJECT-TYPE
    SYNTAX      INTEGER { none(1), 
                          slp8(2), 
                          slp16(3), 
                          slp8Exp8(4),
                          slp8Exp16(5), 
                          slp16Exp8(6), 
                          slp16Exp16(7), 
                          sensorsoft(8) }
    MAX-ACCESS  read-only
    STATUS      current
    DESCRIPTION "The device that is connected to the Device Port."
    ::= { slcDevPortCfgEntry 3 }

slcDevPortCfgDevLogin OBJECT-TYPE
    SYNTAX      OCTET STRING (SIZE(1..32))
    MAX-ACCESS  read-only
    STATUS      current
    DESCRIPTION "The login used to authenticate to the device connected 
                 to the Device Port."
    ::= { slcDevPortCfgEntry 4 }

slcDevPortCfgBreakSeq OBJECT-TYPE
    SYNTAX      OCTET STRING
    MAX-ACCESS  read-only
    STATUS      current
    DESCRIPTION "The character sequence for the Device Port to send a break."
    ::= { slcDevPortCfgEntry 5 }

slcDevPortCfgTelnetState OBJECT-TYPE
    SYNTAX      EnabledState
    MAX-ACCESS  read-only
    STATUS      current
    DESCRIPTION "If enabled, Telnet connections to the Device Port are allowed."
    ::= { slcDevPortCfgEntry 6 }

slcDevPortCfgTelnetPort OBJECT-TYPE
    SYNTAX      Integer32 (1025..65535)
    MAX-ACCESS  read-only
    STATUS      current
    DESCRIPTION "TCP Port number for Telnet in connections."
    ::= { slcDevPortCfgEntry 7 }

slcDevPortCfgTelnetAuth OBJECT-TYPE
    SYNTAX      EnabledState
    MAX-ACCESS  read-only
    STATUS      current
    DESCRIPTION "If enabled, the user is required to authenticate to access 
                 a Device Port with Telnet."
    ::= { slcDevPortCfgEntry 8 }

slcDevPortCfgSSHState OBJECT-TYPE
    SYNTAX      EnabledState
    MAX-ACCESS  read-only
    STATUS      current
    DESCRIPTION "If enabled, SSH connections to the Device Port are allowed."
    ::= { slcDevPortCfgEntry 9 }

slcDevPortCfgSSHPort OBJECT-TYPE
    SYNTAX      Integer32 (1025..65535)
    MAX-ACCESS  read-only
    STATUS      current
    DESCRIPTION "TCP Port number for SSH in connections."
    ::= { slcDevPortCfgEntry 10 }

slcDevPortCfgSSHAuth OBJECT-TYPE
    SYNTAX      EnabledState
    MAX-ACCESS  read-only
    STATUS      current
    DESCRIPTION "If enabled, the user is required to authenticate to access 
                 a Device Port with SSH."
    ::= { slcDevPortCfgEntry 11 }

slcDevPortCfgTCPState OBJECT-TYPE
    SYNTAX      EnabledState
    MAX-ACCESS  read-only
    STATUS      current
    DESCRIPTION "If enabled, TCP connections to the Device Port are allowed."
    ::= { slcDevPortCfgEntry 12 }

slcDevPortCfgTCPPort OBJECT-TYPE
    SYNTAX      Integer32 (1025..65535)
    MAX-ACCESS  read-only
    STATUS      current
    DESCRIPTION "TCP Port number for TCP in connections."
    ::= { slcDevPortCfgEntry 13 }

slcDevPortCfgTCPAuth OBJECT-TYPE
    SYNTAX      EnabledState
    MAX-ACCESS  read-only
    STATUS      current
    DESCRIPTION "If enabled, the user is required to authenticate to access 
                 a Device Port with TCP."
    ::= { slcDevPortCfgEntry 14 }

slcDevPortCfgIP OBJECT-TYPE
    SYNTAX      IpAddress
    MAX-ACCESS  read-only
    STATUS      current
    DESCRIPTION "The IP Address for Telnet, SSH or TCP in to a Device Port."
    ::= { slcDevPortCfgEntry 15 }

slcDevPortCfgBaud OBJECT-TYPE
    SYNTAX      Integer32 
                ( 300 | 600 | 1200 | 2400 | 4800 | 
                  9600 | 19200 | 38400 | 57600 | 115200 )
    MAX-ACCESS  read-only
    STATUS      current
    DESCRIPTION "The baud rate of the Device Port."
    ::= { slcDevPortCfgEntry 16 }

slcDevPortCfgDataBits OBJECT-TYPE
    SYNTAX      Integer32 ( 7 | 8 )
    MAX-ACCESS  read-only
    STATUS      current
    DESCRIPTION "The data bits of the Device Port."
    ::= { slcDevPortCfgEntry 17 }

slcDevPortCfgStopBits OBJECT-TYPE
    SYNTAX      Integer32 ( 1 | 2 )
    MAX-ACCESS  read-only
    STATUS      current
    DESCRIPTION "The stop bits of the Device Port."
    ::= { slcDevPortCfgEntry 18 }

slcDevPortCfgParity OBJECT-TYPE
    SYNTAX      INTEGER { none(1), odd(2), even(3) }
    MAX-ACCESS  read-only
    STATUS      current
    DESCRIPTION "The parity of the Device Port."
    ::= { slcDevPortCfgEntry 19 }

slcDevPortCfgFlowControl OBJECT-TYPE
    SYNTAX      INTEGER { none(1), xonxoff(2), rtscts(3) }
    MAX-ACCESS  read-only
    STATUS      current
    DESCRIPTION "The flow control of the Device Port."
    ::= { slcDevPortCfgEntry 20 }

slcDevPortCfgLogins OBJECT-TYPE
    SYNTAX      EnabledState
    MAX-ACCESS  read-only
    STATUS      current
    DESCRIPTION "If enabled, authentication is required to access a serial 
                 device connected to a Device Port."
    ::= { slcDevPortCfgEntry 21 }

slcDevPortCfgConnectDSR OBJECT-TYPE
    SYNTAX      EnabledState
    MAX-ACCESS  read-only
    STATUS      current
    DESCRIPTION "If enabled, the Device Port only establishes a connection if 
                 DSR (Data Set Ready) transitions to an asserted state."
    ::= { slcDevPortCfgEntry 22 }

slcDevPortCfgDisconnectDSR OBJECT-TYPE
    SYNTAX      EnabledState
    MAX-ACCESS  read-only
    STATUS      current
    DESCRIPTION "If enabled, and a connection to a Device Port is currently 
                 in session, the connection will be terminated if DSR (Data 
                 Set Ready) transitions to a de-asserted state."
    ::= { slcDevPortCfgEntry 23 }

slcDevPortCfgModemState OBJECT-TYPE
    SYNTAX      INTEGER { disabled(1), 
                          dialout(2), 
                          dialin(3), 
                          dialback(4),
                          dialondemand(5),
                          dialinAndDialondemand(6),
                          dialinHostList(7),
                          cbcpServer(8),
                          cbcpClient(9) }
    MAX-ACCESS  read-only
    STATUS      current
    DESCRIPTION "For an external modem attached to the Device Port, indicates 
                 how the modem will be used."
    ::= { slcDevPortCfgEntry 24 }

slcDevPortCfgModemMode OBJECT-TYPE
    SYNTAX      INTEGER { ppp(1), text(2) }
    MAX-ACCESS  read-only
    STATUS      current
    DESCRIPTION "For an external modem attached to the Device Port, the 
                 mode: PPP (for Dial-in and Dial-out) and text (for Dial-in 
                 and Dial-back)."
    ::= { slcDevPortCfgEntry 25 }

slcDevPortCfgLocalIP OBJECT-TYPE
    SYNTAX      IpAddress
    MAX-ACCESS  read-only
    STATUS      current
    DESCRIPTION "For PPP connections, the local IP Address - all zeros if it 
                 should be negotiated."
    ::= { slcDevPortCfgEntry 26 }

slcDevPortCfgRemoteIP OBJECT-TYPE
    SYNTAX      IpAddress
    MAX-ACCESS  read-only
    STATUS      current
    DESCRIPTION "For PPP connections, the remote IP Address - all zeros if it 
                 should be negotiated."
    ::= { slcDevPortCfgEntry 27 }

slcDevPortCfgAuth OBJECT-TYPE
    SYNTAX      INTEGER { pap(1), chap(2) }
    MAX-ACCESS  read-only
    STATUS      current
    DESCRIPTION "For PPP connections, the type of authentication to be used."
    ::= { slcDevPortCfgEntry 28 }

slcDevPortCfgCHAPHost OBJECT-TYPE
    SYNTAX      OCTET STRING
    MAX-ACCESS  read-only
    STATUS      current
    DESCRIPTION "For PPP connections with CHAP authentication, the host (for 
                 Unix) or user (for Windows) to use."
    ::= { slcDevPortCfgEntry 29 }

slcDevPortCfgInitScript OBJECT-TYPE
    SYNTAX      OCTET STRING
    MAX-ACCESS  read-only
    STATUS      current
    DESCRIPTION "The initialization script for an external modem."
    ::= { slcDevPortCfgEntry 30 }

slcDevPortCfgTimeout OBJECT-TYPE
    SYNTAX      Integer32 (0..30)
    MAX-ACCESS  read-only
    STATUS      current
    DESCRIPTION "The timeout (in minutes) for text connections.  A value 
                 of 0 indicates that timeouts are disabled."
    ::= { slcDevPortCfgEntry 31 }

slcDevPortCfgDialoutNum OBJECT-TYPE
    SYNTAX      OCTET STRING
    MAX-ACCESS  read-only
    STATUS      current
    DESCRIPTION "The phone number to use for dial-out connections."
    ::= { slcDevPortCfgEntry 32 }

slcDevPortCfgDialoutLogin OBJECT-TYPE
    SYNTAX      OCTET STRING (SIZE(1..32))
    MAX-ACCESS  read-only
    STATUS      current
    DESCRIPTION "The login to use for dial-out connections."
    ::= { slcDevPortCfgEntry 33 }

slcDevPortCfgDialbackMode OBJECT-TYPE
    SYNTAX      INTEGER { usernumber(1), fixed(2) }
    MAX-ACCESS  read-only
    STATUS      current
    DESCRIPTION "For dial-back connections, defines the phone number to call: 
                 a number associated with the authenticated user, or a fixed 
                 number associated with the Device Port."
    ::= { slcDevPortCfgEntry 34 }

slcDevPortCfgDialbackNum OBJECT-TYPE
    SYNTAX      OCTET STRING
    MAX-ACCESS  read-only
    STATUS      current
    DESCRIPTION "The phone number to use for dial-back connections."
    ::= { slcDevPortCfgEntry 35 }

slcDevPortCfgNATState OBJECT-TYPE
    SYNTAX      EnabledState
    MAX-ACCESS  read-only
    STATUS      current
    DESCRIPTION "If enabled, use NAT (Network Address Translation) to allow 
                 dial-in and dial-back users to access the network connected 
                 to Eth1 and Eth2."
    ::= { slcDevPortCfgEntry 36 }

slcDevPortCfgLocalState OBJECT-TYPE
    SYNTAX      EnabledState
    MAX-ACCESS  read-only
    STATUS      current
    DESCRIPTION "If enabled, local logging is enabled for the Device Port."
    ::= { slcDevPortCfgEntry 37 }

slcDevPortCfgNFSFileState OBJECT-TYPE
    SYNTAX      EnabledState
    MAX-ACCESS  read-only
    STATUS      current
    DESCRIPTION "If enabled, NFS File logging is enabled for the Device Port."
    ::= { slcDevPortCfgEntry 38 }

slcDevPortCfgNFSDir OBJECT-TYPE
    SYNTAX      OCTET STRING
    MAX-ACCESS  read-only
    STATUS      current
    DESCRIPTION "The local directory of a NFS mount to use for logging."
    ::= { slcDevPortCfgEntry 39 }

slcDevPortCfgNFSMaxFiles OBJECT-TYPE
    SYNTAX      Integer32
    MAX-ACCESS  read-only
    STATUS      current
    DESCRIPTION "The maximum number of files to use for NFS file logging."
    ::= { slcDevPortCfgEntry 40 }

slcDevPortCfgNFSMaxSize OBJECT-TYPE
    SYNTAX      Integer32
    MAX-ACCESS  read-only
    STATUS      current
    DESCRIPTION "The maximum size of each file (in bytes) for NFS File logging."
    ::= { slcDevPortCfgEntry 41 }

slcDevPortCfgEmailState OBJECT-TYPE
    SYNTAX      EnabledState
    MAX-ACCESS  read-only
    STATUS      current
    DESCRIPTION "If enabled, Email logging is enabled for the Device Port."
    ::= { slcDevPortCfgEntry 42 }

slcDevPortCfgEmailTrigger OBJECT-TYPE
    SYNTAX      INTEGER { bytecnt(1), textstring(2) }
    MAX-ACCESS  read-only
    STATUS      current
    DESCRIPTION "The type of trigger to use for email notification - specified 
                 number of bytes received, or specified text string received."
    ::= { slcDevPortCfgEntry 43 }

slcDevPortCfgEmailByteThresh OBJECT-TYPE
    SYNTAX      Integer32
    MAX-ACCESS  read-only
    STATUS      current
    DESCRIPTION "For a byte count trigger, the number of bytes required to 
                 trigger an email notification."
    ::= { slcDevPortCfgEntry 44 }

slcDevPortCfgEmailDelay OBJECT-TYPE
    SYNTAX      Integer32
    MAX-ACCESS  read-only
    STATUS      current
    DESCRIPTION "For a byte count trigger, once the number of bytes has been 
                 received, the number of seconds to wait before sending the
                 email notification."
    ::= { slcDevPortCfgEntry 45 }

slcDevPortCfgEmailRestartDelay OBJECT-TYPE
    SYNTAX      Integer32
    MAX-ACCESS  read-only
    STATUS      current
    DESCRIPTION "For a byte count trigger, once the email notification has 
                 been send, the number of seconds to wait before restarting 
                 the byte count process."
    ::= { slcDevPortCfgEntry 46 }

slcDevPortCfgEmailTextString OBJECT-TYPE
    SYNTAX      OCTET STRING
    MAX-ACCESS  read-only
    STATUS      current
    DESCRIPTION "For a text string trigger, the text string to parse for."
    ::= { slcDevPortCfgEntry 47 }

slcDevPortCfgEmailTo OBJECT-TYPE
    SYNTAX      OCTET STRING
    MAX-ACCESS  read-only
    STATUS      current
    DESCRIPTION "List of emails to send email notification to."
    ::= { slcDevPortCfgEntry 48 }

slcDevPortCfgEmailSubject OBJECT-TYPE
    SYNTAX      OCTET STRING
    MAX-ACCESS  read-only
    STATUS      current
    DESCRIPTION "Subject to include with email notification."
    ::= { slcDevPortCfgEntry 49 }

slcDevPortCfgPCCardState OBJECT-TYPE
    SYNTAX      EnabledState
    MAX-ACCESS  read-only
    STATUS      current
    DESCRIPTION "If enabled, PC Card logging is enabled for the Device Port."
    ::= { slcDevPortCfgEntry 50 }

slcDevPortCfgPCCardLogTo OBJECT-TYPE
    SYNTAX      INTEGER { upperSlot(1), lowerSlot(2) }
    MAX-ACCESS  read-only
    STATUS      current
    DESCRIPTION "For PC Card logging, which PC Card slot to use for logging."
    ::= { slcDevPortCfgEntry 51 }

slcDevPortCfgPCCardMaxFiles OBJECT-TYPE
    SYNTAX      Integer32
    MAX-ACCESS  read-only
    STATUS      current
    DESCRIPTION "The maximum number of files to use for PC Card logging."
    ::= { slcDevPortCfgEntry 52 }

slcDevPortCfgPCCardMaxSize OBJECT-TYPE
    SYNTAX      Integer32
    MAX-ACCESS  read-only
    STATUS      current
    DESCRIPTION "The maximum size of each file (in bytes) for PC Card logging."
    ::= { slcDevPortCfgEntry 53 }

slcDevPortCfgAction OBJECT-TYPE
    SYNTAX      INTEGER { noAction(1), 
                          zeroPortCounters(2), 
                          clearLocalLog(3),
                          terminateConnections(4)
                        }
    MAX-ACCESS  read-write
    STATUS      current
    DESCRIPTION "Performs an action on a Device Port.  A read of this object 
                 always returns the value noAction(1).  Setting this object 
                 to zeroPortCounters(2) will reset all port counters given in 
                 slcDevPortStateTable.  Setting this object to clearLocalLog(3) 
                 will clear the local logging buffer.  Setting this object to 
                 terminateConnections(4) will terminate all connections 
                 associated with the Device Port."
    ::= { slcDevPortCfgEntry 54 }

slcDevPortCfgEmailSend OBJECT-TYPE
    SYNTAX      INTEGER { email(1), snmptrap(2), both(3) }
    MAX-ACCESS  read-only
    STATUS      current
    DESCRIPTION "When a trigger is received, the type of notification to send: 
                 email, SNMP trap, or email and SNMP trap."
    ::= { slcDevPortCfgEntry 55 }

slcDevPortCfgBanner OBJECT-TYPE
    SYNTAX      OCTET STRING
    MAX-ACCESS  read-only
    STATUS      current
    DESCRIPTION "The banner displayed when the Device Port is connected to via 
                 SSH or Telnet."
    ::= { slcDevPortCfgEntry 56 }

slcDevPortCfgIdleTimeout OBJECT-TYPE
    SYNTAX      Integer32
    MAX-ACCESS  read-only
    STATUS      current
    DESCRIPTION "The timeout (in seconds) for dial-in and dial-on-demand PPP 
                 connections.  If no traffic is received for the PPP connection 
                 in the time defined by the idle timeout, the PPP connection 
                 will be terminated.  A value of 0 indicates that timeouts are 
                 disabled."
    ::= { slcDevPortCfgEntry 57 }

slcDevPortCfgRestartDelay OBJECT-TYPE
    SYNTAX      Integer32
    MAX-ACCESS  read-only
    STATUS      current
    DESCRIPTION "The delay (in seconds) to wait before restarting dial-out or 
                 dial-on-demand PPP connections."
    ::= { slcDevPortCfgEntry 58 }

slcDevPortCfgCallerIdLogging OBJECT-TYPE
    SYNTAX      EnabledState
    MAX-ACCESS  read-only
    STATUS      current
    DESCRIPTION "If enabled, caller id logging is enabled for a modem dial-in 
                 connection."
    ::= { slcDevPortCfgEntry 59 }

slcDevPortCfgCallerIdATCmd OBJECT-TYPE
    SYNTAX      OCTET STRING
    MAX-ACCESS  read-only
    STATUS      current
    DESCRIPTION "The modem AT command required to initiate caller id logging 
                 by the modem."
    ::= { slcDevPortCfgEntry 60 }

slcDevPortCfgDODAuth OBJECT-TYPE
    SYNTAX      INTEGER { pap(1), chap(2) }
    MAX-ACCESS  read-only
    STATUS      current
    DESCRIPTION "For PPP connections that are configured for both Dial-in and 
                 Dial-on-Demand, the type of authentication to be used for 
                 Dial-on-Demand."
    ::= { slcDevPortCfgEntry 61 }

slcDevPortCfgDODCHAPHost OBJECT-TYPE
    SYNTAX      OCTET STRING
    MAX-ACCESS  read-only
    STATUS      current
    DESCRIPTION "For PPP connections that are configured for both Dial-in and 
                 Dial-on-Demand, with CHAP authentication for Dial-on-Demand, 
                 the host (for Unix) or user (for Windows) to use."
    ::= { slcDevPortCfgEntry 62 }

slcDevPortCfgSLMLoggingState OBJECT-TYPE
    SYNTAX      EnabledState
    MAX-ACCESS  read-only
    STATUS      current
    DESCRIPTION "If enabled, SLM logging is enabled for the Device Port."
    ::= { slcDevPortCfgEntry 63 }

slcDevPortCfgSLMNMS OBJECT-TYPE
    SYNTAX      OCTET STRING
    MAX-ACCESS  read-only
    STATUS      current
    DESCRIPTION "The IP Addresses of up to three SNMP Network Management 
                 Stations defined used for SLM Logging.  Multiple IP Addresses 
                 will be separated by a comma."
    ::= { slcDevPortCfgEntry 64 }

slcDevPortCfgSLMByteThresh OBJECT-TYPE
    SYNTAX      Integer32
    MAX-ACCESS  read-only
    STATUS      current
    DESCRIPTION "The number of bytes required to trigger SLM logging."
    ::= { slcDevPortCfgEntry 65 }

slcDevPortCfgSLMTimeFrame OBJECT-TYPE
    SYNTAX      Integer32
    MAX-ACCESS  read-only
    STATUS      current
    DESCRIPTION "The time frame for SLM logging, in seconds."
    ::= { slcDevPortCfgEntry 66 }

slcDevPortCfgWebColumns OBJECT-TYPE
    SYNTAX      Integer32
    MAX-ACCESS  read-only
    STATUS      current
    DESCRIPTION "The number of columns in the Web SSH or Telnet window for 
                 this Device Port."
    ::= { slcDevPortCfgEntry 67 }

slcDevPortCfgWebRows OBJECT-TYPE
    SYNTAX      Integer32
    MAX-ACCESS  read-only
    STATUS      current
    DESCRIPTION "The number of rows in the Web SSH or Telnet window for 
                 this Device Port."
    ::= { slcDevPortCfgEntry 68 }

slcDevPortCfgSyslogState OBJECT-TYPE
    SYNTAX      EnabledState
    MAX-ACCESS  read-only
    STATUS      current
    DESCRIPTION "If enabled, Syslog logging is enabled for the Device Port."
    ::= { slcDevPortCfgEntry 69 }

slcDevPortCfgHostList OBJECT-TYPE
    SYNTAX      OCTET STRING
    MAX-ACCESS  read-only
    STATUS      current
    DESCRIPTION "When slcDevPortCfgModemState is set to dialinHostList, the 
                 name of the Host List used for Dial-in."
    ::= { slcDevPortCfgEntry 70 }

slcDevPortCfgDevLowTemp OBJECT-TYPE
    SYNTAX      Integer32
    MAX-ACCESS  read-only
    STATUS      current
    DESCRIPTION "The low temperature limit, in Celsius, for the device 
                 connected to this Device Port.  If the temperature is not 
                 applicable, 9999 will be returned."
    ::= { slcDevPortCfgEntry 71 }

slcDevPortCfgDevHighTemp OBJECT-TYPE
    SYNTAX      Integer32
    MAX-ACCESS  read-only
    STATUS      current
    DESCRIPTION "The high temperature limit, in Celsius, for the device 
                 connected to this Device Port.  If the temperature is not 
                 applicable, 9999 will be returned."
    ::= { slcDevPortCfgEntry 72 }

slcDevPortCfgDevTemperature OBJECT-TYPE
    SYNTAX      OCTET STRING
    MAX-ACCESS  read-only
    STATUS      current
    DESCRIPTION "The actual temperature, in Celsius, for the device 
                 connected to this Device Port.  If the temperature is not 
                 applicable, an empty string will be returned."
    ::= { slcDevPortCfgEntry 73 }

slcDevPortCfgDevLowHumidity OBJECT-TYPE
    SYNTAX      Integer32
    MAX-ACCESS  read-only
    STATUS      current
    DESCRIPTION "The low humidty limit, in percentage, for the device 
                 connected to this Device Port.  If the temperature is not 
                 applicable, 9999 will be returned."
    ::= { slcDevPortCfgEntry 74 }

slcDevPortCfgDevHighHumidity OBJECT-TYPE
    SYNTAX      Integer32
    MAX-ACCESS  read-only
    STATUS      current
    DESCRIPTION "The high humidty limit, in percentage, for the device 
                 connected to this Device Port.  If the temperature is not 
                 applicable, 9999 will be returned."
    ::= { slcDevPortCfgEntry 75 }

slcDevPortCfgDevHumidity OBJECT-TYPE
    SYNTAX      OCTET STRING
    MAX-ACCESS  read-only
    STATUS      current
    DESCRIPTION "The actual humidity, in percentage, for the device 
                 connected to this Device Port.  If the temperature is not 
                 applicable, an empty string will be returned."
    ::= { slcDevPortCfgEntry 76 }

slcDevPortCfgDevTraps OBJECT-TYPE
    SYNTAX      EnabledState
    MAX-ACCESS  read-only
    STATUS      current
    DESCRIPTION "If enabled, traps will be sent when one of the limits for the 
                 device connected to this Device Port are exceeded."
    ::= { slcDevPortCfgEntry 77 }

slcDevPortCfgShowLines OBJECT-TYPE
    SYNTAX      EnabledState
    MAX-ACCESS  read-only
    STATUS      current
    DESCRIPTION "If enabled, upon connecting to the Device Port, a series of 
                 characters (or lines) output to the Device Port before it 
                 was connected to are displayed."
    ::= { slcDevPortCfgEntry 78 }

slcDevPortCfgNumberShowLines OBJECT-TYPE
    SYNTAX      Integer32 (1..50)
    MAX-ACCESS  read-only
    STATUS      current
    DESCRIPTION "If slcDevPortCfgShowLines is enabled, the number of lines that 
                 are displayed upon connecting to the Device Port."
    ::= { slcDevPortCfgEntry 79 }

slcDevPortCfgViewPortLog OBJECT-TYPE
    SYNTAX      EnabledState
    MAX-ACCESS  read-only
    STATUS      current
    DESCRIPTION "If enabled, upon using 'connect direct' to a Device Port, 
                 the slcDevPortCfgPortLogSeq key sequence can be typed to 
                 view the end of the port log for the current Device Port, 
                 or a different Device Port."
    ::= { slcDevPortCfgEntry 80 }

slcDevPortCfgPortLogSeq OBJECT-TYPE
    SYNTAX      OCTET STRING
    MAX-ACCESS  read-only
    STATUS      current
    DESCRIPTION "The character sequence to view the port log for the Device 
                 Port."
    ::= { slcDevPortCfgEntry 81 }

slcDevPortCfgMaxDirectConnects OBJECT-TYPE
    SYNTAX      Integer32
    MAX-ACCESS  read-only
    STATUS      current
    DESCRIPTION "The maximum number of direct connects at the CLI for the 
                 Device Port."
    ::= { slcDevPortCfgEntry 82 }

slcDevPortCfgTelnetTimeout OBJECT-TYPE
    SYNTAX      Integer32 (0..1800)
    MAX-ACCESS  read-only
    STATUS      current
    DESCRIPTION "The timeout (in seconds) for Telnet connections.  A value 
                 of 0 indicates that timeouts are disabled."
    ::= { slcDevPortCfgEntry 83 }

slcDevPortCfgSSHTimeout OBJECT-TYPE
    SYNTAX      Integer32 (0..1800)
    MAX-ACCESS  read-only
    STATUS      current
    DESCRIPTION "The timeout (in seconds) for SSH connections.  A value 
                 of 0 indicates that timeouts are disabled."
    ::= { slcDevPortCfgEntry 84 }

slcDevPortCfgTCPTimeout OBJECT-TYPE
    SYNTAX      Integer32 (0..1800)
    MAX-ACCESS  read-only
    STATUS      current
    DESCRIPTION "The timeout (in seconds) for TCP connections.  A value 
                 of 0 indicates that timeouts are disabled."
    ::= { slcDevPortCfgEntry 85 }

slcDevPortCfgCBCPClientType OBJECT-TYPE
    SYNTAX      INTEGER { adminDefined(1), userDefined(2) }
    MAX-ACCESS  read-only
    STATUS      current
    DESCRIPTION "When slcDevPortCfgModemState is set to cbcpClient, the 
                 preferred type of dialback number to use for CBCP negotiation."
    ::= { slcDevPortCfgEntry 86 }

slcDevPortCfgCBCPServerAllowNoCallback OBJECT-TYPE
    SYNTAX      EnabledState
    MAX-ACCESS  read-only
    STATUS      current
    DESCRIPTION "If enabled and slcDevPortCfgModemState is set to cbcpServer, 
                 the SLC will allow the PPP peer to select the No Callback 
                 option during CBCP negotiation."
    ::= { slcDevPortCfgEntry 87 }

slcDevPortCfgDialbackDelay OBJECT-TYPE
    SYNTAX      Integer32 
    MAX-ACCESS  read-only
    STATUS      current
    DESCRIPTION "When slcDevPortCfgModemState is set to dialback, cbcpServer 
                 or cbcpClient, specifies the delay between the dial-in and 
                 dial-out portion of the dialing sequence."
    ::= { slcDevPortCfgEntry 88 }


slcDevPortState     OBJECT IDENTIFIER ::= { slcDevDevicePorts 3 }

slcDevPortStateNumber OBJECT-TYPE
    SYNTAX      Integer32 ( 8 | 16 | 32 | 48 )
    MAX-ACCESS  read-only
    STATUS      current
    DESCRIPTION 
        "The number of entries in the Device Port State table."
    ::= { slcDevPortState 1 }

-- Device Port State table.

slcDevPortStateTable OBJECT-TYPE
    SYNTAX      SEQUENCE OF SlcDevPortStateEntry
    MAX-ACCESS  not-accessible
    STATUS      current
    DESCRIPTION "Table of Device Port state entries.  The number of 
                 entries is given by the value of slcDevPortStateNumber."
    ::= { slcDevPortState 2 }

slcDevPortStateEntry OBJECT-TYPE
    SYNTAX      SlcDevPortStateEntry
    MAX-ACCESS  not-accessible
    STATUS      current
    DESCRIPTION 
        "An entry containing all state information for a Device Port."
    INDEX       { slcDevPortStateIndex }
    ::= { slcDevPortStateTable 1 }

SlcDevPortStateEntry ::= SEQUENCE {
    slcDevPortStateIndex                              Integer32,
    slcDevPortStateBytesInput                         Integer32,
    slcDevPortStateBytesOutput                        Integer32,
    slcDevPortStateFramingErrors                      Integer32,
    slcDevPortStateParityErrors                       Integer32,
    slcDevPortStateOverrunErrors                      Integer32,
    slcDevPortStateFlowControlViolations              Integer32,
    slcDevPortStateDSR                                EnabledState,
    slcDevPortStateDTR                                EnabledState,
    slcDevPortStateCTS                                EnabledState,
    slcDevPortStateRTS                                EnabledState,
    slcDevPortStateCD                                 EnabledState
}

slcDevPortStateIndex OBJECT-TYPE
    SYNTAX      Integer32 (1..48)
    MAX-ACCESS  read-only
    STATUS      current
    DESCRIPTION "Reference index for each Device Port State entry."
    ::= { slcDevPortStateEntry 1 }

slcDevPortStateBytesInput OBJECT-TYPE
    SYNTAX      Integer32
    MAX-ACCESS  read-only
    STATUS      current
    DESCRIPTION "The number of bytes input to the Device Port since boot or 
                 the last time Device Port statistics were zeroed."
    ::= { slcDevPortStateEntry 2 }

slcDevPortStateBytesOutput OBJECT-TYPE
    SYNTAX      Integer32
    MAX-ACCESS  read-only
    STATUS      current
    DESCRIPTION "The number of bytes output from the Device Port since boot or 
                 the last time Device Port statistics were zeroed."
    ::= { slcDevPortStateEntry 3 }

slcDevPortStateFramingErrors OBJECT-TYPE
    SYNTAX      Integer32
    MAX-ACCESS  read-only
    STATUS      current
    DESCRIPTION "The number of framing errors for the Device Port since boot or 
                 the last time Device Port statistics were zeroed."
    ::= { slcDevPortStateEntry 4 }

slcDevPortStateParityErrors OBJECT-TYPE
    SYNTAX      Integer32
    MAX-ACCESS  read-only
    STATUS      current
    DESCRIPTION "The number of parity errors for the Device Port since boot or 
                 the last time Device Port statistics were zeroed."
    ::= { slcDevPortStateEntry 5 }

slcDevPortStateOverrunErrors OBJECT-TYPE
    SYNTAX      Integer32
    MAX-ACCESS  read-only
    STATUS      current
    DESCRIPTION "The number of overrun errors for the Device Port since boot or 
                 the last time Device Port statistics were zeroed."
    ::= { slcDevPortStateEntry 6 }

slcDevPortStateFlowControlViolations OBJECT-TYPE
    SYNTAX      Integer32
    MAX-ACCESS  read-only
    STATUS      current
    DESCRIPTION "The number of flow control violations for the Device Port 
                 since boot or the last time Device Port statistics were 
                 zeroed."
    ::= { slcDevPortStateEntry 7 }

slcDevPortStateDSR OBJECT-TYPE
    SYNTAX      EnabledState
    MAX-ACCESS  read-only
    STATUS      current
    DESCRIPTION "If enabled, Data Set Ready is enabled for the Device Port."
    ::= { slcDevPortStateEntry 8 }

slcDevPortStateDTR OBJECT-TYPE
    SYNTAX      EnabledState
    MAX-ACCESS  read-only
    STATUS      current
    DESCRIPTION 
        "If enabled, Data Terminal Ready is enabled for the Device Port."
    ::= { slcDevPortStateEntry 9 }

slcDevPortStateCTS OBJECT-TYPE
    SYNTAX      EnabledState
    MAX-ACCESS  read-only
    STATUS      current
    DESCRIPTION "If enabled, Clear To Send is enabled for the Device Port."
    ::= { slcDevPortStateEntry 10 }

slcDevPortStateRTS OBJECT-TYPE
    SYNTAX      EnabledState
    MAX-ACCESS  read-only
    STATUS      current
    DESCRIPTION "If enabled, Request To Send is enabled for the Device Port."
    ::= { slcDevPortStateEntry 11 }

slcDevPortStateCD OBJECT-TYPE
    SYNTAX      EnabledState
    MAX-ACCESS  read-only
    STATUS      current
    DESCRIPTION "If enabled, Carrier Detect is enabled for the Device Port."
    ::= { slcDevPortStateEntry 12 }


slcDevPCCard        OBJECT IDENTIFIER ::= { slcDevices 3 }

-- PC Card Configuration table.

slcPCCardCfgTable OBJECT-TYPE
    SYNTAX      SEQUENCE OF SlcPCCardCfgEntry
    MAX-ACCESS  not-accessible
    STATUS      current
    DESCRIPTION "Table of Device Port configuration entries.  There are two 
                 entries in the table, index (1) for the upper PC Card slot, 
                 and index (2) for the lower PC Card slot."
    ::= { slcDevPCCard 1 }

slcPCCardCfgEntry OBJECT-TYPE
    SYNTAX      SlcPCCardCfgEntry
    MAX-ACCESS  not-accessible
    STATUS      current
    DESCRIPTION 
        "An entry containing all configuration settings for a PC Card Slot."
    INDEX       { slcPCCardCfgIndex }
    ::= { slcPCCardCfgTable 1 }

SlcPCCardCfgEntry ::= SEQUENCE {
    slcPCCardCfgIndex               Integer32,
    slcPCCardCfgCardType            INTEGER,
    slcPCCardCfgCardId              OCTET STRING,
-- Modem/ISDN: Data (serial) settings
    slcPCCardCfgBaud                Integer32,
    slcPCCardCfgDataBits            INTEGER,
    slcPCCardCfgStopBits            INTEGER,
    slcPCCardCfgParity              INTEGER,
    slcPCCardCfgFlowControl         INTEGER,
-- Modem/ISDN: Modem settings
    slcPCCardCfgModemState          INTEGER,
    slcPCCardCfgModemMode           INTEGER,
    slcPCCardCfgLocalIP             IpAddress,
    slcPCCardCfgRemoteIP            IpAddress,
    slcPCCardCfgAuth                INTEGER,
    slcPCCardCfgCHAPHost            OCTET STRING,
    slcPCCardCfgInitScript          OCTET STRING,
    slcPCCardCfgTimeout             Integer32,
    slcPCCardCfgInitScript          OCTET STRING,
    slcPCCardCfgDialoutNum          OCTET STRING,
    slcPCCardCfgDialoutLogin        OCTET STRING,
    slcPCCardCfgDialbackMode        INTEGER,     
    slcPCCardCfgDialbackNum         OCTET STRING,     
    slcPCCardCfgNATState            EnabledState,
-- Storage Card settings
    slcPCCardCfgStorageFS           INTEGER,
-- ISDN only settings
    slcPCCardCfgISDNChannel         Integer32,
    slcPCCardCfgISDNChannelNum      OCTET STRING,
-- IP settings
    slcPCCardCfgTelnetState         EnabledState,
    slcPCCardCfgTelnetPort          Integer32,
    slcPCCardCfgTelnetAuth          EnabledState,
    slcPCCardCfgSSHState            EnabledState,
    slcPCCardCfgSSHPort             Integer32,
    slcPCCardCfgSSHAuth             EnabledState,
    slcPCCardCfgTCPState            EnabledState,
    slcPCCardCfgTCPPort             Integer32,
    slcPCCardCfgTCPAuth             EnabledState,
-- GSM/GPRS only settings
    slcPCCardCfgGSMPIN              OCTET STRING,
    slcPCCardCfgGSMNetworkName      OCTET STRING,  -- obsolete
    slcPCCardCfgGSMPPPCompression   EnabledState,
    slcPCCardCfgGSMAutoAcquireDNS   EnabledState,
    slcPCCardCfgGSMDialoutMode      INTEGER,
    slcPCCardCfgGSMContextID        OCTET STRING,
    slcPCCardCfgGSMBearerService    OCTET STRING,
-- Additional settings
    slcPCCardCfgIdleTimeout         Integer32,
    slcPCCardCfgRestartDelay        Integer32,
    slcPCCardCfgCallerIdLogging     EnabledState,
    slcPCCardCfgCallerIdATCmd       OCTET STRING,
    slcPCCardCfgDODAuth             INTEGER,
    slcPCCardCfgDODCHAPHost         OCTET STRING,
    slcPCCardCfgHostList            OCTET STRING,
    slcPCCardCfgCBCPClientType      INTEGER,
    slcPCCardCfgCBCPServerAllowNoCallback EnabledState,
    slcPCCardCfgDialbackDelay       Integer32
}

slcPCCardCfgIndex OBJECT-TYPE
    SYNTAX      Integer32 (1..2)
    MAX-ACCESS  read-only
    STATUS      current
    DESCRIPTION "Reference index for each PC Card Configuration entry."
    ::= { slcPCCardCfgEntry 1 }

slcPCCardCfgCardType OBJECT-TYPE
    SYNTAX      INTEGER { none(1), 
                          storage(2), 
                          modem(3), 
                          isdn(4),
                          wireless(5),
                          gsmmodem(6) }
    MAX-ACCESS  read-only
    STATUS      current
    DESCRIPTION "The type of PC Card in the slot."
    ::= { slcPCCardCfgEntry 2 }

slcPCCardCfgCardId OBJECT-TYPE
    SYNTAX      OCTET STRING
    MAX-ACCESS  read-only
    STATUS      current
    DESCRIPTION "The identifying string of the card in the slot."
    ::= { slcPCCardCfgEntry 3 }

slcPCCardCfgBaud OBJECT-TYPE
    SYNTAX      Integer32 
                ( 300 | 600 | 1200 | 2400 | 4800 | 
                  9600 | 19200 | 38400 | 57600 | 115200 )
    MAX-ACCESS  read-only
    STATUS      current
    DESCRIPTION "For ISDN and modem cards, the baud rate."
    ::= { slcPCCardCfgEntry 4 }

slcPCCardCfgDataBits OBJECT-TYPE
    SYNTAX      Integer32 ( 7 | 8 )
    MAX-ACCESS  read-only
    STATUS      current
    DESCRIPTION "For ISDN and modem cards, the data bits."
    ::= { slcPCCardCfgEntry 5 }

slcPCCardCfgStopBits OBJECT-TYPE
    SYNTAX      Integer32 ( 1 | 2 )
    MAX-ACCESS  read-only
    STATUS      current
    DESCRIPTION "For ISDN and modem cards, the stop bits."
    ::= { slcPCCardCfgEntry 6 }

slcPCCardCfgParity OBJECT-TYPE
    SYNTAX      INTEGER { none(1), odd(2), even(3) }
    MAX-ACCESS  read-only
    STATUS      current
    DESCRIPTION "For ISDN and modem cards, the parity."
    ::= { slcPCCardCfgEntry 7 }

slcPCCardCfgFlowControl OBJECT-TYPE
    SYNTAX      INTEGER { none(1), xonxoff(2), rtscts(3) }
    MAX-ACCESS  read-only
    STATUS      current
    DESCRIPTION "For ISDN and modem cards, the flow control."
    ::= { slcPCCardCfgEntry 8 }

slcPCCardCfgModemState OBJECT-TYPE
    SYNTAX      INTEGER { disabled(1), 
                          dialout(2), 
                          dialin(3), 
                          dialback(4),
                          dialondemand(5),
                          dialinAndDialondemand(6),
                          dialinHostList(7),
                          cbcpServer(8),
                          cbcpClient(9) }
    MAX-ACCESS  read-only
    STATUS      current
    DESCRIPTION 
        "For ISDN and modem cards, indicates how the modem will be used."
    ::= { slcPCCardCfgEntry 9 }

slcPCCardCfgModemMode OBJECT-TYPE
    SYNTAX      INTEGER { ppp(1), text(2) }
    MAX-ACCESS  read-only
    STATUS      current
    DESCRIPTION "For ISDN and modem cards, the mode: PPP (for Dial-in and 
                 Dial-out) and text (for Dial-in and Dial-back)."
    ::= { slcPCCardCfgEntry 10 }

slcPCCardCfgLocalIP OBJECT-TYPE
    SYNTAX      IpAddress
    MAX-ACCESS  read-only
    STATUS      current
    DESCRIPTION "For PPP connections, the local IP Address (all zeros if it 
                 should be negotiated)."
    ::= { slcPCCardCfgEntry 11 }

slcPCCardCfgRemoteIP OBJECT-TYPE
    SYNTAX      IpAddress
    MAX-ACCESS  read-only
    STATUS      current
    DESCRIPTION "For PPP connections, the remote IP Address (all zeros if it 
                 should be negotiated)."
    ::= { slcPCCardCfgEntry 12 }

slcPCCardCfgAuth OBJECT-TYPE
    SYNTAX      INTEGER { pap(1), chap(2) }
    MAX-ACCESS  read-only
    STATUS      current
    DESCRIPTION "For PPP connections, the type of authentication to be used."
    ::= { slcPCCardCfgEntry 13 }

slcPCCardCfgCHAPHost OBJECT-TYPE
    SYNTAX      OCTET STRING
    MAX-ACCESS  read-only
    STATUS      current
    DESCRIPTION "For PPP connections with CHAP authentication, the host (for 
                 Unix) or user (for Windows) to use."
    ::= { slcPCCardCfgEntry 14 }

slcPCCardCfgInitScript OBJECT-TYPE
    SYNTAX      OCTET STRING
    MAX-ACCESS  read-only
    STATUS      current
    DESCRIPTION "The initialization script for an external modem."
    ::= { slcPCCardCfgEntry 15 }

slcPCCardCfgTimeout OBJECT-TYPE
    SYNTAX      Integer32 (0..30)
    MAX-ACCESS  read-only
    STATUS      current
    DESCRIPTION "The timeout (in minutes) for text connections.  A value 
                 of 0 indicates that timeouts are disabled."
    ::= { slcPCCardCfgEntry 16 }

slcPCCardCfgDialoutNum OBJECT-TYPE
    SYNTAX      OCTET STRING
    MAX-ACCESS  read-only
    STATUS      current
    DESCRIPTION "The phone number to use for dial-out connections."
    ::= { slcPCCardCfgEntry 17 }

slcPCCardCfgDialoutLogin OBJECT-TYPE
    SYNTAX      OCTET STRING (SIZE(1..32))
    MAX-ACCESS  read-only
    STATUS      current
    DESCRIPTION "The login to use for dial-out connections."
    ::= { slcPCCardCfgEntry 18 }

slcPCCardCfgDialbackMode OBJECT-TYPE
    SYNTAX      INTEGER { usernumber(1), fixed(2) }
    MAX-ACCESS  read-only
    STATUS      current
    DESCRIPTION "For dial-back connections, defines the phone number to call: 
                 a number associated with the authenticated user, or a fixed 
                 number associated with the Device Port."
    ::= { slcPCCardCfgEntry 19 }

slcPCCardCfgDialbackNum OBJECT-TYPE
    SYNTAX      OCTET STRING
    MAX-ACCESS  read-only
    STATUS      current
    DESCRIPTION "The phone number to use for dial-back connections."
    ::= { slcPCCardCfgEntry 20 }

slcPCCardCfgNATState OBJECT-TYPE
    SYNTAX      EnabledState
    MAX-ACCESS  read-only
    STATUS      current
    DESCRIPTION "If enabled, use NAT (Network Address Translation) to allow 
                 dial-in and dial-back users to access the network connected
                 to Eth1 and Eth2."
    ::= { slcPCCardCfgEntry 21 }

slcPCCardCfgStorageFS OBJECT-TYPE
    SYNTAX      INTEGER { notmounted(1), ext2(2), fat(3) }
    MAX-ACCESS  read-only
    STATUS      current
    DESCRIPTION "For storage cards, the type of filesystem on the card."
    ::= { slcPCCardCfgEntry 22 }

slcPCCardCfgISDNChannel OBJECT-TYPE
    SYNTAX      Integer32
    MAX-ACCESS  read-only
    STATUS      current
    DESCRIPTION "The channel on the ISDN card to use, either 1 or 2."
    ::= { slcPCCardCfgEntry 23 }

slcPCCardCfgISDNChannelNum OBJECT-TYPE
    SYNTAX      OCTET STRING
    MAX-ACCESS  read-only
    STATUS      current
    DESCRIPTION "The phone number associated with the selected ISDN channel."
    ::= { slcPCCardCfgEntry 24 }

slcPCCardCfgTelnetState OBJECT-TYPE
    SYNTAX      EnabledState
    MAX-ACCESS  read-only
    STATUS      current
    DESCRIPTION "If enabled, Telnet connections to the modem/ISDN PC Card 
                 are allowed."
    ::= { slcPCCardCfgEntry 25 }

slcPCCardCfgTelnetPort OBJECT-TYPE
    SYNTAX      Integer32 (1025..65535)
    MAX-ACCESS  read-only
    STATUS      current
    DESCRIPTION "TCP Port number for Telnet connections directly to the 
                 modem/ISDN PC Card."
    ::= { slcPCCardCfgEntry 26 }

slcPCCardCfgTelnetAuth OBJECT-TYPE
    SYNTAX      EnabledState
    MAX-ACCESS  read-only
    STATUS      current
    DESCRIPTION "If enabled, the user is required to authenticate to access 
                 the modem/ISDN PC Card with Telnet."
    ::= { slcPCCardCfgEntry 27 }

slcPCCardCfgSSHState OBJECT-TYPE
    SYNTAX      EnabledState
    MAX-ACCESS  read-only
    STATUS      current
    DESCRIPTION "If enabled, SSH connections to the modem/ISDN PC Card 
                 are allowed."
    ::= { slcPCCardCfgEntry 28 }

slcPCCardCfgSSHPort OBJECT-TYPE
    SYNTAX      Integer32 (1025..65535)
    MAX-ACCESS  read-only
    STATUS      current
    DESCRIPTION "TCP Port number for SSH connections directly to the 
                 modem/ISDN PC Card."
    ::= { slcPCCardCfgEntry 29 }

slcPCCardCfgSSHAuth OBJECT-TYPE
    SYNTAX      EnabledState
    MAX-ACCESS  read-only
    STATUS      current
    DESCRIPTION "If enabled, the user is required to authenticate to access 
                 the modem/ISDN PC Card with SSH."
    ::= { slcPCCardCfgEntry 30 }

slcPCCardCfgTCPState OBJECT-TYPE
    SYNTAX      EnabledState
    MAX-ACCESS  read-only
    STATUS      current
    DESCRIPTION "If enabled, TCP connections to the modem/ISDN PC Card 
                 are allowed."
    ::= { slcPCCardCfgEntry 31 }

slcPCCardCfgTCPPort OBJECT-TYPE
    SYNTAX      Integer32 (1025..65535)
    MAX-ACCESS  read-only
    STATUS      current
    DESCRIPTION "TCP Port number for TCP connections directly to the 
                 modem/ISDN PC Card."
    ::= { slcPCCardCfgEntry 32 }

slcPCCardCfgTCPAuth OBJECT-TYPE
    SYNTAX      EnabledState
    MAX-ACCESS  read-only
    STATUS      current
    DESCRIPTION "If enabled, the user is required to authenticate to access 
                 the modem/ISDN PC Card with TCP."
    ::= { slcPCCardCfgEntry 33 }

slcPCCardCfgGSMPIN OBJECT-TYPE
    SYNTAX      OCTET STRING
    MAX-ACCESS  read-only
    STATUS      current
    DESCRIPTION "The PIN associated with the GSM/GPRS PC Card modem."
    ::= { slcPCCardCfgEntry 34 }

slcPCCardCfgGSMNetworkName OBJECT-TYPE
    SYNTAX      OCTET STRING
    MAX-ACCESS  read-only
    STATUS      obsolete
    DESCRIPTION "The Network Name associated with the GSM/GPRS PC Card modem."
    ::= { slcPCCardCfgEntry 35 }

slcPCCardCfgGSMPPPCompression OBJECT-TYPE
    SYNTAX      EnabledState
    MAX-ACCESS  read-only
    STATUS      current
    DESCRIPTION "If enabled, PPP compression is enabled for GSM/GPRS PC Card 
                 modem connections."
    ::= { slcPCCardCfgEntry 36 }

slcPCCardCfgGSMAutoAcquireDNS OBJECT-TYPE
    SYNTAX      EnabledState
    MAX-ACCESS  read-only
    STATUS      current
    DESCRIPTION "If enabled, DNS servers will be acquired vi GSM/GPRS PC Card 
                 modem PPP connections."
    ::= { slcPCCardCfgEntry 37 }

slcPCCardCfgGSMDialoutMode OBJECT-TYPE
    SYNTAX      INTEGER { gprs(1), gsm(2) }
    MAX-ACCESS  read-only
    STATUS      current
    DESCRIPTION "The mode to be used for GSM/GPRS PC Card modems configured 
                 for dialout."
    ::= { slcPCCardCfgEntry 38 }

slcPCCardCfgGSMContextID OBJECT-TYPE
    SYNTAX      OCTET STRING
    MAX-ACCESS  read-only
    STATUS      current
    DESCRIPTION "The Context Id string used for GSM/GPRS PC Card modems 
                 configured for GPRS dialout mode."
    ::= { slcPCCardCfgEntry 39 }

slcPCCardCfgGSMBearerService OBJECT-TYPE
    SYNTAX      OCTET STRING
    MAX-ACCESS  read-only
    STATUS      current
    DESCRIPTION "The Bearer Service Type string used for GSM/GPRS PC Card 
                 modems configured for GSM dialin/dialout mode."
    ::= { slcPCCardCfgEntry 40 }

slcPCCardCfgIdleTimeout OBJECT-TYPE
    SYNTAX      Integer32
    MAX-ACCESS  read-only
    STATUS      current
    DESCRIPTION "The timeout (in seconds) for dial-in and dial-on-demand PPP 
                 connections.  If no traffic is received for the PPP connection 
                 in the time defined by the idle timeout, the PPP connection 
                 will be terminated.  A value of 0 indicates that timeouts are 
                 disabled."
    ::= { slcPCCardCfgEntry 41 }

slcPCCardCfgRestartDelay OBJECT-TYPE
    SYNTAX      Integer32
    MAX-ACCESS  read-only
    STATUS      current
    DESCRIPTION "The delay (in seconds) to wait before restarting dial-out or 
                 dial-on-demand PPP connections."
    ::= { slcPCCardCfgEntry 42 }

slcPCCardCfgCallerIdLogging OBJECT-TYPE
    SYNTAX      EnabledState
    MAX-ACCESS  read-only
    STATUS      current
    DESCRIPTION "If enabled, caller id logging is enabled for a modem dial-in 
                 connection."
    ::= { slcPCCardCfgEntry 43 }

slcPCCardCfgCallerIdATCmd OBJECT-TYPE
    SYNTAX      OCTET STRING
    MAX-ACCESS  read-only
    STATUS      current
    DESCRIPTION "The modem AT command required to initiate caller id logging 
                 by the modem."
    ::= { slcPCCardCfgEntry 44 }

slcPCCardCfgDODAuth OBJECT-TYPE
    SYNTAX      INTEGER { pap(1), chap(2) }
    MAX-ACCESS  read-only
    STATUS      current
    DESCRIPTION "For PPP connections that are configured for both Dial-in and 
                 Dial-on-Demand, the type of authentication to be used for 
                 Dial-on-Demand."
    ::= { slcPCCardCfgEntry 45 }

slcPCCardCfgDODCHAPHost OBJECT-TYPE
    SYNTAX      OCTET STRING
    MAX-ACCESS  read-only
    STATUS      current
    DESCRIPTION "For PPP connections that are configured for both Dial-in and 
                 Dial-on-Demand, with CHAP authentication for Dial-on-Demand, 
                 the host (for Unix) or user (for Windows) to use."
    ::= { slcPCCardCfgEntry 46 }

slcPCCardCfgHostList OBJECT-TYPE
    SYNTAX      OCTET STRING
    MAX-ACCESS  read-only
    STATUS      current
    DESCRIPTION "When slcPCCardCfgModemState is set to dialinHostList, the 
                 name of the Host List used for Dial-in."
    ::= { slcPCCardCfgEntry 47 }

slcPCCardCfgCBCPClientType OBJECT-TYPE
    SYNTAX      INTEGER { adminDefined(1), userDefined(2) }
    MAX-ACCESS  read-only
    STATUS      current
    DESCRIPTION "When slcPCCardCfgModemState is set to cbcpClient, the 
                 preferred type of dialback number to use for CBCP negotiation."
    ::= { slcPCCardCfgEntry 48 }

slcPCCardCfgCBCPServerAllowNoCallback OBJECT-TYPE
    SYNTAX      EnabledState
    MAX-ACCESS  read-only
    STATUS      current
    DESCRIPTION "If enabled and slcPCCardCfgModemState is set to cbcpServer, 
                 the SLC will allow the PPP peer to select the No Callback 
                 option during CBCP negotiation."
    ::= { slcPCCardCfgEntry 49 }

slcPCCardCfgDialbackDelay OBJECT-TYPE
    SYNTAX      Integer32 
    MAX-ACCESS  read-only
    STATUS      current
    DESCRIPTION "When slcPCCardCfgModemState is set to dialback, cbcpServer 
                 or cbcpClient, specifies the delay between the dial-in and 
                 dial-out portion of the dialing sequence."
    ::= { slcPCCardCfgEntry 50 }


slcDevPowerSupply   OBJECT IDENTIFIER ::= { slcDevices 4 }

slcDevPowerSupplyType OBJECT-TYPE
    SYNTAX      INTEGER { acOnePowerSupply(1), 
                          acTwoPowerSupplies(2),
                          dcTwoPowerSupplies(3)
                        }
    MAX-ACCESS  read-only
    STATUS      current
    DESCRIPTION "The type of power supply for the SLC."
    ::= { slcDevPowerSupply 1 }

slcDevPowerSupplyA OBJECT-TYPE
    SYNTAX      INTEGER { up(1), down(2) }
    MAX-ACCESS  read-only
    STATUS      current
    DESCRIPTION "The status of Power Supply A."
    ::= { slcDevPowerSupply 2 }

slcDevPowerSupplyB OBJECT-TYPE
    SYNTAX      INTEGER { up(1), down(2), notInstalled(3) }
    MAX-ACCESS  read-only
    STATUS      current
    DESCRIPTION "The status of Power Supply B."
    ::= { slcDevPowerSupply 3 }


--
-- Connections Group
--

slcConnNumber OBJECT-TYPE
    SYNTAX      Integer32
    MAX-ACCESS  read-only
    STATUS      current
    DESCRIPTION 
        "The number of entries in the Connections table."
    ::= { slcConnections 1 }

-- SLC Connections table

slcConnTable OBJECT-TYPE
    SYNTAX      SEQUENCE OF SlcConnEntry
    MAX-ACCESS  not-accessible
    STATUS      current
    DESCRIPTION "Table of connection entries.  The number of entries is given 
                 by the value of slcConnNumber."
    ::= { slcConnections 2 }

slcConnEntry OBJECT-TYPE
    SYNTAX      SlcConnEntry
    MAX-ACCESS  not-accessible
    STATUS      current
    DESCRIPTION "An entry containing a connection."
    INDEX       { slcConnIndex }
    ::= { slcConnTable 1 }

SlcConnEntry ::= SEQUENCE {
    slcConnIndex        Integer32,
    slcConnEndPt1       OCTET STRING,
    slcConnEndPt2       OCTET STRING,
    slcConnFlow         INTEGER,
    slcConnUser         OCTET STRING,
    slcConnDuration     Integer32,
    slcConnDurationStr  OCTET STRING,
    slcConnIdle         Integer32,
    slcConnIdleStr      OCTET STRING,
    slcConnSourceIP     IpAddress
}

slcConnIndex OBJECT-TYPE
    SYNTAX      INTEGER
    MAX-ACCESS  read-only
    STATUS      current
    DESCRIPTION "Reference index for each connection."
    ::= { slcConnEntry 1 }

slcConnEndPt1 OBJECT-TYPE
    SYNTAX      OCTET STRING
    MAX-ACCESS  read-only
    STATUS      current
    DESCRIPTION "A description of one of the end points of the connection."
    ::= { slcConnEntry 2 }

slcConnEndPt2 OBJECT-TYPE
    SYNTAX      OCTET STRING
    MAX-ACCESS  read-only
    STATUS      current
    DESCRIPTION "A description of one of the end points of the connection."
    ::= { slcConnEntry 3 }

slcConnFlow OBJECT-TYPE
    SYNTAX      INTEGER { bidirectional(1), 
                          endpt1toendpt2(2), 
                          endpt2toendpt1(3) }
    MAX-ACCESS  read-only
    STATUS      current
    DESCRIPTION "The direction that data is flowing in the connection."
    ::= { slcConnEntry 4 }

slcConnUser OBJECT-TYPE
    SYNTAX      OCTET STRING (SIZE(1..32))
    MAX-ACCESS  read-only
    STATUS      current
    DESCRIPTION "The user that initiated the connection."
    ::= { slcConnEntry 5 }

slcConnDuration OBJECT-TYPE
    SYNTAX      Integer32 
    MAX-ACCESS  read-only
    STATUS      current
    DESCRIPTION "The duration, in seconds, that the connection has existed."
    ::= { slcConnEntry 6 }

slcConnDurationStr OBJECT-TYPE
    SYNTAX      OCTET STRING
    MAX-ACCESS  read-only
    STATUS      current
    DESCRIPTION "The duration, formatted in hours:minutes:seconds, that the 
                 connection has existed."
    ::= { slcConnEntry 7 }

slcConnIdle OBJECT-TYPE
    SYNTAX      Integer32 
    MAX-ACCESS  read-only
    STATUS      current
    DESCRIPTION "The amount of time that the connection has been idle, 
                 in seconds."
    ::= { slcConnEntry 8 }

slcConnIdleStr OBJECT-TYPE
    SYNTAX      OCTET STRING
    MAX-ACCESS  read-only
    STATUS      current
    DESCRIPTION "The amount of time that the connection has been idle,
                 formatted in hours:minutes:seconds."
    ::= { slcConnEntry 9 }

slcConnSourceIP OBJECT-TYPE
    SYNTAX      IpAddress
    MAX-ACCESS  read-only
    STATUS      current
    DESCRIPTION "For network (Telnet and SSH) connections into the SLC, the 
                 source IP Address."
    ::= { slcConnEntry 10 }


--
-- System Group
--

slcSystemModel OBJECT-TYPE
    SYNTAX      OCTET STRING
    MAX-ACCESS  read-only
    STATUS      current
    DESCRIPTION "The model of the SLC: SLC8, SLC16, SLC32, SLC48."
    ::= { slcSystem 1 }

slcSystemSerialNo OBJECT-TYPE
    SYNTAX      OCTET STRING
    MAX-ACCESS  read-only
    STATUS      current
    DESCRIPTION "The serial number of the SLC."
    ::= { slcSystem 2 }

slcSystemFWRev OBJECT-TYPE
    SYNTAX      OCTET STRING
    MAX-ACCESS  read-only
    STATUS      current
    DESCRIPTION "The firmware version of the SLC."
    ::= { slcSystem 3 }

slcSystemLoadVia OBJECT-TYPE
    SYNTAX      INTEGER { ftp(1), 
                          tftp(2), 
                          sftp(3), 
                          slm(4),
                          https(5), 
                          nfs(6), 
                          pccard(7) 
                         }
    MAX-ACCESS  read-only
    STATUS      current
    DESCRIPTION "The method used for firmware updates."
    ::= { slcSystem 4 }

slcSystemFTPServer OBJECT-TYPE
    SYNTAX      IpAddress
    MAX-ACCESS  read-only
    STATUS      current
    DESCRIPTION "The IP Address of the FTP/TFTP server used for firmware 
                 updates, and for saving and restoring configurations."
    ::= { slcSystem 5 }

slcSystemFTPPath OBJECT-TYPE
    SYNTAX      OCTET STRING
    MAX-ACCESS  read-only
    STATUS      current
    DESCRIPTION "The path on the FTP server used for firmware updates, and 
                 for saving and restoring configurations."
    ::= { slcSystem 6 }

slcSystemKeypadLock OBJECT-TYPE
    SYNTAX      EnabledState
    MAX-ACCESS  read-only
    STATUS      current
    DESCRIPTION "If enabled, the LCD keypad is locked for editing 
                 configuration.  The keys can only be used to view settings."
    ::= { slcSystem 7 }

slcSystemTimeZone OBJECT-TYPE
    SYNTAX      OCTET STRING
    MAX-ACCESS  read-only
    STATUS      current
    DESCRIPTION "The time zone of the SLC."
    ::= { slcSystem 8 }

slcSystemWelcomeBanner OBJECT-TYPE
    SYNTAX      OCTET STRING
    MAX-ACCESS  read-only
    STATUS      current
    DESCRIPTION "The banner displayed before the login prompt."
    ::= { slcSystem 9 }

slcSystemLoginBanner OBJECT-TYPE
    SYNTAX      OCTET STRING
    MAX-ACCESS  read-only
    STATUS      current
    DESCRIPTION "The banner displayed after successful login."
    ::= { slcSystem 10 }

slcSystemLogoutBanner OBJECT-TYPE
    SYNTAX      OCTET STRING
    MAX-ACCESS  read-only
    STATUS      current
    DESCRIPTION "The banner displayed after logout."
    ::= { slcSystem 11 }

slcSystemWebTimeout OBJECT-TYPE
    SYNTAX      Integer32 (0|5..120)
    MAX-ACCESS  read-only
    STATUS      current
    DESCRIPTION "The timeout (in minutes) for web sessions.  A value of 0 
                 indicates that timeouts are disabled."
    ::= { slcSystem 12 }

slcSystemWebGadget OBJECT-TYPE
    SYNTAX      EnabledState
    MAX-ACCESS  read-only
    STATUS      current
    DESCRIPTION "If enabled, iGoogle Gadget web content is enabled."
    ::= { slcSystem 13 }

slcSystemAction OBJECT-TYPE
    SYNTAX      INTEGER { noAction(1), 
                          rebootSLC(2), 
                          shutdownSLC(3)
                        }
    MAX-ACCESS  read-write
    STATUS      current
    DESCRIPTION "Performs an action on the SLC.  A read of this object always 
                 returns the value noAction(1).  Setting this object to 
                 rebootSLC(2) will terminate all connections and reboot the 
                 SLC.  Setting this object to shutdownSLC(3) will terminate 
                 all connections and shutdown the SLC so it can be powered off."
    ::= { slcSystem 14 }

slcSystemSSHPreAuthBanner OBJECT-TYPE
    SYNTAX      OCTET STRING
    MAX-ACCESS  read-only
    STATUS      current
    DESCRIPTION "The banner displayed prior to SSH authentication."
    ::= { slcSystem 15 }

slcSystemSiteRackRow OBJECT-TYPE
    SYNTAX      Integer32 (1..999)
    MAX-ACCESS  read-only
    STATUS      current
    DESCRIPTION "The identifier of the row of racks in a data center 
                 containing the SLC."
    ::= { slcSystem 16 }

slcSystemSiteRackCluster OBJECT-TYPE
    SYNTAX      Integer32 (1..999)
    MAX-ACCESS  read-only
    STATUS      current
    DESCRIPTION "The identifier of the group of racks in a given row 
                 (slcSystemSiteRackRow) containing the SLC."
    ::= { slcSystem 17 }

slcSystemSiteRack OBJECT-TYPE
    SYNTAX      Integer32 (1..999)
    MAX-ACCESS  read-only
    STATUS      current
    DESCRIPTION "The identifier of the rack in a given rack group
                 (slcSystemSiteRackCluster) containing the SLC."
    ::= { slcSystem 18 }

slcSystemLCDScreens OBJECT-TYPE
    SYNTAX      OCTET STRING
    MAX-ACCESS  read-only
    STATUS      current
    DESCRIPTION "A string describing the enabled LCD screens, in the order they 
                 are displayed.  Each screen is separated by a comma.  The 
                 possible screens are Current Time, Network, Console, Release, 
                 Date/Time, Device Ports, Location and User Strings."
    ::= { slcSystem 19 }

slcSystemLCDUserStrLine1 OBJECT-TYPE
    SYNTAX      OCTET STRING
    MAX-ACCESS  read-only
    STATUS      current
    DESCRIPTION "For the LCD screen User Strings, this is the first line 
                 displayed on the LCD."
    ::= { slcSystem 20 }

slcSystemLCDUserStrLine2 OBJECT-TYPE
    SYNTAX      OCTET STRING
    MAX-ACCESS  read-only
    STATUS      current
    DESCRIPTION "For the LCD screen User Strings, this is the second line 
                 displayed on the LCD."
    ::= { slcSystem 21 }

slcSystemLCDScrolling OBJECT-TYPE
    SYNTAX      EnabledState
    MAX-ACCESS  read-only
    STATUS      current
    DESCRIPTION "If enabled, the LCD automatically scrolls through the 
                 enabled screens."
    ::= { slcSystem 22 }

slcSystemLCDScrollDelay OBJECT-TYPE
    SYNTAX      Integer32 (1..60)
    MAX-ACCESS  read-only
    STATUS      current
    DESCRIPTION "If LCD scrolling is enabled (slcSystemLCDScrolling), the 
                 delay in seconds between displaying screens."
    ::= { slcSystem 23 }

slcSystemLCDIdleDelay OBJECT-TYPE
    SYNTAX      Integer32 (5..60)
    MAX-ACCESS  read-only
    STATUS      current
    DESCRIPTION "If LCD scrolling is enabled (slcSystemLCDScrolling), the 
                 number of seconds after keypad input before auto-scrolling 
                 restarts."
    ::= { slcSystem 24 }

slcSystemInternalTemp OBJECT-TYPE
    SYNTAX      Integer32
    MAX-ACCESS  read-only
    STATUS      current
    DESCRIPTION "The internal temperature of the SLC, given in Celsius. 
                 A value of 9999 is returned if an error is encountered 
                 reading the temperature."
    ::= { slcSystem 25 }

slcSystemWebProtocol OBJECT-TYPE
    SYNTAX      INTEGER { tlsv1SSLv3(1), 
                          tlsv1SSLv3SSLv2(2)
                        }
    MAX-ACCESS  read-only
    STATUS      current
    DESCRIPTION "The protocol used by the web server."
    ::= { slcSystem 26 }

slcSystemWebCipher OBJECT-TYPE
    SYNTAX      INTEGER { highMedium(1), 
                          highMediumLow(2)
                        }
    MAX-ACCESS  read-only
    STATUS      current
    DESCRIPTION "The strength of the cipher used by the web server.  A cipher 
                 with high strength uses 256, 168 or 128 bits; a cipher with 
                 medium strength uses 128 bits; a cipher with low strength 
                 uses 64 or 56 bits."
    ::= { slcSystem 27 }


-- SLC Monitoring Traps

slcEvents       OBJECT IDENTIFIER ::= { slc 0 }
slcEventObjects OBJECT IDENTIFIER ::= { slc 7 }

slcPowerSupplyId OBJECT-TYPE
    SYNTAX      INTEGER { powerSupplyA(1), powerSupplyB(2) }
    MAX-ACCESS  read-only
    STATUS      current
    DESCRIPTION "The identifier of the power supply in a slcEventPowerSupply 
                 trap."
    ::= { slcEventObjects 1 }

slcPowerSupplyAction OBJECT-TYPE
    SYNTAX      INTEGER { powerSupplyFailed(1), powerSupplyRestored(2) }
    MAX-ACCESS  read-only
    STATUS      current
    DESCRIPTION "The action that occurred for a power supply in a 
                 slcEventPowerSupply trap."
    ::= { slcEventObjects 2 }

slcDevPortNumBytes OBJECT-TYPE
    SYNTAX      Integer32
    MAX-ACCESS  read-only
    STATUS      current
    DESCRIPTION "The number of bytes received on a Device Port to trigger a 
                 slcEventDevicePortData or slcEventDevicePortSLMData trap."
    ::= { slcEventObjects 3 }

slcDevPortData OBJECT-TYPE
    SYNTAX      OCTET STRING
    MAX-ACCESS  read-only
    STATUS      current
    DESCRIPTION "The character data received on a Device Port to trigger a 
                 slcEventDevicePortData trap."
    ::= { slcEventObjects 4 }

slcDevPortStartByte OBJECT-TYPE
    SYNTAX      Integer32
    MAX-ACCESS  read-only
    STATUS      current
    DESCRIPTION "The starting byte within the logging buffer of data received 
                 on a Device Port, which triggered a slcEventDevicePortSLMData 
                 trap."
    ::= { slcEventObjects 5 }

slcDevPortTimeFrame OBJECT-TYPE
    SYNTAX      Integer32
    MAX-ACCESS  read-only
    STATUS      current
    DESCRIPTION "The time frame, in seconds, after which a 
                 slcEventDevicePortSLMData trap is sent to the SLM to trigger 
                 retrieval of Device Port data."
    ::= { slcEventObjects 6 }

slcDevPortDeviceErrorStatus OBJECT-TYPE
    SYNTAX      INTEGER { lowPower(1), damageOrTamper(2) }
    MAX-ACCESS  read-only
    STATUS      current
    DESCRIPTION "The status returned when an error occurs in a device connected 
                 to a Device Port."
    ::= { slcEventObjects 7 }

slcHostname OBJECT-TYPE
    SYNTAX      OCTET STRING
    MAX-ACCESS  read-only
    STATUS      current
    DESCRIPTION "The hostname of the SLC sending the trap."
    ::= { slcEventObjects 8 }

slcPCCardSlot OBJECT-TYPE
    SYNTAX      INTEGER { upperSlot(1), lowerSlot(2) }
    MAX-ACCESS  read-only
    STATUS      current
    DESCRIPTION "The PC Card slot indicated for the trap."
    ::= { slcEventObjects 9 }

slcPCCardAction OBJECT-TYPE
    SYNTAX      INTEGER { cardInserted(1), cardRemoved(2) }
    MAX-ACCESS  read-only
    STATUS      current
    DESCRIPTION "The action that occurred on a PC Card slot."
    ::= { slcEventObjects 10 }

slcPCCardType OBJECT-TYPE
    SYNTAX      INTEGER { none(1), 
                          storage(2), 
                          modem(3), 
                          isdn(4),
                          wireless(5),
                          gsmmodem(6) }
    MAX-ACCESS  read-only
    STATUS      current
    DESCRIPTION "The type of card inserted in a PC Card slot."
    ::= { slcEventObjects 11 }


slcEventPowerSupply NOTIFICATION-TYPE
    OBJECTS { slcPowerSupplyId, slcPowerSupplyAction }
    STATUS      current
    DESCRIPTION "The SNMP trap that is generated when a power supply fails 
                 or is restored."
    ::= { slcEvents 1 }

slcEventSysadminPassword NOTIFICATION-TYPE
    STATUS      current
    DESCRIPTION "The SNMP trap that is generated when the sysadmin user 
                 password is changed."
    ::= { slcEvents 2 }

slcEventSLCShutdown NOTIFICATION-TYPE
    STATUS      current
    DESCRIPTION "The SNMP trap that is generated when the SLC is shutdown."
    ::= { slcEvents 3 }

slcEventDevicePortData NOTIFICATION-TYPE
    OBJECTS { slcDevPortId, slcDevPortNumBytes, slcDevPortData,
              slcDevPortCfgEmailTextString, slcHostname }
    STATUS      current
    DESCRIPTION "The SNMP trap that is generated when data is received on a 
                 Device Port, and the Device Port has been configured to 
                 generate a trap when a specified number of bytes 
                 (slcDevPortNumBytes) or a specified sequence of bytes 
                 (slcDevPortCfgEmailTextString) is received.  
                 slcDevPortData is the actual data received."
    ::= { slcEvents 4 }

slcEventDevicePortSLMData NOTIFICATION-TYPE
    OBJECTS { slcDevPortId, slcDevPortNumBytes, slcDevPortStartByte }
    STATUS      current
    DESCRIPTION "The SNMP trap that is generated when data is received on a 
                 Device Port, and the Device Port has been configured to 
                 generate a trap designated for the SecureLinx Manager (SLM) 
                 when a specified number of bytes is received or a specified 
                 time frame is passed.  This trap is only sent to the SLM."
    ::= { slcEvents 5 }

slcEventDevicePortSLMConfig NOTIFICATION-TYPE
    OBJECTS { slcDevPortId, slcDevPortNumBytes, slcDevPortTimeFrame }
    STATUS      current
    DESCRIPTION "The SNMP trap that is generated when the SLM logging 
                 configuration is changed for a Device Port, and the Device 
                 Port has been configured to generate a trap designated for 
                 the SecureLinx Manager (SLM).  This trap specifies the new 
                 SLM logging configuration for the Device Port, and is only 
                 sent to the SLM."
    ::= { slcEvents 6 }

slcEventDevicePortDeviceLowTemp NOTIFICATION-TYPE
    OBJECTS     { slcDevPortId, slcDevPortCfgDevTemperature, 
                  slcDevPortCfgDevLowTemp }
    STATUS      current
    DESCRIPTION "The SNMP trap that is generated when the low temperature 
                 limit for a sensor connected to a Device Port is exceeded."
    ::= { slcEvents 7 }

slcEventDevicePortDeviceHighTemp NOTIFICATION-TYPE
    OBJECTS     { slcDevPortId, slcDevPortCfgDevTemperature, 
                  slcDevPortCfgDevHighTemp }
    STATUS      current
    DESCRIPTION "The SNMP trap that is generated when the high temperature 
                 limit for a sensor connected to a Device Port is exceeded."
    ::= { slcEvents 8 }

slcEventDevicePortDeviceLowHumidity NOTIFICATION-TYPE
    OBJECTS     { slcDevPortId, slcDevPortCfgDevHumidity, 
                  slcDevPortCfgDevLowHumidity }
    STATUS      current
    DESCRIPTION "The SNMP trap that is generated when the low humidity 
                 limit for a sensor connected to a Device Port is exceeded."
    ::= { slcEvents 9 }

slcEventDevicePortDeviceHighHumidity NOTIFICATION-TYPE
    OBJECTS     { slcDevPortId, slcDevPortCfgDevHumidity, 
                  slcDevPortCfgDevHighHumidity }
    STATUS      current
    DESCRIPTION "The SNMP trap that is generated when the high humidity 
                 limit for a sensor connected to a Device Port is exceeded."
    ::= { slcEvents 10 }

slcEventDevicePortDeviceError NOTIFICATION-TYPE
    OBJECTS     { slcDevPortId, slcDevPortDeviceErrorStatus }
    STATUS      current
    DESCRIPTION "The SNMP trap that is generated when an error occurs on a 
                 device connected to a Device Port."
    ::= { slcEvents 11 }

slcEventPCCardAction NOTIFICATION-TYPE
    OBJECTS     { slcPCCardSlot, slcPCCardAction, slcPCCardType }
    STATUS      current
    DESCRIPTION "The SNMP trap that is generated when an event occurs on one 
                 of the PC Card slots."
    ::= { slcEvents 12 }

slcEventSLCInternalTemp NOTIFICATION-TYPE
    OBJECTS     { slcSystemInternalTemp }
    STATUS      current
    DESCRIPTION "The SNMP trap that is generated when the internal temperature 
                 of the SLC is outside of the acceptable operating range."
    ::= { slcEvents 13 }

END
