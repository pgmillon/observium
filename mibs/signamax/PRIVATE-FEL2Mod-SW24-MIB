PRIVATE-FEL2Mod-SW24-MIB DEFINITIONS ::= BEGIN

IMPORTS
    DisplayString FROM SNMPv2-TC
    MODULE-COMPLIANCE,OBJECT-GROUP, NOTIFICATION-GROUP       FROM SNMPv2-CONF
    enterprises,MODULE-IDENTITY,OBJECT-TYPE,NOTIFICATION-TYPE,Counter32,IpAddress        FROM SNMPv2-SMI
    ifIndex    FROM RFC1213-MIB;


privatetech MODULE-IDENTITY
        LAST-UPDATED "200607030000Z"
        ORGANIZATION "xxx Tech Corp."
        CONTACT-INFO
            "xxx"
        DESCRIPTION
            "The MIB module is for xxx Tech."
        ::= { enterprises 5205 }

switch                       OBJECT IDENTIFIER ::= { privatetech 2 }

feL2ModSW24ProductID	        OBJECT IDENTIFIER ::= { switch 19 }

feL2ModSW24Produces            OBJECT IDENTIFIER ::= { feL2ModSW24ProductID 1 }

feL2ModSW24System           	OBJECT IDENTIFIER ::= { feL2ModSW24Produces 1 }

feL2ModSW24CommonSys           	OBJECT IDENTIFIER ::= { feL2ModSW24System 1 }

feL2ModSW24Reboot OBJECT-TYPE
	SYNTAX		INTEGER(0|1|2)
	MAX-ACCESS	    read-write
	STATUS		current
	DESCRIPTION
		"Reboot the system. Get this OID always return zero.
            0 - do nothing
			1 - Reboot without saving start
			2 - Reboot with saving start"
	::= { feL2ModSW24CommonSys 1 }

feL2ModSW24BiosVsersion	OBJECT-TYPE
	SYNTAX		DisplayString
	MAX-ACCESS	    read-only
	STATUS		current
	DESCRIPTION
		"Get the BIOS version of the system."
	::= { feL2ModSW24CommonSys 2 }

feL2ModSW24FirmwareVersion	OBJECT-TYPE
	SYNTAX		DisplayString
	MAX-ACCESS	    read-only
	STATUS		current
	DESCRIPTION
		"Get the firmware version of the system."
	::= { feL2ModSW24CommonSys 3 }

feL2ModSW24HardwareVersion	OBJECT-TYPE
	SYNTAX		DisplayString
	MAX-ACCESS	    read-only
	STATUS		current
	DESCRIPTION
		"Get the hardware version of the system."
	::= { feL2ModSW24CommonSys 4 }

feL2ModSW24MechanicalVersion OBJECT-TYPE
	SYNTAX		DisplayString
	MAX-ACCESS 	    read-only
	STATUS		current
	DESCRIPTION
		"Get the mechanical version of the system."
	::= { feL2ModSW24CommonSys 5 }

feL2ModSW24SerialNumber	OBJECT-TYPE
	SYNTAX		DisplayString
	MAX-ACCESS	    read-only
	STATUS		current
	DESCRIPTION
		"Get the Serial number of the system."
	::= { feL2ModSW24CommonSys 6 }

feL2ModSW24HostMacAddress	OBJECT-TYPE
	SYNTAX		DisplayString
	MAX-ACCESS	    read-only
	STATUS		current
	DESCRIPTION
		"Get the MAC address of the system."
	::= { feL2ModSW24CommonSys 7 }

feL2ModSW24DevicePort	OBJECT-TYPE
	SYNTAX		DisplayString
	MAX-ACCESS  	read-only
	STATUS		current
	DESCRIPTION
		"Get the quantity of ports that this system owns now."
	::= { feL2ModSW24CommonSys 8 }

feL2ModSW24RamSize  OBJECT-TYPE
    SYNTAX      DisplayString
    MAX-ACCESS      read-only
    STATUS      current
    DESCRIPTION
        "Get the RAM size of the system."
	::= { feL2ModSW24CommonSys 9 }

feL2ModSW24FlashSize  OBJECT-TYPE
    SYNTAX      DisplayString
    MAX-ACCESS      read-only
    STATUS      current
    DESCRIPTION
        "Get the flash size of the system."
	::= { feL2ModSW24CommonSys 10 }


feL2ModSW24IP           	OBJECT IDENTIFIER ::= { feL2ModSW24System 2 }

feL2ModSW24DhcpSetting OBJECT-TYPE
	SYNTAX		    INTEGER(0|1)
	MAX-ACCESS	        read-write
	STATUS		    current
	DESCRIPTION
		"Get/Set DHCP status of the system.
			0 - DHCP disable
			1 - DHCP enable"
	::= { feL2ModSW24IP 1 }

feL2ModSW24IPAddress OBJECT-TYPE
	SYNTAX      IpAddress
	MAX-ACCESS	    read-write
	STATUS		current
	DESCRIPTION
		"Get/Set the IP address of the system.
		 You can't set this OID if DHCP status is enabled."
	::= { feL2ModSW24IP 2 }

feL2ModSW24NetMask OBJECT-TYPE
	SYNTAX      IpAddress
	MAX-ACCESS	    read-write
	STATUS		current
	DESCRIPTION
		"Get/Set the subnet mask of the system.
		 You can't set this OID if DHCP status is enabled."
	::= { feL2ModSW24IP 3 }

feL2ModSW24DefaultGateway OBJECT-TYPE
	SYNTAX      IpAddress
	MAX-ACCESS	    read-write
	STATUS		current
	DESCRIPTION
		"Get/Set the default gateway of the system.
		 You can't set this OID if DHCP status is enabled."
	::= { feL2ModSW24IP 4 }

feL2ModSW24DnsSetting OBJECT-TYPE
	SYNTAX      INTEGER(0|1)
	MAX-ACCESS	    read-write
	STATUS		current
	DESCRIPTION
		"Get/Set the source of DNS server.
		 You can't set this OID if DHCP status is disabled.
			0 - manual, the DNS server is from manual setting
            1 - auto, the DNS server is assigned by DHCP server."
	::= { feL2ModSW24IP 5 }

feL2ModSW24DnsServer OBJECT-TYPE
	SYNTAX      IpAddress
	MAX-ACCESS	    read-write
	STATUS		current
	DESCRIPTION
		"Get/Set the DNS server of the system."
	::= { feL2ModSW24IP 6 }

feL2ModSW24Time           	OBJECT IDENTIFIER ::= { feL2ModSW24System 3 }

feL2ModSW24SystemCurrentTime OBJECT-TYPE
	SYNTAX      DisplayString
	MAX-ACCESS	    read-only
	STATUS		current
	DESCRIPTION
		"Get the current time of the system."
	::= { feL2ModSW24Time 1 }

feL2ModSW24ManualTimeSetting OBJECT-TYPE
	SYNTAX      DisplayString
	MAX-ACCESS	    read-write
	STATUS		current
	DESCRIPTION
		"Get/Set the system time of the device.
        The input format is 'Year/Month/Day/Hour/Minute/Second'.
        ex: 2004/1/1/12/34/25  means 2004/1/1 - 12:24:25 .
        The value range:
        Year    : 2000 - 2036,
        Mouth   : 1 - 12,
        Day     : 1 - 31,
        Hour    : 0 - 23,
        Minute  : 0 - 59,
        Sec     : 0 - 59."
	::= { feL2ModSW24Time 2 }

feL2ModSW24NTPServer OBJECT-TYPE
	SYNTAX      DisplayString
	MAX-ACCESS	    read-write
	STATUS		current
	DESCRIPTION
		"Get/Set the NTP Time Server. You can use the IP address or domain name."
	::= { feL2ModSW24Time 3 }

feL2ModSW24NTPTimeZone OBJECT-TYPE
	SYNTAX      INTEGER(-12..13)
	MAX-ACCESS	    read-write
	STATUS		current
	DESCRIPTION
		"Get/Set the NTP Time Zone.
		The value range is between -12 and 13
		-12 - GMT -12:00,
		-11 - GMT -11:00,
		-10 - GMT -10:00,
		 -9 - GMT -09:00,
		 -8 - GMT -08:00,
		 -7 - GMT -07:00,
		 -6 - GMT -06:00,
		 -5 - GMT -05:00,
		 -4 - GMT -04:00,
		 -3 - GMT -03:00,
		 -2 - GMT -02:00,
		 -1 - GMT -01:00,
		  0 - GMT +00:00,
		  1 - GMT +01:00,
		  2 - GMT +02:00,
		  3 - GMT +03:00,
		  4 - GMT +04:00,
		  5 - GMT +05:00,
		  6 - GMT +06:00,
		  7 - GMT +07:00,
		  8 - GMT +08:00,
		  9 - GMT +09:00,
		 10 - GMT +10:00,
		 11 - GMT +11:00,
		 12 - GMT +12:00,
		 13 - GMT +13:00. "
	::= { feL2ModSW24Time 4 }

feL2ModSW24NTPTimeSync OBJECT-TYPE
	SYNTAX      INTEGER(0|1)
	MAX-ACCESS	    read-write
	STATUS		current
	DESCRIPTION
		"Sync time from NTP Server. Get this OID always return zero.
		Set the Time Server and Time Zone before doing time sync.
		Notice that time server must be correct!
		The value range (0|1):
		1 - sync.
        0 - do nothing."
	::= { feL2ModSW24Time 5 }

feL2ModSW24DaylightSavingTime OBJECT-TYPE
	SYNTAX      INTEGER(-5..5)
	MAX-ACCESS	    read-write
	STATUS		current
	DESCRIPTION
		"Get/Set the daylight saving time.
		The value range is between -5 and 5. (Unit: hour)"
	::= { feL2ModSW24Time 6 }

feL2ModSW24DaylightStartTime OBJECT-TYPE
	SYNTAX      DisplayString
	MAX-ACCESS	    read-write
	STATUS		current
	DESCRIPTION
		"Get/Set the Start time of Daylight Saving.
		The input format is 'MM/DD/HH',
		and daylight saving start month can't equal end month.
		example: month/day/hour   10/01/00
		month: 01~12, day: 01~31, hour: 00~23 ."
	::= { feL2ModSW24Time 7 }

feL2ModSW24DaylightEndTime OBJECT-TYPE
	SYNTAX      DisplayString
	MAX-ACCESS	    read-write
	STATUS		current
	DESCRIPTION
		"Get/Set the End time of Daylight Saving.
		The input format is 'MM/DD/HH',
		and daylight saving start month can't equal end month.
		example: month/day/hour   04/01/00
		month: 01~12, day: 01~31, hour: 00~23 ."
	::= { feL2ModSW24Time 8 }


feL2ModSW24Account           	OBJECT IDENTIFIER ::= { feL2ModSW24System 4 }

feL2ModSW24AccountNumber OBJECT-TYPE
	SYNTAX      INTEGER(1..5)
	MAX-ACCESS	    read-only
	STATUS		current
	DESCRIPTION
		"Get the current account number(s) of the system."
	::= { feL2ModSW24Account 1 }

feL2ModSW24AccountTable	OBJECT-TYPE
	SYNTAX		SEQUENCE OF FEL2ModSW24AccountEntry
	MAX-ACCESS	not-accessible
	STATUS		current
	DESCRIPTION
		"This is a list of FEL2ModSW24AccountEntry. The numbers of entries are given by
		the value of feL2ModSW24AccountNumber."
	::= { feL2ModSW24Account 2 }

FEL2ModSW24AccountEntry ::=
SEQUENCE {
    feL2ModSW24AccountIndex		    INTEGER,
    feL2ModSW24AccountAuthorization	DisplayString,
    feL2ModSW24AccountName             DisplayString,
    feL2ModSW24AccountPassword         DisplayString
}

feL2ModSW24AccountEntry	OBJECT-TYPE
	SYNTAX		FEL2ModSW24AccountEntry
	MAX-ACCESS	    not-accessible
	STATUS		current
	DESCRIPTION
		"This is the Entry(s) for account information."
	INDEX {feL2ModSW24AccountIndex}
	::= { feL2ModSW24AccountTable 1 }

feL2ModSW24AccountIndex	OBJECT-TYPE
	SYNTAX		INTEGER(1..5)
	MAX-ACCESS	    read-only
	STATUS		current
	DESCRIPTION
		"This is the index of the account entry."
	::= { feL2ModSW24AccountEntry 1 }

feL2ModSW24AccountAuthorization	OBJECT-TYPE
	SYNTAX		DisplayString
	MAX-ACCESS	    read-only
	STATUS		current
	DESCRIPTION
		"This is the authorization of the account entry."
	::= { feL2ModSW24AccountEntry 2 }

feL2ModSW24AccountName	OBJECT-TYPE
	SYNTAX		DisplayString
	MAX-ACCESS	    read-write
	STATUS		current
	DESCRIPTION
		"This is the username of the account entry."
	::= { feL2ModSW24AccountEntry 3 }

feL2ModSW24AccountPassword	OBJECT-TYPE
	SYNTAX		DisplayString
	MAX-ACCESS	    read-write
	STATUS		current
	DESCRIPTION
		"This is the password of the account entry. The return value is always '********'."
	::= { feL2ModSW24AccountEntry 4 }

feL2ModSW24AccountAddName OBJECT-TYPE
	SYNTAX      DisplayString
	MAX-ACCESS	    read-write
	STATUS		current
	DESCRIPTION
		"This is the account name for adding operation."
	::= { feL2ModSW24Account 3 }

feL2ModSW24AccountAddPassword OBJECT-TYPE
	SYNTAX      DisplayString
	MAX-ACCESS	    read-write
	STATUS		current
	DESCRIPTION
		"This is the account password for adding operation. The return value is always '********'."
	::= { feL2ModSW24Account 4 }

feL2ModSW24DoAccountAdd OBJECT-TYPE
	SYNTAX      INTEGER(0|1)
	MAX-ACCESS	    read-write
	STATUS		current
	DESCRIPTION
		"Add account name. OID feL2ModSW24AccountAddName and feL2ModSW24AccountAddPassword must be
        filled first. Get this OID always return zero.
            1 - add account.
            0 - do nothing."
	::= { feL2ModSW24Account 5 }

feL2ModSW24AccountDel	OBJECT-TYPE
	SYNTAX		INTEGER(2..5)
	MAX-ACCESS	    read-write
	STATUS		current
	DESCRIPTION
		"Delete account. The value is valid feL2ModSW24AccountIndex(Can't delete administrator)."
	::= { feL2ModSW24Account 6 }




feL2ModSW24Snmp           	OBJECT IDENTIFIER ::= { feL2ModSW24Produces 2 }

feL2ModSW24GetCommunity OBJECT-TYPE
	SYNTAX      DisplayString
	MAX-ACCESS	    read-write
	STATUS		current
	DESCRIPTION
		"Get/Set the get-community of the SNMP."
	::= { feL2ModSW24Snmp 1 }

feL2ModSW24SetCommunity OBJECT-TYPE
	SYNTAX      DisplayString
	MAX-ACCESS	    read-write
	STATUS		current
	DESCRIPTION
		"Get/Set the set-community of the SNMP."
	::= { feL2ModSW24Snmp 2 }

feL2ModSW24TrapHostNumber OBJECT-TYPE
	SYNTAX      INTEGER(1..6)
	MAX-ACCESS	    read-only
	STATUS		current
	DESCRIPTION
		"Get the number of trap hosts."
	::= { feL2ModSW24Snmp 3 }

feL2ModSW24TrapHostTable	OBJECT-TYPE
	SYNTAX		SEQUENCE OF FEL2ModSW24TrapHostEntry
	MAX-ACCESS	not-accessible
	STATUS		current
	DESCRIPTION
		"A list of trap host entry. The numbers of entries are given by the value of feL2ModSW24TrapHostNumber."
    ::= { feL2ModSW24Snmp 4 }

FEL2ModSW24TrapHostEntry ::=
SEQUENCE {
    feL2ModSW24TrapHostIndex		    INTEGER,
    feL2ModSW24TrapHostIP          	IpAddress,
    feL2ModSW24TrapHostPort            INTEGER,
    feL2ModSW24TrapHostCommunity       DisplayString
}

feL2ModSW24TrapHostEntry	OBJECT-TYPE
	SYNTAX		FEL2ModSW24TrapHostEntry
	MAX-ACCESS	    not-accessible
	STATUS		current
	DESCRIPTION
		"This is the entry information for trap host."
	INDEX {feL2ModSW24TrapHostIndex}
	::= { feL2ModSW24TrapHostTable 1 }

feL2ModSW24TrapHostIndex	OBJECT-TYPE
	SYNTAX		INTEGER(1..6)
	MAX-ACCESS	    read-only
	STATUS		current
	DESCRIPTION
		"The index of the trap host entry."
	::= { feL2ModSW24TrapHostEntry 1 }

feL2ModSW24TrapHostIP	OBJECT-TYPE
	SYNTAX		IpAddress
	MAX-ACCESS	    read-write
	STATUS		current
	DESCRIPTION
		"This is the IP of the trap host."
	::= { feL2ModSW24TrapHostEntry 2 }


feL2ModSW24TrapHostPort	OBJECT-TYPE
	SYNTAX		INTEGER(1..65535)
	MAX-ACCESS	    read-write
	STATUS		current
	DESCRIPTION
		"This is the receiving-port number of the trap host."
	::= { feL2ModSW24TrapHostEntry 3 }


feL2ModSW24TrapHostCommunity	OBJECT-TYPE
	SYNTAX		DisplayString
	MAX-ACCESS	    read-write
	STATUS		current
	DESCRIPTION
		"The community name for the trap PDU."
	::= { feL2ModSW24TrapHostEntry 4 }



feL2ModSW24Alarm           	OBJECT IDENTIFIER ::= { feL2ModSW24Produces 3 }

feL2ModSW24Event           	OBJECT IDENTIFIER ::= { feL2ModSW24Alarm 1 }

feL2ModSW24EventNumber OBJECT-TYPE
	SYNTAX      INTEGER(1..2147483647)
	MAX-ACCESS	    read-only
	STATUS		current
	DESCRIPTION
		"Get the total number of alarm events."
	::= { feL2ModSW24Event 1 }

feL2ModSW24EventTable	OBJECT-TYPE
	SYNTAX		SEQUENCE OF FEL2ModSW24EventEntry
	MAX-ACCESS	not-accessible
	STATUS		current
    DESCRIPTION
        "A list of alarm event entry. The numbers of entries are given by the value of feL2ModSW24EventNumber."
	::= { feL2ModSW24Event 2 }

FEL2ModSW24EventEntry ::=
SEQUENCE {
    feL2ModSW24EventIndex		    INTEGER,
    feL2ModSW24EventName          	DisplayString,
    feL2ModSW24EventSendEmail      INTEGER,
    feL2ModSW24EventSendSMS        INTEGER,
    feL2ModSW24EventSendTrap       INTEGER
}

feL2ModSW24EventEntry	OBJECT-TYPE
	SYNTAX		FEL2ModSW24EventEntry
	MAX-ACCESS	    not-accessible
	STATUS		current
	DESCRIPTION
		"This is the entry information for alarm event."
	INDEX {feL2ModSW24EventIndex}
	::= { feL2ModSW24EventTable 1 }

feL2ModSW24EventIndex	OBJECT-TYPE
	SYNTAX		INTEGER(1..2147483647)
	MAX-ACCESS	    read-only
	STATUS		current
	DESCRIPTION
		"This is the index of the alarm event entry."
	::= { feL2ModSW24EventEntry 1 }

feL2ModSW24EventName	OBJECT-TYPE
	SYNTAX		DisplayString
	MAX-ACCESS	    read-only
	STATUS		current
	DESCRIPTION
		"This is the alarm event name."
	::= { feL2ModSW24EventEntry 2 }

feL2ModSW24EventSendEmail	OBJECT-TYPE
	SYNTAX		INTEGER(0|1)
	MAX-ACCESS	    read-write
	STATUS		current
	DESCRIPTION
		"Send email when alarm event is triggered."
	::= { feL2ModSW24EventEntry 3 }

feL2ModSW24EventSendSMS	OBJECT-TYPE
	SYNTAX		INTEGER(0|1)
	MAX-ACCESS	    read-write
	STATUS		current
	DESCRIPTION
		"Send SMS when alarm event is triggered."
	::= { feL2ModSW24EventEntry 4 }

feL2ModSW24EventSendTrap	OBJECT-TYPE
	SYNTAX		INTEGER(0|1)
	MAX-ACCESS	    read-write
	STATUS		current
	DESCRIPTION
		"Send trap when alarm event is triggered."
	::= { feL2ModSW24EventEntry 5 }




feL2ModSW24Email           	OBJECT IDENTIFIER ::= { feL2ModSW24Alarm 2 }

feL2ModSW24EmailServer OBJECT-TYPE
	SYNTAX      DisplayString
	MAX-ACCESS	    read-write
	STATUS		current
	DESCRIPTION
		"This is the SMTP server for alarm event."
	::= { feL2ModSW24Email 1 }

feL2ModSW24EmailUsername OBJECT-TYPE
	SYNTAX      DisplayString
	MAX-ACCESS	    read-write
	STATUS		current
	DESCRIPTION
		"This is the Username of SMTP server."
	::= { feL2ModSW24Email 2 }

feL2ModSW24EmailPassword OBJECT-TYPE
	SYNTAX      DisplayString
	MAX-ACCESS	    read-write
	STATUS		current
	DESCRIPTION
		"This is the User Password of SMTP server."
	::= { feL2ModSW24Email 3 }

feL2ModSW24EmailUserNumber OBJECT-TYPE
	SYNTAX      INTEGER(1..6)
	MAX-ACCESS	    read-only
	STATUS		current
	DESCRIPTION
		"The number of the email users that you want to send the alarm notification."
	::= { feL2ModSW24Email 4 }

feL2ModSW24EmailUserTable	OBJECT-TYPE
	SYNTAX		SEQUENCE OF FEL2ModSW24EmailUserEntry
	MAX-ACCESS	not-accessible
	STATUS		current
    DESCRIPTION
        "This is a list of email user entry. The numbers of entries are given by the value of feL2ModSW24EmailUserNumber."
	::= { feL2ModSW24Email 5 }

FEL2ModSW24EmailUserEntry ::=
SEQUENCE {
    feL2ModSW24EmailUserIndex		    INTEGER,
    feL2ModSW24EmailUserAddress       	DisplayString
}

feL2ModSW24EmailUserEntry	OBJECT-TYPE
	SYNTAX		FEL2ModSW24EmailUserEntry
	MAX-ACCESS	    not-accessible
	STATUS		current
	DESCRIPTION
		"This is the Entry information for email user entry."
	INDEX {feL2ModSW24EmailUserIndex}
	::= { feL2ModSW24EmailUserTable 1 }

feL2ModSW24EmailUserIndex	OBJECT-TYPE
	SYNTAX		INTEGER(1..6)
	MAX-ACCESS	    read-only
	STATUS		current
	DESCRIPTION
		"This is the index of the email user entry."
	::= { feL2ModSW24EmailUserEntry 1 }

feL2ModSW24EmailUserAddress	OBJECT-TYPE
	SYNTAX		DisplayString
	MAX-ACCESS	    read-write
	STATUS		current
	DESCRIPTION
		"This is the email address of the email user entry."
	::= { feL2ModSW24EmailUserEntry 2 }



feL2ModSW24SMS           	OBJECT IDENTIFIER ::= { feL2ModSW24Alarm 3 }

feL2ModSW24SMSServer OBJECT-TYPE
	SYNTAX      DisplayString
	MAX-ACCESS	    read-write
	STATUS		current
	DESCRIPTION
		"This is the SMS server for alarm event."
	::= { feL2ModSW24SMS 1 }

feL2ModSW24SMSUsername OBJECT-TYPE
	SYNTAX      DisplayString
	MAX-ACCESS	    read-write
	STATUS		current
	DESCRIPTION
		"This is the Username of SMS server."
	::= { feL2ModSW24SMS 2 }

feL2ModSW24SMSPassword OBJECT-TYPE
	SYNTAX      DisplayString
	MAX-ACCESS	    read-write
	STATUS		current
	DESCRIPTION
		"This is the Password of SMS server."
	::= { feL2ModSW24SMS 3 }

feL2ModSW24SMSUserNumber OBJECT-TYPE
	SYNTAX      INTEGER(1..6)
	MAX-ACCESS	    read-only
	STATUS		current
	DESCRIPTION
		"The number of the SMS users that you want to send the alarm notification."
	::= { feL2ModSW24SMS 4 }

feL2ModSW24SMSUserTable	OBJECT-TYPE
	SYNTAX		SEQUENCE OF FEL2ModSW24SMSUserEntry
	MAX-ACCESS	not-accessible
	STATUS		current
    DESCRIPTION
        "This is a list of SMS user entry. The numbers of entries are given by the value of feL2ModSW24SMSUserNumber."
    ::= { feL2ModSW24SMS 5 }

FEL2ModSW24SMSUserEntry ::=
SEQUENCE {
    feL2ModSW24SMSUserIndex		    INTEGER,
    feL2ModSW24SMSUserMobilePhone       	DisplayString
}

feL2ModSW24SMSUserEntry	OBJECT-TYPE
	SYNTAX		FEL2ModSW24SMSUserEntry
	MAX-ACCESS	    not-accessible
	STATUS		current
	DESCRIPTION
		"This is the Entry information for SMS user entry."
	INDEX {feL2ModSW24SMSUserIndex}
	::= { feL2ModSW24SMSUserTable 1 }

feL2ModSW24SMSUserIndex	OBJECT-TYPE
	SYNTAX		INTEGER(1..6)
	MAX-ACCESS	    read-only
	STATUS		current
	DESCRIPTION
		"This is the index of the SMS user entry."
	::= { feL2ModSW24SMSUserEntry 1 }

feL2ModSW24SMSUserMobilePhone	OBJECT-TYPE
	SYNTAX		DisplayString
	MAX-ACCESS	    read-write
	STATUS		current
	DESCRIPTION
		"The SMS phone number of the SMS user entry."
	::= { feL2ModSW24SMSUserEntry 2 }



feL2ModSW24Tftp           	OBJECT IDENTIFIER ::= { feL2ModSW24Produces 4 }

feL2ModSW24TftpServer OBJECT-TYPE
	SYNTAX      IpAddress
	MAX-ACCESS	    read-write
	STATUS		current
	DESCRIPTION
		"Get/Set the tftp server."
	::= { feL2ModSW24Tftp 1 }




feL2ModSW24Configuration           	OBJECT IDENTIFIER ::= { feL2ModSW24Produces 5 }

feL2ModSW24SaveRestore           	OBJECT IDENTIFIER ::= { feL2ModSW24Configuration 1 }

feL2ModSW24SaveStart OBJECT-TYPE
	SYNTAX      INTEGER(0|1)
	MAX-ACCESS	    read-write
	STATUS		current
	DESCRIPTION
		"Save current configuration into flash memory (Save as Start Configuration).
        Get this OID always return zero.
            1 - save.
            0 - do nothing. "
	::= { feL2ModSW24SaveRestore 1 }

feL2ModSW24SaveUser OBJECT-TYPE
	SYNTAX      INTEGER(0|1)
	MAX-ACCESS	    read-write
	STATUS		current
	DESCRIPTION
		"Save current configuration into flash memory (Save as User Configuration).
        Get this OID always return zero.
            1 - save.
            0 - do nothing. "
	::= { feL2ModSW24SaveRestore 2 }

feL2ModSW24RestoreDefault OBJECT-TYPE
	SYNTAX      INTEGER(0|1|2)
	MAX-ACCESS	    read-write
	STATUS		current
	DESCRIPTION
		"Restore factory default configuration.
        Get this OID always return zero.
            2 - restore default included default ip address.
            1 - restore default without changing current ip address.
            0 - do nothing. "
	::= { feL2ModSW24SaveRestore 3 }

feL2ModSW24RestoreUser OBJECT-TYPE
	SYNTAX      INTEGER(0|1)
	MAX-ACCESS	    read-write
	STATUS		current
	DESCRIPTION
		"Restore user configuration.
        Get this OID always return zero.
            1 - restore.
            0 - do nothing. "
	::= { feL2ModSW24SaveRestore 4 }




feL2ModSW24ConfigFile           	OBJECT IDENTIFIER ::= { feL2ModSW24Configuration 2 }

feL2ModSW24ExportConfigName OBJECT-TYPE
	SYNTAX      DisplayString
	MAX-ACCESS	    read-write
	STATUS		current
	DESCRIPTION
		"Get/Set the export file path and name."
	::= { feL2ModSW24ConfigFile 1 }

feL2ModSW24DoExportConfig OBJECT-TYPE
	SYNTAX      INTEGER(1|2)
	MAX-ACCESS	    read-write
	STATUS		current
	DESCRIPTION
		"Do export-config.
        Get this oid always return zero.
			1	-	export start section.
			2	-	export user-conf section."
	::= { feL2ModSW24ConfigFile 2 }

feL2ModSW24ImportConfigName OBJECT-TYPE
	SYNTAX      DisplayString
	MAX-ACCESS	    read-write
	STATUS		current
	DESCRIPTION
        "Get/Set the import file path and name."
	::= { feL2ModSW24ConfigFile 3 }

feL2ModSW24DoImportConfig OBJECT-TYPE
	SYNTAX      INTEGER(1|2)
	MAX-ACCESS	    read-write
	STATUS		current
	DESCRIPTION
		"Do import-config.
        Get this OID always return zero.
			1	-	import start section.
			2	-	import user-conf section."
	::= { feL2ModSW24ConfigFile 4 }



feL2ModSW24Diagnostic           	OBJECT IDENTIFIER ::= { feL2ModSW24Produces 6 }

feL2ModSW24EEPROMTest OBJECT-TYPE
	SYNTAX      DisplayString
	MAX-ACCESS	    read-only
	STATUS		current
	DESCRIPTION
		"EEPROM access test."
	::= { feL2ModSW24Diagnostic 1 }

feL2ModSW24UartTest OBJECT-TYPE
	SYNTAX      DisplayString
	MAX-ACCESS	    read-only
	STATUS		current
	DESCRIPTION
		"UART access test."
	::= { feL2ModSW24Diagnostic 2 }

feL2ModSW24DramTest OBJECT-TYPE
	SYNTAX      DisplayString
	MAX-ACCESS	    read-only
	STATUS		current
	DESCRIPTION
		"DRAM access test."
	::= { feL2ModSW24Diagnostic 3 }

feL2ModSW24FlashTest OBJECT-TYPE
	SYNTAX      DisplayString
	MAX-ACCESS	    read-only
	STATUS		current
	DESCRIPTION
		"Flash memory access test."
	::= { feL2ModSW24Diagnostic 4 }

feL2ModSW24InternalLoopbackTest OBJECT-TYPE
	SYNTAX      DisplayString
	MAX-ACCESS	    read-only
	STATUS		current
	DESCRIPTION
		"Internal loopback test."
	::= { feL2ModSW24Diagnostic 5 }

feL2ModSW24ExternalLoopbackTest OBJECT-TYPE
	SYNTAX      DisplayString
	MAX-ACCESS	    read-only
	STATUS		current
	DESCRIPTION
		"External loopback test."
	::= { feL2ModSW24Diagnostic 6 }

feL2ModSW24PingTest OBJECT-TYPE
	SYNTAX      DisplayString
	MAX-ACCESS	    read-write
	STATUS		current
	DESCRIPTION
		"Set the host address that you want to ping and the system will return the test result."
	::= { feL2ModSW24Diagnostic 7 }



feL2ModSW24Log           	OBJECT IDENTIFIER ::= { feL2ModSW24Produces 7 }

feL2ModSW24ClearLog OBJECT-TYPE
	SYNTAX      INTEGER(0|1)
	MAX-ACCESS	    read-write
	STATUS		current
	DESCRIPTION
		"Clear system log.
        Get this OID always return zero.
            1 - clear log.
            0 - do nothing. "
	::= { feL2ModSW24Log 1 }

feL2ModSW24UploadLog OBJECT-TYPE
	SYNTAX      INTEGER(0|1)
	MAX-ACCESS	    read-write
	STATUS		current
	DESCRIPTION
		"Upload current system log. Set the correct tftp server first.
        The format of log file is 'ModelName_SerialNumbuer_YYMMDD_HHMM'.
        Get this OID always return zero.
            1 - upload log
            0 - do nothing. "
	::= { feL2ModSW24Log 2 }

feL2ModSW24AutoUploadLogState OBJECT-TYPE
	SYNTAX      INTEGER(0|1)
	MAX-ACCESS	    read-write
	STATUS		current
	DESCRIPTION
		"Enable auto-upload log function. Set the correct tftp server first.
        The format of log file is 'ModelName_SerialNumbuer_YYMMDD_HHMM'.
        Get this OID always return zero.
            1 - Enable auto-upload
            0 - do nothing. "
	::= { feL2ModSW24Log 3 }

feL2ModSW24LogNumber OBJECT-TYPE
	SYNTAX      INTEGER(0..120)
	MAX-ACCESS	    read-only
	STATUS		current
	DESCRIPTION
		"Get the number of current system log. "
	::= { feL2ModSW24Log 4 }

feL2ModSW24LogTable	OBJECT-TYPE
	SYNTAX		SEQUENCE OF FEL2ModSW24LogEntry
	MAX-ACCESS	not-accessible
	STATUS		current
    DESCRIPTION
        "This is a list of log entry. The numbers of entries are given by the value of feL2ModSW24LogNumber."
	::= { feL2ModSW24Log 5 }

FEL2ModSW24LogEntry ::=
SEQUENCE {
    feL2ModSW24LogIndex		    INTEGER,
    feL2ModSW24LogEvent           	DisplayString
}

feL2ModSW24LogEntry	OBJECT-TYPE
	SYNTAX		FEL2ModSW24LogEntry
	MAX-ACCESS	    not-accessible
	STATUS		current
	DESCRIPTION
		"This is the Entry information for system log."
	INDEX {feL2ModSW24LogIndex}
	::= { feL2ModSW24LogTable 1 }

feL2ModSW24LogIndex	OBJECT-TYPE
	SYNTAX		INTEGER(1..120)
	MAX-ACCESS	    read-only
	STATUS		current
	DESCRIPTION
		"This is the index of the log entry."
	::= { feL2ModSW24LogEntry 1 }

feL2ModSW24LogEvent	OBJECT-TYPE
	SYNTAX		DisplayString
	MAX-ACCESS	    read-only
	STATUS		current
	DESCRIPTION
		"This is the detail information of the log entry."
	::= { feL2ModSW24LogEntry 2 }



feL2ModSW24Firmware           	OBJECT IDENTIFIER ::= { feL2ModSW24Produces 8 }

feL2ModSW24FirmwareFileName OBJECT-TYPE
	SYNTAX      DisplayString
	MAX-ACCESS	    read-write
	STATUS		current
	DESCRIPTION
		"Get/Set the path and filename for firmware upgrading."
	::= { feL2ModSW24Firmware 1 }

feL2ModSW24DoFirmwareUpgrade OBJECT-TYPE
	SYNTAX      INTEGER(0|1)
	MAX-ACCESS	    read-write
	STATUS		current
	DESCRIPTION
		"Do firmware upgrade. Get this OID always return zero.
            1 - do firmware upgrade.
            0 - do nothing."
	::= { feL2ModSW24Firmware 2 }



feL2ModSW24Port           	OBJECT IDENTIFIER ::= { feL2ModSW24Produces 9 }

feL2ModSW24PortStatus           	OBJECT IDENTIFIER ::= { feL2ModSW24Port 1 }

feL2ModSW24PortStatusNumber OBJECT-TYPE
	SYNTAX      INTEGER(1..2147483647)
	MAX-ACCESS	    read-only
	STATUS		current
	DESCRIPTION
		"Get the number of port."
	::= { feL2ModSW24PortStatus 1 }

feL2ModSW24PortStatusTable	OBJECT-TYPE
	SYNTAX		SEQUENCE OF FEL2ModSW24PortStatusEntry
	MAX-ACCESS	not-accessible
	STATUS		current
    DESCRIPTION
        "This is a list of port status entry. The numbers of entries are given by the value of feL2ModSW24PortStatusNumber."
	::= { feL2ModSW24PortStatus 2 }

FEL2ModSW24PortStatusEntry ::=
SEQUENCE {
    feL2ModSW24PortStatusIndex		    INTEGER,
    feL2ModSW24PortStatusMedia          DisplayString,
    feL2ModSW24PortStatusLink           DisplayString,
    feL2ModSW24PortStatusPortState      DisplayString,
    feL2ModSW24PortStatusAutoNego       DisplayString,
    feL2ModSW24PortStatusSpdDpx         DisplayString,
    feL2ModSW24PortStatusFlwCtrl        DisplayString,
    feL2ModSW24PortStatuDescription     DisplayString
}

feL2ModSW24PortStatusEntry	OBJECT-TYPE
	SYNTAX		FEL2ModSW24PortStatusEntry
	MAX-ACCESS	    not-accessible
	STATUS		current
	DESCRIPTION
		"This is the entry(s) for port status information."
	INDEX {feL2ModSW24PortStatusIndex}
	::= { feL2ModSW24PortStatusTable 1 }

feL2ModSW24PortStatusIndex	OBJECT-TYPE
	SYNTAX		INTEGER(1..2147483647)
	MAX-ACCESS	    read-only
	STATUS		current
	DESCRIPTION
		"This is the index of the port status entry."
	::= { feL2ModSW24PortStatusEntry 1 }

feL2ModSW24PortStatusMedia	OBJECT-TYPE
	SYNTAX		DisplayString
	MAX-ACCESS	    read-only
	STATUS		current
	DESCRIPTION
		"The port media type of the port status entry."
	::= { feL2ModSW24PortStatusEntry 2 }

feL2ModSW24PortStatusLink	OBJECT-TYPE
	SYNTAX		DisplayString
	MAX-ACCESS	    read-only
	STATUS		current
	DESCRIPTION
		"This is the port link of the port status entry."
	::= { feL2ModSW24PortStatusEntry 3 }

feL2ModSW24PortStatusPortState	OBJECT-TYPE
	SYNTAX		DisplayString
	MAX-ACCESS	    read-only
	STATUS		current
	DESCRIPTION
		"This is the port state of the port status entry."
	::= { feL2ModSW24PortStatusEntry 4 }

feL2ModSW24PortStatusAutoNego	OBJECT-TYPE
	SYNTAX		DisplayString
	MAX-ACCESS	    read-only
	STATUS		current
	DESCRIPTION
		"This is the auto negotiation of the port status entry."
	::= { feL2ModSW24PortStatusEntry 5 }

feL2ModSW24PortStatusSpdDpx 	OBJECT-TYPE
	SYNTAX		DisplayString
	MAX-ACCESS	    read-only
	STATUS		current
	DESCRIPTION
		"This is the speed/duplex of the port status entry."
	::= { feL2ModSW24PortStatusEntry 6 }

feL2ModSW24PortStatusFlwCtrl 	OBJECT-TYPE
	SYNTAX		DisplayString
	MAX-ACCESS	    read-only
	STATUS		current
	DESCRIPTION
		"This is the flow control of the port status entry."
	::= { feL2ModSW24PortStatusEntry 7 }

feL2ModSW24PortStatuDescription	OBJECT-TYPE
	SYNTAX		DisplayString
	MAX-ACCESS	    read-only
	STATUS		current
	DESCRIPTION
		"The description of port."
	::= { feL2ModSW24PortStatusEntry 8 }

feL2ModSW24PortConf           	OBJECT IDENTIFIER ::= { feL2ModSW24Port 2 }

feL2ModSW24PortConfNumber OBJECT-TYPE
	SYNTAX      INTEGER(1..2147483647)
	MAX-ACCESS	    read-only
	STATUS		current
	DESCRIPTION
		"Get the number of port configuration."
	::= { feL2ModSW24PortConf 1 }

feL2ModSW24PortConfTable	OBJECT-TYPE
	SYNTAX		SEQUENCE OF FEL2ModSW24PortConfEntry
	MAX-ACCESS	not-accessible
	STATUS		current
    DESCRIPTION
        "This is a list of port configuration entry. The numbers of entries are given by the value of feL2ModSW24PortConfNumber."
	::= { feL2ModSW24PortConf 2 }

FEL2ModSW24PortConfEntry ::=
SEQUENCE {
    feL2ModSW24PortConfIndex		    INTEGER,
    feL2ModSW24PortConfPortState        INTEGER,
    feL2ModSW24PortConfSpdDpx           INTEGER,
    feL2ModSW24PortConfFlwCtrl          INTEGER,
    feL2ModSW24PortConfDescription      DisplayString
}

feL2ModSW24PortConfEntry	OBJECT-TYPE
	SYNTAX		FEL2ModSW24PortConfEntry
	MAX-ACCESS	    not-accessible
	STATUS		current
	DESCRIPTION
		"This is the Entry(s) for port configuration information."
	INDEX {feL2ModSW24PortConfIndex}
	::= { feL2ModSW24PortConfTable 1 }

feL2ModSW24PortConfIndex	OBJECT-TYPE
	SYNTAX		INTEGER(1..2147483647)
	MAX-ACCESS	    read-only
	STATUS		current
	DESCRIPTION
		"This is the index of the port configuration entry."
	::= { feL2ModSW24PortConfEntry 1 }

feL2ModSW24PortConfPortState	OBJECT-TYPE
	SYNTAX		INTEGER(0|1)
	MAX-ACCESS	    read-write
	STATUS		current
	DESCRIPTION
		"This is the port state of the port configuration entry.
		 0 - disabled.
		 1 - enabled. "
	::= { feL2ModSW24PortConfEntry 2 }

feL2ModSW24PortConfSpdDpx	OBJECT-TYPE
	SYNTAX		INTEGER(0..5)
	MAX-ACCESS	    read-write
	STATUS		current
	DESCRIPTION
		"This is the speed/duplex of the port configuration entry.
		 0 - auto.
		 1 - 10M/Half.
		 2 - 10M/Full.
		 3 - 100M/Half.
		 4 - 100M/Full.
		 5 - 1G/Full.  "
	::= { feL2ModSW24PortConfEntry 3 }

feL2ModSW24PortConfFlwCtrl	OBJECT-TYPE
	SYNTAX		INTEGER(0|1)
	MAX-ACCESS	    read-write
	STATUS		current
	DESCRIPTION
		"This is the flow control of the port configuration entry.
		 0 - disabled.
		 1 - enabled.  "
	::= { feL2ModSW24PortConfEntry 4 }

feL2ModSW24PortConfDescription	OBJECT-TYPE
	SYNTAX		DisplayString
	MAX-ACCESS	    read-write
	STATUS		current
	DESCRIPTION
		"The description of port."
	::= { feL2ModSW24PortConfEntry 5 }

feL2ModSW24Mirror           	OBJECT IDENTIFIER ::= { feL2ModSW24Produces 10 }

feL2ModSW24MirrorMode OBJECT-TYPE
	SYNTAX      INTEGER(0|1)
	MAX-ACCESS	    read-write
	STATUS		current
	DESCRIPTION
		"Get/Set the Mirror mode.
		 0 - disabled.
		 1 - rx enable.  "
	::= { feL2ModSW24Mirror 1 }

feL2ModSW24MirroringPort OBJECT-TYPE
	SYNTAX      INTEGER(1..2147483647)
	MAX-ACCESS	    read-write
	STATUS		current
	DESCRIPTION
		"Get/Set the mirroring port.
		 The port range is from 1 to 24."
	::= { feL2ModSW24Mirror 2 }

feL2ModSW24MirroredPorts OBJECT-TYPE
	SYNTAX      DisplayString
	MAX-ACCESS	    read-write
	STATUS		current
	DESCRIPTION
		"Get/Set the monitored ports.
		 The port range is from 1 to 24, and the syntax is 1,5-7."
	::= { feL2ModSW24Mirror 3 }



feL2ModSW24MaxPktLen           	OBJECT IDENTIFIER ::= { feL2ModSW24Produces 11 }

feL2ModSW24MaxPktLen1           	OBJECT IDENTIFIER ::= { feL2ModSW24MaxPktLen 1 }

feL2ModSW24MaxPktLenPortNumber OBJECT-TYPE
	SYNTAX      INTEGER(1..2147483647)
	MAX-ACCESS	    read-only
	STATUS		current
	DESCRIPTION
		"Get the number of Max. packet length."
	::= { feL2ModSW24MaxPktLen1 1 }

feL2ModSW24MaxPktLenConfTable	OBJECT-TYPE
	SYNTAX		SEQUENCE OF FEL2ModSW24MaxPktLenConfEntry
	MAX-ACCESS	not-accessible
	STATUS		current
    DESCRIPTION
        "This is a list of Max. packet length entry. The numbers of entries are given by the value of feL2ModSW24MaxPktLenPortNumber."
	::= { feL2ModSW24MaxPktLen1 2 }

FEL2ModSW24MaxPktLenConfEntry ::=
SEQUENCE {
    feL2ModSW24MaxPktLenConfIndex		    INTEGER,
    feL2ModSW24MaxPktLenConfSetting         INTEGER
}

feL2ModSW24MaxPktLenConfEntry	OBJECT-TYPE
	SYNTAX		FEL2ModSW24MaxPktLenConfEntry
	MAX-ACCESS	    not-accessible
	STATUS		current
	DESCRIPTION
		"Entry(s) for Max. packet length information."
	INDEX {feL2ModSW24MaxPktLenConfIndex}
	::= { feL2ModSW24MaxPktLenConfTable 1 }

feL2ModSW24MaxPktLenConfIndex	OBJECT-TYPE
	SYNTAX		INTEGER(1..2147483647)
	MAX-ACCESS	    read-only
	STATUS		current
	DESCRIPTION
		"This is the index of the Max. packet length entry."
	::= { feL2ModSW24MaxPktLenConfEntry 1 }

feL2ModSW24MaxPktLenConfSetting	OBJECT-TYPE
	SYNTAX		INTEGER(1518|1532|9216)
	MAX-ACCESS	    read-write
	STATUS		current
	DESCRIPTION
		"Get/Set the Max. packet length.
		 The Max. packet length is 1518,1532,or 9216.  "
	::= { feL2ModSW24MaxPktLenConfEntry 2 }



feL2ModSW24Bandwidth           	OBJECT IDENTIFIER ::= { feL2ModSW24Produces 12 }

feL2ModSW24Bandwidth1           	OBJECT IDENTIFIER ::= { feL2ModSW24Bandwidth 1 }

feL2ModSW24BandwidthPortNumber OBJECT-TYPE
	SYNTAX      INTEGER(1..2147483647)
	MAX-ACCESS	    read-only
	STATUS		current
	DESCRIPTION
		"Get the number of bandwidth management configuration."
	::= { feL2ModSW24Bandwidth1 1 }

feL2ModSW24BandwidthConfTable	OBJECT-TYPE
	SYNTAX		SEQUENCE OF FEL2ModSW24BandwidthConfEntry
	MAX-ACCESS	not-accessible
	STATUS		current
    DESCRIPTION
        "A list of bandwidth management configuration entry. The numbers of entries are given by the value of feL2ModSW24BandwidthPortNumber."
	::= { feL2ModSW24Bandwidth1 2 }

FEL2ModSW24BandwidthConfEntry ::=
SEQUENCE {
    feL2ModSW24BandwidthConfIndex		     INTEGER,
    feL2ModSW24BandwidthConfIngressState      INTEGER,
    feL2ModSW24BandwidthConfIngressBW         INTEGER,
    feL2ModSW24BandwidthConfStormState       INTEGER,
    feL2ModSW24BandwidthConfStormBW          INTEGER,
    feL2ModSW24BandwidthConfEgressState      INTEGER,
    feL2ModSW24BandwidthConfEgressBW         INTEGER
}

feL2ModSW24BandwidthConfEntry	OBJECT-TYPE
	SYNTAX		FEL2ModSW24BandwidthConfEntry
	MAX-ACCESS	    not-accessible
	STATUS		current
	DESCRIPTION
		"This is the Entry(s) for bandwidth management configuration information."
	INDEX {feL2ModSW24BandwidthConfIndex}
	::= { feL2ModSW24BandwidthConfTable 1 }

feL2ModSW24BandwidthConfIndex	OBJECT-TYPE
	SYNTAX		INTEGER(1..2147483647)
	MAX-ACCESS	    read-only
	STATUS		current
	DESCRIPTION
		"This is the index of the bandwidth management configuration entry."
	::= { feL2ModSW24BandwidthConfEntry 1 }

feL2ModSW24BandwidthConfIngressState	OBJECT-TYPE
	SYNTAX		INTEGER(0|1)
	MAX-ACCESS	    read-write
	STATUS		current
	DESCRIPTION
		"The ingress state of the bandwidth management configures entry.
		 0 - disabled.
		 1 - enabled. "
	::= { feL2ModSW24BandwidthConfEntry 2 }

feL2ModSW24BandwidthConfIngressBW	OBJECT-TYPE
	SYNTAX		INTEGER(0..1000)
	MAX-ACCESS	    read-write
	STATUS		current
	DESCRIPTION
		"Get/Set the ingress rate of the bandwidth management configuration.
		 The ingress rate is from 0 to 1000.  "
	::= { feL2ModSW24BandwidthConfEntry 3 }

feL2ModSW24BandwidthConfStormState	OBJECT-TYPE
	SYNTAX		INTEGER(0|1)
	MAX-ACCESS	    read-write
	STATUS		current
	DESCRIPTION
		"The storm state of the bandwidth management configuration entry.
		 0 - disabled.
		 1 - enabled. "
	::= { feL2ModSW24BandwidthConfEntry 4 }

feL2ModSW24BandwidthConfStormBW	OBJECT-TYPE
	SYNTAX		INTEGER(0..1000)
	MAX-ACCESS	    read-write
	STATUS		current
	DESCRIPTION
		"Get/Set the storm rate of the bandwidth management configuration.
		 The storm rate is from 0 to 1000.  "
	::= { feL2ModSW24BandwidthConfEntry 5 }

feL2ModSW24BandwidthConfEgressState	OBJECT-TYPE
	SYNTAX		INTEGER(0|1)
	MAX-ACCESS	    read-write
	STATUS		current
	DESCRIPTION
		"The egress state of the bandwidth management configuration entry.
		 0 - disabled.
		 1 - enabled. "
	::= { feL2ModSW24BandwidthConfEntry 6 }

feL2ModSW24BandwidthConfEgressBW	OBJECT-TYPE
	SYNTAX		INTEGER(0..1000)
	MAX-ACCESS	    read-write
	STATUS		current
	DESCRIPTION
		"Get/Set the egress rate of the bandwidth management configuration.
		 The egress rate is from 0 to 1000.  "
	::= { feL2ModSW24BandwidthConfEntry 7 }

feL2ModSW24LoopDetectedConf           	OBJECT IDENTIFIER ::= { feL2ModSW24Produces 13 }

feL2ModSW24LoopDetectedNumber OBJECT-TYPE
	SYNTAX      INTEGER(1..2147483647)
	MAX-ACCESS	    read-only
	STATUS		current
	DESCRIPTION
		"Get the number of loop detected entry."
	::= { feL2ModSW24LoopDetectedConf 1 }

feL2ModSW24LoopDetectedTable	OBJECT-TYPE
	SYNTAX		SEQUENCE OF FEL2ModSW24LoopDetectedEntry
	MAX-ACCESS	not-accessible
	STATUS		current
    DESCRIPTION
        "A list of loop detected entry. The numbers of entries are given by the value of feL2ModSW24LoopDetectedNumber."
	::= { feL2ModSW24LoopDetectedConf 2 }

FEL2ModSW24LoopDetectedEntry ::=
SEQUENCE {
    feL2ModSW24LoopDetectedfIndex           INTEGER,
    feL2ModSW24LoopDetectedStateEbl         INTEGER,
    feL2ModSW24LoopDetectedCurrentStatus    INTEGER,
    feL2ModSW24LoopDetectedResumed          INTEGER
}

feL2ModSW24LoopDetectedEntry	OBJECT-TYPE
	SYNTAX		FEL2ModSW24LoopDetectedEntry
	MAX-ACCESS	    not-accessible
	STATUS		current
	DESCRIPTION
		"Entry(s) for loop detected information."
	INDEX {feL2ModSW24LoopDetectedfIndex}
	::= { feL2ModSW24LoopDetectedTable 1 }

feL2ModSW24LoopDetectedfIndex	OBJECT-TYPE
	SYNTAX		INTEGER(1..2147483647)
	MAX-ACCESS	    read-only
	STATUS		current
	DESCRIPTION
		"The index of the loop detected entry."
	::= { feL2ModSW24LoopDetectedEntry 1 }

feL2ModSW24LoopDetectedStateEbl	OBJECT-TYPE
	SYNTAX		INTEGER(0|1)
	MAX-ACCESS	    read-write
	STATUS		current
	DESCRIPTION
		"The state of the loop detected entry.
		 0 - disabled.
		 1 - enabled. "
	::= { feL2ModSW24LoopDetectedEntry 2 }

feL2ModSW24LoopDetectedCurrentStatus	OBJECT-TYPE
	SYNTAX		INTEGER(0|1)
	MAX-ACCESS	    read-only
	STATUS		current
	DESCRIPTION
		"The current status of the loop detected port.
         0 - unlocked
         1 - locked due to the loop condition "
	::= { feL2ModSW24LoopDetectedEntry 3 }

feL2ModSW24LoopDetectedResumed	OBJECT-TYPE
	SYNTAX		INTEGER(0|1)
	MAX-ACCESS	    read-write
	STATUS		current
	DESCRIPTION
		"Unlock the port which is locked due to loop condition. Get this OID always return zero.
         1 - unlock the port,
         0 - do nothing."
	::= { feL2ModSW24LoopDetectedEntry 4 }

feL2ModSW24LoopDetectedAction OBJECT-TYPE
	SYNTAX      INTEGER(0|1)
	MAX-ACCESS	    read-write
	STATUS		current
	DESCRIPTION
		"Set the corresponding action while loop is detected.
         1 - lock the loop port,
         0 - do nothing."
	::= { feL2ModSW24LoopDetectedConf 3 }

feL2ModSW24SFPInfo           	OBJECT IDENTIFIER ::= { feL2ModSW24Produces 14 }

feL2ModSW24SFPInfoNumber OBJECT-TYPE
	SYNTAX      INTEGER(1..2147483647)
	MAX-ACCESS	    read-only
	STATUS		current
	DESCRIPTION
		"Get the number of sfp info entry."
	::= { feL2ModSW24SFPInfo 1 }

feL2ModSW24SFPInfoTable	OBJECT-TYPE
	SYNTAX		SEQUENCE OF FEL2ModSW24SFPInfoEntry
	MAX-ACCESS	not-accessible
	STATUS		current
    DESCRIPTION
        "A list of sfp info entry. The numbers of entries are given by the value of feL2ModSW24SFPInfoNumber."
	::= { feL2ModSW24SFPInfo 2 }

FEL2ModSW24SFPInfoEntry ::=
SEQUENCE {
    feL2ModSW24SFPInfoIndex INTEGER,
    feL2ModSW24SFPConnectorType DisplayString,
    feL2ModSW24SFPFiberType DisplayString,
    feL2ModSW24SFPWavelength DisplayString,
    feL2ModSW24SFPBaudRate DisplayString,
    feL2ModSW24SFPVendorOUI DisplayString,
    feL2ModSW24SFPVendorName DisplayString,
    feL2ModSW24SFPVendorPN DisplayString,
    feL2ModSW24SFPVendorRev DisplayString,
    feL2ModSW24SFPVendorSN DisplayString,
    feL2ModSW24SFPDateCode DisplayString,
    feL2ModSW24SFPTemperature DisplayString,
    feL2ModSW24SFPVcc DisplayString,
    feL2ModSW24SFPTxBias DisplayString,
    feL2ModSW24SFPTxPWR DisplayString,
    feL2ModSW24SFPRxPWR DisplayString
}

feL2ModSW24SFPInfoEntry	OBJECT-TYPE
	SYNTAX		FEL2ModSW24SFPInfoEntry
	MAX-ACCESS	    not-accessible
	STATUS		current
	DESCRIPTION
		"Entry(s) for SFP information."
	INDEX {feL2ModSW24SFPInfoIndex}
	::= { feL2ModSW24SFPInfoTable 1 }

feL2ModSW24SFPInfoIndex	OBJECT-TYPE
	SYNTAX		INTEGER(1..2147483647)
	MAX-ACCESS	    read-only
	STATUS		current
	DESCRIPTION
		"The index of the sfp info entry."
	::= { feL2ModSW24SFPInfoEntry 1 }

feL2ModSW24SFPConnectorType	OBJECT-TYPE
	SYNTAX		DisplayString
	MAX-ACCESS	    read-only
	STATUS		current
	DESCRIPTION
		"Get connector type of the sfp."
	::= { feL2ModSW24SFPInfoEntry 2 }

feL2ModSW24SFPFiberType	OBJECT-TYPE
	SYNTAX		DisplayString
	MAX-ACCESS	    read-only
	STATUS		current
	DESCRIPTION
		"Get fiber type of the sfp."
	::= { feL2ModSW24SFPInfoEntry 3 }

feL2ModSW24SFPWavelength	OBJECT-TYPE
	SYNTAX		DisplayString
	MAX-ACCESS	    read-only
	STATUS		current
	DESCRIPTION
		"Get tx central wavelength of the sfp."
	::= { feL2ModSW24SFPInfoEntry 4 }

feL2ModSW24SFPBaudRate	OBJECT-TYPE
	SYNTAX		DisplayString
	MAX-ACCESS	    read-only
	STATUS		current
	DESCRIPTION
		"Get baud rate of the sfp."
	::= { feL2ModSW24SFPInfoEntry 5 }

feL2ModSW24SFPVendorOUI	OBJECT-TYPE
	SYNTAX		DisplayString
	MAX-ACCESS	    read-only
	STATUS		current
	DESCRIPTION
		"Get vendor OUI of the sfp."
	::= { feL2ModSW24SFPInfoEntry 6 }

feL2ModSW24SFPVendorName	OBJECT-TYPE
	SYNTAX		DisplayString
	MAX-ACCESS	    read-only
	STATUS		current
	DESCRIPTION
		"Get vendor name of the sfp."
	::= { feL2ModSW24SFPInfoEntry 7 }

feL2ModSW24SFPVendorPN	OBJECT-TYPE
	SYNTAX		DisplayString
	MAX-ACCESS	    read-only
	STATUS		current
	DESCRIPTION
		"Get vendor part number of the sfp."
	::= { feL2ModSW24SFPInfoEntry 8 }

feL2ModSW24SFPVendorRev	OBJECT-TYPE
	SYNTAX		DisplayString
	MAX-ACCESS	    read-only
	STATUS		current
	DESCRIPTION
		"Get vendor revision number of the sfp."
	::= { feL2ModSW24SFPInfoEntry 9 }

feL2ModSW24SFPVendorSN	OBJECT-TYPE
	SYNTAX		DisplayString
	MAX-ACCESS	    read-only
	STATUS		current
	DESCRIPTION
		"Get vendor serial number of the sfp."
	::= { feL2ModSW24SFPInfoEntry 10 }

feL2ModSW24SFPDateCode	OBJECT-TYPE
	SYNTAX		DisplayString
	MAX-ACCESS	    read-only
	STATUS		current
	DESCRIPTION
		"Get data code of the sfp."
	::= { feL2ModSW24SFPInfoEntry 11 }

feL2ModSW24SFPTemperature	OBJECT-TYPE
	SYNTAX		DisplayString
	MAX-ACCESS	    read-only
	STATUS		current
	DESCRIPTION
		"Get current temperature of the sfp."
	::= { feL2ModSW24SFPInfoEntry 12 }

feL2ModSW24SFPVcc	OBJECT-TYPE
	SYNTAX		DisplayString
	MAX-ACCESS	    read-only
	STATUS		current
	DESCRIPTION
		"Get current internal supply voltage of the sfp."
	::= { feL2ModSW24SFPInfoEntry 13 }

feL2ModSW24SFPTxBias	OBJECT-TYPE
	SYNTAX		DisplayString
	MAX-ACCESS	    read-only
	STATUS		current
	DESCRIPTION
		"Get current TX Bias of the sfp."
	::= { feL2ModSW24SFPInfoEntry 14 }

feL2ModSW24SFPTxPWR	OBJECT-TYPE
	SYNTAX		DisplayString
	MAX-ACCESS	    read-only
	STATUS		current
	DESCRIPTION
		"Get current TX output power of the sfp."
	::= { feL2ModSW24SFPInfoEntry 15 }

feL2ModSW24SFPRxPWR	OBJECT-TYPE
	SYNTAX		DisplayString
	MAX-ACCESS	    read-only
	STATUS		current
	DESCRIPTION
		"Get current Received Power of the sfp."
	::= { feL2ModSW24SFPInfoEntry 16 }

feL2ModSW24TrapEntry	       OBJECT IDENTIFIER ::= { feL2ModSW24Produces 20 }

feL2ModSW24ModuleInserted NOTIFICATION-TYPE
    OBJECTS { ifIndex }
	STATUS    current
	DESCRIPTION
	    "Send the trap when a module is inserted to the system. The OID value means
	     the port number."
	::= { feL2ModSW24TrapEntry 1 }

feL2ModSW24ModuleRemoved NOTIFICATION-TYPE
    OBJECTS { ifIndex }
	STATUS    current
	DESCRIPTION
	    "Send the trap when a module is removed from the system. The OID value means
	     the port number."
	::= { feL2ModSW24TrapEntry 2 }

feL2ModSW24LoopDetected NOTIFICATION-TYPE
    OBJECTS { ifIndex }
	STATUS    current
	DESCRIPTION
	    "Send the trap when loop condition has been detected. The OID value means the port number."
	::= { feL2ModSW24TrapEntry 5 }

feL2ModSW24StpStateDisabled NOTIFICATION-TYPE
	STATUS		current
	DESCRIPTION
	   "Send the trap when the operational state of STP is from enabled to disabled. "
	::= { feL2ModSW24TrapEntry 100 }

feL2ModSW24StpStateEnabled NOTIFICATION-TYPE
	STATUS		current
	DESCRIPTION
	   "Send the trap when the operational state of STP is from disabled to enabled. "
	::= { feL2ModSW24TrapEntry 101 }

feL2ModSW24StpTopologyChanged NOTIFICATION-TYPE
    OBJECTS { ifIndex }
	STATUS		current
	DESCRIPTION
	   "Send the trap when RSTP determines a port should enter the FORWARDING state
	    (a topology change occurs). The OID value is the ifIndex of the port that
	    produces the topology change"
	::= { feL2ModSW24TrapEntry 102 }

feL2ModSW24LacpStateDisabled NOTIFICATION-TYPE
    OBJECTS {ifIndex, groupId}
	STATUS		current
	DESCRIPTION
	   "Send the trap when the operational state of LACP is from enabled to disabled.
	    The OID value means the disabled Group ID."
	::= { feL2ModSW24TrapEntry 120 }

feL2ModSW24LacpStateEnabled NOTIFICATION-TYPE
    OBJECTS {ifIndex, groupId}
	STATUS		current
	DESCRIPTION
	   "Send the trap when the operational state of LACP is from disabled to enabled.
	    The OID value means the disabled Group ID."
	::= { feL2ModSW24TrapEntry 121 }

feL2ModSW24LacpPortAdded NOTIFICATION-TYPE
    OBJECTS   { ifIndex, actorkey, partnerkey }
	STATUS		current
	DESCRIPTION
	   "Send the trap when the state of port is in 'trunk ready'."
	::= { feL2ModSW24TrapEntry 123 }

feL2ModSW24LacpPortTrunkFailure NOTIFICATION-TYPE
    OBJECTS   { ifIndex, actorkey, partnerkey}
	STATUS		current
	DESCRIPTION
	   "Send the trap when one port is not able to be aggregated
	    due to duplex-mode of the port. "
	::= { feL2ModSW24TrapEntry 124 }

feL2ModSW24GvrpStateDisabled NOTIFICATION-TYPE
	STATUS		current
	DESCRIPTION
	   "Send the trap when the operational state of GVRP is from enabled to disabled. "
	::= { feL2ModSW24TrapEntry 140 }

feL2ModSW24GvrpStateEnabled NOTIFICATION-TYPE
	STATUS		current
	DESCRIPTION
	   "Send the trap when the operational state of LACP is from disabled to enabled. "
	::= { feL2ModSW24TrapEntry 141 }

feL2ModSW24VlanStateDisabled NOTIFICATION-TYPE
	STATUS		current
	DESCRIPTION
	   "Send the trap when the operational state of vlan is from enabled to disabled.
	    The OID value means the enabled Group ID. "
	::= { feL2ModSW24TrapEntry 150 }

feL2ModSW24VlanPortBaseEnabled NOTIFICATION-TYPE
	STATUS		current
	DESCRIPTION
	   "Send the trap when the operational state of vlan is changed to port-based vlan."
	::= { feL2ModSW24TrapEntry 151 }

feL2ModSW24VlanTagBaseEnabled NOTIFICATION-TYPE
	STATUS		current
	DESCRIPTION
	   "Send the trap when the operational state of vlan is changed to tag-based vlan."
	::= { feL2ModSW24TrapEntry 152 }

feL2ModSW24VlanMetroModeEnabled NOTIFICATION-TYPE
    OBJECTS   {uplink}
	STATUS		current
	DESCRIPTION
	   "Send the trap when the operational state of vlan is changed to Metro-mode vlan.
        The OID value means the uplink port with this metro-mode vlan."
	::= { feL2ModSW24TrapEntry 153 }

feL2ModSW24VlanDoubleTagEnabled NOTIFICATION-TYPE
	STATUS		current
	DESCRIPTION
	   "Send the trap when the operational state of vlan is changed to Double-tag vlan."
	::= { feL2ModSW24TrapEntry 154 }

feL2ModSW24UserLogin NOTIFICATION-TYPE
    OBJECTS   {username}
	STATUS		current
	DESCRIPTION
	   "Send the trap when one user logins the system."
	::= { feL2ModSW24TrapEntry 200 }

feL2ModSW24UserLogout NOTIFICATION-TYPE
    OBJECTS   {username}
	STATUS		current
	DESCRIPTION
	   "Send the trap when one user logouts the system."
	::= { feL2ModSW24TrapEntry 201 }

feL2ModSW24TrapVariable	OBJECT IDENTIFIER ::= { feL2ModSW24Produces 21 }

username OBJECT-TYPE
    SYNTAX      DisplayString
	MAX-ACCESS  read-only
	STATUS      current
	DESCRIPTION
	    "System account name."
	::= { feL2ModSW24TrapVariable 1 }

groupId OBJECT-TYPE
    SYNTAX      INTEGER(1..8)
	MAX-ACCESS  read-only
	STATUS      current
	DESCRIPTION
	    "The Trunk group ID of LACP."
	::= { feL2ModSW24TrapVariable 2 }

actorkey OBJECT-TYPE
    SYNTAX	INTEGER(1..2147483647)
	MAX-ACCESS  read-only
	STATUS      current
	DESCRIPTION
	    "This is the actor key information for LACP."
	::= { feL2ModSW24TrapVariable 3 }

partnerkey OBJECT-TYPE
    SYNTAX	INTEGER(1..2147483647)
	MAX-ACCESS  read-only
	STATUS      current
	DESCRIPTION
	    "This is the partner key information for LACP."
	::= { feL2ModSW24TrapVariable 4 }

uplink OBJECT-TYPE
    SYNTAX	DisplayString
	MAX-ACCESS  read-only
	STATUS      current
	DESCRIPTION
	    "Uplink port(s) in the metro-mode vlan."
	::= { feL2ModSW24TrapVariable 5 }

END
