GUDEADS-EPC2X6-MIB DEFINITIONS ::= BEGIN

IMPORTS
	enterprises,
	MODULE-IDENTITY,
	OBJECT-TYPE,
	NOTIFICATION-TYPE,
	Counter32,
	Integer32,
	IpAddress
		FROM SNMPv2-SMI
	OBJECT-GROUP,
	NOTIFICATION-GROUP
		FROM SNMPv2-CONF;

gudeads MODULE-IDENTITY
	LAST-UPDATED "200703051356Z"	-- Mar 5, 2007 1:56:00 PM
	ORGANIZATION "Gude Analog- und Digitalsysteme GmbH"
	CONTACT-INFO
		"http://www.gudeads.com/"
	DESCRIPTION
		""
	REVISION "200703051356Z"	-- Mar 5, 2007 1:56:00 PM
	DESCRIPTION
		"$Id: GUDEADS-EPC2X6-MIB.txt,v 1.5 2009-04-03 14:03:39 petes1 Exp $"
	-- 1.3.6.1.4.1.28507
	::= { enterprises 28507 }


epc2x6portFuses OBJECT-TYPE
	SYNTAX  Integer32 (0..3)
	MAX-ACCESS read-only
	STATUS  current
	DESCRIPTION
		"Bit State of Fuses (Bit 0 = Fuse1, Bit 1 = Fuse2)"
	-- 1.3.6.1.4.1.28507.6.1.2.3
	::= { epc2x6powerports 3 }


epc2x6Temperature OBJECT-TYPE
	SYNTAX  Integer32
	UNITS
		"10th of degree Celsius"
	MAX-ACCESS read-only
	STATUS  current
	DESCRIPTION
		"actual Temperature, if sensor is not supported
		'9998', not  connected '9999' is given back as
		result"
	-- 1.3.6.1.4.1.28507.6.1.3
	::= { epc2x6Objects 3 }



epc2x6witchEvt1 NOTIFICATION-TYPE
	OBJECTS {
		epc2x6PortName,
		epc2x6PortState,
		epc2x6PortSwitchCount}
	STATUS  current
	DESCRIPTION
		"Event is triggered when"
	-- 1.3.6.1.4.1.28507.0.1
	::= { events 1 }


epc2x6witchEvt2 NOTIFICATION-TYPE
	OBJECTS {
		epc2x6PortName,
		epc2x6PortState,
		epc2x6PortSwitchCount}
	STATUS  current
	DESCRIPTION
		"Event is triggered when"
	-- 1.3.6.1.4.1.28507.0.2
	::= { events 2 }


epc2x6witchEvt3 NOTIFICATION-TYPE
	OBJECTS {
		epc2x6PortName,
		epc2x6PortState,
		epc2x6PortSwitchCount}
	STATUS  current
	DESCRIPTION
		"Event is triggered when"
	-- 1.3.6.1.4.1.28507.0.3
	::= { events 3 }


epc2x6witchEvt4 NOTIFICATION-TYPE
	OBJECTS {
		epc2x6PortName,
		epc2x6PortState,
		epc2x6PortSwitchCount}
	STATUS  current
	DESCRIPTION
		"Event is triggered when"
	-- 1.3.6.1.4.1.28507.0.4
	::= { events 4 }


epc2x6witchEvt5 NOTIFICATION-TYPE
	OBJECTS {
		epc2x6PortName,
		epc2x6PortState,
		epc2x6PortSwitchCount}
	STATUS  current
	DESCRIPTION
		"Event is triggered when"
	-- 1.3.6.1.4.1.28507.0.5
	::= { events 5 }


epc2x6witchEvt6 NOTIFICATION-TYPE
	OBJECTS {
		epc2x6PortName,
		epc2x6PortState,
		epc2x6PortSwitchCount}
	STATUS  current
	DESCRIPTION
		"Event is triggered when"
	-- 1.3.6.1.4.1.28507.0.6
	::= { events 6 }


epc2x6witchEvt7 NOTIFICATION-TYPE
	OBJECTS {
		epc2x6PortName,
		epc2x6PortState,
		epc2x6PortSwitchCount}
	STATUS  current
	DESCRIPTION
		"Event is triggered when"
	-- 1.3.6.1.4.1.28507.0.7
	::= { events 7 }


epc2x6witchEvt8 NOTIFICATION-TYPE
	OBJECTS {
		epc2x6PortName,
		epc2x6PortState,
		epc2x6PortSwitchCount}
	STATUS  current
	DESCRIPTION
		"Event is triggered when"
	-- 1.3.6.1.4.1.28507.0.8
	::= { events 8 }


epc2x6witchEvt9 NOTIFICATION-TYPE
	OBJECTS {
		epc2x6PortName,
		epc2x6PortState,
		epc2x6PortSwitchCount}
	STATUS  current
	DESCRIPTION
		"Event is triggered when"
	-- 1.3.6.1.4.1.28507.0.9
	::= { events 9 }


epc2x6witchEvt10 NOTIFICATION-TYPE
	OBJECTS {
		epc2x6PortName,
		epc2x6PortState,
		epc2x6PortSwitchCount}
	STATUS  current
	DESCRIPTION
		"Event is triggered when"
	-- 1.3.6.1.4.1.28507.0.10
	::= { events 10 }


epc2x6witchEvt11 NOTIFICATION-TYPE
	OBJECTS {
		epc2x6PortName,
		epc2x6PortState,
		epc2x6PortSwitchCount}
	STATUS  current
	DESCRIPTION
		"Event is triggered when"
	-- 1.3.6.1.4.1.28507.0.11
	::= { events 11 }


epc2x6witchEvt12 NOTIFICATION-TYPE
	OBJECTS {
		epc2x6PortName,
		epc2x6PortState,
		epc2x6PortSwitchCount}
	STATUS  current
	DESCRIPTION
		"Event is triggered when"
	-- 1.3.6.1.4.1.28507.0.12
	::= { events 12 }

-- Notification Types
--

events OBJECT IDENTIFIER 
	-- 1.3.6.1.4.1.28507.0
	::= { gudeads 0 }

epc2x6SNMPaccess OBJECT IDENTIFIER 
	-- 1.3.6.1.4.1.28507.6.1.1
	::= { epc2x6Objects 1 }

epc2x6TrapCtrl OBJECT-TYPE
	SYNTAX  Integer32 (0..2)
	MAX-ACCESS read-write
	STATUS  current
	DESCRIPTION
		"0 = off
		1 = Ver. 1
		2 = Ver. 2c"
	-- 1.3.6.1.4.1.28507.6.1.1.1
	::= { epc2x6SNMPaccess 1 }


epc2x6TrapIPTable OBJECT-TYPE
	SYNTAX  SEQUENCE OF Epc2x6TrapIPEntry
	MAX-ACCESS not-accessible
	STATUS  current
	DESCRIPTION
		"list of all Trap receiver"
	-- 1.3.6.1.4.1.28507.6.1.1.2
	::= { epc2x6SNMPaccess 2 }


gadsEPC2x6 OBJECT IDENTIFIER 
	-- 1.3.6.1.4.1.28507.6
	::= { gudeads 6 }

-- Scalars and Tables
--

epc2x6Objects OBJECT IDENTIFIER 
	-- 1.3.6.1.4.1.28507.6.1
	::= { gadsEPC2x6 1 }

epc2x6TrapIPEntry OBJECT-TYPE
	SYNTAX  Epc2x6TrapIPEntry
	MAX-ACCESS not-accessible
	STATUS  current
	DESCRIPTION
		"an entry containing management
		informations regarding the list of trap
		receivers"
	INDEX {
		epc2x6TrapIPIndex }
	-- 1.3.6.1.4.1.28507.6.1.1.2.1
	::= { epc2x6TrapIPTable 1 }


Epc2x6TrapIPEntry ::= SEQUENCE {

	epc2x6TrapIPIndex Integer32,
	epc2x6TrapIPAddr  IpAddress,
	epc2x6TrapIPPort  Integer32 }


epc2x6TrapIPIndex OBJECT-TYPE
	SYNTAX  Integer32 (1..8)
	MAX-ACCESS not-accessible
	STATUS  current
	DESCRIPTION
		"A unique value, greater than zero, for each receiver slot."
	-- 1.3.6.1.4.1.28507.6.1.1.2.1.1
	::= { epc2x6TrapIPEntry 1 }


epc2x6TrapIPPort OBJECT-TYPE
	SYNTAX  Integer32 (0..1024)
	MAX-ACCESS read-write
	STATUS  current
	DESCRIPTION
		"IP Port specifying one Trap receiver slot.
		A value of  0 disables this slot."
	DEFVAL { 162 }
	-- 1.3.6.1.4.1.28507.6.1.1.2.1.3
	::= { epc2x6TrapIPEntry 3 }


epc2x6powerports OBJECT IDENTIFIER 
	-- 1.3.6.1.4.1.28507.6.1.2
	::= { epc2x6Objects 2 }

epc2x6portNumber OBJECT-TYPE
	SYNTAX  Integer32 (1..12)
	MAX-ACCESS read-only
	STATUS  current
	DESCRIPTION
		"The number of PowerPorts"
	-- 1.3.6.1.4.1.28507.6.1.2.1
	::= { epc2x6powerports 1 }


-- the Interfaces table
-- The Interfaces table contains information on the entity's
-- interfaces.  Each sub-layer below the internetwork-layer
-- of a network interface is considered to be an interface.

epc2x6portTable OBJECT-TYPE
	SYNTAX  SEQUENCE OF Epc2x6portEntry
	MAX-ACCESS not-accessible
	STATUS  current
	DESCRIPTION
		"list of all EPC Powerports"
	-- 1.3.6.1.4.1.28507.6.1.2.2
	::= { epc2x6powerports 2 }


epc2x6portEntry OBJECT-TYPE
	SYNTAX  Epc2x6portEntry
	MAX-ACCESS not-accessible
	STATUS  current
	DESCRIPTION
		"An entry containing management information applicable to a
		particular powerport."
	INDEX {
		epc2x6PortIndex }
	-- 1.3.6.1.4.1.28507.6.1.2.2.1
	::= { epc2x6portTable 1 }


Epc2x6portEntry ::= SEQUENCE {

	epc2x6PortIndex        Integer32,
	epc2x6PortName         OCTET STRING,
	epc2x6PortState        INTEGER,
	epc2x6PortSwitchCount  Counter32,
	epc2x6PortStartupMode  INTEGER,
	epc2x6PortStartupDelay Integer32,
	epc2x6PortRepowerTime  Integer32 }


epc2x6PortIndex OBJECT-TYPE
	SYNTAX  Integer32 (1..12)
	MAX-ACCESS not-accessible
	STATUS  current
	DESCRIPTION
		"A unique value, greater than zero, for each PowerPort."
	-- 1.3.6.1.4.1.28507.6.1.2.2.1.1
	::= { epc2x6portEntry 1 }


epc2x6PortName OBJECT-TYPE
	SYNTAX  OCTET STRING (SIZE (0..15))
	MAX-ACCESS read-only
	STATUS  current
	DESCRIPTION
		"A textual string containing name of a PowerPort."
	-- 1.3.6.1.4.1.28507.6.1.2.2.1.2
	::= { epc2x6portEntry 2 }


epc2x6PortState OBJECT-TYPE
	SYNTAX  INTEGER {
			off(0),
			on(1) }
	MAX-ACCESS read-write
	STATUS  current
	DESCRIPTION
		"current state a PowerPort"
	-- 1.3.6.1.4.1.28507.6.1.2.2.1.3
	::= { epc2x6portEntry 3 }


epc2x6PortSwitchCount OBJECT-TYPE
	SYNTAX  Counter32
	MAX-ACCESS read-only
	STATUS  current
	DESCRIPTION
		"The total number of switch actions ocurred on a PowerPort.
		Does not count switch commands which will not switch
		the ralay state, so just real relay switches are displayed here."
	-- 1.3.6.1.4.1.28507.6.1.2.2.1.4
	::= { epc2x6portEntry 4 }


-- Conformance
--

epc2x6Conf OBJECT IDENTIFIER 
	-- 1.3.6.1.4.1.28507.6.3
	::= { gadsEPC2x6 3 }

-- Groups
--

epc2x6Groups OBJECT IDENTIFIER 
	-- 1.3.6.1.4.1.28507.6.3.1
	::= { epc2x6Conf 1 }

-- Compliance
--

epc2x6Compls OBJECT IDENTIFIER 
	-- 1.3.6.1.4.1.28507.6.3.2
	::= { epc2x6Conf 2 }

epc2x6BasicGroup OBJECT-GROUP
	OBJECTS {
		epc2x6portNumber,
		epc2x6PortName,
		epc2x6PortState,
		epc2x6PortSwitchCount,
		epc2x6TrapCtrl,
		epc2x6TrapIPAddr,
		epc2x6TrapIPPort,
		epc2x6Temperature,
		epc2x6portFuses,
		epc2x6PortStartupMode,
		epc2x6PortStartupDelay,
		epc2x6PortRepowerTime }
	STATUS  current
	DESCRIPTION
		"Basic objects."
	-- 1.3.6.1.4.1.28507.6.3.1.1
	::= { epc2x6Groups 1 }

epc2x6TrapIPAddr OBJECT-TYPE
	SYNTAX  IpAddress
	MAX-ACCESS read-write
	STATUS  current
	DESCRIPTION
		"IP Address specifying one Trap receiver slot.
		A value of '00000000'H disables this slot."
	DEFVAL { '00000000'H }
	-- 1.3.6.1.4.1.28507.6.1.1.2.1.2
	::= { epc2x6TrapIPEntry 2 }


epc2x6NotificationGroup NOTIFICATION-GROUP
	NOTIFICATIONS {
		epc2x6witchEvt1,
		epc2x6witchEvt2,
		epc2x6witchEvt3,
		epc2x6witchEvt4,
		epc2x6witchEvt5,
		epc2x6witchEvt6,
		epc2x6witchEvt7,
		epc2x6witchEvt8,
		epc2x6witchEvt9,
		epc2x6witchEvt10,
		epc2x6witchEvt11,
		epc2x6witchEvt12,
		epc2x6TempEvt,
		epc2x6FuseEvt }
	STATUS  current
	DESCRIPTION
		""
	-- 1.3.6.1.4.1.28507.6.3.1.2
	::= { epc2x6Groups 2 }

epc2x6PortStartupMode OBJECT-TYPE
	SYNTAX  INTEGER {
			off(0),
			on(1),
			laststate(2) }
	MAX-ACCESS read-write
	STATUS  current
	DESCRIPTION
		"set Mode of startup sequence (off, on , remember last state)"
	DEFVAL { off }
	-- 1.3.6.1.4.1.28507.6.1.2.2.1.5
	::= { epc2x6portEntry 5 }


epc2x6PortStartupDelay OBJECT-TYPE
	SYNTAX  Integer32
	UNITS
		"seconds"
	MAX-ACCESS read-write
	STATUS  current
	DESCRIPTION
		"Delay in sec for startup action"
	DEFVAL { 0 }
	-- 1.3.6.1.4.1.28507.6.1.2.2.1.6
	::= { epc2x6portEntry 6 }


epc2x6PortRepowerTime OBJECT-TYPE
	SYNTAX  Integer32 (0..65535)
	UNITS
		"seconds"
	MAX-ACCESS read-write
	STATUS  current
	DESCRIPTION
		"Delay in sec for repower port after switching off"
	DEFVAL { 0 }
	-- 1.3.6.1.4.1.28507.6.1.2.2.1.7
	::= { epc2x6portEntry 7 }



epc2x6FuseEvt NOTIFICATION-TYPE
	OBJECTS {
		epc2x6portFuses}
	STATUS  current
	DESCRIPTION
		""
	-- 1.3.6.1.4.1.28507.0.13
	::= { events 13 }


epc2x6TempEvt NOTIFICATION-TYPE
	OBJECTS {
		epc2x6Temperature}
	STATUS  current
	DESCRIPTION
		"change of temperature"
	-- 1.3.6.1.4.1.28507.0.14
	::= { events 14 }

END
