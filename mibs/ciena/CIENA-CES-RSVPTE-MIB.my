-- This file was included in WWP MIB release 04-10-01-0027
 --
 -- CIENA-CES-RSVPTE-MIB.my
 --

 CIENA-CES-RSVPTE-MIB DEFINITIONS ::= BEGIN

 IMPORTS 		
  	TimeTicks, Integer32, Unsigned32, IpAddress, OBJECT-TYPE, MODULE-IDENTITY			
	FROM SNMPv2-SMI			
   	DisplayString, MacAddress, RowStatus, TruthValue, TEXTUAL-CONVENTION			
	FROM SNMPv2-TC	
	CienaGlobalState
	FROM CIENA-TC							
	cienaCesConfig,cienaCesNotifications 
	FROM CIENA-SMI;
	

 cienaCesRsvpteMIB MODULE-IDENTITY
	    LAST-UPDATED "201102020000Z"
	    ORGANIZATION "Ciena, Inc"
	    CONTACT-INFO
		    "   Mib Meister
		  	115 North Sullivan Road
			Spokane Valley, WA 99037
		        USA		 		
		        Phone:  +1 509 242 9000
			Email:  support@ciena.com"
	    DESCRIPTION
		    "This MIB module is for the RSVP-TE configuration for MPLS tunnels"

	    REVISION
	    	"201102020000Z"
	    DESCRIPTION
		"Initial version."

	    ::= { cienaCesConfig 16 }


--
-- Textual convention
--
 AdvertisedLabel ::= TEXTUAL-CONVENTION
     STATUS       current
     DESCRIPTION  "Advertised Label"
     SYNTAX       INTEGER {
                    implicitnull(1),
                    nonreserved(99)
                   } 

 RsvpOperStatus ::= TEXTUAL-CONVENTION
    STATUS      current
    DESCRIPTION
       "The current operational state of RSVP-TE."
    SYNTAX      INTEGER {
                  operStatusUp(1),       -- active
                  operStatusDown(2),     -- inactive
                  operStatusGoingUp(3),  -- activating
                  operStatusGoingDown(4),-- deactivating
                  operStatusActFailed(5) -- activation failed
                }


 --
 -- Node definitions
 --
	
 cienaCesRsvpteMIBObjects OBJECT IDENTIFIER ::= { cienaCesRsvpteMIB 1 }
 cienaCesRsvpteObjects    OBJECT IDENTIFIER ::= { cienaCesRsvpteMIBObjects 1 }
 cienaCesRsvpte           OBJECT IDENTIFIER ::= { cienaCesRsvpteMIBObjects 2 }

 cienaCesRsvpteAdminStatus OBJECT-TYPE
      SYNTAX      CienaGlobalState
      MAX-ACCESS  read-only
      STATUS      current
      DESCRIPTION
          "The desired administrative state of RSVP-TE."
      ::= { cienaCesRsvpteObjects 1 }

 cienaCesRsvpteOperStatus OBJECT-TYPE
      SYNTAX      RsvpOperStatus
      MAX-ACCESS  read-only
      STATUS      current
      DESCRIPTION
          "The current operational state of RSVP-TE."
      ::= { cienaCesRsvpteObjects 2 }
      
 cienaCesRsvpteRetryInterval OBJECT-TYPE
      SYNTAX      Unsigned32 (3..65)
      UNITS       "seconds"
      MAX-ACCESS  read-only
      STATUS      current
      DESCRIPTION
          "The persistent tunnel retry interval.
           This is the interval between the first failure of a persistent
           tunnel and the first attempt to re-establish the tunnel.
           This cannot be changed while admin status is enable or oper status is up"
      DEFVAL      { 3 }
      ::= { cienaCesRsvpteObjects 3 }

 cienaCesRsvpteRetryInfiniteState OBJECT-TYPE
      SYNTAX      INTEGER {
      				on(1),
      				off(2)
      				}      
      MAX-ACCESS  read-only
      STATUS      current
      DESCRIPTION
          "The persistent tunnel retry infinity.
           This is the State which when on will trigger RSVP-TE to try to restore the tunnels
           infinite times. This object can only be set if RSVP-TE is globally disabled."
      DEFVAL      { on }
      ::= { cienaCesRsvpteObjects 4 }

 cienaCesRsvpteRetryMax OBJECT-TYPE
      SYNTAX      INTEGER (1..255)
      MAX-ACCESS  read-only
      STATUS      current
      DESCRIPTION
          "The maximum number of retry attempts that will be made before a
           persistent tunnel is deemed inoperable.  Once in this state,
           a management agent should set mplsTunnelAdminStatus to 'up' to
           attempt to reestablish the tunnel.
           This field is not used when cienaCesRsvpteRetryInfiniteState is on "
      DEFVAL      { 10 }
      ::= { cienaCesRsvpteObjects 5 }


 cienaCesRsvpteRefreshInterval OBJECT-TYPE
      SYNTAX      Integer32
      UNITS       "milliseconds"
      MAX-ACCESS  read-only
      STATUS      current
      DESCRIPTION
       "This RSVP-TE value, R,  which is used to set the average
        interval between refresh path and resv messages."
      DEFVAL { 30000 }
      ::= { cienaCesRsvpteObjects 6 }

 cienaCesRsvpteRefreshMultiple OBJECT-TYPE
      SYNTAX      Integer32 (1..214783647)
      MAX-ACCESS  read-only
      STATUS      current
      DESCRIPTION
       "The RSVP-TE value, K, which is the number of unresponded Path
        or Resv refresh attempts which must be made, spaced by
        the refresh interval before the state is deemed to have
        timed out."
      DEFVAL { 3 }
      ::= { cienaCesRsvpteObjects 7 }

 cienaCesRsvpteRefreshSlewDenominator OBJECT-TYPE
      SYNTAX      Integer32 (1..214783647)
      MAX-ACCESS  read-only
      STATUS      current
      DESCRIPTION
       "The denominator of the fraction, SlewMax, which is the
        maximum allowable increase in the refresh interval, R, to
        prevent state timeout while changing R.  R is increased by
        this fraction until it reaches the new desired value."
      DEFVAL { 10 }
      ::= { cienaCesRsvpteObjects 8 }

 cienaCesRsvpteRefreshSlewNumerator OBJECT-TYPE
      SYNTAX      Integer32 (1..214783647)
      MAX-ACCESS  read-only
      STATUS      current
      DESCRIPTION
       "The numerator of the fraction, SlewMax, which is the maximum
        allowable increase in the refresh interval, R, to prevent
        state timeout while changing R.  R is increased by this
        fraction until it reaches the new desired value."
      DEFVAL { 3 }
      ::= { cienaCesRsvpteObjects 9 }

 cienaCesRsvpteBlockadeMultiple OBJECT-TYPE
      SYNTAX      Integer32 (1..214783647)
      MAX-ACCESS  read-only
      STATUS      current
      DESCRIPTION
       "The RSVP-TE value, Kb, which is the number of refresh timeout
        periods after which blockade state is deleted."
      DEFVAL { 2 }
      ::= { cienaCesRsvpteObjects 10 }

 cienaCesRsvpteLSPSetupPriority OBJECT-TYPE
      SYNTAX      Integer32 (0..7)
      MAX-ACCESS  read-only
      STATUS      current
      DESCRIPTION
       "The setup priority to apply to LSPs which are not
        signalling this parameter.  0 represents the highest
        priority, 7 the lowest.  The value of this object must be
        numerically more or equal (so lower or equal priority)
        than the value of the holding priority object."
      DEFVAL { 4 }
      ::= { cienaCesRsvpteObjects 11 }

 cienaCesRsvpteLSPHoldingPriority OBJECT-TYPE
      SYNTAX      Integer32 (0..7)
      MAX-ACCESS  read-only
      STATUS      current
      DESCRIPTION
      "The holding priority to apply to LSPs which are not
       signalling this parameter.  0 represents the highest
       priority, 7 the lowest.  The value of this object must be
       numerically less or equal (so higher or equal priority)
       than the value of the holding priority object."
      DEFVAL { 3 }
      ::= { cienaCesRsvpteObjects 12 }

 cienaCesRsvpteUseHopByHop OBJECT-TYPE
      SYNTAX      TruthValue
      MAX-ACCESS  read-only
      STATUS      current
      DESCRIPTION
        "A flag to indicate that RSVP-TE should use the hop by hop
         addressing scheme for PATH and PATH-TEAR messages it
         sends.  If set then the IP addresses used in the IP header
         of PATH messages forwarded by RSVP-TE set source as the
         local outgoing interface IP address, and destination as
         the next hop router IP address."
      DEFVAL { false }
      ::= { cienaCesRsvpteObjects 13 }

 cienaCesRsvpteRestartCapable OBJECT-TYPE
      SYNTAX      TruthValue
      MAX-ACCESS  read-only
      STATUS      current
      DESCRIPTION
          "A flag to indicate whether the local node should advertise
           itself as restart capable."
      DEFVAL { true }
      ::= { cienaCesRsvpteObjects 14 }

 cienaCesRsvpteRestartTime OBJECT-TYPE
      SYNTAX      Unsigned32
      MAX-ACCESS  read-only
      STATUS      current
      DESCRIPTION
        "The time in milliseconds that the local node takes to
         restart RSVP-TE and the communication channel used for
         RSVP-TE communication.  This is advertised to neighbors in
         the Restart_Cap object in Hello messages.

         Only used if cienaCesRsvpteRestartCapable is set to true."
      DEFVAL { 10000 }
      ::= { cienaCesRsvpteObjects 15 }

 cienaCesRsvpteRecoveryTime OBJECT-TYPE
      SYNTAX      Unsigned32
      MAX-ACCESS  read-only
      STATUS      current
      DESCRIPTION
        "The period of time in milliseconds that the local node
         would like neighbors to take to resyncronize RSVP-TE and
         MPLS forwarding information after the re-establishment of
         Hello connectivity.  This is advertised to neighbors in
         the Restart_Cap object in Hello messages.

         A value of zero indicates that the node does not support
         resynchronization following failure of the local node.

         A value of 0xFFFFFFFF indicates an infinite recovery time.

         Only used if cienaCesRsvpteRestartCapable is set to true."
      DEFVAL { 0 }
      ::= { cienaCesRsvpteObjects 16 }

 cienaCesRsvpteMinPeerRestart OBJECT-TYPE
      SYNTAX      Integer32
      MAX-ACCESS  read-only
      STATUS      current
      DESCRIPTION
        "The mininum period of time in milliseconds that RSVP-TE
         should wait for a restart capable neighbor to regain
         Hello connectivity before invoking procedures related to
         communication loss.

         RSVP-TE will wait for the maximum of this time and the
         restart_time advertised in the RESTART_CAP object in Hello
         messages from the neighbor."
      DEFVAL { 0 }
      ::= { cienaCesRsvpteObjects 17 }

 cienaCesRsvpteIfTable OBJECT-TYPE
      SYNTAX      SEQUENCE OF CienaCesRsvpteIfEntry
      MAX-ACCESS  not-accessible
      STATUS      current
      DESCRIPTION
          "A table of interfaces that RSVP-TE can be enabled on."
      ::= { cienaCesRsvpte 1 }
    
 cienaCesRsvpteIfEntry OBJECT-TYPE
      SYNTAX      CienaCesRsvpteIfEntry
      MAX-ACCESS  not-accessible
      STATUS      current
      DESCRIPTION
          "CIENA Descr."
           INDEX       { cienaCesRsvpteIfIndex }
      ::= { cienaCesRsvpteIfTable 1 }

 CienaCesRsvpteIfEntry ::= SEQUENCE {
      cienaCesRsvpteIfIndex           	INTEGER,
      cienaCesRsvpteIfName            	OCTET STRING,
      cienaCesRsvpteIfIpAddr          	IpAddress,
      cienaCesRsvpteIfMtu             	INTEGER,
      cienaCesRsvpteIfAdminStatus     	CienaGlobalState,
      cienaCesRsvpteIfOperStatus      	INTEGER,
      cienaCesRsvpteIfHelloInterval   	Unsigned32,
      cienaCesRsvpteIfHelloTolerance  	Unsigned32,
      cienaCesRsvpteIfAdvertisedLabel 	AdvertisedLabel	
 }


 cienaCesRsvpteIfIndex OBJECT-TYPE
      SYNTAX      INTEGER (1..4096)
      MAX-ACCESS  not-accessible
      STATUS      current
      DESCRIPTION
          "Interface Index"
      ::= { cienaCesRsvpteIfEntry 1 }

 cienaCesRsvpteIfName OBJECT-TYPE
      SYNTAX      OCTET STRING (SIZE (0..32))
      MAX-ACCESS  read-only
      STATUS      current
      DESCRIPTION
          "Interface Name"
      ::= { cienaCesRsvpteIfEntry 2 }


 cienaCesRsvpteIfIpAddr OBJECT-TYPE
      SYNTAX      IpAddress
      MAX-ACCESS  read-only
      STATUS      current
      DESCRIPTION
          "Interface IP Address"
      ::= { cienaCesRsvpteIfEntry 3 }

 cienaCesRsvpteIfAdminStatus OBJECT-TYPE
      SYNTAX            CienaGlobalState
      MAX-ACCESS  read-only
      STATUS      current
      DESCRIPTION
          "Desired RSVP-TE status on this Interface"
      ::= { cienaCesRsvpteIfEntry 4 }

 cienaCesRsvpteIfOperStatus OBJECT-TYPE
      SYNTAX      INTEGER {
                     up(1),
                     down(2)
                  }
      MAX-ACCESS  read-only
      STATUS      current
      DESCRIPTION
          "RSVP-TE Operational Status on this Interface"
      ::= { cienaCesRsvpteIfEntry 5 }

 cienaCesRsvpteIfHelloInterval OBJECT-TYPE
      SYNTAX      Unsigned32 (0..30)    
      UNITS	      "seconds"
      MAX-ACCESS  read-only
      STATUS      current
      DESCRIPTION
          "RSVP-TE hello message interval. "
      DEFVAL	  { 0 }      
      ::= { cienaCesRsvpteIfEntry 6 }

  cienaCesRsvpteIfHelloTolerance OBJECT-TYPE
      SYNTAX      Unsigned32 (0..10)
      MAX-ACCESS  read-only
      STATUS      current            
      DESCRIPTION
          "RSVP-TE hello tolerance defines number of hello interval which may pass without receiving a
           successful Hello message from a partner before the Hello session times out."
      DEFVAL	  { 3 }     
      ::= { cienaCesRsvpteIfEntry 7 }
 
 cienaCesRsvpteIfAdvertisedLabel OBJECT-TYPE
      SYNTAX      AdvertisedLabel
      MAX-ACCESS  read-only
      STATUS      current            
      DESCRIPTION
          "This attribute decides what kind of a Label will be advertised by RSVP-TE for a 
          Label Request received on this L3 Interface"
      DEFVAL	  { 99 }     
      ::= { cienaCesRsvpteIfEntry 8 }
 
 END
 
--
-- CIENA-CES-RSVPTE-MIB
--
