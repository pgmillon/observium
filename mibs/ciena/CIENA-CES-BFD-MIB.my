-- This file was included in WWP MIB release 04-10-01-0027
 --
 -- CIENA-CES-BFD-MIB.my
 --    

 CIENA-CES-BFD-MIB DEFINITIONS ::= BEGIN

 IMPORTS                
   TimeTicks, Integer32, Unsigned32, OBJECT-TYPE, NOTIFICATION-TYPE, MODULE-IDENTITY                       
        FROM SNMPv2-SMI                 
   DisplayString, MacAddress, TruthValue                
        FROM SNMPv2-TC                                                  
    cienaGlobalSeverity, cienaGlobalMacAddress
   		FROM  CIENA-GLOBAL-MIB
   CienaGlobalState, CienaStatsClear,CienaMacAddress
   		FROM CIENA-TC
   cienaCesConfig,cienaCesStatistics, cienaCesNotifications         
        FROM CIENA-SMI;
        
 cienaCesBfdMIB MODULE-IDENTITY
	LAST-UPDATED "201107260000Z"
	ORGANIZATION "Ciena, Inc"
	CONTACT-INFO
                       "Mib Meister
                        115 North Sullivan Road
                        Spokane Valley, WA 99037
                        USA            
                        Phone:  +1 509 242 9000
			Email:  support@ciena.com"
	DESCRIPTION
	                    "This module defines the BFD SNMP objects."

                        REVISION  "201107260000Z"
                        DESCRIPTION
                            "Intial creation."
                        ::= { cienaCesConfig 22 }
--
-- Node Definitions
-- 

 cienaCesBfdMIBObjects 			OBJECT IDENTIFIER ::= { cienaCesBfdMIB 1 } 
 cienaCesBfdSession 			        OBJECT IDENTIFIER ::= { cienaCesBfdMIBObjects 2 }

-- Statistics

   cienaCesBfdSessionStats			OBJECT IDENTIFIER ::= { cienaCesStatistics 7 } 

-- Notifications 
  
 cienaCesBfdSessionMIBNotificationPrefix  	OBJECT IDENTIFIER ::= { cienaCesNotifications 19 } 
 
 cienaCesBfdSessionMIBNotification              OBJECT IDENTIFIER ::=  { cienaCesBfdSessionMIBNotificationPrefix 0 }

--
-- BFD Session Table
--                           
 cienaCesBfdSessionTable OBJECT-TYPE
     SYNTAX SEQUENCE OF CienaCesBfdSessionEntry
     MAX-ACCESS not-accessible
     STATUS current
     DESCRIPTION
            "The (conceptual) table listing the config 
            parameters for the Bfd Session Table."  
     ::= { cienaCesBfdSession 1 }
                
 cienaCesBfdSessionEntry OBJECT-TYPE
     SYNTAX      CienaCesBfdSessionEntry
     MAX-ACCESS  not-accessible
     STATUS      current
     DESCRIPTION
           "An entry (conceptual row) in the cienaCesBfdSessionTable."
     INDEX {cienaCesBfdSessionIndex}
     ::= { cienaCesBfdSessionTable 1 }
        
 CienaCesBfdSessionEntry ::=  SEQUENCE {               
     cienaCesBfdSessionIndex                             Unsigned32,
     cienaCesBfdSessionName                              DisplayString,
     cienaCesBfdSessionAdminState                        CienaGlobalState,     
     cienaCesBfdSessionOperState                         CienaGlobalState
}


cienaCesBfdSessionIndex OBJECT-TYPE
     SYNTAX      Unsigned32  
     MAX-ACCESS  not-accessible
     STATUS      current
     DESCRIPTION
             "A unique identifier for BFD Session entry."
     ::= { cienaCesBfdSessionEntry 1 }


 cienaCesBfdSessionName OBJECT-TYPE
     SYNTAX       DisplayString 
     MAX-ACCESS   read-only
     STATUS       current
     DESCRIPTION
             "This mib object specifies the BFD session name."
     ::= { cienaCesBfdSessionEntry 2 }         

 cienaCesBfdSessionAdminState OBJECT-TYPE
     SYNTAX       CienaGlobalState                          
     MAX-ACCESS   read-only
     STATUS       current
     DESCRIPTION
             "This object specifies the admin state of BFD Session."
     ::= { cienaCesBfdSessionEntry 3 }
 
 cienaCesBfdSessionOperState OBJECT-TYPE
     SYNTAX       CienaGlobalState
     MAX-ACCESS   read-only
     STATUS       current
     DESCRIPTION
             "This object specifies the operational state of BFD Session."
     ::= { cienaCesBfdSessionEntry 4 }



--
-- BFD Session Statistics
--
 cienaCesBfdSessionStatsTable OBJECT-TYPE
     SYNTAX  SEQUENCE OF CienaCesBfdSessionStatsEntry
     MAX-ACCESS not-accessible
     STATUS     current
     DESCRIPTION
            "The (conceptual) table listing the statistics 
            for a given BFD Session"  
     ::= { cienaCesBfdSessionStats 1 }

 
 cienaCesBfdSessionStatsEntry OBJECT-TYPE
     SYNTAX      CienaCesBfdSessionStatsEntry
     MAX-ACCESS  not-accessible
     STATUS      current
     DESCRIPTION
           "An entry (conceptual row) in the cienaCesBfdSessionStatsTable."
     INDEX {cienaCesBfdSessionIndex}
     ::= { cienaCesBfdSessionStatsTable 1 }

 CienaCesBfdSessionStatsEntry ::=  SEQUENCE { 
    cienaCesBfdSessionIndex             Unsigned32,
	cienaCesBfdSessionStatsTotalTx		Unsigned32,
 	cienaCesBfdSessionStatsTotalRx 		Unsigned32,
    cienaCesBfdSessionUpTime            Unsigned32,
    cienaCesBfdSessionDownTimeCount     Unsigned32 	
	}

 cienaCesBfdSessionStatsTotalTx OBJECT-TYPE
     SYNTAX       Unsigned32
     MAX-ACCESS   read-only
     STATUS       current
     DESCRIPTION
             "This object specifies the no: of Transmitted Packets in a BFD Session."
     ::= { cienaCesBfdSessionStatsEntry 1 }

 cienaCesBfdSessionStatsTotalRx OBJECT-TYPE
     SYNTAX       Unsigned32
     MAX-ACCESS   read-only
     STATUS       current
     DESCRIPTION
             "This object specifies the no: of Received Packets in a BFD Session."
     ::= { cienaCesBfdSessionStatsEntry 2 }   
     
  cienaCesBfdSessionUpTime OBJECT-TYPE
     SYNTAX       Unsigned32
     MAX-ACCESS   read-only
     STATUS       current
     DESCRIPTION
             "This object specifies the time duration in seconds the session has been in the up state"
     ::= { cienaCesBfdSessionStatsEntry 3 }

 cienaCesBfdSessionDownTimeCount OBJECT-TYPE
     SYNTAX       Unsigned32
     MAX-ACCESS   read-only
     STATUS       current
     DESCRIPTION
             "This object specifies the total number of times a session changes from up to operationally down state since creation"
     ::= { cienaCesBfdSessionStatsEntry 4 }
    

--
-- Notifications
--  
 cienaCesBfdSessionOperStateChangeTrap  NOTIFICATION-TYPE
        OBJECTS      {      
          cienaGlobalSeverity,
          cienaGlobalMacAddress,
          cienaCesBfdSessionName,                                      
          cienaCesBfdSessionIndex,
          cienaCesBfdSessionAdminState,                 
          cienaCesBfdSessionOperState
       }
   STATUS      current
   DESCRIPTION
      "A notification is sent whenever the Bfd Session Oper State has changed. To send this trap,the 
       cienaCesBfdSessionOperTrapState object must be enabled (which is enabled by default)."
   ::= { cienaCesBfdSessionMIBNotification 1 }
 
 END
