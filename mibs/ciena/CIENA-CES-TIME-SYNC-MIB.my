-- This file was included in WWP MIB release 04-10-01-0027
 --
 -- CIENA-CES-TIME-SYNC-MIB.my
 --

 CIENA-CES-TIME-SYNC-MIB DEFINITIONS ::= BEGIN

 IMPORTS 		
   	Integer32, Unsigned32, OBJECT-TYPE, MODULE-IDENTITY, NOTIFICATION-TYPE	
	FROM SNMPv2-SMI			
   	DisplayString, TEXTUAL-CONVENTION
	FROM SNMPv2-TC							
   	cienaCesConfig, cienaCesNotifications 
	FROM CIENA-SMI
	CienaGlobalState
	FROM CIENA-TC							
        cienaGlobalSeverity, cienaGlobalMacAddress
        FROM CIENA-GLOBAL-MIB;

	
 cienaCesTimeSyncMIB MODULE-IDENTITY
	    LAST-UPDATED "201206200000Z"
	    ORGANIZATION "Ciena, Inc"
	    CONTACT-INFO
		    "   Mib Meister
		  	115 North Sullivan Road
			Spokane Valley, WA 99037
		        USA		 		
		        Phone:  +1 509 242 9000
			Email:  support@ciena.com"
	    DESCRIPTION
		    "This MIB module defines objects and associated notifications
                     for the System Timing feature."

	    REVISION
	    	"201206200000Z"
	    DESCRIPTION
		"Initial version."

	    ::= { cienaCesConfig 28 }

 --
 -- Textual convention
 --

 SsmStratumLevel ::= TEXTUAL-CONVENTION
     STATUS       current
     DESCRIPTION  "International and North American SSM Values"
     SYNTAX       INTEGER 
                  {
                     unknown(1),
                     prc(2), 
                     ssua(3),
                     ssub(4),
                     sec(5),
                     dnu(6),
                     prs(7),
                     stu(8),
                     st2(9),
                     tnc(10),
                     st3e(11),
                     st3(12),
                     smc(13),
                     st4(14),
                     dus(15),
                     prov(16)
                  }

 SyncInterfaceProtocol ::= TEXTUAL-CONVENTION
     STATUS       current
     DESCRIPTION  "Interface protocol of an input/output reference."
     SYNTAX       INTEGER
                  {
                     unknown(1),
                     bits(2),
                     synce(3)
                  }

 SyncBITSSignalMode ::= TEXTUAL-CONVENTION
     STATUS       current
     DESCRIPTION  "Station Clock BITS signal mode."
     SYNTAX       INTEGER
                  {
                     modeunknown(1),
                     modet1(2),
                     modee1(3),
                     modej1(4),
                     mode2048khz(5),
                     mode64kcc(6),
                     mode6312khz(7)
                  }

 SyncBITSSignalFormat ::= TEXTUAL-CONVENTION
     STATUS       current
     DESCRIPTION  "Station Clock BITS signal format.  Esf and sf are applied to t1 signal
                   only where as ccs and cas are applied to e1 signal."
     SYNTAX       INTEGER
                  {
                     unknown(1),
                     cas(2),
                     cascrc(3),
                     esf(4),
                     fas(5),
                     fascrc(6),
                     sf(7)
                  }

 SyncBITSSignalEncoding ::= TEXTUAL-CONVENTION
     STATUS       current
     DESCRIPTION  "Encoding method used on T1/E1 BITS signal."
     SYNTAX       INTEGER
                  {
                     unknown(1),
                     b8zs(2),
                     ami(3),
                     hdb3(4)
                  }

 SyncRefOperationalStatus ::= TEXTUAL-CONVENTION
     STATUS       current
     DESCRIPTION  "Operational status of an input/output reference."
     SYNTAX       INTEGER
                  {
                     unknown(1),
                     active(2),
                     selected(3),
                     lossofsignal(4),
                     lossofframe(5),
                     alarmindicationsignal(6),
                     hardwarefault(7),
                     hardwarenotconfigured(8),
                     qlbelowthreshold(9),
                     rxtimeout(10),
                     notauthenticated(11),
                     loopbacktx(12),
                     loopbackrx(13),
                     linkflap(14)
                  }

 --
 -- Node definitions
 --

 cienaCesTimeSyncMIBObjects   OBJECT IDENTIFIER ::= { cienaCesTimeSyncMIB 1 }
 cienaCesTimeSyncObjects      OBJECT IDENTIFIER ::= { cienaCesTimeSyncMIBObjects 1 }

 -- Notifications   
 cienaCesTimeSyncMIBNotificationPrefix  OBJECT IDENTIFIER ::=  { cienaCesNotifications 28 } 
 cienaCesTimeSyncMIBNotifications       OBJECT IDENTIFIER ::=  { cienaCesTimeSyncMIBNotificationPrefix 0 }


--
-- Global objects 
--
    
 cienaCesSyncAdminState OBJECT-TYPE
     SYNTAX      CienaGlobalState
     MAX-ACCESS  read-only
     STATUS      current
     DESCRIPTION
         "Globally enable/disable Sync"
    ::= { cienaCesTimeSyncObjects 1 }

 cienaCesSyncOptionType OBJECT-TYPE
    SYNTAX      INTEGER
                {
                   unknown(1),
                   option1(2),
                   option2(3)
                }
    MAX-ACCESS  read-only
    STATUS      current
    DESCRIPTION
        "Indication of which set of SSM values being used.  Option 1 is
         for International standard and Option 2 is for North American."
    ::= { cienaCesTimeSyncObjects 2 }

 cienaCesSyncRevertiveMode OBJECT-TYPE
    SYNTAX      INTEGER
                {
                   unknown(1),
                   revertive(2),
                   nonrevertive(3)
                }
    MAX-ACCESS  read-only
    STATUS      current
    DESCRIPTION
        "Revertive mode."
    ::= { cienaCesTimeSyncObjects 3 }

 cienaCesSyncWaitToRestoreTimer OBJECT-TYPE
    SYNTAX      Unsigned32
    MAX-ACCESS  read-only
    STATUS      current
    DESCRIPTION
        "User configured timer for a timing reference source to wait
         before transitioning from bad to good clock signal."
    ::= { cienaCesTimeSyncObjects 4 }


--
-- SyncInputProtectionGroupTable
--

cienaCesSyncInputProtectionGroupTable OBJECT-TYPE
    SYNTAX      SEQUENCE OF CienaCesSyncInputProtectionGroupEntry
    MAX-ACCESS  not-accessible
    STATUS      current
    DESCRIPTION
        "A table of protection groups for input timing reference."
    ::= {  cienaCesTimeSyncObjects 5 }

cienaCesSyncInputProtectionGroupEntry OBJECT-TYPE
    SYNTAX      CienaCesSyncInputProtectionGroupEntry
    MAX-ACCESS  not-accessible
    STATUS      current
    DESCRIPTION
        "An entry in this table represents information on a protection
         group for input timing reference"
    INDEX       { cienaCesInputPGEntityId }
    ::= { cienaCesSyncInputProtectionGroupTable 1 }

CienaCesSyncInputProtectionGroupEntry ::= SEQUENCE {
        cienaCesInputPGEntityId                  Integer32,
        cienaCesInputPGEntityName                DisplayString,
        cienaCesInputPGPreferredReference        DisplayString,
        cienaCesInputPGSelectedReference         DisplayString,
        cienaCesInputPGForcedReference           DisplayString,
        cienaCesInputPGThresholdQualityLevel     SsmStratumLevel,
        cienaCesInputPGState                     CienaGlobalState,
        cienaCesInputPGStateDuration             DisplayString,
        cienaCesInputPGReferenceSwitchCount      Unsigned32,
        cienaCesInputPGOperationalStatus         INTEGER
        }

 cienaCesInputPGEntityId OBJECT-TYPE
    SYNTAX      Integer32 (1)
    MAX-ACCESS  not-accessible
    STATUS      current
    DESCRIPTION
        "The unique identifier of this input protection group."
    ::= { cienaCesSyncInputProtectionGroupEntry 1 }
            
 cienaCesInputPGEntityName OBJECT-TYPE
    SYNTAX      DisplayString (SIZE (1..31))
    MAX-ACCESS  read-only
    STATUS      current
    DESCRIPTION
        "The unique name of this input protection group."
    ::= { cienaCesSyncInputProtectionGroupEntry 2 }
            
 cienaCesInputPGPreferredReference OBJECT-TYPE
    SYNTAX      DisplayString (SIZE (1..31))
    MAX-ACCESS  read-only
    STATUS      current
    DESCRIPTION
        "Preferred timing reference source, configured by users."
    ::= { cienaCesSyncInputProtectionGroupEntry 3 }
            
 cienaCesInputPGSelectedReference OBJECT-TYPE
    SYNTAX      DisplayString (SIZE (1..31))
    MAX-ACCESS  read-only
    STATUS      current
    DESCRIPTION
        "System selected timing reference source."
    ::= { cienaCesSyncInputProtectionGroupEntry 4 }
            
 cienaCesInputPGForcedReference OBJECT-TYPE
    SYNTAX      DisplayString (SIZE (1..31))
    MAX-ACCESS  read-only
    STATUS      current
    DESCRIPTION
        "System was forced to used this timing reference source."
    ::= { cienaCesSyncInputProtectionGroupEntry 5 }
            
 cienaCesInputPGThresholdQualityLevel OBJECT-TYPE
    SYNTAX      SsmStratumLevel
    MAX-ACCESS  read-only
    STATUS      current
    DESCRIPTION
        "Specified Quality Level threshold for a reference source
         being selected."
    ::= { cienaCesSyncInputProtectionGroupEntry 6 }

 cienaCesInputPGState OBJECT-TYPE
    SYNTAX      CienaGlobalState
    MAX-ACCESS  read-only
    STATUS      current
    DESCRIPTION
        "Configured state of this protection group."
    ::= { cienaCesSyncInputProtectionGroupEntry 7 }

 cienaCesInputPGStateDuration OBJECT-TYPE
    SYNTAX      DisplayString (SIZE (1..31))
    MAX-ACCESS  read-only
    STATUS      current
    DESCRIPTION
        "Duration since the system entered current state."
    ::= { cienaCesSyncInputProtectionGroupEntry 8 }
            
 cienaCesInputPGReferenceSwitchCount OBJECT-TYPE
    SYNTAX      Unsigned32
    MAX-ACCESS  read-only
    STATUS      current
    DESCRIPTION
        "The number of timing reference switching since the system stared up."
    ::= { cienaCesSyncInputProtectionGroupEntry 9 }
            
 cienaCesInputPGOperationalStatus OBJECT-TYPE
    SYNTAX      INTEGER
                {
                   unknown(1),
                   freerun(2),
                   holdover(3),
                   locked(4),
                   acquiringlock(5)
                }
    MAX-ACCESS  read-only
    STATUS      current
    DESCRIPTION
        "Operational status of this protection group."
    ::= { cienaCesSyncInputProtectionGroupEntry 10 }

--
-- SyncInputProtectionUnitTable
--

cienaCesSyncInputProtectionUnitTable OBJECT-TYPE
    SYNTAX      SEQUENCE OF CienaCesSyncInputProtectionUnitEntry
    MAX-ACCESS  not-accessible
    STATUS      current
    DESCRIPTION
        "A table of protection units for input timing reference."
    ::= {  cienaCesTimeSyncObjects 6 }

cienaCesSyncInputProtectionUnitEntry OBJECT-TYPE
    SYNTAX      CienaCesSyncInputProtectionUnitEntry
    MAX-ACCESS  not-accessible
    STATUS      current
    DESCRIPTION
        "An entry in this table represents information on a protection
         unit for input timing reference."
    INDEX       { cienaCesInputPUEntityId }
    ::= { cienaCesSyncInputProtectionUnitTable 1 }

CienaCesSyncInputProtectionUnitEntry ::= SEQUENCE {
        cienaCesInputPUEntityId                  Integer32,
        cienaCesInputPUEntityName                DisplayString,
        cienaCesInputPUPGEntityName              DisplayString,
        cienaCesInputPUTimingInterfaceName       DisplayString,
        cienaCesInputPUTimingInterfaceProtocol   SyncInterfaceProtocol,
        cienaCesInputPUUserPriority              Unsigned32,
        cienaCesInputPUOperationalQL             SsmStratumLevel,
        cienaCesInputPUForcedQL                  SsmStratumLevel,
        cienaCesInputPUReceivedQL                SsmStratumLevel,
        cienaCesInputPUSsmEnabled                INTEGER,
        cienaCesInputPUOperationalStatus         SyncRefOperationalStatus,
        cienaCesInputPUBITSSignalMode            SyncBITSSignalMode,
        cienaCesInputPUBITSSignalFormat          SyncBITSSignalFormat,
        cienaCesInputPUBITSSignalEncoding        SyncBITSSignalEncoding
        }

 cienaCesInputPUEntityId OBJECT-TYPE
    SYNTAX      Integer32 (1..48)
    MAX-ACCESS  not-accessible
    STATUS      current
    DESCRIPTION
        "The unique identifier of this input protection unit."
    ::= { cienaCesSyncInputProtectionUnitEntry 1 }
            
 cienaCesInputPUEntityName OBJECT-TYPE
    SYNTAX      DisplayString (SIZE (1..31))
    MAX-ACCESS  read-only
    STATUS      current
    DESCRIPTION
        "The unique name of this input protection unit."
    ::= { cienaCesSyncInputProtectionUnitEntry 2 }
            
 cienaCesInputPUPGEntityName OBJECT-TYPE
    SYNTAX      DisplayString (SIZE (1..31))
    MAX-ACCESS  read-only
    STATUS      current
    DESCRIPTION
        "The identifier of the input protection group which this input
         protection unit belongs to."
    ::= { cienaCesSyncInputProtectionUnitEntry 3 }

 cienaCesInputPUTimingInterfaceName OBJECT-TYPE
    SYNTAX      DisplayString (SIZE (1..31))
    MAX-ACCESS  read-only
    STATUS      current
    DESCRIPTION
        "The interface name of this input protection unit."
    ::= { cienaCesSyncInputProtectionUnitEntry 4 }

 cienaCesInputPUTimingInterfaceProtocol OBJECT-TYPE
    SYNTAX      SyncInterfaceProtocol
    MAX-ACCESS  read-only
    STATUS      current
    DESCRIPTION
        "The interface protocol of this input protection unit."
    ::= { cienaCesSyncInputProtectionUnitEntry 5 }

 cienaCesInputPUUserPriority OBJECT-TYPE
    SYNTAX      Unsigned32
    MAX-ACCESS  read-only
    STATUS      current
    DESCRIPTION
        "The user configured priority of this input protection unit."
    ::= { cienaCesSyncInputProtectionUnitEntry 6 }

 cienaCesInputPUOperationalQL OBJECT-TYPE
    SYNTAX      SsmStratumLevel
    MAX-ACCESS  read-only
    STATUS      current
    DESCRIPTION
        "Operational clock quality level of this input protection unit."
    ::= { cienaCesSyncInputProtectionUnitEntry 7 }

 cienaCesInputPUForcedQL OBJECT-TYPE
    SYNTAX      SsmStratumLevel
    MAX-ACCESS  read-only
    STATUS      current
    DESCRIPTION
        "User configured clock quality level that this input protection unit
         is forced to operate at."
    ::= { cienaCesSyncInputProtectionUnitEntry 8 }

 cienaCesInputPUReceivedQL OBJECT-TYPE
    SYNTAX      SsmStratumLevel
    MAX-ACCESS  read-only
    STATUS      current
    DESCRIPTION
        "Actual received clock quality level of this input protection unit."
    ::= { cienaCesSyncInputProtectionUnitEntry 9 }

 cienaCesInputPUSsmEnabled OBJECT-TYPE
    SYNTAX      INTEGER
                {
                   unknown(1),
                   disabled(2),
                   enabled(3)
                }
    MAX-ACCESS  read-only
    STATUS      current
    DESCRIPTION
        "Enable/disable reading of actual received clock quality level for 
         this input protection unit."
    ::= { cienaCesSyncInputProtectionUnitEntry 10 }

 cienaCesInputPUOperationalStatus OBJECT-TYPE
    SYNTAX      SyncRefOperationalStatus
    MAX-ACCESS  read-only
    STATUS      current
    DESCRIPTION
        "Operational status of this input protection unit."
    ::= { cienaCesSyncInputProtectionUnitEntry 11 }

 cienaCesInputPUBITSSignalMode OBJECT-TYPE
    SYNTAX      SyncBITSSignalMode
    MAX-ACCESS  read-only
    STATUS      current
    DESCRIPTION
        "BITS Signal Mode, set if BITS signal is used as a protection unit."
    ::= { cienaCesSyncInputProtectionUnitEntry 12 }

 cienaCesInputPUBITSSignalFormat OBJECT-TYPE
    SYNTAX      SyncBITSSignalFormat
    MAX-ACCESS  read-only
    STATUS      current
    DESCRIPTION
        "BITS Signal Format, set if BITS signal is used as a protection unit."
    ::= { cienaCesSyncInputProtectionUnitEntry 13 }

 cienaCesInputPUBITSSignalEncoding OBJECT-TYPE
    SYNTAX      SyncBITSSignalEncoding
    MAX-ACCESS  read-only
    STATUS      current
    DESCRIPTION
        "BITS Signal encoding, set if BITS signal is used as a protection unit."
    ::= { cienaCesSyncInputProtectionUnitEntry 14 }

--
-- SyncOutputTable
--

cienaCesSyncOutputTable OBJECT-TYPE
    SYNTAX      SEQUENCE OF CienaCesSyncOutputEntry
    MAX-ACCESS  not-accessible
    STATUS      current
    DESCRIPTION
        "A table of output timing references."
    ::= {  cienaCesTimeSyncObjects 7 }

cienaCesSyncOutputEntry OBJECT-TYPE
    SYNTAX      CienaCesSyncOutputEntry
    MAX-ACCESS  not-accessible
    STATUS      current
    DESCRIPTION
        "An entry in this table represents information for an output 
         timing reference."
    INDEX       { cienaCesOutputEntityId }
    ::= { cienaCesSyncOutputTable 1 }

CienaCesSyncOutputEntry ::= SEQUENCE {
        cienaCesOutputEntityId                  Integer32,
        cienaCesOutputEntityName                DisplayString,
        cienaCesOutputTimingInterfaceName       DisplayString,
        cienaCesOutputTimingInterfaceProtocol   SyncInterfaceProtocol,
        cienaCesOutputOperationalQL             SsmStratumLevel,
        cienaCesOutputOperationalStatus         SyncRefOperationalStatus,
        cienaCesOutputBITSSignalMode            SyncBITSSignalMode,
        cienaCesOutputBITSSignalFormat          SyncBITSSignalFormat,
        cienaCesOutputBITSSignalEncoding        SyncBITSSignalEncoding,
        cienaCesOutputBITSSignalLineBuildout    INTEGER,
        cienaCesOutputBITSSignalSsmLocation     INTEGER
        }

 cienaCesOutputEntityId OBJECT-TYPE
    SYNTAX      Integer32 (1..48)
    MAX-ACCESS  not-accessible
    STATUS      current
    DESCRIPTION
        "The unique identifier of this output reference entity."
    ::= { cienaCesSyncOutputEntry 1 }
            
 cienaCesOutputEntityName OBJECT-TYPE
    SYNTAX      DisplayString (SIZE (1..31))
    MAX-ACCESS  read-only
    STATUS      current
    DESCRIPTION
        "The unique name of this output reference entity."
    ::= { cienaCesSyncOutputEntry 2 }
            
 cienaCesOutputTimingInterfaceName OBJECT-TYPE
    SYNTAX      DisplayString (SIZE (1..31))
    MAX-ACCESS  read-only
    STATUS      current
    DESCRIPTION
        "The interface name of this output reference."
    ::= { cienaCesSyncOutputEntry 3 }

 cienaCesOutputTimingInterfaceProtocol OBJECT-TYPE
    SYNTAX      SyncInterfaceProtocol
    MAX-ACCESS  read-only
    STATUS      current
    DESCRIPTION
        "The interface protocol of this output reference."
    ::= { cienaCesSyncOutputEntry 4 }

 cienaCesOutputOperationalQL OBJECT-TYPE
    SYNTAX      SsmStratumLevel
    MAX-ACCESS  read-only
    STATUS      current
    DESCRIPTION
        "Operational clock quality level of this output reference."
    ::= { cienaCesSyncOutputEntry 5 }

 cienaCesOutputOperationalStatus OBJECT-TYPE
    SYNTAX      SyncRefOperationalStatus
    MAX-ACCESS  read-only
    STATUS      current
    DESCRIPTION
        "Operational status of this output reference."
    ::= { cienaCesSyncOutputEntry 6 }

 cienaCesOutputBITSSignalMode OBJECT-TYPE
    SYNTAX      SyncBITSSignalMode
    MAX-ACCESS  read-only
    STATUS      current
    DESCRIPTION
        "BITS Signal Mode, set if BITS signal is used as an output reference."
    ::= { cienaCesSyncOutputEntry 7 }

 cienaCesOutputBITSSignalFormat OBJECT-TYPE
    SYNTAX      SyncBITSSignalFormat
    MAX-ACCESS  read-only
    STATUS      current
    DESCRIPTION
        "BITS Signal Format, set if BITS signal is used as an output reference."
    ::= { cienaCesSyncOutputEntry 8 }

 cienaCesOutputBITSSignalEncoding OBJECT-TYPE
    SYNTAX      SyncBITSSignalEncoding
    MAX-ACCESS  read-only
    STATUS      current
    DESCRIPTION
        "BITS Signal encoding, set if BITS signal is used as an output reference."
    ::= { cienaCesSyncOutputEntry 9 }

 cienaCesOutputBITSSignalLineBuildout OBJECT-TYPE
    SYNTAX      INTEGER
                {
                   unknown(1),
                   lbo133(2),
                   lbo266(3),
                   lbo399(4),
                   lbo533(5),
                   lbo655(6)
                }
    MAX-ACCESS  read-only
    STATUS      current
    DESCRIPTION
        "BITS Signal Line Buildout, set if BITS signal is used as an output reference."
    ::= { cienaCesSyncOutputEntry 10 }

 cienaCesOutputBITSSignalSsmLocation OBJECT-TYPE
    SYNTAX      INTEGER
                {
                   unknown(1),
                   sa4(2),
                   sa5(3),
                   sa6(4),
                   sa7(5)
                }
    MAX-ACCESS  read-only
    STATUS      current
    DESCRIPTION
        "BITS Signal Ssm Location, set if BITS signal is used as an output reference."
    ::= { cienaCesSyncOutputEntry 11 }

 --
 -- notifications
 --

 cienaCesSyncInputPUStateChangeNotification NOTIFICATION-TYPE
    OBJECTS {  
               cienaGlobalSeverity,
               cienaGlobalMacAddress,       
               cienaCesInputPUEntityName,
               cienaCesInputPUPGEntityName,
               cienaCesInputPUTimingInterfaceName,
               cienaCesInputPUTimingInterfaceProtocol,
               cienaCesInputPUOperationalStatus
            }
    STATUS  current
    DESCRIPTION
        "Sent when a timing reference source failed." 
    ::= { cienaCesTimeSyncMIBNotifications 1 }
 
 cienaCesSyncInputProtectionGroupStateChangeNotification NOTIFICATION-TYPE
    OBJECTS {  
               cienaGlobalSeverity,
               cienaGlobalMacAddress,       
               cienaCesInputPGEntityName,
               cienaCesInputPGOperationalStatus
            }
    STATUS  current
    DESCRIPTION
        "Sent when system timing could not lock into a reference source
         and entered hold over state." 
    ::= { cienaCesTimeSyncMIBNotifications 2 }
 
  END
 
 --
 -- CIENA-CES-TIME-SYNC-MIB
 --
