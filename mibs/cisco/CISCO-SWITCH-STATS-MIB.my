-- *****************************************************************
-- CISCO-SWITCH-STATS-MIB.my: Switch Statistics Configuration and
-- Information MIB.
--   
-- January 2009, Guichuan Tang, Jayakumar Kadirvelu
--   
-- Copyright (c) 2009 by Cisco Systems, Inc.
-- All rights reserved.
--   
-- *****************************************************************

CISCO-SWITCH-STATS-MIB DEFINITIONS ::= BEGIN

IMPORTS
    MODULE-IDENTITY,
    OBJECT-TYPE,
    Unsigned32,
    Counter32,
    Counter64
        FROM SNMPv2-SMI
    MODULE-COMPLIANCE,
    OBJECT-GROUP
        FROM SNMPv2-CONF
    SnmpAdminString
        FROM SNMP-FRAMEWORK-MIB
    VlanIndex
        FROM Q-BRIDGE-MIB
    ifIndex
        FROM IF-MIB
    entPhysicalIndex
        FROM ENTITY-MIB
    ciscoMgmt
        FROM CISCO-SMI;


ciscoSwitchStatsMIB MODULE-IDENTITY
    LAST-UPDATED    "200910300000Z"
    ORGANIZATION    "Cisco Systems, Inc."
    CONTACT-INFO
            "Cisco Systems
            Customer Service

            Postal: 170 W Tasman Drive
            San Jose, CA 95134
            USA

            Tel: +1 800 553-NETS

            E-mail: cs-lan-switch-snmp@cisco.com"
    DESCRIPTION
        "The MIB module provides management information for
        configuration and monitoring of traffic statistics 
        on Cisco's switching devices."
    REVISION        "200910300000Z"
    DESCRIPTION
        "Initial version of this MIB module."
    ::= { ciscoMgmt 652 }


ciscoSwitchStatsMIBNotifs  OBJECT IDENTIFIER
    ::= { ciscoSwitchStatsMIB 0 }

ciscoSwitchStatsMIBObjects  OBJECT IDENTIFIER
    ::= { ciscoSwitchStatsMIB 1 }

ciscoSwitchStatsMIBConform  OBJECT IDENTIFIER
    ::= { ciscoSwitchStatsMIB 2 }

csstConfigurableStats  OBJECT IDENTIFIER
    ::= { ciscoSwitchStatsMIBObjects 1 }

csstVlanStats  OBJECT IDENTIFIER
    ::= { ciscoSwitchStatsMIBObjects 2 }

csstSwitchTrafficStats OBJECT IDENTIFIER
    ::= { ciscoSwitchStatsMIBObjects 3 }

-- The configurable statistics group

csstConfigStatsOptionTable OBJECT-TYPE
    SYNTAX          SEQUENCE OF CsstConfigStatsOptionEntry 
    MAX-ACCESS      not-accessible
    STATUS          current
    DESCRIPTION
        "This table contains a list of network traffic statistics
        options capable to be configured in csstConfigStatsMap 
        for the statistics collection by the device."
    ::= { csstConfigurableStats 1 }

csstConfigStatsOptionEntry OBJECT-TYPE
    SYNTAX          CsstConfigStatsOptionEntry
    MAX-ACCESS      not-accessible
    STATUS          current
    DESCRIPTION
        "Each entry contains statistics information for a
        specific traffic statistics option."
    INDEX           { csstConfigStatsOptionIndex } 
    ::= { csstConfigStatsOptionTable 1 }

CsstConfigStatsOptionEntry ::= SEQUENCE {
        csstConfigStatsOptionIndex Unsigned32,
        csstConfigStatsOptionDesc  SnmpAdminString
}

csstConfigStatsOptionIndex OBJECT-TYPE
    SYNTAX          Unsigned32 (1..4294967295 )
    MAX-ACCESS      not-accessible
    STATUS          current
    DESCRIPTION
        "A unique value to indicate a specific traffic statistics
        option." 
    ::= { csstConfigStatsOptionEntry 1 }

csstConfigStatsOptionDesc OBJECT-TYPE
    SYNTAX          SnmpAdminString
    MAX-ACCESS      read-only
    STATUS          current
    DESCRIPTION
        "Indicates the description corresponding to a specific
        traffic statistics option." 
    ::= { csstConfigStatsOptionEntry 2 }
 


csstConfigStatsMapSize OBJECT-TYPE
    SYNTAX          Unsigned32
    MAX-ACCESS      read-only
    STATUS          current
    DESCRIPTION
        "Indicates the length of the csstConfigStatsMap object.
        This object value indicates the total number of traffic 
        statistics options that can be configured in 
        csstConfigStatsMap." 
    ::= { csstConfigurableStats 2 }

csstConfigStatsMap OBJECT-TYPE
    SYNTAX          OCTET STRING (SIZE  (0..256))
    MAX-ACCESS      read-write
    STATUS          current
    DESCRIPTION
        "Specifies the sequence of the traffic statistics options
        that are configured to be collected by the device.

        The length of this object is specified by the 
        csstConfigStatsMapSize object value, and the value of 
        each octet in the instance value of this object shall be 
        unique and can only be selected from the set of
        csstConfigStatsOptionIndex values currently populated
        in csstConfigStatsOptionTable.

        If a traffic statistics option is configured in this object, 
        the corresponding network traffic statistics will be collected 
        on all the applicable interfaces in this device. 

        Setting this object to a different value will trigger the 
        csstConfigStatsIfTable to be repopulated." 
    ::= { csstConfigurableStats 3 }

csstConfigStatsIfTable OBJECT-TYPE
    SYNTAX          SEQUENCE OF CsstConfigStatsIfEntry 
    MAX-ACCESS      not-accessible
    STATUS          current
    DESCRIPTION
        "This table contains information about interface traffic
        statistics, which is configured through csstConfigStatsMap, 
        for interfaces that are capable of providing such 
        information. 

        The total number of traffic statistics and the traffic 
        statistics options populated in this table will be based on 
        csstConfigStatsMapSize and csstConfigStatsMap.

        When the csstConfigStatsMap object value is changed to a
        different value, it will trigger this table to be 
        repopulated."
    ::= { csstConfigurableStats 4 }

csstConfigStatsIfEntry OBJECT-TYPE
    SYNTAX          CsstConfigStatsIfEntry
    MAX-ACCESS      not-accessible
    STATUS          current
    DESCRIPTION
        "Each entry provides traffic statistics information for
        a specific interface."
    INDEX           { ifIndex } 
    ::= { csstConfigStatsIfTable 1 }

CsstConfigStatsIfEntry ::= SEQUENCE {
        csstConfigStatsIfPackets1 Counter64,
        csstConfigStatsIfOctets1  Counter64,
        csstConfigStatsIfPackets2 Counter64,
        csstConfigStatsIfOctets2  Counter64,
        csstConfigStatsIfPackets3 Counter64,
        csstConfigStatsIfOctets3  Counter64,
        csstConfigStatsIfPackets4 Counter64,
        csstConfigStatsIfOctets4  Counter64,
        csstConfigStatsIfPackets5 Counter64,
        csstConfigStatsIfOctets5  Counter64,
        csstConfigStatsIfPackets6 Counter64,
        csstConfigStatsIfOctets6  Counter64,
        csstConfigStatsIfPackets7 Counter64,
        csstConfigStatsIfOctets7  Counter64,
        csstConfigStatsIfPackets8 Counter64,
        csstConfigStatsIfOctets8  Counter64
}

csstConfigStatsIfPackets1 OBJECT-TYPE
    SYNTAX          Counter64
    UNITS           "packets"
    MAX-ACCESS      read-only
    STATUS          current
    DESCRIPTION
        "The total number of packets counted on this interface
        for the traffic statistics option that is specified by the first 
        octet value of the csstConfigStatsMap object." 
    ::= { csstConfigStatsIfEntry 1 }

csstConfigStatsIfOctets1 OBJECT-TYPE
    SYNTAX          Counter64
    UNITS           "octets"
    MAX-ACCESS      read-only
    STATUS          current
    DESCRIPTION
        "The total number of octets counted on this interface
        for the traffic statistics option that is specified by the first 
        octet value of the csstConfigStatsMap object." 
    ::= { csstConfigStatsIfEntry 2 }

csstConfigStatsIfPackets2 OBJECT-TYPE
    SYNTAX          Counter64
    UNITS           "packets"
    MAX-ACCESS      read-only
    STATUS          current
    DESCRIPTION
        "The total number of packets counted on this interface
        for the traffic statistics option that is specified by the second 
        octet value of the csstConfigStatsMap object." 
    ::= { csstConfigStatsIfEntry 3 }

csstConfigStatsIfOctets2 OBJECT-TYPE
    SYNTAX          Counter64
    UNITS           "octets"
    MAX-ACCESS      read-only
    STATUS          current
    DESCRIPTION
        "The total number of octets counted on this interface
        for the traffic statistics option that is specified by the second 
        octet value of the csstConfigStatsMap object." 
    ::= { csstConfigStatsIfEntry 4 }

csstConfigStatsIfPackets3 OBJECT-TYPE
    SYNTAX          Counter64
    UNITS           "packets"
    MAX-ACCESS      read-only
    STATUS          current
    DESCRIPTION
        "The total number of packets counted on this interface
        for the traffic statistics option that is specified by the third 
        octet value of the csstConfigStatsMap object." 
    ::= { csstConfigStatsIfEntry 5 }

csstConfigStatsIfOctets3 OBJECT-TYPE
    SYNTAX          Counter64
    UNITS           "octets"
    MAX-ACCESS      read-only
    STATUS          current
    DESCRIPTION
        "The total number of octets counted on this interface
        for the traffic statistics option that is specified by the third 
        octet value of the csstConfigStatsMap object." 
    ::= { csstConfigStatsIfEntry 6 }

csstConfigStatsIfPackets4 OBJECT-TYPE
    SYNTAX          Counter64
    UNITS           "packets"
    MAX-ACCESS      read-only
    STATUS          current
    DESCRIPTION
        "The total number of packets counted on this interface
        for the traffic statistics option that is specified by the fourth 
        octet value of the csstConfigStatsMap object." 
    ::= { csstConfigStatsIfEntry 7 }

csstConfigStatsIfOctets4 OBJECT-TYPE
    SYNTAX          Counter64
    UNITS           "octets"
    MAX-ACCESS      read-only
    STATUS          current
    DESCRIPTION
        "The total number of octets counted on this interface
        for the traffic statistics option that is specified by the fourth 
        octet value of the csstConfigStatsMap object." 
    ::= { csstConfigStatsIfEntry 8 }

csstConfigStatsIfPackets5 OBJECT-TYPE
    SYNTAX          Counter64
    UNITS           "packets"
    MAX-ACCESS      read-only
    STATUS          current
    DESCRIPTION
        "The total number of packets counted on this interface
        for the traffic statistics option that is specified by the fifth 
        octet value of the csstConfigStatsMap object." 
    ::= { csstConfigStatsIfEntry 9 }

csstConfigStatsIfOctets5 OBJECT-TYPE
    SYNTAX          Counter64
    UNITS           "octets"
    MAX-ACCESS      read-only
    STATUS          current
    DESCRIPTION
        "The total number of octets counted on this interface
        for the traffic statistics option that is specified by the fifth 
        octet value of the csstConfigStatsMap object." 
    ::= { csstConfigStatsIfEntry 10 }

csstConfigStatsIfPackets6 OBJECT-TYPE
    SYNTAX          Counter64
    UNITS           "packets"
    MAX-ACCESS      read-only
    STATUS          current
    DESCRIPTION
        "The total number of packets counted on this interface
        for the traffic statistics option that is specified by the sixth 
        octet value of the csstConfigStatsMap object." 
    ::= { csstConfigStatsIfEntry 11 }

csstConfigStatsIfOctets6 OBJECT-TYPE
    SYNTAX          Counter64
    UNITS           "octets"
    MAX-ACCESS      read-only
    STATUS          current
    DESCRIPTION
        "The total number of octets counted on this interface
        for the traffic statistics option that is specified by the sixth 
        octet value of the csstConfigStatsMap object." 
    ::= { csstConfigStatsIfEntry 12 }

csstConfigStatsIfPackets7 OBJECT-TYPE
    SYNTAX          Counter64
    UNITS           "packets"
    MAX-ACCESS      read-only
    STATUS          current
    DESCRIPTION
        "The total number of packets counted on this interface
        for the traffic statistics option that is specified by the seventh 
        octet value of the csstConfigStatsMap object." 
    ::= { csstConfigStatsIfEntry 13 }

csstConfigStatsIfOctets7 OBJECT-TYPE
    SYNTAX          Counter64
    UNITS           "octets"
    MAX-ACCESS      read-only
    STATUS          current
    DESCRIPTION
        "The total number of octets counted on this interface
        for the traffic statistics option that is specified by the seventh 
        octet value of the csstConfigStatsMap object." 
    ::= { csstConfigStatsIfEntry 14 }

csstConfigStatsIfPackets8 OBJECT-TYPE
    SYNTAX          Counter64
    UNITS           "packets"
    MAX-ACCESS      read-only
    STATUS          current
    DESCRIPTION
        "The total number of packets counted on this interface
        for the traffic statistics option that is specified by the eighth 
        octet value of the csstConfigStatsMap object." 
    ::= { csstConfigStatsIfEntry 15 }

csstConfigStatsIfOctets8 OBJECT-TYPE
    SYNTAX          Counter64
    UNITS           "octets"
    MAX-ACCESS      read-only
    STATUS          current
    DESCRIPTION
        "The total number of octets counted on this interface
        for the traffic statistics option that is specified by the eighth 
        octet value of the csstConfigStatsMap object." 
    ::= { csstConfigStatsIfEntry 16 }
 

-- The VLAN statistics group

csstVlanStatsTable OBJECT-TYPE
    SYNTAX          SEQUENCE OF CsstVlanStatsEntry 
    MAX-ACCESS      not-accessible
    STATUS          current
    DESCRIPTION
        "This table provides specific traffic statistics
        information for VLANs that are capable of providing 
        such statistics information."
    ::= { csstVlanStats 1 }

csstVlanStatsEntry OBJECT-TYPE
    SYNTAX          CsstVlanStatsEntry
    MAX-ACCESS      not-accessible
    STATUS          current
    DESCRIPTION
        "An entry providing traffic statistics information collected
        for a specific VLAN"
    INDEX           { csstVlanIndex } 
    ::= { csstVlanStatsTable 1 }

CsstVlanStatsEntry ::= SEQUENCE {
        csstVlanIndex                    VlanIndex,
        csstVlanKnownBridgedUcastPkts    Counter64,
        csstVlanKnownBridgedUcastOctets  Counter64,
        csstVlanKnownBridgedNUcastPkts   Counter64,
        csstVlanKnownBridgedNUcastOctets Counter64
}

csstVlanIndex OBJECT-TYPE
    SYNTAX          VlanIndex
    MAX-ACCESS      not-accessible
    STATUS          current
    DESCRIPTION
        "Indicates the VLAN number." 
    ::= { csstVlanStatsEntry 1 }

csstVlanKnownBridgedUcastPkts OBJECT-TYPE
    SYNTAX          Counter64
    UNITS           "packets"
    MAX-ACCESS      read-only
    STATUS          current
    DESCRIPTION
        "The total number of bridged unicast packets,
        counted on this VLAN, with known MAC (Media 
        Access Control) DA (destination address)." 
    ::= { csstVlanStatsEntry 2 }

csstVlanKnownBridgedUcastOctets OBJECT-TYPE
    SYNTAX          Counter64
    UNITS           "octets"
    MAX-ACCESS      read-only
    STATUS          current
    DESCRIPTION
        "The total number of octets for the bridged unicast
        packets, counted on this VLAN, with known MAC DA." 
    ::= { csstVlanStatsEntry 3 }

csstVlanKnownBridgedNUcastPkts OBJECT-TYPE
    SYNTAX          Counter64
    UNITS           "packets"
    MAX-ACCESS      read-only
    STATUS          current
    DESCRIPTION
        "The total number of bridged non-unicast packets,
        counted on this VLAN,  with known MAC DA." 
    ::= { csstVlanStatsEntry 4 }

csstVlanKnownBridgedNUcastOctets OBJECT-TYPE
    SYNTAX          Counter64
    UNITS           "octets"
    MAX-ACCESS      read-only
    STATUS          current
    DESCRIPTION
        "The total number of octets for the bridged
        non-unicast packets, counted on this VLAN, 
        with known MAC DA." 
    ::= { csstVlanStatsEntry 5 }


-- The Switch statistics table

csstSwitchStatsTable OBJECT-TYPE
    SYNTAX          SEQUENCE OF CsstSwitchStatsEntry
    MAX-ACCESS      not-accessible
    STATUS          current
    DESCRIPTION
        "This table provides specific L2/L3 traffic statistics
        information of switching engines." 
    ::= { csstSwitchTrafficStats 1 }

csstSwitchStatsEntry OBJECT-TYPE
    SYNTAX          CsstSwitchStatsEntry
    MAX-ACCESS      not-accessible
    STATUS          current
    DESCRIPTION
        "An entry providing L2/L3 traffic statistics information 
        maintained by a particular switching engine entity 
        (identified by entPhysicalIndex). 
 
 
        An entry of this table is created if a switch engine with 
        these L2/L3 traffic statistics is detected by the 
        managed system. 
 
 
        An entry of this table is deleted if the 
        removal of the switching engine itself."
    INDEX           { entPhysicalIndex }
    ::= { csstSwitchStatsTable 1 }

CsstSwitchStatsEntry ::= SEQUENCE {
        csstL2TotalBridgedPkts           Counter32,
        csstL3FibSwitchedIpv4UcastPkts   Counter32,
        csstL3FibSwitchedIpv6UcastPkts   Counter32,
        csstL3FibSwitchedEoMplsPkts      Counter32,
        csstL3FibSwitchedMplsPkts        Counter32,
        csstL3TotalMulticastPkts         Counter32, 
        csstL3IgmpMldPkts                Counter32,
        csstL3Ipv4MulticastPkts          Counter32, 
        csstL3Ipv6MulticastPkts          Counter32,
        csstL3MulticastLeakPkts          Counter32,
        csstL3InputAclRoutedPkts         Counter32,
        csstL3OutputAclRoutedPkts        Counter32,
        csstL3InputNetflowSwitchedPkts   Counter32,
        csstL3OutputNetflowSwitchedPkts  Counter32,
        csstL3InExceptionRedirectPkts    Counter32,
        csstL3OutExceptionRedirectPkts   Counter32
}

csstL2TotalBridgedPkts OBJECT-TYPE
    SYNTAX          Counter32
    UNITS           "packets"
    MAX-ACCESS      read-only
    STATUS          current
    DESCRIPTION
        "The total number of bridged packets on this
        switching engine."
    ::= { csstSwitchStatsEntry 1 }

csstL3FibSwitchedIpv4UcastPkts OBJECT-TYPE
    SYNTAX          Counter32
    UNITS           "packets"
    MAX-ACCESS      read-only
    STATUS          current
    DESCRIPTION
        "The total number of IPv4 Unicast packets,
        switched by the FIB (Forwarding Information Base)
        on this switching engine."
    ::= { csstSwitchStatsEntry 2 }

csstL3FibSwitchedIpv6UcastPkts OBJECT-TYPE
    SYNTAX          Counter32
    UNITS           "packets"
    MAX-ACCESS      read-only
    STATUS          current
    DESCRIPTION
        "The total number of IPv6 Unicast packets,
        switched by the FIB (Forwarding Information Base)
        on this switching engine."
    ::= { csstSwitchStatsEntry 3 }

csstL3FibSwitchedEoMplsPkts OBJECT-TYPE
    SYNTAX          Counter32
    UNITS           "packets"
    MAX-ACCESS      read-only
    STATUS          current
    DESCRIPTION
        "The total number of EoMPLS (Ethernet over MPLS)
        packets switched by the FIB Forwarding 
        Information Base) on this switching engine."
    ::= { csstSwitchStatsEntry 4 }

csstL3FibSwitchedMplsPkts OBJECT-TYPE
    SYNTAX          Counter32
    UNITS           "packets"
    MAX-ACCESS      read-only
    STATUS          current
    DESCRIPTION
        "The total number of MPLS (Multiprotocol Label 
        Switching) packets switched by the FIB Forwarding
        Information Base) on this switching engine."
    ::= { csstSwitchStatsEntry 5 }

csstL3TotalMulticastPkts OBJECT-TYPE
    SYNTAX          Counter32
    UNITS           "packets"
    MAX-ACCESS      read-only
    STATUS          current
    DESCRIPTION
        "The total number of Multicast packets switched
        at Layer3 by this switching engine."
    ::= { csstSwitchStatsEntry 6 }

csstL3IgmpMldPkts OBJECT-TYPE
    SYNTAX          Counter32
    UNITS           "packets"
    MAX-ACCESS      read-only
    STATUS          current
    DESCRIPTION
        "The total number of IGMP MLD (Multicast Listener 
        Discovery) packets switched by this switching engine."
    ::= { csstSwitchStatsEntry 7 }

csstL3Ipv4MulticastPkts OBJECT-TYPE
    SYNTAX          Counter32
    UNITS           "packets"
    MAX-ACCESS      read-only
    STATUS          current
    DESCRIPTION
        "The total number of IPv4 Multicast packets
        switched at Layer3 by this switching engine."
    ::= { csstSwitchStatsEntry 8 }
    
csstL3Ipv6MulticastPkts OBJECT-TYPE
    SYNTAX          Counter32
    UNITS           "packets"
    MAX-ACCESS      read-only
    STATUS          current
    DESCRIPTION
        "The total number of IPv6 Multicast packets
        switched at Layer3 by this switching engine."
    ::= { csstSwitchStatsEntry 9 }

csstL3MulticastLeakPkts OBJECT-TYPE
    SYNTAX          Counter32
    UNITS           "packets"
    MAX-ACCESS      read-only
    STATUS          current
    DESCRIPTION
        "The total number of Multicast Reverse Path Forwarding 
        (RPF) check failed packets which are leaked to the
        CPU for processing."
    ::= { csstSwitchStatsEntry 10 }

csstL3InputAclRoutedPkts OBJECT-TYPE
    SYNTAX          Counter32
    UNITS           "packets"
    MAX-ACCESS      read-only
    STATUS          current
    DESCRIPTION
        "The total number of Input ACL Routed packets."
    ::= { csstSwitchStatsEntry 11 }

csstL3OutputAclRoutedPkts OBJECT-TYPE
    SYNTAX          Counter32
    UNITS           "packets"
    MAX-ACCESS      read-only
    STATUS          current
    DESCRIPTION
        "The total number of Output ACL Routed packets."
    ::= { csstSwitchStatsEntry 12 }

csstL3InputNetflowSwitchedPkts OBJECT-TYPE
    SYNTAX          Counter32
    UNITS           "packets"
    MAX-ACCESS      read-only
    STATUS          current
    DESCRIPTION
        "The total number of Input Netflow Switched packets."
    ::= { csstSwitchStatsEntry 13 }

csstL3OutputNetflowSwitchedPkts OBJECT-TYPE
    SYNTAX          Counter32
    UNITS           "packets"
    MAX-ACCESS      read-only
    STATUS          current
    DESCRIPTION
        "The total number of Output Netflow Switched packets." 
    ::= { csstSwitchStatsEntry 14 }

csstL3InExceptionRedirectPkts OBJECT-TYPE
    SYNTAX          Counter32
    UNITS           "packets"
    MAX-ACCESS      read-only
    STATUS          current
    DESCRIPTION
        "The total number of Input packets which are redirected
        to the CPU due to an exception."
    ::= { csstSwitchStatsEntry 15 }

csstL3OutExceptionRedirectPkts OBJECT-TYPE
    SYNTAX          Counter32
    UNITS           "packets"
    MAX-ACCESS      read-only
    STATUS          current
    DESCRIPTION
        "The total number of Output packets which are redirected
        to the CPU due to an exception."
    ::= { csstSwitchStatsEntry 16 }


-- Conformance information

csstSwitchStatsMIBCompliances  OBJECT IDENTIFIER
    ::= { ciscoSwitchStatsMIBConform 1 }

csstSwitchStatsMIBGroups  OBJECT IDENTIFIER
    ::= { ciscoSwitchStatsMIBConform 2 }


-- Compliance statements

csstSwitchStatsMIBCompliance MODULE-COMPLIANCE
    STATUS          current
    DESCRIPTION
        "The compliance statement for CISCO-SWITCH-STATS-MIB."
    MODULE          -- this module
    GROUP           ciscoSwitchStatsConfOptionGroup
    DESCRIPTION
        "This group is mandatory for devices that provide
        traffic statistics options for configuration."

    GROUP           ciscoSwitchStatsConfMapGroup
    DESCRIPTION
        "This group is mandatory for devices that provide
        configuration of traffic statistics."

    GROUP           ciscoSwitchStatsConfIfGroup
    DESCRIPTION
        "This group is mandatory for devices that support
        configurable interface traffic statistics collection."

    GROUP           ciscoSwitchStatsVlanGroup
    DESCRIPTION
        "This group is mandatory for devices that support
        VLAN traffic statistics."

    GROUP           ciscoSwitchStatsL2Group
    DESCRIPTION
        "This group is mandatory for devices that support
        L2 Total Bridged Packets statistics."

    GROUP           ciscoSwitchStatsL3Group
    DESCRIPTION
        "This group is mandatory for devices that support
        L3 traffic statistics." 

    OBJECT          csstConfigStatsMap
    MIN-ACCESS      read-only
    DESCRIPTION
        "Write access is not required."
    ::= { csstSwitchStatsMIBCompliances 1 }

-- Units of Conformance

ciscoSwitchStatsConfOptionGroup OBJECT-GROUP
    OBJECTS         { csstConfigStatsOptionDesc }
    STATUS          current
    DESCRIPTION
        "A collection of objects providing information
        for optional traffic statistics for configuration."
    ::= { csstSwitchStatsMIBGroups 1 }

ciscoSwitchStatsConfMapGroup OBJECT-GROUP
    OBJECTS         {
                        csstConfigStatsMapSize,
                        csstConfigStatsMap
                    }
    STATUS          current
    DESCRIPTION
        "A collection of objects providing information
        for configuration of traffic statistics on 
        this device."
    ::= { csstSwitchStatsMIBGroups 2 }

ciscoSwitchStatsConfIfGroup OBJECT-GROUP
    OBJECTS         {
                        csstConfigStatsIfPackets1,
                        csstConfigStatsIfOctets1,
                        csstConfigStatsIfPackets2,
                        csstConfigStatsIfOctets2,
                        csstConfigStatsIfPackets3,
                        csstConfigStatsIfOctets3,
                        csstConfigStatsIfPackets4,
                        csstConfigStatsIfOctets4,
                        csstConfigStatsIfPackets5,
                        csstConfigStatsIfOctets5,
                        csstConfigStatsIfPackets6,
                        csstConfigStatsIfOctets6,
                        csstConfigStatsIfPackets7,
                        csstConfigStatsIfOctets7,
                        csstConfigStatsIfPackets8,
                        csstConfigStatsIfOctets8
                    }
    STATUS          current
    DESCRIPTION
        "A collection of objects providing information
        for configured statistics for interfaces that are 
        capable of providing such information."
    ::= { csstSwitchStatsMIBGroups 3 }

ciscoSwitchStatsVlanGroup OBJECT-GROUP
    OBJECTS         {
                        csstVlanKnownBridgedUcastPkts,
                        csstVlanKnownBridgedUcastOctets,
                        csstVlanKnownBridgedNUcastPkts,
                        csstVlanKnownBridgedNUcastOctets
                    }
    STATUS          current
    DESCRIPTION
        "A collection of objects providing information
        for traffic statistics for VLANs that are
        capable of providing such information."
    ::= { csstSwitchStatsMIBGroups 4 }

ciscoSwitchStatsL2Group OBJECT-GROUP
    OBJECTS         {
                        csstL2TotalBridgedPkts
                    }
    STATUS          current
    DESCRIPTION
        "A collection of objects providing information
        for L2 Total Bridged Packets for switching engines."
    ::= { csstSwitchStatsMIBGroups 5 }

ciscoSwitchStatsL3Group OBJECT-GROUP
    OBJECTS         {
                        csstL3FibSwitchedIpv4UcastPkts,
                        csstL3FibSwitchedIpv6UcastPkts, 
                        csstL3FibSwitchedEoMplsPkts,    
                        csstL3FibSwitchedMplsPkts,      
                        csstL3TotalMulticastPkts,       
                        csstL3IgmpMldPkts,              
                        csstL3Ipv4MulticastPkts,        
                        csstL3Ipv6MulticastPkts,        
                        csstL3MulticastLeakPkts,        
                        csstL3InputAclRoutedPkts,       
                        csstL3OutputAclRoutedPkts,      
                        csstL3InputNetflowSwitchedPkts, 
                        csstL3OutputNetflowSwitchedPkts,
                        csstL3InExceptionRedirectPkts,  
                        csstL3OutExceptionRedirectPkts
                    }
    STATUS          current
    DESCRIPTION
        "A collection of objects providing information
        for L3 traffic statistics for switching engines."
    ::= { csstSwitchStatsMIBGroups 6 }

END
