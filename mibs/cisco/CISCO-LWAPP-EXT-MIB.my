-- *******************************************************************
-- CISCO-LWAPP-EXT-MIB.my
-- May 2013
--
-- Copyright (c) 2005-2006, 2012-13 by Cisco Systems, Inc.
-- All rights reserved.
-- *******************************************************************

CISCO-LWAPP-EXT-MIB DEFINITIONS ::= BEGIN

IMPORTS
    MODULE-IDENTITY,
    OBJECT-TYPE,
    Unsigned32,
    Counter32
        FROM SNMPv2-SMI
    MODULE-COMPLIANCE,
    OBJECT-GROUP,
    NOTIFICATION-GROUP
        FROM SNMPv2-CONF
    DisplayString, TruthValue,
    RowStatus
        FROM SNMPv2-TC
    ciscoMgmt
        FROM CISCO-SMI
    InetAddressType, InetAddress
            FROM INET-ADDRESS-MIB
    SnmpAdminString
            FROM SNMP-FRAMEWORK-MIB
    ifIndex
            FROM IF-MIB
    cLApSysMacAddress,
    cLApDot11IfSlotId,
    cLApIfSmtDot11Bssid,
    cLApLastRebootReason,
    cLApDataEncryptionStatus,
    cLApName,
    cLApIfSmtDot11Bssid,
    cLApEthernetIfSlotId,
    cLApDot11RadioCurrentChannel,
    cLApRSSI,
    cLApDot11RadioMACAddress,
    cLApDot11RadioChannelNumber
            FROM CISCO-LWAPP-AP-MIB
    cLWlanIndex,
    cLWlanSsid
            FROM CISCO-LWAPP-WLAN-MIB
    cldHtDot11nBand
            FROM CISCO-LWAPP-DOT11-MIB
    cldcClientMacAddress,
    cldcApMacAddress,
    cldcClientSSID 
            FROM CISCO-LWAPP-DOT11-CLIENT-MIB
    cLRFProfileName
            FROM CISCO-LWAPP-RF-MIB
    bsnDot11EssSecurityAuthType
            FROM AIRESPACE-WIRELESS-MIB
    IANAifType                          
            FROM IANAifType-MIB
    clsPortDot1dBasePort
            FROM CISCO-LWAPP-SYS-MIB;

-- ********************************************************************
-- *  MODULE IDENTITY
-- ********************************************************************

ciscoLwappExtMIB MODULE-IDENTITY
    LAST-UPDATED    "201207170000Z"
    ORGANIZATION    "Cisco Systems Inc."
    CONTACT-INFO
            "Cisco Systems,
            Customer Service

            Postal: 170 West Tasman Drive
            San Jose, CA  95134
            USA

            Tel: +1 800 553-NETS

            Email: cs-wnbu-snmp@cisco.com"
    DESCRIPTION
            "This MIB is intended to be implemented on all those
            devices operating as Central Controllers (CC) that
            terminate the Light Weight Access Point Protocol
            tunnel from Light-weight LWAPP Access Points.

            This MIB provides configuration and status information
            about the Web Ext Server on the controller.

            Particularly this mib covers the portal server for the wireless
            controllers.

                                    GLOSSARY

            Access Point ( AP )

            An entity that contains an 802.11 medium access control
            ( MAC ) and physical layer ( PHY ) interface and provides
            access to the distribution services via the wireless medium
            for associated clients.

            Light Weight Access Point Protocol ( LWAPP )

            This is a generic protocol that defines the communication
            between the Access Points and the Central Controller.

            REFERENCE

            [1] Part 11 Wireless LAN Medium Access Control ( MAC ) and
            Physical Layer ( PHY ) Specifications.
            "
    REVISION        "201305140000Z"
    DESCRIPTION
        "Added for CMCC related MIBs."
          ::= { ciscoMgmt 9998 }


ciscoLwappExtMIBNotifs  OBJECT IDENTIFIER
    ::= { ciscoLwappExtMIB 0 }

ciscoLwappExtMIBObjects  OBJECT IDENTIFIER
    ::= { ciscoLwappExtMIB 1 }

ciscoLwappExtMIBConform  OBJECT IDENTIFIER
    ::= { ciscoLwappExtMIB 2 }

ciscoLwappExtMIBNotifObjects OBJECT IDENTIFIER
    ::= { ciscoLwappExtMIB 3 }

ciscoLwappExtConfig  OBJECT IDENTIFIER
    ::= { ciscoLwappExtMIBObjects 1 }

ciscoLwappExtStats OBJECT IDENTIFIER
    ::= { ciscoLwappExtMIBObjects 2 }

CLSwitch ::= TEXTUAL-CONVENTION
    STATUS          current 
    DESCRIPTION
        "This textual convention contains the state of a switch."
    SYNTAX      INTEGER  {
                            off(0),
                            on(1)
                         }
CLExtApDisassocReason ::= TEXTUAL-CONVENTION
    STATUS     current
    DESCRIPTION
        "This textual convention defines the possible reasons 
        for an AP's disassociate to a controller.

        The semantics are as follows:  

        unknown - The reason for the AP disassociated to controller 
        is unknown.

        missedEchoFromAp - The reason is controller does not receive 
        the echo packets from AP.

        wtpRest - The reason for AP not being able to 
        associate is wtp rest.

        msgTimerExpiry - the reason is the message timer expiry.

        heartBeatExpiry - the reason is the heart beat expiry." 

    SYNTAX     INTEGER {
            unknown(1),
            missedEchoFromAp(2),
            wtpReset(3),
            msgTimerExpiry(4),
            heartBeatExpiry(5)
    }
--********************************************************************
-- *  Extension System Information
--********************************************************************
clExtSys OBJECT IDENTIFIER ::= { ciscoLwappExtConfig 1 }
  
clExtNMHeartBeatEnable       OBJECT-TYPE
    SYNTAX                 CLSwitch
    MAX-ACCESS             read-write
    STATUS                 current
    DESCRIPTION
        "This object specifies whether heart beat trap to network
        manager is enabled or disabled. If the value is on the
        Network Manager Heart Beat feature is Enabled otherwise
        Disabled."
    DEFVAL { off }
    ::= { clExtSys 1 }

clExtAgentResetSystem OBJECT-TYPE
    SYNTAX      INTEGER {
            disable(0),
            enable(1)
    }
    MAX-ACCESS  read-write
    STATUS      current
    DESCRIPTION
        "reset the switch"
    ::= { clExtSys 2 }

clExtAgentClearConfig OBJECT-TYPE
    SYNTAX      INTEGER {
            disable(0),
            enable(2)
    }
    MAX-ACCESS  read-write
    STATUS      current
    DESCRIPTION
        "Clear configuration to factory defaults"
    ::= { clExtSys 3 }

clExtSystemCurrentTime OBJECT-TYPE
    SYNTAX DisplayString (SIZE(0..32))
    MAX-ACCESS read-write
    STATUS current
    DESCRIPTION
        "Use this attribute to change the System time on the Switch.
        Specify the new time in this Format yyyy-mm-dd hh24:mi:ss.
        For example, 2013-05-01 18:00:00."
    ::= { clExtSys 4 }

--********************************************************************
    -- clsExtPortModeConfigTable
--********************************************************************
clExtPortModeConfigTable OBJECT-TYPE
    SYNTAX      SEQUENCE OF ClExtPortModeConfigEntry
    MAX-ACCESS  not-accessible
    STATUS      current
    DESCRIPTION
                "This table contains the entries for physical port related status"
    ::= { clExtSys 5 }

clExtPortModeConfigEntry OBJECT-TYPE
    SYNTAX      ClExtPortModeConfigEntry
    MAX-ACCESS  not-accessible
    STATUS      current
    DESCRIPTION
                "This entry contains the Switch's physical port phyical mode related attribues"
    INDEX       { clsPortDot1dBasePort }
    ::= { clExtPortModeConfigTable 1 }

ClExtPortModeConfigEntry ::= SEQUENCE {
    clExtPortOperStatus                INTEGER
    }

clExtPortOperStatus OBJECT-TYPE
    SYNTAX      INTEGER {
                  up(1),
                  down(2),
                  testing(3),
                  admindown(4)
               }
    MAX-ACCESS  read-only
    STATUS      current
    DESCRIPTION
                "The switch's Port Operation Status.This
                 is the current actual status."
    ::= { clExtPortModeConfigEntry 1 }

clExtSysMaxNewConnectionPerSecond OBJECT-TYPE
    SYNTAX      Integer32
    MAX-ACCESS  read-only
    STATUS      current
    DESCRIPTION
         "This object specifies maximum number of new client count connect to
         the controller  per-second, it's a performance data and associated 
         with the platform"
    ::= { clExtSys 6 }

--********************************************************************
-- *  Extension Interface Information
--********************************************************************
clExtIf OBJECT IDENTIFIER ::= { ciscoLwappExtConfig 2 }

clExtIfTable OBJECT-TYPE
    SYNTAX      SEQUENCE OF ClExtIfEntry
    MAX-ACCESS  not-accessible
    STATUS      current
    DESCRIPTION
        "A list of interface entries.  The number of entries
        is given by the value of ifNumber."
    ::= { clExtIf 1 }

clExtIfEntry OBJECT-TYPE
    SYNTAX      ClExtIfEntry
    MAX-ACCESS  not-accessible
    STATUS      current
    DESCRIPTION
        "An entry containing management information applicable
        to a particular interface."
    INDEX   { ifIndex }
    ::= { clExtIfTable 1 }

ClExtIfEntry ::=
    SEQUENCE {
        clExtIfSpeed                 Gauge32,
        clExtIfSinceLastChange       TimeTicks
    }

clExtIfSpeed OBJECT-TYPE
    SYNTAX      Gauge32
    MAX-ACCESS  read-only
    STATUS      current
    DESCRIPTION
        "An estimate of the interface's current bandwidth in
        million bits per second.  For interfaces which do not vary in
        bandwidth or for those where no accurate estimation
        can be made, this object should contain the nominal
        bandwidth.  If the bandwidth of the interface is
        greater than the maximum value reportable by this
        object then this object should report its maximum
        value (4,294,967,295 bps) and ifHighSpeed must be used to
        report the interface's speed.  For a sub-layer which
        has no concept of bandwidth, this object should be
        zero."
    ::= { clExtIfEntry 1 }

clExtIfSinceLastChange OBJECT-TYPE
    SYNTAX      TimeTicks
    MAX-ACCESS  read-only
    STATUS      current
    DESCRIPTION
        "The value of time duration since the time the interface
        entered its current operational state.  If the current
        time is prior to the last updating of the local network
        management subsystem, then this object contains a zero value."
    ::= { clExtIfEntry 2 }

--********************************************************************
-- *  Extension AP Information
--********************************************************************
clExtAp OBJECT IDENTIFIER ::= { ciscoLwappExtConfig 3 }
clExtApTable OBJECT-TYPE
    SYNTAX     SEQUENCE OF ClExtApEntry
    MAX-ACCESS not-accessible
    STATUS     current
    DESCRIPTION
        "This table represents the information about the
        802.11 LWAPP Access Points that have joined the
        controller.

        LWAPP APs exchange configuration messages with the
        controller and get the required configuration for
        their 802.11 related operations, after they join the
        controller. "
    ::= { clExtAp 1 }

clExtApEntry OBJECT-TYPE
    SYNTAX     ClExtApEntry
    MAX-ACCESS not-accessible
    STATUS     current
    DESCRIPTION
        "Each entry in this table provides information about
        one 802.11 LWAPP Access Point that has joined the
        controller.

        Entries are removed when the APs lose their
        association with the controller due to loss
        of communication. "
    INDEX   { cLApSysMacAddress }
    ::= { clExtApTable 1 }

ClExtApEntry ::= SEQUENCE {
        clExtApRealTimeStatsModeEnabled       CLSwitch,
        clExtApMonitorMode                    INTEGER,
        clExtApSysManufacture                 SnmpAdminString,
        clExtApSysSoftwareName                SnmpAdminString,
        clExtApSysSoftwareVersion             SnmpAdminString,
        clExtApSysSoftwareVendor              SnmpAdminString,
        clExtApQosMinBandwidth                Integer32,
        clExtApTotalPhyInterfaceCount         Unsigned32,
        clExtApName                           SnmpAdminString
    }

clExtApRealTimeStatsModeEnabled OBJECT-TYPE
    SYNTAX      CLSwitch
    MAX-ACCESS  read-write
    STATUS      current
    DESCRIPTION
        "This object specifies whether currently stats mode is 'realtime'.
         There are two stats-mode, realtime and normal, that specifies the
         stats-timer range to be 10-180 sec and 2-5 sec each. Set to on
         if current mode is realtime."
    DEFVAL  { off }
    ::= { clExtApEntry 1 }

clExtApMonitorMode OBJECT-TYPE
    SYNTAX INTEGER {
               normal(0),
               monitor(1),
               semimonitor(2)
           }
    MAX-ACCESS read-write
    STATUS current
    DESCRIPTION
        "This object specifies the monitor mode of AP. 
        monitor : no client can connect. 
        normal : no monitor function at all.
        semimonitor : AP can monitor it's working radio while clients connected.
        The mapping between clExtApMonitorMode and CISCO existing function is as the belows:
        clExtApMonitorMode          Cisco Exist Value
        LOCAL                       AP MODE: LOCAL + ROGUE DETECTION : disable
        MONITOR                     AP MODE: MONITOR
        SEMIMONITOR                 AP MODE: LOCAL + ROGUE DETECTION : enable
        "
    ::= { clExtApEntry 2  }

clExtApSysManufacture     OBJECT-TYPE
    SYNTAX      SnmpAdminString
    MAX-ACCESS  read-only
    STATUS      current
    DESCRIPTION
        "This object specifies the AP manufacture."
    ::= { clExtApEntry 3 }

clExtApSysSoftwareName    OBJECT-TYPE
    SYNTAX      SnmpAdminString
    MAX-ACCESS  read-only
    STATUS      current
    DESCRIPTION
        "This object specifies the AP software name."
    ::= { clExtApEntry 4 }

clExtApSysSoftwareVersion OBJECT-TYPE
    SYNTAX      SnmpAdminString
    MAX-ACCESS  read-only
    STATUS      current
    DESCRIPTION
        "This object specifies the AP software version."
    ::= { clExtApEntry 5 }

clExtApSysSoftwareVendor  OBJECT-TYPE
    SYNTAX      SnmpAdminString
    MAX-ACCESS  read-only
    STATUS      current
    DESCRIPTION
        "This object specifies the AP software vendor."
    ::= { clExtApEntry 6 }

clExtApQosMinBandwidth OBJECT-TYPE
    SYNTAX      Integer32
    MAX-ACCESS  read-write
    STATUS      current
    DESCRIPTION
        "This object specifies the minimum bandwidth for QOS on the AP.  
        It is measured by Mbps."
    DEFVAL  { 80 }
    ::= { clExtApEntry 7 }

clExtApTotalPhyInterfaceCount OBJECT-TYPE
    SYNTAX      Unsigned32
    MAX-ACCESS  read-only
    STATUS      current
    DESCRIPTION
            "This object specifies the total wired physical interface
            count for the Access Points that have joined the controller."
    ::= { clExtApEntry 8 }

clExtApName OBJECT-TYPE
    SYNTAX      SnmpAdminString
    MAX-ACCESS  read-write
    STATUS      current
    DESCRIPTION
       "This object represents the administrative name 
        assigned to the AP by the user. If an AP is not configured, 
        its factory default name will be ap:<last three byte 
        of MACAddress> eg. ap:af:12:be." 
    ::= { clExtApEntry 9 }

clExtApDot11IfTable OBJECT-TYPE
    SYNTAX SEQUENCE OF ClExtApDot11IfEntry
    MAX-ACCESS not-accessible
    STATUS     current
    DESCRIPTION
        "This table represents the information about the
        basic functional parameters corresponding to
        the dot11 interfaces of the APs that have joined
        the controller. "
    ::= { clExtAp 2 }

clExtApDot11IfEntry OBJECT-TYPE
    SYNTAX     ClExtApDot11IfEntry
    MAX-ACCESS not-accessible
    STATUS     current
    DESCRIPTION
        "An entry in this table represents the 802.11
        functional parameters of the dot11 interface of
        an AP that has joined the controller.

        Entries are added when the APs associate to this
        controller and deleted when they lose their
        association. " 
    INDEX   {
            cLApSysMacAddress,
            cLApDot11IfSlotId
    } 
    ::= { clExtApDot11IfTable 1 }

ClExtApDot11IfEntry ::= SEQUENCE {
                clExtAp11nChannelBandwidth    INTEGER,
                clExtApDot11IfIANAType        IANAifType,
                clExtApIfPhyChannelAssignment CLSwitch,
                clExtApDot11RadioStatsRxByteCount Counter64,
                clExtApDot11RadioStatsTxByteCount Counter64,
                clExtApDot11WirelessModeSupported  INTEGER,
                clExtApDot11IfAdminStatus     INTEGER,
                clExtApDot11IfOperStatus      INTEGER,
                cLExtAPDot11IfRTSThreshold    Integer32 
        }

clExtAp11nChannelBandwidth OBJECT-TYPE
    SYNTAX     INTEGER {
            forty(1),
            twenty(2)
    }
    UNITS  "mhz"
    MAX-ACCESS read-write
    STATUS current
    DESCRIPTION
        "This object indicates the channel bandwidth for
        this AP. This applies to 802.11n networks only."
    ::= { clExtApDot11IfEntry 1 }

clExtApDot11IfIANAType OBJECT-TYPE
    SYNTAX      IANAifType
    MAX-ACCESS  read-only
    STATUS      current
    DESCRIPTION
       "This object represents the type of this interface.
        The value of the type is defined by IANA."
    ::= { clExtApDot11IfEntry 2 }

clExtApIfPhyChannelAssignment OBJECT-TYPE
    SYNTAX     CLSwitch
    MAX-ACCESS read-write
    STATUS current
    DESCRIPTION
        "If this value is on, then bsnAPDot11CurrentChannel  in
        bsnAPIfDot11PhyDSSSTable is assigned by dynamic
        algorithm and is read-only."
    ::= { clExtApDot11IfEntry 3 }

clExtApDot11RadioStatsRxByteCount OBJECT-TYPE
    SYNTAX      Counter64
    UNITS       "bytes"
    MAX-ACCESS  read-only
    STATUS      current
    DESCRIPTION
            "This object represents the total bytes of
             packets received on the radio."
    ::= { clExtApDot11IfEntry 4 }

clExtApDot11RadioStatsTxByteCount OBJECT-TYPE
    SYNTAX      Counter64
    UNITS       "bytes"
    MAX-ACCESS  read-only
    STATUS      current
    DESCRIPTION
            "This object represents the total bytes of
             packets transmitted on the radio."
    ::= { clExtApDot11IfEntry 5 }

clExtApDot11WirelessModeSupported OBJECT-TYPE     
    SYNTAX INTEGER (0..31)
    MAX-ACCESS read-only
    STATUS current
    DESCRIPTION
        "This object represents wireless mode supported.

        bit 0 - dot11a
        bit 1 - dot11b
        bit 2 - dot11g
        bit 3 - dot11an
        bit 4 - dot11gn

        AP can support wireless multi-mode, the value can follow the example:
        gn  an  g   b   a
        --------------------
        0    0  1   1   0
        value:6, means b/g"
    ::= { clExtApDot11IfEntry 6 }

clExtApDot11IfAdminStatus OBJECT-TYPE
    SYNTAX     INTEGER {
                       up(1),      
                       down(2),
                       testing(3) 
                   }
    MAX-ACCESS  read-write
    STATUS      current
    DESCRIPTION
           "This object represents the AP's interface administrational
	   status."
    ::= { clExtApDot11IfEntry 7 }

clExtApDot11IfOperStatus OBJECT-TYPE
    SYNTAX  INTEGER {
                up(1),        
                down(2),
                testing(3),   
                admindown(4) 
            }
    MAX-ACCESS  read-only
    STATUS      current
    DESCRIPTION
        "This object represents the AP's wireless interface current operational
    status."
    ::= { clExtApDot11IfEntry 8 }

cLExtAPDot11IfRTSThreshold OBJECT-TYPE
    SYNTAX Integer32
    MAX-ACCESS read-write
    STATUS current
    DESCRIPTION
        "This object represents RTS threshold value."
    ::= { clExtApDot11IfEntry 9 }

--********************************************************************
-- *  Ext AP Dot11 radio statistics Information
--********************************************************************
clExtApDot11RadioStatsTable OBJECT-TYPE
        SYNTAX SEQUENCE OF ClExtApDot11RadioStatsEntry
        MAX-ACCESS  not-accessible
        STATUS      current
        DESCRIPTION
                 "This table represents the statistics information
                  about the radios of the APs that have joined the
                  controller."
       ::= { clExtAp 3 }
 
clExtApDot11RadioStatsEntry OBJECT-TYPE
        SYNTAX      ClExtApDot11RadioStatsEntry
        MAX-ACCESS  not-accessible
        STATUS      current
        DESCRIPTION
                "An entry in this table represents a statistics of
                 the radio of an AP that has joined the conttroller.

                 Entries are added when the APs associate to this
                 controller and deleted when they lose their
                 association."
        INDEX   {
                    cLApSysMacAddress,
                    cLApDot11IfSlotId
                }
        ::= { clExtApDot11RadioStatsTable 1 }

ClExtApDot11RadioStatsEntry ::= SEQUENCE {
        clExtApDot11RadioStatsRetryFrameCount   Counter64,
        clExtApDot11RadioStatsRetryPacketCount  Counter64,
        clExtApDot11RadioStatsRxErrorPacketCount Counter32
        }

clExtApDot11RadioStatsRetryFrameCount OBJECT-TYPE
        SYNTAX      Counter64
        UNITS       "frames"
        MAX-ACCESS  read-only
        STATUS      current
        DESCRIPTION
                "This object represents the total number of
                 downstream retry frames on the radio."
        ::= { clExtApDot11RadioStatsEntry 1 }

clExtApDot11RadioStatsRetryPacketCount OBJECT-TYPE
        SYNTAX      Counter64
        UNITS       "packets"
        MAX-ACCESS  read-only
        STATUS      current
        DESCRIPTION
                "This object represents the total number of
                 downstream retry packets on the radio."
        ::= { clExtApDot11RadioStatsEntry 2 }

clExtApDot11RadioStatsRxErrorPacketCount OBJECT-TYPE
        SYNTAX      Counter32
        UNITS       "packets"
        MAX-ACCESS  read-only
        STATUS      current
        DESCRIPTION
                "This object represents the total number of
                received error packets on the radio ."
        ::= { clExtApDot11RadioStatsEntry 3 }

---********************************************************************
-- *  AP EthernetIf  Info
--********************************************************************
clExtApEthernetIfTable OBJECT-TYPE
        SYNTAX SEQUENCE OF ClExtApEthernetIfEntry
        MAX-ACCESS not-accessible
        STATUS     current
        DESCRIPTION
            "This table represents the information about the
            basic functional parameters corresponding to
            the Ethernet interfaces of the APs that have joined
            the controller. "
        ::= { clExtAp 4 }

clExtApEthernetIfEntry OBJECT-TYPE
        SYNTAX     ClExtApEthernetIfEntry
        MAX-ACCESS not-accessible
        STATUS     current
        DESCRIPTION
                "An entry in this table represents the functional
                parameters of the Ethernet interface of an AP that
                has joined the controller.

                Entries are added when the APs associate to this
                controller and deleted when they lose their
                association. " 
        INDEX       {
                        cLApSysMacAddress,
                        cLApEthernetIfSlotId
                    } 
        ::= { clExtApEthernetIfTable 1 }

ClExtApEthernetIfEntry ::= SEQUENCE {
             clExtApEthernetIfOperStatus   INTEGER,
             clExtApEthernetIfRxBcastPkts  Counter32,
             clExtApEthernetIfRxMcastPkts  Counter32,
             clExtApEthernetIfTxBcastPkts  Counter32,
             clExtApEthernetIfTxMcastPkts  Counter32
        }

clExtApEthernetIfOperStatus OBJECT-TYPE
        SYNTAX    INTEGER  {
                   up(1),        
                   down(2),
                   testing(3),   
                   admindown(4) 
                    }
        MAX-ACCESS read-only
        STATUS     current
        DESCRIPTION
            "This object represents the operational state
            of the physical Ethernet interface on the AP." 
        ::= { clExtApEthernetIfEntry 1 }
 
clExtApEthernetIfRxBcastPkts OBJECT-TYPE
        SYNTAX      Counter32
        UNITS       "packets"
        MAX-ACCESS  read-only
        STATUS      current
        DESCRIPTION
                "This object represents total number of
        broadcast packets received on the interface" 
        ::= { clExtApEthernetIfEntry 2 }                                                             

clExtApEthernetIfRxMcastPkts OBJECT-TYPE
        SYNTAX      Counter32
        UNITS       "packets"
        MAX-ACCESS  read-only
        STATUS      current
        DESCRIPTION
                "This object represents total number of
        multicast packets received on the interface" 
        ::= { clExtApEthernetIfEntry 3 }                                                             

clExtApEthernetIfTxBcastPkts OBJECT-TYPE
        SYNTAX      Counter32
        UNITS       "packets"
        MAX-ACCESS  read-only
        STATUS      current
        DESCRIPTION
                "This object represents total number of
        broadcast packets transmitted on the interface" 
        ::= { clExtApEthernetIfEntry 4 }                                                             

clExtApEthernetIfTxMcastPkts OBJECT-TYPE
        SYNTAX      Counter32
        UNITS       "packets"
        MAX-ACCESS  read-only
        STATUS      current
        DESCRIPTION
                "This object represents total number of
        multicast packets transmitted on the interface" 
        ::= { clExtApEthernetIfEntry 5 }     
  
--********************************************************************
-- *  AP Operation Info
--********************************************************************
cLApOperationInfoTable OBJECT-TYPE
        SYNTAX     SEQUENCE OF CLApOperationInfoEntry
        MAX-ACCESS not-accessible
        STATUS     current
        DESCRIPTION
                "This table represents the operation information 
                for each AP."
        ::= { clExtAp 5 }

cLApOperationInfoEntry OBJECT-TYPE
        SYNTAX     CLApOperationInfoEntry
        MAX-ACCESS not-accessible
        STATUS     current
        DESCRIPTION
                "Each entry in this table provides operation 
                information for each AP. "
        INDEX   { cLApOperationSysMacAddress }
        ::= { cLApOperationInfoTable 1 }

CLApOperationInfoEntry ::= 
        SEQUENCE {
                cLApOperationSysMacAddress  MacAddress,
                cLApOperationStatus         INTEGER
        }

cLApOperationSysMacAddress      OBJECT-TYPE
       SYNTAX      MacAddress
       MAX-ACCESS  not-accessible
       STATUS      current
       DESCRIPTION
               "This object specifies the AP mac address."
       ::= {  cLApOperationInfoEntry 1 }

cLApOperationStatus             OBJECT-TYPE
    SYNTAX          INTEGER  {
                        disassociated(0),
                        associated (1)
                    }
        MAX-ACCESS read-only
        STATUS     current
        DESCRIPTION
                "This object represents operation status of each ap."
        ::= {  cLApOperationInfoEntry 2 }
    
--********************************************************************
-- *  Extension WLAN Information
--********************************************************************
clExtWlan OBJECT IDENTIFIER ::= { ciscoLwappExtConfig 4 }

clExtWlanConfigTable OBJECT-TYPE
    SYNTAX          SEQUENCE OF ClExtWlanConfigEntry
    MAX-ACCESS      not-accessible
    STATUS          current
    DESCRIPTION
        "This table represents the WLAN configuration sent by
        the controller to the LWAPP APs for their operation.

        LWAPP APs exchange configuration messages with the
        controller and get the required configuration for
        their 802.11 related operations.  As part of these
        messages, the WLAN configuration is pushed by the
        controller to the LWAPP APs.

        Rows are added or deleted by explicit
        management actions initiated by the user from a
        network management station through the
        cLWlanRowStatus object."
    ::= { clExtWlan 1 }

clExtWlanConfigEntry OBJECT-TYPE
    SYNTAX          ClExtWlanConfigEntry
    MAX-ACCESS      not-accessible
    STATUS          current
    DESCRIPTION
        "Each entry in this table represents the WLAN
        configuration sent by the controller to LWAPP APs
        for use during their operations. entries can be 
        added/deleted by explicit management actions by 
        NMS or by user console"
    INDEX           { cLWlanIndex } 
    ::= { clExtWlanConfigTable 1 }

ClExtWlanConfigEntry ::= SEQUENCE {
    clExtWlanAdminStatus          TruthValue,
    clExtWlanBroadcastSsidEnable  TruthValue,
    clExtWlanLoadBalancingMode    INTEGER,
    clExtWlanSecurityAuthType     INTEGER,
    clExtWlanP2PBlocking          TruthValue,
    clExtWlanDot11Auth            INTEGER,
    clExtWlanSecurity             INTEGER,
    clExtWlanAuthenMode           INTEGER,
    clExtWlanSecurityCiphers      INTEGER,
    clExtWepCipherKeyIndex        INTEGER,
    clExtWepCipherKeyValue        OCTET STRING,
    clExtWepCipherKeyCharType     INTEGER
}

clExtWlanAdminStatus OBJECT-TYPE
    SYNTAX         TruthValue
    MAX-ACCESS read-create
    STATUS current
    DESCRIPTION
        "Administrative Status of ESS(WLAN). By disabling an
        ESS the corresponding SSID is no longer broadcasted
        in AP beacons."
    DEFVAL { false }
    ::= { clExtWlanConfigEntry 1 }

clExtWlanBroadcastSsidEnable  OBJECT-TYPE
    SYNTAX           TruthValue
    MAX-ACCESS read-create
    STATUS current
    DESCRIPTION
        "This attribute when enabled allows the switch to
        broadcast this SSID and when disabled doesn't allow that."
    DEFVAL { true }
    ::= { clExtWlanConfigEntry 2 }

clExtWlanLoadBalancingMode OBJECT-TYPE
    SYNTAX          INTEGER {
            none(0),
            uplinkUsage(1),
            clientCount(2)
    }
    MAX-ACCESS      read-create
    STATUS          current
    DESCRIPTION
        "This object indicates the load balancing mode enabled
        on the controller for this WLAN . A value of 'none'
        indicates Load Balance is turned off for this Wlan.
        A value of 'clientCount' indicates load balance is based
        on AP client count scheme. And a value of 'uplinkUsage'
        indicates load balance is based on AP uplink usage scheme."
    DEFVAL           { clientCount }
    ::= { clExtWlanConfigEntry 3 }
  
clExtWlanP2PBlocking OBJECT-TYPE
    SYNTAX          TruthValue
    MAX-ACCESS      read-create
    STATUS          current
    DESCRIPTION
        "This object represents per WLAN peer-to-peer
        blocking behavior on controller. Peer-to-peer     
        blocking means traffic between two clients on     
        same VLAN will not be bridged.     

            false     : Peer-to-peer blocking is disabled     
                        and traffic is bridged locally     
                        within the controller.     
            true      : The packet will be discarded or     
                        be forwarded on the upstream VLAN.     
                        If it is forwarded on the upstream
                        VLAN, the device 'north' of the controller     
                        can then make the decision about     
                        decision about what to do with the     
                        packet." 
    DEFVAL           { false }
    ::= { clExtWlanConfigEntry 4 }

clExtWlanSecurityAuthType OBJECT-TYPE
    SYNTAX          INTEGER  {
                        authOpen(0),
                        authSharedKey(1),
                        authCiscoLeap(128)
                    }
    MAX-ACCESS read-create
    STATUS current
    DESCRIPTION
        "This object represents per WLAN type 
        of 802.11 Authentication.
        authOpen        : The WLAN uses open authentication method
        authSharedKey   : The WLAN uses shared authentication method
        authCiscoLeap   : The WLAN uses CISCO LEAP authentication
                          method"
    DEFVAL { authOpen }
    ::= { clExtWlanConfigEntry 5 }

clExtWlanDot11Auth     OBJECT-TYPE
    SYNTAX          INTEGER{
        opensystem(0),
        sharekey(1)
    }
    MAX-ACCESS      read-create
    STATUS          current
    DESCRIPTION
        "This object allows the user to configure
        802.11 Authentication."
    ::= { clExtWlanConfigEntry 6 }

clExtWlanSecurity      OBJECT-TYPE
    SYNTAX          INTEGER{
        none(0),
        wpa(1),
        wpa2(2),
        wapi(3)
    }
    MAX-ACCESS      read-create
    STATUS          current
    DESCRIPTION
        "This object allows the user to configure
        the security type in frame."
    ::= { clExtWlanConfigEntry 7 }

clExtWlanAuthenMode    OBJECT-TYPE
    SYNTAX          INTEGER{
        none(0),
        psk(1),
        radius(2),
        wapi-cer(3)
    }
    MAX-ACCESS      read-create
    STATUS          current
    DESCRIPTION
        "This object allows the user to configure
        the authentication mode."
    ::= { clExtWlanConfigEntry 8 }

clExtWlanSecurityCiphers   OBJECT-TYPE
    SYNTAX          INTEGER{
        none(0),
        wep40(1),
        wep104(2),
        tkip(3),
        aesccmp(4),
        wpi-sms4(5)
    }
    MAX-ACCESS      read-create
    STATUS          current
    DESCRIPTION
        "This object allows the user to configure
        encryption mode."
    ::= { clExtWlanConfigEntry 9 }

clExtWepCipherKeyIndex OBJECT-TYPE
    SYNTAX            INTEGER(1..4)
    MAX-ACCESS        read-write
    STATUS            current
    DESCRIPTION
        "This object represents the key index of WEP.
        According to 802.11 standard 4 keys are supported.
        So 802.11 Mobile Stations(Client) can have upto 4
        keys.  This index is for informing Mobile Station
        which key it should use for Static WEP Authentication."
    ::= { clExtWlanConfigEntry 10 }

clExtWepCipherKeyValue  OBJECT-TYPE
    SYNTAX            OCTET STRING (SIZE(5..26))
    MAX-ACCESS        read-write
    STATUS            current
    DESCRIPTION
        "This object represents the key value of WEP.  
        For wep104 encryption either 26 bit hex key or 
        13 bit ascii key should be specified. 
        For wep40 encryption 10 bit hex key or 5 bit
        ascii key should be specified."
    ::= { clExtWlanConfigEntry 11 }

clExtWepCipherKeyCharType  OBJECT-TYPE
    SYNTAX            INTEGER{
        default(1),
        hex(2),
        ascii(3)
    }
    MAX-ACCESS        read-write
    STATUS            current
    DESCRIPTION
        "This object represents the key type of WEP.
        Length of key specified in Key depends on this attribute."
    ::= { clExtWlanConfigEntry 12 }

--********************************************************************
-- *  Extension Dot11 Client Information
--********************************************************************
clExtDot11Client OBJECT IDENTIFIER ::= { ciscoLwappExtConfig 5 }

clExtClientTable OBJECT-TYPE
    SYNTAX     SEQUENCE OF ClExtClientEntry
    MAX-ACCESS not-accessible
    STATUS     current
    DESCRIPTION
        "This table represents the 802.11 wireless clients 
        that are associated with the APs that have joined 
        this controller.
        An entry is created automatically by the controller 
        when the client gets associated to the AP. An existing
        entry gets deleted when the association gets dropped.
        Each client added to this table is uniquely identified
        by the client's MAC address."
    ::= { clExtDot11Client 1 }
    
clExtClientEntry OBJECT-TYPE
    SYNTAX     ClExtClientEntry
    MAX-ACCESS not-accessible
    STATUS     current
    DESCRIPTION
        "Each entry represents a conceptual row in this 
        table and provides the information about the
        clients associated to the APs that have joined 
        the controller. An entry is identified the client's
        MAC address."
    INDEX { cldcClientMacAddress }
    ::= { clExtClientTable 1 }
     
ClExtClientEntry ::= SEQUENCE {
    clExtClientProtocol       INTEGER,
    clExtClientPowerSaveMode  INTEGER,
    clExtClientUpTime         TimeTicks,
    clExtClientAuthFailReason DisplayString, 
    clExtClientRxThroughput   Unsigned32,
    clExtClientTxThroughput   Unsigned32
}

clExtClientProtocol OBJECT-TYPE
    SYNTAX     INTEGER {  
            dot11a(1),
            dot11b(2),
            dot11g(4),
            dot11n5(8),
            dot11n24(16)
    }
    MAX-ACCESS read-only
    STATUS     current
    DESCRIPTION
            "The 802.11 protocol type of the client.
            'dot11a'   - The client is using 802.11a standard 
                         to connect to the access point (AP)
            'dot11b'   - The client is using 802.11b standard 
                         to connect to the access point (AP)
            'dot11g'   - The client is using 802.11g standard 
                         to connect to the access point (AP)
            'dot11n5'  - The client is using 802.11n standard 
                         with 5 GHz frequency to connect to 
                         the access point (AP).
            'dot11n24' - The client is using 802.11n standard 
                         with 2.4 GHz frequency to connect to 
                         the access point (AP)"
    ::= { clExtClientEntry 1 }

clExtClientPowerSaveMode OBJECT-TYPE
    SYNTAX      INTEGER {
            active(0),
            powersave(1) 
    }
    MAX-ACCESS read-only
    STATUS     current
    DESCRIPTION
        "This object indicates the power management mode of the client.
        The possible two modes are:
        active(0)    - this client is not in power-save mode
                       and it is actively sending or receiving
                       data.
        powersave(1) - this client is in power-save mode and it
                       wakes up once a while to check for
                       pending data."
    ::= { clExtClientEntry 2 }

clExtClientUpTime OBJECT-TYPE
        SYNTAX     TimeTicks
        MAX-ACCESS read-only
        STATUS     current
        DESCRIPTION                
            "This object indicates the duration for which the client has
            been associated with this device."
        ::= { clExtClientEntry  3 }  

clExtClientAuthFailReason  OBJECT-TYPE
        SYNTAX     DisplayString
        MAX-ACCESS read-only
        STATUS     current
        DESCRIPTION
           "This object specifies the reason of the client authentication failure."
        ::= { clExtClientEntry 5 }

clExtClientRxThroughput OBJECT-TYPE
        SYNTAX     Unsigned32
        UNITS      "bit/s"
        MAX-ACCESS read-only
        STATUS     current
        DESCRIPTION                
            "This object indicates the receiving throughput which expressing a instantaneous throughput of the bytes 
           received by the client over last time slot."
        ::= { clExtClientEntry  6 }

clExtClientTxThroughput OBJECT-TYPE
        SYNTAX     Unsigned32
        UNITS      "bit/s"
        MAX-ACCESS read-only
        STATUS     current
        DESCRIPTION                
            "This object indicates the transmitting throughput which expressing a instantaneous throughput of the bytes 
           transmitted by the client over last time slot."
        ::= { clExtClientEntry  7 }
 
--********************************************************************
-- *  Extension Dot11 Information
--********************************************************************
clExtDot11 OBJECT IDENTIFIER ::= { ciscoLwappExtConfig 6 }

clExtHtMacOperationsTable OBJECT-TYPE
    SYNTAX          SEQUENCE OF ClExtHtMacOperationsEntry 
    MAX-ACCESS      not-accessible
    STATUS          current
    DESCRIPTION
        "This table represents the operational parameters
        at the MAC layer for the 802.11n networks managed 
        through the controller. An agent adds an entry to 
        this table for every 802.11n band on startup."
    ::= { clExtDot11 1 }

clExtHtMacOperationsEntry OBJECT-TYPE
    SYNTAX          ClExtHtMacOperationsEntry
    MAX-ACCESS      not-accessible
    STATUS          current
    DESCRIPTION
        "Each entry represents the operational parameters
        at the MAC layer for 802.11n networks."
    INDEX           { cldHtDot11nBand } 
    ::= { clExtHtMacOperationsTable 1 }

ClExtHtMacOperationsEntry ::= SEQUENCE {
    clExtHtDot11nAmpduEnable CLSwitch,
    clExtHtDot11nGuardIntervalEnable CLSwitch
}

clExtHtDot11nAmpduEnable OBJECT-TYPE
    SYNTAX          CLSwitch
    MAX-ACCESS      read-write
    STATUS          current
    DESCRIPTION
        "This object is used to indicate the support for 802.11n
        A-MPDU on this band. A value of 'on' indicates that
        A-MPDU is enabled for this band. A value of 'off'
        indicates that A-MPDU is disabled for this band."
    DEFVAL          { on }
    ::= { clExtHtMacOperationsEntry 1 }

clExtHtDot11nGuardIntervalEnable OBJECT-TYPE
    SYNTAX          CLSwitch
    MAX-ACCESS      read-write
    STATUS          current
    DESCRIPTION
        "This object is used to indicate the support for 802.11n
        guard interval on this band. A value of 'on' indicates
        that guard interval is enabled for this band. A value of
        'off' indicates that guard interval is disabled for
        this band."
    DEFVAL          { on }
    ::= { clExtHtMacOperationsEntry 2 }

--********************************************************************
-- *  Extension RF Information
--********************************************************************
clExtRF OBJECT IDENTIFIER ::= { ciscoLwappExtConfig 7 }

clExtRFProfileTable OBJECT-TYPE
    SYNTAX          SEQUENCE OF ClExtRFProfileEntry 
    MAX-ACCESS      not-accessible
    STATUS          current
    DESCRIPTION
        "This table lists the configuration for each
        RF profile."
    ::= { clExtRF 1 }

clExtRFProfileEntry OBJECT-TYPE
    SYNTAX          ClExtRFProfileEntry
    MAX-ACCESS      not-accessible
    STATUS          current
    DESCRIPTION
        "An entry containing the configuration attributes
        that affect the operation of  802.11 RF domain.

        Entries can be added/deleted by explicit management 
        action from NMS/EMS or through user console."
    INDEX           { cLRFProfileName } 
    ::= { clExtRFProfileTable 1 }

ClExtRFProfileEntry ::= SEQUENCE {
        clExtRFProfileWirelessMode                  Unsigned32
}

clExtRFProfileWirelessMode OBJECT-TYPE
    SYNTAX Unsigned32 (0..31)
    MAX-ACCESS read-write
    STATUS current
    DESCRIPTION
        "This object represents wireless mode configuration.

        bit 0 - dot11a
        bit 1 - dot11b
        bit 2 - dot11g
        bit 3 - dot11an
        bit 4 - dot11gn

        AP can support wireless multi-mode, the value can follow the example:
        gn  an  g   b   a
        --------------------
        0    0  1   1   0
        value:6, means b/g"
   ::= { clExtRFProfileEntry 1 }

--********************************************************************
-- *  Extension Security Information
--********************************************************************
clExtSecurity OBJECT IDENTIFIER ::= { ciscoLwappExtConfig 8 }

clExtAbnormalOfflineClientOnSecurityTypeTable OBJECT-TYPE
    SYNTAX          SEQUENCE OF ClExtAbnormalOfflineClientOnSecurityTypeEntry 
    MAX-ACCESS      not-accessible
    STATUS          current
    DESCRIPTION
        "This table lists the abnormal offline clients for the required 
        security type."
    ::= { clExtSecurity 1 }


clExtAbnormalOfflineClientOnSecurityTypeEntry OBJECT-TYPE
    SYNTAX          ClExtAbnormalOfflineClientOnSecurityTypeEntry
    MAX-ACCESS      not-accessible
    STATUS          current
    DESCRIPTION
        "Each entry in this table represents the abnormal 
         offline counter based on security type."
    INDEX           { clExtSecurityType } 
    ::= { clExtAbnormalOfflineClientOnSecurityTypeTable 1 }

ClExtAbnormalOfflineClientOnSecurityTypeEntry ::= SEQUENCE {
        clExtSecurityType                INTEGER,
        clExtAbnormalOfflineClientCount  Counter32
}

clExtSecurityType OBJECT-TYPE
    SYNTAX INTEGER  {
                        open(1),
                        wepPsk(2),
                        peapSim(3),
                        webAuth(4)
                    }
    MAX-ACCESS not-accessible 
    STATUS current
    DESCRIPTION
        "This object represents the client security type.  
        open        : The client uses open authentication method
        wepPsk      : The client uses WEP/PSK authentication method
        peapSim     : The client uses PEAP/SIM authentication method
        webAuth     : The client uses WebAuth authentication method"
    DEFVAL { open }
    ::= { clExtAbnormalOfflineClientOnSecurityTypeEntry 1 }

clExtAbnormalOfflineClientCount OBJECT-TYPE
    SYNTAX          Counter32
    MAX-ACCESS      read-only
    STATUS          current
    DESCRIPTION
        "This object represents the current abnormal offline clients 
         based on security type on the controller."
    ::= { clExtAbnormalOfflineClientOnSecurityTypeEntry 2 }

--********************************************************************
-- *  Notifications Objects
--********************************************************************
cLExtApDisassocReason OBJECT-TYPE
        SYNTAX     CLExtApDisassocReason
        MAX-ACCESS accessible-for-notify
        STATUS     current
        DESCRIPTION
                "This object specifies the failure reasons when
                the AP disassociate with a controller."
        ::= { ciscoLwappExtMIBNotifObjects 1 }

cLExtDot11ClientAssocFailReason OBJECT-TYPE
        SYNTAX     DisplayString
        MAX-ACCESS accessible-for-notify
        STATUS     current
        DESCRIPTION
           "This object specifies the reason of the station association failure."
        ::= { ciscoLwappExtMIBNotifObjects 2 }

cLExtApDetectedMacAddress OBJECT-TYPE
        SYNTAX     MacAddress
        MAX-ACCESS accessible-for-notify
        STATUS     current
        DESCRIPTION
                "This object represents the radio MAC address 
                common to the dot11 interfaces of the detected AP."
        ::= {  ciscoLwappExtMIBNotifObjects 3}

cLExtApDetectedChannel OBJECT-TYPE
        SYNTAX CLDot11Channel
        MAX-ACCESS accessible-for-notify
        STATUS     current
        DESCRIPTION
             "This object represents the detected channel number."
        ::= {  ciscoLwappExtMIBNotifObjects 4}			   

cLExtApDectedSsid OBJECT-TYPE
        SYNTAX     SnmpAdminString
        MAX-ACCESS accessible-for-notify
        STATUS     current
        DESCRIPTION
                "This object represents the SSID used by the
                 rogue AP to intrude the network." 
        ::= {  ciscoLwappExtMIBNotifObjects 5}

--********************************************************************
-- *  Notifications
--********************************************************************

ciscoLwappApAssociatedNotify NOTIFICATION-TYPE
    OBJECTS         {
                        cLApName,
                        cLApSysMacAddress,
                        cLApLastRebootReason,
                        cLApDataEncryptionStatus
                    }
    STATUS current
    DESCRIPTION
        "This notification is generated whenever an AP joins the
        controller successfully. This notification contains
        information about the last reboot reason, Data
        Encryption status and the MAC address of the AP."
    ::= { ciscoLwappExtMIBNotifs 1 }

ciscoLwappApDisassociated NOTIFICATION-TYPE
     OBJECTS         {
                        cLApName,
                        cLApSysMacAddress,
                        cLExtApDisassocReason
                    }
    STATUS current
    DESCRIPTION
        "This notification is generated whenever an AP disassociate the
        controller successfully. This notification contains
        information about the last associate fail reason and MAC address
        of the AP."
    ::= { ciscoLwappExtMIBNotifs 2 }

ciscoLwappExtDot11ClientAuthenticationFailTrap NOTIFICATION-TYPE
    OBJECTS         {
                     cldcClientMacAddress,
                     cldcApMacAddress,
                     cldcClientSSID,
                     cLApIfSmtDot11Bssid,
                     bsnDot11EssSecurityAuthType,
                     clExtClientAuthFailReason
                    }
    STATUS current
    DESCRIPTION
         "This notification is generated whenever client Authentication
          failure is detected."
    ::= { ciscoLwappExtMIBNotifs 3 }

ciscoLwappExtDot11ClientAssocFailTrap NOTIFICATION-TYPE
    OBJECTS         {
                     cldcClientMacAddress,
                     cLApSysMacAddress,
                     cLWlanSsid,
                     cLApIfSmtDot11Bssid,
                     cLExtDot11ClientAssocFailReason
                    }
    STATUS current
    DESCRIPTION
         "This notification is generated whenever station associtation
          failure is detacted."
    ::= { ciscoLwappExtMIBNotifs 4 }

ciscoLwappExtAdjChannelOverRssiDetected NOTIFICATION-TYPE
    OBJECTS         {
            cLApSysMacAddress, 
            cLExtApDetectedMacAddress,
            cLExtApDetectedChannel, 
            cLApRSSI, 
            cLApDot11RadioCurrentChannel
    }
    STATUS          current
    DESCRIPTION
        "This notification is generated whenever an AP is
        detected at the Adjacent channels"
    ::= { ciscoLwappExtMIBNotifs 5 }

ciscoLwappExtAdjChannelOverRssiRemoved NOTIFICATION-TYPE
    OBJECTS         {
        cLApSysMacAddress, 
        cLExtApDetectedMacAddress,
        cLExtApDetectedChannel,
        cLApDot11RadioCurrentChannel
    }
    STATUS          current
    DESCRIPTION
        "This notification is generated whenever an AP is
        detected at the Adjacent channels and then
        subsequently if its been removed from the network."
    ::= { ciscoLwappExtMIBNotifs  6}

ciscoLwappExtCurrentChannelOverRssiDetected NOTIFICATION-TYPE
    OBJECTS         {
        cLApSysMacAddress, 
        cLExtApDetectedMacAddress,
        cLExtApDetectedChannel, 
        cLApRSSI, 
        cLApDot11RadioCurrentChannel
    }
    STATUS          current
    DESCRIPTION
        "This notification is generated whenever an AP is
        detected at the Current channels"
    ::= { ciscoLwappExtMIBNotifs 7 }

ciscoLwappExtCurrentChannelOverRssiRemoved NOTIFICATION-TYPE
    OBJECTS         {
        cLApSysMacAddress, 
        cLExtApDetectedMacAddress,
        cLExtApDetectedChannel,
        cLApDot11RadioCurrentChannel
    }
    STATUS          current
    DESCRIPTION
        "This notification is generated whenever an AP is
        detected at the Current channels and then
        subsequently if its been removed from the network."
    ::= { ciscoLwappExtMIBNotifs 8 }

ciscoLwappExtClientOverRssiDetected NOTIFICATION-TYPE
    OBJECTS         {
        cLApDot11RadioMACAddress,
        cLApDot11RadioChannelNumber,
        cLExtApDetectedMacAddress,
        cldcClientMacAddress,
        cLApIfSmtDot11Bssid,
        cLExtApDetectedChannel
    }
    STATUS          current
    DESCRIPTION
        "This notification is generated when a client's rssi 
        exceeds threshold configured add to network. 
        The details of AP and  Clients is sent in the notification."
    ::= { ciscoLwappExtMIBNotifs 9 }

ciscoLwappExtClientOverRssiRemoved NOTIFICATION-TYPE
    OBJECTS         {
        cLApDot11RadioMACAddress,
        cLApDot11RadioChannelNumber,
        cLExtApDetectedMacAddress,
        cldcClientMacAddress,
        cLApIfSmtDot11Bssid,
        cLExtApDetectedChannel
    }
    STATUS          current
    DESCRIPTION
        "This notification is generated when a client's rssi 
        exceeds threshold configured removed from network. 
        The details of AP and  Clients is sent in the notification."
    ::= { ciscoLwappExtMIBNotifs 10 }

END
