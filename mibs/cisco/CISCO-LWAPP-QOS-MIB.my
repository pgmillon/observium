-- *******************************************************************
-- CISCO-LWAPP-QOS-MIB.my 
-- November 2005, Devesh Pujari, Bharat Biswal, 
-- Prasanna Viswakumar, Srinath Candadai
--
-- Copyright (c) 2005, 2006 by Cisco Systems, Inc.
-- All rights reserved.
-- *******************************************************************
--
CISCO-LWAPP-QOS-MIB DEFINITIONS ::= BEGIN

IMPORTS 
        MODULE-IDENTITY, 
        OBJECT-TYPE,
        Unsigned32,
        Counter32,
        Gauge32
                FROM SNMPv2-SMI
        MODULE-COMPLIANCE, 
        OBJECT-GROUP
                FROM SNMPv2-CONF
        RowStatus,
        TruthValue,
        DisplayString,
        TimeStamp
                FROM SNMPv2-TC 
        ciscoMgmt
                FROM CISCO-SMI
        TimeIntervalSec
                FROM CISCO-TC
--        cLApDot11IfEntry 
--                FROM CISCO-LWAPP-AP-MIB
        cldcClientMacAddress
                FROM CISCO-LWAPP-DOT11-CLIENT-MIB
        cLApSysMacAddress,
        cLApDot11IfSlotId,
        cLApName,
        cLApDot11IfType
                FROM CISCO-LWAPP-AP-MIB
        SnmpAdminString
                FROM SNMP-FRAMEWORK-MIB
        InetAddressType,
        InetAddress
                FROM INET-ADDRESS-MIB
        cLWlanIndex
                FROM CISCO-LWAPP-WLAN-MIB;


--********************************************************************
--*  MODULE IDENTITY
--********************************************************************

ciscoLwappQosMIB   MODULE-IDENTITY
        LAST-UPDATED   "201007210000Z"
        ORGANIZATION   "Cisco Systems Inc."
        CONTACT-INFO  
               "        Cisco Systems,
                        Customer Service
                Postal: 170 West Tasman Drive
                        San Jose, CA  95134
                        USA
                   Tel: +1 800 553-NETS

                 Email: cs-wnbu-snmp@cisco.com"

        DESCRIPTION             
                "This MIB is intended to be implemented on all those
                devices operating as Central controllers, that
                terminate the Light Weight Access Point Protocol
                tunnel from Cisco Light-weight LWAPP Access Points.

                Information provided by this MIB is used to study
                the quality of service in the voice and video traffic
                on the WLAN.

                The relationship between CC and the LWAPP APs
                can be depicted as follows:

                      +......+     +......+     +......+
                      +      +     +      +     +      +
                      +  CC  +     +  CC  +     +  CC  +
                      +      +     +      +     +      +
                      +......+     +......+     +......+
                        ..            .             .
                        ..            .             .
                       .  .            .             .
                      .    .            .             .
                     .      .            .             .
                    .        .            .             .
                +......+ +......+     +......+      +......+
                +      + +      +     +      +      +      +
                +  AP  + +  AP  +     +  AP  +      +  AP  +
                +      + +      +     +      +      +      +
                +......+ +......+     +......+      +......+
                           .              .             .
                         .  .              .             .
                        .    .              .             .
                       .      .              .             .
                      .        .              .             .
                   +......+ +......+     +......+      +......+
                   +      + +      +     +      +      +      +
                   +  MN  + +  MN  +     +  MN  +      +  MN  +
                   +      + +      +     +      +      +      +
                   +......+ +......+     +......+      +......+


                The LWAPP tunnel exists between the controller and
                the APs.  The MNs communicate with the APs through
                the protocol defined by the 802.11 standard.

                LWAPP APs, upon bootup, discover and join one of the
                controllers and the controller pushes the configuration,
                that includes the WLAN parameters, to the LWAPP APs.
                The APs then encapsulate all the 802.11 frames from
                wireless clients inside LWAPP frames and forward
                the LWAPP frames to the controller.

                                   GLOSSARY

                Access Point ( AP )

                An entity that contains an 802.11 medium access
                control ( MAC ) and physical layer ( PHY ) interface
                and provides access to the distribution services via
                the wireless medium for associated clients.  

                LWAPP APs encapsulate all the 802.11 frames in
                LWAPP frames and sends them to the controller to which
                it is logically connected.

                Gratuitous Probe Response (GPR)

                The Gratuitous Probe Response feature aids in conserving
                battery power of WLAN-enabled cell phones by providing
                a high rate packet on the order of tens of milliseconds
                such that these kind of phones can wake up and wait at
                predefined intervals, to reduce battery power.  The 
                GPR packet is transmitted from the AP at a predefined
                time interval.
                 

                Light Weight Access Point Protocol ( LWAPP )

                This is a generic protocol that defines the 
                communication between the Access Points and the
                Central Controller. 

                Mobile Node ( MN )

                A roaming 802.11 wireless device in a wireless
                network associated with an access point. Mobile Node 
                and client are used interchangeably. 

                TU

                A measurement of time in units of 1024 microseconds.

                User Priority ( UP )

                Specifies a the priority rules in QOS for handling user 
                priority.

                EDCA
                
                As defined in 802.11e standard, Enhanced distributed
                channel access(EDCA) parameter set element is used 
                by the AP to establish policy, to change policy when
                accepting new clients, or to adapt to changes in 
                offered load. 

                KTS (Key Telephone System)

		Key Telephone System is an alternative to a private branch exchange (PBX) 
		phone system. A KTS is equipped with several buttons that allow a caller to
		directly select outgoing lines or incoming calls, and use intercom and 
		conference facilities. 

                REFERENCE
 
                [1] Wireless LAN Medium Access Control ( MAC ) and
                Physical Layer ( PHY ) Specifications
  
                [2] Draft-obara-capwap-lwapp-00.txt, IETF Light 
                Weight Access Point Protocol "
    REVISION        "201007210000Z"
    DESCRIPTION
        "Added the following groups:
        ciscoLwappQosMIBComplianceRev2, 
        ciscoLwappQosDot11aConfigGroupSup2, 
        ciscoLwappQosDot11bConfigGroupSup2, 
        ciscoLwappQosDot11SipCacStatsGroup, 
        ciscoLwappQosDot11SipConfigGroup, 
        ciscoLwappQosDot11VoiceStatsGroup, 
        ciscoLwappQosDot11VoiceConfigGroup, 
        ciscoLwappQosConfigGroup,
        ciscoLwappQosDot11VoiceNotifGroup 

        Deprecated ciscoLwappQosMIBComplianceRev1 and 
        replaced it with ciscoLwappQosMIBComplianceRev2."        
        REVISION      "200701070000Z"
        DESCRIPTION
                "Added ciscoLwappQosDot11aConfigGroupSup1 and 
                 ciscoLwappQosDot11bConfigGroupSup1 objects."
        REVISION      "200604130000Z"
        DESCRIPTION
                "Initial version of this MIB module. "
        ::= { ciscoMgmt 524 } 
        
ciscoLwappQosMIBNotifs  OBJECT IDENTIFIER ::= { ciscoLwappQosMIB 0 }
ciscoLwappQosMIBObjects OBJECT IDENTIFIER ::= { ciscoLwappQosMIB 1 }
ciscoLwappQosMIBConform OBJECT IDENTIFIER ::= { ciscoLwappQosMIB 2 }
ciscoLwappQosMIBNotifObjects  
                   OBJECT IDENTIFIER ::= { ciscoLwappQosMIB 3 }

cLQd11aCACConfig OBJECT IDENTIFIER ::= { ciscoLwappQosMIBObjects 1 }
cLQd11bCACConfig OBJECT IDENTIFIER ::= { ciscoLwappQosMIBObjects 2 }
cLQd11GprConfig  OBJECT IDENTIFIER ::= { ciscoLwappQosMIBObjects 3 }
cLQd11CACStats   OBJECT IDENTIFIER ::= { ciscoLwappQosMIBObjects 4 }
cLQEntConfConfig OBJECT IDENTIFIER ::= { ciscoLwappQosMIBObjects 5 }
cLQd11VoiceStats   OBJECT IDENTIFIER ::= { ciscoLwappQosMIBObjects 6 }
cLQVoiceWlanConfig  OBJECT IDENTIFIER ::= { ciscoLwappQosMIBObjects 7 }
cLQVoiceClient  OBJECT IDENTIFIER ::= { ciscoLwappQosMIBObjects 8 }
cLQMediaClient  OBJECT IDENTIFIER ::= { ciscoLwappQosMIBObjects 9 }
cLQd11SipCacConfig OBJECT IDENTIFIER ::= { ciscoLwappQosMIBObjects 10 }
cLQMediaStreamConfig  OBJECT IDENTIFIER ::= { ciscoLwappQosMIBObjects 11 }
cLQPreferredCallConfig  OBJECT IDENTIFIER ::= { ciscoLwappQosMIBObjects 12 }
cLQConfigObjects  OBJECT IDENTIFIER
    ::= { ciscoLwappQosMIBObjects 13 }
cLQoSProfileConfig OBJECT IDENTIFIER ::= { ciscoLwappQosMIBObjects 14 }
cLQoSSipSnoopingConfig OBJECT IDENTIFIER ::= { ciscoLwappQosMIBObjects 15 }

CiscoLwappDot11aPhyRates ::= TEXTUAL-CONVENTION
    STATUS          current
    DESCRIPTION
        "This field indicates the physical rates supported by a
        802.11a radio.
        The different physical rates (in Mbps) are 6,9,
        12, 18, 24, 36, 48, 54.
        11n rates: 65,72.2, 130, 135, 144.4, 150, 270, 300."
    SYNTAX     INTEGER {
                        six(6),
                        nine(9),
                        twelve(12),
                        eighteen(18),
                        twentyfour(24),
                        thirtysix(36),
                        fortyeight(48),
                        fiftyfour(54),
                        sixtyfive(65),
                        seventyTwoPointTwo(72),
                        oneThirty(130),
                        oneThirtyfive(135),
                        oneFortyFourPointFour(144),
                        oneFifty(150),
                        twoSeventy(270),
                        threeHundred(300)
                      
        }
 
CiscoLwappDot11bPhyRates ::= TEXTUAL-CONVENTION
    STATUS          current
    DESCRIPTION
        "This field indicates the physical rates supported by a
        802.11b radio.
        The different physical rates (in Mbps) are 1, 2,
        5.5, 6, 9, 11, 12, 18, 24, 36, 48, 54.
        11n rates: 65,72.2, 130, 135, 144.4, 150, 270, 300."
        SYNTAX     INTEGER {
                        one(1),
                        two(2),
                        fivepointfive(5),
                        six(6),
                        nine(9),
                        eleven(11),
                        twelve(12),
                        eighteen(18),
                        twentyfour(24),
                        thirtysix(36),
                        fortyeight(48),
                        fiftyfour(54),
                        sixtyfive(65),
                        seventyTwoPointTwo(72),
                        oneThirty(130),
                        oneThirtyfive(135),
                        oneFortyFourPointFour(144),
                        oneFifty(150),
                        twoSeventy(270),
                        threeHundred(300)

        }

--********************************************************************
--*    Configuration for Call Admission Control parameters
--*    for VOICE traffic in 802.11a interfaces in the controller
--********************************************************************

cLQd11aVoiceAdmCtrlSupport OBJECT-TYPE
        SYNTAX     TruthValue
        MAX-ACCESS read-write
        STATUS     current
        DESCRIPTION
                "This object is used to enable or disable admission 
                control for voice traffic flowing through the 802.11a 
                interfaces in the controller.
    
                When set to 'true', controller will reserve and manage 
                max-bandwidth (cLQd11aVoiceMaxAdmBandwidth) 
                and roaming-bandwidth
                (cLQd11aVoiceMaxRoamBandwidth) as per user 
                configured values.
    
                When disabled, admission control will not be enforced. 
                This may delay voice traffic depending on load on
                the WLAN. "
        DEFVAL { true }
        ::= { cLQd11aCACConfig 1 }

cLQd11aVoiceMaxAdmBandwidth OBJECT-TYPE
        SYNTAX     Unsigned32 (0..100)
        UNITS      "Percent"
        MAX-ACCESS read-write
        STATUS     current
        DESCRIPTION
                "This object denotes the maximum bandwidth 
                that can be allocated by controller for voice
                traffic when admission control is enabled for
                for 802.11a interfaces in the controller.

                Please note that the write operation on this
                object will be successful only if the 802.11a
                network is not operational and the total
                value populated for this object for all the
                admission control attributes (voice, video)
                together does not exceed 100%. " 
        ::= { cLQd11aCACConfig 2 }

cLQd11aVoiceMaxRoamBandwidth OBJECT-TYPE
        SYNTAX     Unsigned32 (0..100)
        UNITS      "Percent"
        MAX-ACCESS read-write
        STATUS     current
        DESCRIPTION
                "This object represents the bandwidth relative
                to the maximum allocated bandwidth indicated by
                cLQd11aVoiceMaxAdmBandwidth, that can be 
                allocated to roaming clients for voice traffic,
                when admission control is enabled for 802.11a
                interfaces in the controller.

                Please note that the write operation on this
                object will be successful only if the 802.11a
                network is disabled and not operational.  The
                value configured through this object takes
                effect when the 802.11a network is enabled. "
        DEFVAL { 0 }
        ::= { cLQd11aCACConfig 3 }


--********************************************************************
--*    Configuration for Call Admission Control parameters
--*    for VIDEO traffic in 802.11a interfaces in the controller
--********************************************************************

cLQd11aVideoAdmCtrlSupport OBJECT-TYPE
        SYNTAX     TruthValue
        MAX-ACCESS read-write
        STATUS     current
        DESCRIPTION
                "This object is used to enable or disable admission 
                control for video traffic flowing through the 802.11a 
                interfaces in the controller.

                When set to 'true', controller will reserve and manage 
                max-bandwidth (cLQd11aVideoMaxAdmBandwidth) 
                and roaming-bandwidth
                (cLQd11aVideoMaxRoamBandwidth) as per user  
                configured values.
    
                When disabled, admission control will not be enforced. 
                This may delay video traffic depending on load on
                the WLAN. "
        DEFVAL { true }
        ::= { cLQd11aCACConfig 4 }

cLQd11aVideoMaxAdmBandwidth OBJECT-TYPE
        SYNTAX     Unsigned32 (0..100)
        UNITS      "Percent"   
        MAX-ACCESS read-write
        STATUS current
        DESCRIPTION
                "This object denotes the maximum bandwidth 
                that can be allocated by controller for video traffic
                when admission control is enabled for 802.11a 
                interfaces in the controller.  When set to 0, all
                available bandwidth in 802.11a interfaces can be
                allocated to video traffic.

                Please note that the write operation on this
                object will be successful only if the 802.11a
                network is not operational and the total
                value populated for this object for all the
                admission control attributes (voice, video)
                together does not exceed 100%. " 
        DEFVAL { 0 }
        ::= { cLQd11aCACConfig 5 }

cLQd11aVideoMaxRoamBandwidth OBJECT-TYPE
        SYNTAX     Unsigned32 (0..100)
        UNITS      "Percent"
        MAX-ACCESS read-write
        STATUS     current
        DESCRIPTION
                "This object represents the bandwidth relative
                to the maximum allocated bandwidth indicated by
                cLQd11aVideoMaxAdmBandwidth, that can be 
                allocated to roaming clients for video traffic,
                when admission control is enabled for 802.11a
                interfaces in the controller.

                Please note that the write operation on this
                object will be successful only if the 802.11a
                network is disabled and not operational.  The
                value configured through this object takes effect 
                when the 802.11a network is enabled and 
                operational. "
        DEFVAL { 0 }
        ::= { cLQd11aCACConfig 6 }


--********************************************************************
--*    Configuration of GPR (Gratuitous Probe Response) probe interval
--*    for all 802.11a interfaces in the controller
--********************************************************************
cLQd11aGprProbeInterval OBJECT-TYPE
        SYNTAX     Unsigned32(10..100)
        UNITS      "TU"
        MAX-ACCESS read-write
        STATUS current
        DESCRIPTION
                "This object is used to set GPR probe interval
                period to be used by all 802.11a interfaces in the
                controller, when the radios are advertising any
                WLAN with GPR support enabled.

                Please note that the write operation on this
                object will be successful only if the 802.11a
                network is not operational.  The value configured
                through this object takes effect when the 802.11a
                network is enabled and operational. "
        DEFVAL { 10 }
        ::= { cLQd11aCACConfig 7 }


cLQd11aVoiceCtrl OBJECT-TYPE
        SYNTAX     INTEGER {
                             loadBased(1),
                             static(2)
                           }
        MAX-ACCESS read-write
        STATUS     current
        DESCRIPTION
                "When admission control is enabled these parameters
                can be modified.
                    loadBased - controller will reserve and manage
                                max-bandwidth and roaming-bandwidth
                                based on the load on the WLAN.
                    static    - controller will reserve and
                                manage max-bandwidth
                                (cLQd11aVoiceMaxAdmBandwidth)
                                and roaming-bandwidth
                                (cLQd11aVoiceMaxRoamBandwidth)
                                as per user configured values.
                 When ACM is disabled, admission control will not
                 be enforced. This may delay voice traffic depending
                 on the traffic on the WLAN. "
        DEFVAL { loadBased }
        ::= { cLQd11aCACConfig 8 }

cLQd11aExpeditedBw   OBJECT-TYPE
      SYNTAX      TruthValue
      MAX-ACCESS  read-write
      STATUS      current
      DESCRIPTION
             "This object specifies if expedited BW feature is
              enabled or not.
              A value of 'true' will ensure that the APs advertise
              the expedited BW support in their beacons and
              association responses.
              A value of 'false' will ensure that the APs do not
              advertise the expedited BW support in their beacons
              and association responses."
       ::= { cLQd11aCACConfig  9 }

cLQd11aEdcaProfile OBJECT-TYPE
    SYNTAX          INTEGER  {
                        wmmDefault(1),
                        svpVoice(2),
                        optimizedVoice(3),
                        optimizedVideoVoice(4),
                        customVoice(5)
                    }
    MAX-ACCESS      read-write
    STATUS          current
    DESCRIPTION
        "This object specifies the EDCA profile to be used
        in EDCA Parameter set element. See glossary for EDCA. 
           wmmDefault     - WMM default standard parameters.
           svpVoice       - Spectralink voice priority 
                             parameters.
           optimizedVoice      - parameters for voice optimization.
           optimizedVideoVoice - parameters for video and voice
                                   optimization. 
           customVoice - parameters for customized voice."
    ::= { cLQd11aCACConfig 10 }

cLQd11aMacOptimization OBJECT-TYPE
    SYNTAX          TruthValue
    MAX-ACCESS      read-write
    STATUS          current
    DESCRIPTION
        "This object specifies MAC enhancements for voice,
        resulting in improvement in number of voice calls
        serviced per access point.
        A value of 'true' enables MAC optimization. 
        A value of 'false' disables MAC optimization." 
    ::= { cLQd11aCACConfig 11 }

cLQd11aMaxCallLimit OBJECT-TYPE
    SYNTAX          Unsigned32
    MAX-ACCESS      read-write
    STATUS          deprecated
    DESCRIPTION
        "This object specifies the max number of CAC Voice Calls
        allowed on dot11a radio band.
        Value of zero denotes no limit." 
    ::= { cLQd11aCACConfig 12 }

--********************************************************************
--*    Configuration for Call Admission Control parameters
--*    for mc2uc in 802.11a interfaces in the controller
--********************************************************************

cLQd11aMcastDirectEnable OBJECT-TYPE
        SYNTAX     TruthValue
        MAX-ACCESS read-write
        STATUS     current
        DESCRIPTION
                "This object denotes the decision flag to allow multicast direct
        stream on radio. Overrides RRC status"
        DEFVAL { true }
        ::= { cLQd11aCACConfig 13}

cLQd11aBestEffortAdmission OBJECT-TYPE
        SYNTAX     TruthValue
        MAX-ACCESS read-write
        STATUS     current
        DESCRIPTION
                "This object specifies whether to admit a media stream in best 
                 effort queue "
        DEFVAL { false }
        ::= { cLQd11aCACConfig 14}

cLQd11aRedirectBestEffort OBJECT-TYPE
        SYNTAX     TruthValue
        MAX-ACCESS read-write
        STATUS     current
        DESCRIPTION
               "This object specifies whether a unicast or multicast only video 
                 stream can be redirected to best effort  "
        DEFVAL { true }
        ::= { cLQd11aCACConfig 15}

cLQd11aRadioMaxStreams OBJECT-TYPE
        SYNTAX     INTEGER (0..20)
        MAX-ACCESS read-write
        STATUS     current
        DESCRIPTION
                "This object denotes the Maximum number of allowed streams per 
                 radio for a 802.11a band "
        DEFVAL { 0 }
        ::= { cLQd11aCACConfig 16}

cLQd11aMaxVideoATPercent OBJECT-TYPE
        SYNTAX     INTEGER (0..85)
        UNITS      "Percent"
        MAX-ACCESS read-write
        STATUS     current
        DESCRIPTION
                "This object denotes the Maximum Allowed Bandwidth for video 
                 traffic  "
        ::= { cLQd11aCACConfig 17}

cLQd11aMaxVoiceATPercent OBJECT-TYPE
        SYNTAX     INTEGER (0..85)
        UNITS      "Percent"
        MAX-ACCESS read-write
        STATUS     current
        DESCRIPTION
                "This object denotes the Maximum Allowed Bandwidth for voice 
                 traffic  "
        ::= { cLQd11aCACConfig 18}

cLQd11aMaxMediaATPercent OBJECT-TYPE
        SYNTAX     INTEGER (0..100)
        UNITS      "Percent"
        MAX-ACCESS read-write
        STATUS     current
        DESCRIPTION
                "This object denotes the Maximum Allowed Bandwidth for Media 
                 traffic  "
        ::= { cLQd11aCACConfig 19}

cLQd11aMinPhyRate OBJECT-TYPE
        SYNTAX     CiscoLwappDot11aPhyRates 
        UNITS      "Mbps"
        MAX-ACCESS read-write
        STATUS     current
        DESCRIPTION
                "This object denotes that Client needs to have at least this 
                 rate enabled in order to join media stream  "
        DEFVAL { 1 }
        ::= { cLQd11aCACConfig 20}

cLQd11aClientMaxStreams OBJECT-TYPE
        SYNTAX     INTEGER (0..20)
        MAX-ACCESS read-write
        STATUS     current
        DESCRIPTION
                "This object denotes the Maximum number of allowed streams per
                 client for a 802.11a band "
        DEFVAL { 0 }
        ::= { cLQd11aCACConfig 21}

cLQd11aSipCacSupportEnable  OBJECT-TYPE
      SYNTAX      TruthValue
      MAX-ACCESS  read-write
      STATUS      current
      DESCRIPTION
             "This object represents if SIP CAC is supported on dot11a radio band.
              A value of 'true' enables SIP CAC support on dot11a radio band.
              A value of 'false' disable SIP CAC support on dot11a radio band."
        DEFVAL { false }
       ::= { cLQd11aCACConfig  22 }


cLQd11aMaxRetryPercent OBJECT-TYPE
        SYNTAX     INTEGER (0..100)
        UNITS      "Percent"
        MAX-ACCESS read-write
        STATUS     current
        DESCRIPTION
                "This object denotes the maximum retry percent for Media
                 traffic on dot11a radio band."
        ::= { cLQd11aCACConfig 23}

--******************************************************************
--      Configuration of Video CAC Method
--******************************************************************

cLQd11aVideoCtrl OBJECT-TYPE
        SYNTAX     INTEGER {
                             loadBased(1),
                             static(2)
                           }
        MAX-ACCESS read-write
        STATUS     current
        DESCRIPTION
                "This object denotes the admission control (ACM) method
                used on dot11a radio band. When admission control is 
                enabled these parameters can be modified.
                    loadBased - controller will reserve and manage
                                max-bandwidth and roaming-bandwidth
                                based on the load on the WLAN.
                    static    - controller will reserve and
                                manage max-bandwidth
                                (cLQd11aVideoMaxAdmBandwidth)
                                and roaming-bandwidth
                                (cLQd11aVideoMaxRoamBandwidth)
                                as per user configured values.
                 When ACM is disabled, admission control will not
                 be enforced. This may delay video traffic depending
                 on the traffic on the WLAN. "
        DEFVAL { loadBased }
        ::= { cLQd11aCACConfig 24 }

--******************************************************************
--      Configuration of SIP based Video-CAC method
--******************************************************************

cLQd11aSipCacVideoEnable  OBJECT-TYPE
      SYNTAX      TruthValue
      MAX-ACCESS  read-write
      STATUS      current
      DESCRIPTION
             "This object represents if SIP based Video-CAC is enabled on dot11a radio band.
              A value of 'true' enables SIP based Video-CAC on dot11a radio band.
              A value of 'false' disable SIP based Video-CAC on dot11a radio band."
        DEFVAL { false }
       ::= { cLQd11aCACConfig  25 }

--********************************************************************
--*    Configuration for  Call Admission Control parameters
--*    for VOICE traffic in 802.11b/g interfaces in the controller
--********************************************************************
cLQd11bVoiceAdmCtrlSupport OBJECT-TYPE
        SYNTAX     TruthValue
        MAX-ACCESS read-write
        STATUS     current
        DESCRIPTION
                "This object is used to enable or disable admission 
                control for voice traffic flowing through the 
                802.11b/g interfaces in the controller.
    
                When set to 'true', controller will reserve and manage
                max-bandwidth (cLQd11bVoiceMaxAdmBandwidth)
                and roaming-bandwidth
                (cLQd11bVoiceMaxRoamingBandwidth) as per user
                configured values.
 
                When disabled, admission control will not be enforced. 
                This may delay voice traffic depending on load on the 
                WLAN. "
       DEFVAL { true }
       ::= { cLQd11bCACConfig 1 }

cLQd11bVoiceMaxAdmBandwidth OBJECT-TYPE
        SYNTAX     Unsigned32 (0..100)
        UNITS      "Percent"
        MAX-ACCESS read-write
        STATUS     current
        DESCRIPTION
                "This object denotes the maximum bandwidth that
                can be allocated by controller for voice traffic 
                when admission control is enabled for 802.11b/g
                interfaces in the controller.

                Please note that the write operation on this
                object will be successful only if the 802.11b/g
                network is not operational and the total
                value populated for this object for all the
                admission control attributes (voice, video)
                together does not exceed 100%. "
        ::= { cLQd11bCACConfig 2 }

cLQd11bVoiceMaxRoamBandwidth OBJECT-TYPE
        SYNTAX     Unsigned32 (0..100)
        UNITS      "Percent"
        MAX-ACCESS read-write
        STATUS     current
        DESCRIPTION
                "This object represents the bandwidth relative
                to the maximum allocated bandwidth indicated by
                cLQd11bVoiceMaxAdmBandwidth, that can be 
                allocated to roaming clients for voice traffic,
                when admission control is enabled for 802.11b
                interfaces in the controller.

                Please note that the write operation on this
                object will be successful only if the 802.11b/g
                network is not operational.  The value configured
                through this object takes effect when the 802.11b/g
                network is enabled and operational. " 
        DEFVAL { 0 }
        ::= { cLQd11bCACConfig 3 }

--********************************************************************
--*    Configuration for Call Admission Control parameters
--*    for VIDEO traffic in 802.11b/g interfaces in the controller
--********************************************************************
cLQd11bVideoAdmCtrlSupport OBJECT-TYPE
        SYNTAX     TruthValue
        MAX-ACCESS read-write
        STATUS     current
        DESCRIPTION
                "This object is used to enable or disable admission 
                control for video traffic flowing through the 
                802.11b/g interfaces in the controller.
    
                When set to 'true', controller will reserve and manage
                max-bandwidth (cLQd11bVideoMaxAdmBandwidth) 
                and roaming-bandwidth
                (cLQd11bVideoMaxRoamBandwidth) as per user 
                configured values.
 
                When disabled, admission control will not be enforced. 
                This may delay video traffic depending on load on the 
                WLAN. "
        DEFVAL { true }
        ::= { cLQd11bCACConfig 4 }

cLQd11bVideoMaxAdmBandwidth OBJECT-TYPE
        SYNTAX     Unsigned32 (0..100)
        UNITS      "Percent"
        MAX-ACCESS read-write
        STATUS     current
        DESCRIPTION
                "This object denotes the maximum bandwidth that 
                can be allocated by controller for video traffic when
                admission control is enabled for 802.11b/g interfaces 
                in the controller.  When set to 0, all available
                bandwidth in 802.11b/g interfaces can be allocated
                to video traffic.

                Please note that the write operation on this
                object will be successful only if the 802.11b/g
                network is not operational and the total
                value populated for this object for all the
                admission control attributes (voice, video)
                together does not exceed 100%. " 
        DEFVAL { 0 }
        ::= { cLQd11bCACConfig 5 }

cLQd11bVideoMaxRoamBandwidth OBJECT-TYPE
        SYNTAX     Unsigned32 (0..100)
        UNITS      "Percent"
        MAX-ACCESS read-write
        STATUS     current
        DESCRIPTION
                "This objects represents the bandwidth relative
                to the maximum allocated bandwidth indicated by
                cLQd11bVideoMaxAdmBandwidth, that can be 
                allocated to roaming clients for video traffic,
                when admission control is enabled for 802.11b
                interfaces in the controller.

                Please note that the write operation on this
                object will be successful only if the 802.11b/g
                network is not operational.  The value configured
                through this object takes effect when the 802.11b/g
                network is enabled and operational. "
        DEFVAL { 0 }
        ::= { cLQd11bCACConfig 6 }


--********************************************************************
--*    Configuration of GPR (Gratuitous Probe Response) probe interval
--*    for all 802.11b/g interfaces in the controller
--********************************************************************

cLQd11bGprProbeInterval OBJECT-TYPE
        SYNTAX     Unsigned32(10..100)
        UNITS      "TU"
        MAX-ACCESS read-write
        STATUS     current
        DESCRIPTION
                "This object is used to set GPR probe interval
                period to be used by all 802.11b/g interfaces in the
                controller, when the radios are advertising any
                WLAN with GPR support enabled.

                Please note that the write operation on this
                object will be successful only if the 802.11b/g
                network is not operational.  The value configured
                through this object takes effect when the 802.11b/g
                network is enabled. "
        DEFVAL { 10 }
        ::= { cLQd11bCACConfig 7 }

cLQd11bVoiceCtrl OBJECT-TYPE
        SYNTAX     INTEGER {
                             loadBased(1),
                             static(2)
                           }
        MAX-ACCESS read-write
        STATUS     current
        DESCRIPTION
                "When admission control is enabled these parameters
                can be modified.
                    loadBased - controller will reserve and manage
                                max-bandwidth and roaming-bandwidth
                                based on the load on the WLAN.
                    static    - controller will reserve and
                                manage max-bandwidth
                                (cLQd11bVoiceMaxAdmBandwidth)
                                and roaming-bandwidth
                                (cLQd11bVoiceMaxRoamBandwidth)
                                as per user configured values.
                 When ACM is disabled, admission control will not
                 be enforced. This may delay voice traffic depending
                 on the traffic on the WLAN. "
        DEFVAL { loadBased }
        ::= { cLQd11bCACConfig 8 }

cLQd11bExpeditedBw   OBJECT-TYPE
      SYNTAX      TruthValue
      MAX-ACCESS  read-write
      STATUS      current
      DESCRIPTION
             "This object specifies if expedited BW feature is
              enabled or not.
              A value of 'true' will ensure that the APs advertise
              the expedited BW support in their beacons and
              association responses.
              A value of 'false' will ensure that the APs do not
              advertise the expedited BW support in their beacons
              and association responses."
       ::= { cLQd11bCACConfig  9 }

cLQd11bEdcaProfile OBJECT-TYPE
    SYNTAX          INTEGER  {
                        wmmDefault(1),
                        svpVoice(2),
                        optimizedVoice(3),
                        optimizedVideoVoice(4),
                        customVoice(5)
                    }
    MAX-ACCESS      read-write
    STATUS          current
    DESCRIPTION
        "This object specifies the EDCA profile to be used
        in EDCA Parameter set element. See glossary for EDCA. 
           wmmDefault     - WMM default standard parameters.
           svpVoice       - Spectralink voice priority 
                             parameters.
           optimizedVoice      - parameters for voice optimization.
           optimizedVideoVoice - parameters for video and voice
                                   optimization. 
           customVoice - parameters for customized voice."
    ::= { cLQd11bCACConfig 10 }

cLQd11bMacOptimization OBJECT-TYPE
    SYNTAX          TruthValue
    MAX-ACCESS      read-write
    STATUS          current
    DESCRIPTION
        "This object specifies MAC enhancements for voice,
        resulting in improvement in number of voice calls
        serviced per access point.
        A value of 'true' enables MAC optimization. 
        A value of 'false' disables MAC optimization." 
    ::= { cLQd11bCACConfig 11 }

cLQd11bMaxCallLimit OBJECT-TYPE
    SYNTAX          Unsigned32
    MAX-ACCESS      read-write
    STATUS          deprecated
    DESCRIPTION
        "This object specifies the max number of CAC Voice Calls
        allowed on dot11b radio band.
        Value of zero denotes no limit." 
    ::= { cLQd11bCACConfig 12 }

--********************************************************************
--*    Configuration for Call Admission Control parameters
--*    for mc2uc in 802.11b interfaces in the controller
--********************************************************************

cLQd11bMcastDirectEnable OBJECT-TYPE
        SYNTAX     TruthValue
        MAX-ACCESS read-write
        STATUS     current
        DESCRIPTION
                "This object denotes the decision flag to allow multicast direct
        stream on radio. This overrides Resource Reservation Control status"
        DEFVAL { true }
        ::= { cLQd11bCACConfig 13}

cLQd11bBestEffortAdmission OBJECT-TYPE
        SYNTAX     TruthValue
        MAX-ACCESS read-write
        STATUS     current
        DESCRIPTION
                "This object specifies whether to admit a media stream in best
                 effort queue "
        DEFVAL { false }
        ::= { cLQd11bCACConfig 14}

cLQd11bRedirectBestEffort OBJECT-TYPE
        SYNTAX     TruthValue
        MAX-ACCESS read-write
        STATUS     current
        DESCRIPTION
                "This object specifies whether a unicast or multicast only video
                 stream can be redirected to best effort  "
        DEFVAL { true }
        ::= { cLQd11bCACConfig 15}


cLQd11bRadioMaxStreams OBJECT-TYPE
        SYNTAX     INTEGER (0..20)
        MAX-ACCESS read-write
        STATUS     current
        DESCRIPTION
                "This object denotes the Maximum number of allowed streams per
                 radio for a 802.11b band "
        DEFVAL { 0 }
        ::= { cLQd11bCACConfig 16}

cLQd11bMaxVideoATPercent OBJECT-TYPE
        SYNTAX     INTEGER (0..85)
        UNITS      "Percent"
        MAX-ACCESS read-write
        STATUS     current
        DESCRIPTION
                "This object denotes the Maximum Allowed Bandwidth for video
                 traffic  "
        ::= { cLQd11bCACConfig 17}

cLQd11bMaxVoiceATPercent OBJECT-TYPE
        SYNTAX     INTEGER (0..85)
        UNITS      "Percent"
        MAX-ACCESS read-write
        STATUS     current
        DESCRIPTION
                "This object denotes the Maximum Allowed Bandwidth for voice
                 traffic  "
        ::= { cLQd11bCACConfig 18}

cLQd11bMaxMediaATPercent OBJECT-TYPE
        SYNTAX     INTEGER (0..100)
        UNITS      "Percent"
        MAX-ACCESS read-write
        STATUS     current
        DESCRIPTION
                "This object denotes the Maximum Allowed Bandwidth for Media
                 traffic  "
        ::= { cLQd11bCACConfig 19}

cLQd11bMinPhyRate OBJECT-TYPE
        SYNTAX     CiscoLwappDot11bPhyRates 
        UNITS      "Mbps"
        MAX-ACCESS read-write
        STATUS     current
        DESCRIPTION
                "This object denotes that Client needs to have at least this
                 rate enabled in order to join media stream  "
        DEFVAL { 1 }
        ::= { cLQd11bCACConfig 20}

cLQd11bClientMaxStreams OBJECT-TYPE
        SYNTAX     INTEGER (0..20)
        MAX-ACCESS read-write
        STATUS     current
        DESCRIPTION
                "This object denotes the Maximum number of allowed streams per
                 client for a 802.11b band "
        DEFVAL { 0 }
        ::= { cLQd11bCACConfig 21}

cLQd11bSipCacSupportEnable  OBJECT-TYPE
      SYNTAX      TruthValue
      MAX-ACCESS  read-write
      STATUS      current
      DESCRIPTION
             "This object represents if SIP CAC is supported on dot11b radio band.
              A value of 'true' enables SIP CAC support on dot11b radio band.
              A value of 'false' disable SIP CAC support on dot11b radio band."
        DEFVAL { false }
       ::= { cLQd11bCACConfig  22 }

cLQd11bMaxRetryPercent OBJECT-TYPE
        SYNTAX     INTEGER (0..100)
        UNITS      "Percent"
        MAX-ACCESS read-write
        STATUS     current
        DESCRIPTION
                "This object denotes the maximum retry percent for Media
                 traffic on dot11b radio band."
        ::= { cLQd11bCACConfig 23}

--******************************************************************
--      Configuration of Video CAC Method
--******************************************************************
cLQd11bVideoCtrl OBJECT-TYPE
        SYNTAX     INTEGER {
                             loadBased(1),
                             static(2)
                           }
        MAX-ACCESS read-write
        STATUS     current
        DESCRIPTION
                "This object denotes the admission control (ACM) method
                used on dot11a radio band. When admission control is
                enabled these parameters can be modified.
                    loadBased - controller will reserve and manage
                                max-bandwidth and roaming-bandwidth
                                based on the load on the WLAN.
                    static    - controller will reserve and
                                manage max-bandwidth
                                (cLQd11aVoiceMaxAdmBandwidth)
                                and roaming-bandwidth
                                (cLQd11aVoiceMaxRoamBandwidth)
                                as per user configured values.
                 When ACM is disabled, admission control will not
                 be enforced. This may delay video traffic depending
                 on the traffic on the WLAN. "
        DEFVAL { loadBased }
        ::= { cLQd11bCACConfig 24 }

--******************************************************************
--      Configuration of SIP based Video-CAC method
--******************************************************************
cLQd11bSipCacVideoEnable  OBJECT-TYPE
      SYNTAX      TruthValue
      MAX-ACCESS  read-write
      STATUS      current
      DESCRIPTION
             "This object represents if SIP based Video-CAC is enabled on dot11a radio band.
              A value of 'true' enables SIP based Video-CAC on dot11a radio band.
              A value of 'false' disable SIP based Video-CAC on dot11a radio band."
        DEFVAL { false }
       ::= { cLQd11bCACConfig  25 }


--********************************************************************
-- Table to represent (Gratuitous Probe Response) GPR 
-- parameters per each WLAN. 
--********************************************************************

cLQd11GprTable OBJECT-TYPE
        SYNTAX     SEQUENCE OF CLQd11GprEntry
        MAX-ACCESS not-accessible
        STATUS     current
        DESCRIPTION
                "This table populates the GPR configuration on the
                WLANs configured on this controller.  

                There exists a row in this table for each WLAN
                configured through cLWlanConfigTable.  A row is added
                is to this table by the agent when a WLAN is created
                by the user through an explicit management action
                initiated from a network management station.
                Similarly a row gets deleted automatically when the
                user deletes the particular WLAN. "
        ::= { cLQd11GprConfig 1 }

cLQd11GprEntry OBJECT-TYPE
        SYNTAX     CLQd11GprEntry 
        MAX-ACCESS not-accessible
        STATUS     current
        DESCRIPTION
                "Each entry represents a conceptual row in
                cLQd11GprTable and corresponds to the
                GPR configuration on a WLAN. " 
        INDEX { cLWlanIndex }
        ::= { cLQd11GprTable 1 }

CLQd11GprEntry ::=
        SEQUENCE {
                cLQd11GprSupport        TruthValue
        }

cLQd11GprSupport OBJECT-TYPE
        SYNTAX     TruthValue
        MAX-ACCESS read-write
        STATUS     current
        DESCRIPTION
                "If 'true', then the corresponding radios that 
                advertise this WLAN, will send Gratuitous Probe 
                Response.  If 'false', then the corresponding radios 
                that advertise this WLAN, will not send Gratuitous 
                Probe Response. "
        DEFVAL { false }
        ::= { cLQd11GprEntry 1}

--********************************************************************
--*  CALL admission control statistics
--********************************************************************

cLQd11CACStatsTable OBJECT-TYPE
        SYNTAX     SEQUENCE OF CLQd11CACStatsEntry
        MAX-ACCESS not-accessible
        STATUS     current
        DESCRIPTION
                "This table populates the call admission control
                metrics collected by observing the voice or video
                traffic on the dot11 interface of a particular
                AP. 

                There exists a row in this table for each row
                corresponding to a dot11 interface found in
                cLApDot11IfTable.  A row corresponding to a
                dot11 interface is added when an AP joins the
                controller.  The row gets deleted when the AP
                dissociates from the controller. "
        ::= {  cLQd11CACStats 1 }

CLQd11CACStatsEntry ::= 
        SEQUENCE {
                cLQd11CacVoiceBwInUse         Gauge32, 
                cLQd11CacVideoBwInUse         Gauge32, 
                cLQd11CacVoiceCallsInProgress Gauge32,
                cLQd11CacRoamVoiceCallsInProg Gauge32,
                cLQd11CacTotalVoiceCallsAP    Counter32,
                cLQd11CacTotalRoamCallsAP     Counter32,
                cLQd11CacVoiceCallsRejectedAP Counter32,
                cLQd11CacRoamCallsRejectedAP  Counter32,
                cLQd11CacRejCallsInsufBw      Counter32,
                cLQd11CacRejCallsBadParams    Counter32,
                cLQd11CacRejCallsPhyRate      Counter32,
                cLQd11CacRejCallsQosPolicy    Counter32,
                cLQd11SipCacNonRoamCallsInProgress Gauge32,
                cLQd11SipCacRoamCallsInProg      Gauge32,
                cLQd11SipCacTotalNonRoamCallsAP  Counter32,
                cLQd11SipCacTotalRoamCallsAP     Counter32,
                cLQd11SipCacNonRoamCallsRejectedInSuffBw Counter32,
                cLQd11SipCacRoamCallsRejectedInSuffBw  Counter32,
                cLQd11SipCacNonRoamCallsRejectedMaxLimit Counter32,
                cLQd11SipCacRoamCallsRejectedMaxLimit  Counter32,
                cLQd11SipCacRejCallsQosPolicy      Counter32,
                cLQd11SipCacPreferredCallsReceived Counter32,
                cLQd11SipCacPreferredCallsAccepted Counter32,
                cLQd11KtsCacNonRoamCallsInProgress Gauge32,
                cLQd11KtsCacRoamCallsInProg        Gauge32,
                cLQd11KtsCacTotalNonRoamCallsAP    Counter32,
                cLQd11KtsCacTotalRoamCallsAP       Counter32,
                cLQd11KtsCacNonRoamCallsRejectedInSuffBw Counter32,
                cLQd11KtsCacRoamCallsRejectedInSuffBw    Counter32,

                cLQd11CacVideoRoamBwInUse          Gauge32,
                cLQd11CacVideoTotalBwInUse         Gauge32,
                cLQd11CacVideoCallsInProgress      Gauge32,
                cLQd11CacVideoRoamCallsInProg      Gauge32,
                cLQd11CacVideoTotalCallsAP         Counter32,
                cLQd11CacVideoTotalRoamCallsAP     Counter32,
                cLQd11CacVideoCallsRejectedAP      Counter32,
                cLQd11CacVideoRoamCallsRejectedAP  Counter32,
                cLQd11CacVideoRejCallsInsufBw      Counter32,
                cLQd11CacVideoRejCallsBadParams    Counter32,
                cLQd11CacVideoRejCallsPhyRate      Counter32,
                cLQd11CacVideoRejCallsQosPolicy    Counter32,
                cLQd11SipCacVideoCallsInProgress              Gauge32,
                cLQd11SipCacVideoRoamCallsInProg              Gauge32,
                cLQd11SipCacVideoTotalCallsAP                 Counter32,
                cLQd11SipCacVideoTotalRoamCallsAP             Counter32,
                cLQd11SipCacVideoCallsRejectedInSuffBw        Counter32,
                cLQd11SipCacVideoRoamCallsRejectedInSuffBw    Counter32
        }

cLQd11CACStatsEntry OBJECT-TYPE
        SYNTAX     CLQd11CACStatsEntry
        MAX-ACCESS not-accessible
        STATUS     current
        DESCRIPTION
                "Each entry represents a conceptual row in
                CLQd11CACStatsTable and corresponds to the 
                admission control statistics for a particular
                dot11 interface. "
-- The following was converted from AUGMENTS to INDEX to separate
-- implementation and does not have any external impact
-- to users of MIB. The version available at mib-police page
-- will be shipped to the customers. This version is for
-- INTERNAL USE ONLY.
--      AUGMENTS { cLApDot11IfEntry }
        INDEX  {
                cLApSysMacAddress,
                cLApDot11IfSlotId
        }
        ::= {  cLQd11CACStatsTable 1 }
                 
cLQd11CacVoiceBwInUse OBJECT-TYPE
        SYNTAX     Gauge32(0..100)
        UNITS      "Percent" 
        MAX-ACCESS read-only
        STATUS     current
        DESCRIPTION
                "This object indicates the voice bandwidth in use
                as a percentage of the bandwidth configured through
                cLQd11aVoiceMaxAdmBandwidth or
                cLQd11bVoiceMaxAdmBandwidth, depending on the type
                of this dot11 interface. "  
        ::= {  cLQd11CACStatsEntry 1 }

cLQd11CacVideoBwInUse OBJECT-TYPE
        SYNTAX     Gauge32(0..100)
        UNITS      "Percent" 
        MAX-ACCESS read-only
        STATUS     current
        DESCRIPTION
                "This object indicates the video bandwidth in use
                as a percentage of the bandwidth configured through
                cLQd11aVideoMaxAdmBandwidth or
                cLQd11bVideoMaxAdmBandwidth, depending on the type
                of this dot11 interface. "  
        ::= {  cLQd11CACStatsEntry 2 }

cLQd11CacVoiceCallsInProgress OBJECT-TYPE
        SYNTAX     Gauge32
        MAX-ACCESS read-only
        STATUS     current
        DESCRIPTION
                "This object indicates the count of the number of 
                voice calls currently in progress on this dot11
                interface. "
        ::= {  cLQd11CACStatsEntry 3 }

cLQd11CacRoamVoiceCallsInProg OBJECT-TYPE
        SYNTAX     Gauge32 
        MAX-ACCESS read-only
        STATUS     current
        DESCRIPTION
                "This object indicates the count of the number of 
                voice calls initiated from roaming clients
                currently in progress on this dot11 interface. "
        ::= {  cLQd11CACStatsEntry 4 }

cLQd11CacTotalVoiceCallsAP OBJECT-TYPE
        SYNTAX     Counter32
        MAX-ACCESS read-only
        STATUS     current
        DESCRIPTION
                "This object indicates the count of the number of 
                voice calls observed on this dot11 interface
                ever since this AP has joined the controller. "
        ::= {  cLQd11CACStatsEntry 5 }

cLQd11CacTotalRoamCallsAP OBJECT-TYPE
        SYNTAX     Counter32
        MAX-ACCESS read-only
        STATUS     current
        DESCRIPTION
                "This object indicates the count of the number of 
                voice and video calls initiated from roaming clients
                observed on this dot11 interface ever since
                this AP has joined the controller. "
        ::= {  cLQd11CACStatsEntry 6 }

cLQd11CacVoiceCallsRejectedAP OBJECT-TYPE
        SYNTAX     Counter32
        MAX-ACCESS read-only
        STATUS     current
        DESCRIPTION
                "This object indicates the count of the number of 
                voice calls observed as rejected on this dot11
                interface, ever since this AP has joined the
                controller. "
        ::= {  cLQd11CACStatsEntry 7 }

cLQd11CacRoamCallsRejectedAP OBJECT-TYPE
        SYNTAX     Counter32
        MAX-ACCESS read-only
        STATUS     current
        DESCRIPTION
                "This object indicates the count of the number of 
                voice and video calls initiated from roaming
                clients observed as rejected on this dot11
                interface, ever since this AP has joined the
                controller. "
        ::= {  cLQd11CACStatsEntry 8 }

cLQd11CacRejCallsInsufBw OBJECT-TYPE
        SYNTAX     Counter32
        MAX-ACCESS read-only
        STATUS     current
        DESCRIPTION
                "This object indicates the count of the number of 
                calls observed as rejected on this dot11
                interface due to insufficient bandwidth, ever
                since this AP has joined the controller. "
        ::= {  cLQd11CACStatsEntry 9 }

cLQd11CacRejCallsBadParams OBJECT-TYPE
        SYNTAX     Counter32
        MAX-ACCESS read-only
        STATUS     current
        DESCRIPTION
                "This object indicates the count of the number of 
                calls observed as rejected on this dot11
                interface due to mismatch in call parameters, ever
                since this AP has joined the controller. "
        ::= {  cLQd11CACStatsEntry 10 }

cLQd11CacRejCallsPhyRate OBJECT-TYPE
        SYNTAX     Counter32
        MAX-ACCESS read-only
        STATUS     current
        DESCRIPTION
                "This object indicates the count of the number of 
                calls observed as rejected on this dot11
                interface due to mismatch in 802.11 data rates,
                ever since this AP has joined the controller. "
        ::= {  cLQd11CACStatsEntry 11 }

cLQd11CacRejCallsQosPolicy OBJECT-TYPE
        SYNTAX     Counter32
        MAX-ACCESS read-only
        STATUS     current
        DESCRIPTION
                "This object indicates the count of the number of 
                calls observed as rejected on this dot11
                interface due to restrictions imposed by QOS
                policies, ever since this AP has joined the
                controller. "
        ::= {  cLQd11CACStatsEntry 12 }

cLQd11SipCacNonRoamCallsInProgress OBJECT-TYPE
    SYNTAX          Gauge32
    MAX-ACCESS      read-only
    STATUS          current
    DESCRIPTION
        "This object indicates the number of non-roaming SIP calls
        currently in progress on this dot11 interface." 
    ::= { cLQd11CACStatsEntry 13 }

cLQd11SipCacRoamCallsInProg OBJECT-TYPE
    SYNTAX          Gauge32
    MAX-ACCESS      read-only
    STATUS          current
    DESCRIPTION
        "This object indicates the number of SIP calls initiated
        from roaming clients currently in progress on this 
        dot11 interface." 
    ::= { cLQd11CACStatsEntry 14 }

cLQd11SipCacTotalNonRoamCallsAP OBJECT-TYPE
    SYNTAX          Counter32
    MAX-ACCESS      read-only
    STATUS          current
    DESCRIPTION
        "This object indicates the number of non-roaming SIP calls
        observed on this dot11 interface since this AP has joined 
        the controller." 
    ::= { cLQd11CACStatsEntry 15 }

cLQd11SipCacTotalRoamCallsAP OBJECT-TYPE
    SYNTAX          Counter32
    MAX-ACCESS      read-only
    STATUS          current
    DESCRIPTION
        "This object indicates the number of SIP calls initiated
        from roaming clients observed on this dot11 interface ever 
        this AP has joined the controller." 
    ::= { cLQd11CACStatsEntry 16 }

cLQd11SipCacNonRoamCallsRejectedInSuffBw OBJECT-TYPE
    SYNTAX          Counter32
    MAX-ACCESS      read-only
    STATUS          current
    DESCRIPTION
        "This object indicates the number of non-roaming SIP calls
        observed as rejected on this dot11 interface due to insufficient
        bandwidth, since this AP has joined the controller." 
    ::= { cLQd11CACStatsEntry 17 }

cLQd11SipCacRoamCallsRejectedInSuffBw OBJECT-TYPE
    SYNTAX          Counter32
    MAX-ACCESS      read-only
    STATUS          current
    DESCRIPTION
        "This object indicates the number of SIP calls initiated
        from roaming clients observed as rejected on this dot11
        interface due to insufficient bandwidth, since this AP has 
        joined the controller." 
    ::= { cLQd11CACStatsEntry 18 }

cLQd11SipCacNonRoamCallsRejectedMaxLimit OBJECT-TYPE
    SYNTAX          Counter32
    MAX-ACCESS      read-only
    STATUS          current
    DESCRIPTION
        "This object indicates the number of non-roaming SIP calls
        observed as rejected on this dot11 interface due to maximum 
        limit exceeded, since this AP has joined the controller." 
    ::= { cLQd11CACStatsEntry 19 }

cLQd11SipCacRoamCallsRejectedMaxLimit OBJECT-TYPE
    SYNTAX          Counter32
    MAX-ACCESS      read-only
    STATUS          current
    DESCRIPTION
        "This object indicates the number of roaming SIP calls observed
        as rejected on this dot11 interface due to maximum limit 
        exceeded, since this AP has joined the controller." 
    ::= { cLQd11CACStatsEntry 20 }

cLQd11SipCacRejCallsQosPolicy OBJECT-TYPE
    SYNTAX          Counter32
    MAX-ACCESS      read-only
    STATUS          deprecated
    DESCRIPTION
        "This object indicates the number of SIP calls observed as
        rejected on this dot11 interface due to restrictions imposed 
        by QOS policies, ever since this AP has joined the controller." 
    ::= { cLQd11CACStatsEntry 21 }

cLQd11SipCacPreferredCallsReceived OBJECT-TYPE
        SYNTAX     Counter32
        MAX-ACCESS read-only
        STATUS     current
        DESCRIPTION
                "This object indicates the count of the number of
                Preferred calls observed as received on this dot11
                interface due to restrictions imposed by QOS
                policies, ever since this AP has joined the
                controller. "
        ::= {  cLQd11CACStatsEntry 22 }

cLQd11SipCacPreferredCallsAccepted OBJECT-TYPE
        SYNTAX     Counter32
        MAX-ACCESS read-only
        STATUS     current
        DESCRIPTION
                "This object indicates the count of the number of
                Preferred calls observed as accepted on this dot11
                interface due to restrictions imposed by QOS
                policies, ever since this AP has joined the
                controller. "
        ::= {  cLQd11CACStatsEntry 23 }

cLQd11KtsCacNonRoamCallsInProgress OBJECT-TYPE
    SYNTAX          Gauge32
    MAX-ACCESS      read-only
    STATUS          current
    DESCRIPTION
        "This object indicates the number of non-roaming KTS calls
        currently in progress on this dot11 interface."
    ::= { cLQd11CACStatsEntry 24 }

cLQd11KtsCacRoamCallsInProg OBJECT-TYPE
    SYNTAX          Gauge32
    MAX-ACCESS      read-only
    STATUS          current
    DESCRIPTION
        "This object indicates the number of KTS calls initiated
        from roaming clients currently in progress on this
        dot11 interface."
    ::= { cLQd11CACStatsEntry 25 }

cLQd11KtsCacTotalNonRoamCallsAP OBJECT-TYPE
    SYNTAX          Counter32
    MAX-ACCESS      read-only
    STATUS          current
    DESCRIPTION
        "This object indicates the number of non-roaming KTS calls
        observed on this dot11 interface since this AP has joined
        the controller."
    ::= { cLQd11CACStatsEntry 26 }

cLQd11KtsCacTotalRoamCallsAP OBJECT-TYPE
    SYNTAX          Counter32
    MAX-ACCESS      read-only
    STATUS          current
    DESCRIPTION
        "This object indicates the number of KTS calls initiated
        from roaming clients observed on this dot11 interface ever
        this AP has joined the controller."
    ::= { cLQd11CACStatsEntry 27 }

cLQd11KtsCacNonRoamCallsRejectedInSuffBw OBJECT-TYPE
    SYNTAX          Counter32
    MAX-ACCESS      read-only
    STATUS          current
    DESCRIPTION
        "This object indicates the number of non-roaming KTS calls
        observed as rejected on this dot11 interface due to insufficient
        bandwidth, since this AP has joined the controller."
    ::= { cLQd11CACStatsEntry 28 }

cLQd11KtsCacRoamCallsRejectedInSuffBw OBJECT-TYPE
    SYNTAX          Counter32
    MAX-ACCESS      read-only
    STATUS          current
    DESCRIPTION
        "This object indicates the number of KTS calls initiated
        from roaming clients observed as rejected on this dot11
        interface due to insufficient bandwidth, since this AP has
        joined the controller."
    ::= { cLQd11CACStatsEntry 29 }

cLQd11CacVideoRoamBwInUse OBJECT-TYPE
    SYNTAX     Gauge32(0..100)
    UNITS      "Percent"
    MAX-ACCESS read-only
    STATUS     current
    DESCRIPTION
        "This object indicates the video roaming bandwidth in use
        as a percentage of the bandwidth configured through
        cLQd11aVideoMaxRoamBandwidth or cLQd11bVideoMaxRoamBandwidth, 
        depending on the type of this dot11 interface. "
    ::= {  cLQd11CACStatsEntry 30 }

cLQd11CacVideoTotalBwInUse OBJECT-TYPE
    SYNTAX     Gauge32(0..100)
    UNITS      "Percent"
    MAX-ACCESS read-only
    STATUS     current
    DESCRIPTION
        "This object indicates the total video bandwidth in use."
    ::= {  cLQd11CACStatsEntry 31 }

cLQd11CacVideoCallsInProgress OBJECT-TYPE
    SYNTAX     Gauge32
    MAX-ACCESS read-only
    STATUS     current
    DESCRIPTION
        "This object indicates the count of the number of
        video calls currently in progress on this dot11
        interface. "
    ::= {  cLQd11CACStatsEntry 32 }

cLQd11CacVideoRoamCallsInProg OBJECT-TYPE
    SYNTAX     Gauge32
    MAX-ACCESS read-only
    STATUS     current
    DESCRIPTION
        "This object indicates the count of the number of
        video calls initiated from roaming clients
        currently in progress on this dot11 interface. "
    ::= {  cLQd11CACStatsEntry 33 }
 
cLQd11CacVideoTotalCallsAP OBJECT-TYPE
    SYNTAX     Counter32
    MAX-ACCESS read-only
    STATUS     current
    DESCRIPTION
        "This object indicates the count of the number of
        video calls observed on this dot11 interface
        ever since this AP has joined the controller. "
    ::= {  cLQd11CACStatsEntry 34 }

cLQd11CacVideoTotalRoamCallsAP     OBJECT-TYPE
    SYNTAX     Counter32
    MAX-ACCESS read-only
    STATUS     current
    DESCRIPTION
        "This object indicates the count of the number of
        video calls initiated from roaming clients
        observed on this dot11 interface ever since
        this AP has joined the controller. "
    ::= {  cLQd11CACStatsEntry 35 }
 
cLQd11CacVideoCallsRejectedAP OBJECT-TYPE
    SYNTAX     Counter32
    MAX-ACCESS read-only
    STATUS     current
    DESCRIPTION
        "This object indicates the count of the number of 
        video calls observed as rejected on this dot11
        interface, ever since this AP has joined the
        controller. "
    ::= {  cLQd11CACStatsEntry 36 }
 
cLQd11CacVideoRoamCallsRejectedAP  OBJECT-TYPE
    SYNTAX     Counter32
    MAX-ACCESS read-only
    STATUS     current
    DESCRIPTION
        "This object indicates the count of the number of 
        video calls initiated from roaming
        clients observed as rejected on this dot11
        interface, ever since this AP has joined the
        controller. "
    ::= {  cLQd11CACStatsEntry 37 }
 
cLQd11CacVideoRejCallsInsufBw    OBJECT-TYPE
    SYNTAX     Counter32
    MAX-ACCESS read-only
    STATUS     current
    DESCRIPTION
        "This object indicates the count of the number of 
        video calls observed as rejected on this dot11
        interface due to insufficient bandwidth, ever
        since this AP has joined the controller. "
    ::= {  cLQd11CACStatsEntry 38 }
 
cLQd11CacVideoRejCallsBadParams    OBJECT-TYPE
    SYNTAX     Counter32
    MAX-ACCESS read-only
    STATUS     current
    DESCRIPTION
        "This object indicates the count of the number of 
        video calls observed as rejected on this dot11
        interface due to mismatch in call parameters, ever
        since this AP has joined the controller. "
    ::= {  cLQd11CACStatsEntry 39 }
 
cLQd11CacVideoRejCallsPhyRate OBJECT-TYPE
    SYNTAX     Counter32
    MAX-ACCESS read-only
    STATUS     current
    DESCRIPTION
        "This object indicates the count of the number of 
        video calls observed as rejected on this dot11
        interface due to mismatch in 802.11 data rates,
        ever since this AP has joined the controller. "
    ::= {  cLQd11CACStatsEntry 40 }
 
cLQd11CacVideoRejCallsQosPolicy OBJECT-TYPE
    SYNTAX     Counter32
    MAX-ACCESS read-only
    STATUS     current
    DESCRIPTION
        "This object indicates the count of the number of 
        video calls observed as rejected on this dot11
        interface due to restrictions imposed by QOS
        policies, ever since this AP has joined the
        controller. "
    ::= {  cLQd11CACStatsEntry 41 }
 
cLQd11SipCacVideoCallsInProgress OBJECT-TYPE
    SYNTAX          Gauge32
    MAX-ACCESS      read-only
    STATUS          current
    DESCRIPTION
        "This object indicates the number of non-roaming SIP video 
        calls currently in progress on this dot11 interface." 
    ::= { cLQd11CACStatsEntry 42 }
 
cLQd11SipCacVideoRoamCallsInProg OBJECT-TYPE
    SYNTAX          Gauge32
    MAX-ACCESS      read-only
    STATUS          current
    DESCRIPTION
        "This object indicates the number of SIP video calls initiated
        from roaming clients currently in progress on this 
        dot11 interface." 
    ::= { cLQd11CACStatsEntry 43 }
 
cLQd11SipCacVideoTotalCallsAP OBJECT-TYPE
    SYNTAX          Counter32
    MAX-ACCESS      read-only
    STATUS          current
    DESCRIPTION
        "This object indicates the number of non-roaming SIP video calls
        observed on this dot11 interface since this AP has joined 
        the controller." 
    ::= { cLQd11CACStatsEntry 44 }
 
cLQd11SipCacVideoTotalRoamCallsAP OBJECT-TYPE
    SYNTAX          Counter32
    MAX-ACCESS      read-only
    STATUS          current
    DESCRIPTION
        "This object indicates the number of SIP video calls initiated
        from roaming clients observed on this dot11 interface ever 
        this AP has joined the controller." 
    ::= { cLQd11CACStatsEntry 45 }
 
cLQd11SipCacVideoCallsRejectedInSuffBw OBJECT-TYPE
    SYNTAX          Counter32
    MAX-ACCESS      read-only
    STATUS          current
    DESCRIPTION
        "This object indicates the number of non-roaming SIP video calls
        observed as rejected on this dot11 interface due to insufficient
        bandwidth, since this AP has joined the controller." 
    ::= { cLQd11CACStatsEntry 46 }
 
cLQd11SipCacVideoRoamCallsRejectedInSuffBw OBJECT-TYPE
    SYNTAX          Counter32
    MAX-ACCESS      read-only
    STATUS          current
    DESCRIPTION
        "This object indicates the number of SIP video calls initiated
        from roaming clients observed as rejected on this dot11
        interface due to insufficient bandwidth, since this AP has 
        joined the controller." 
    ::= { cLQd11CACStatsEntry 47 }
 

--********************************************************************
--*    Voice stats per radio
--********************************************************************
cLQd11VoiceStatsTable OBJECT-TYPE
    SYNTAX          SEQUENCE OF CLQd11VoiceStatsEntry 
    MAX-ACCESS      not-accessible
    STATUS          current
    DESCRIPTION
        "This table represents the voice statistics
        calculated for each radio on an AP.
        An entry is automatically added by the controller
        when a voice call is successfully placed. 
        Entry is deleted when AP disassociates the 
        Controller."
    ::= { cLQd11VoiceStats 1 }

cLQd11VoiceStatsEntry OBJECT-TYPE
    SYNTAX          CLQd11VoiceStatsEntry
    MAX-ACCESS      not-accessible
    STATUS          current
    DESCRIPTION
        "Each entry in this table provides voice related statistics for
        each radio on an AP. 
        Entries are removed when the AP disassociates the controller."
    INDEX           {
                        cLApSysMacAddress,
                        cLApDot11IfSlotId
                    } 
    ::= { cLQd11VoiceStatsTable 1 }

CLQd11VoiceStatsEntry ::= SEQUENCE {
        cLQd11VoiceCallCounts        Counter32,
        cLQd11CacVoiceCallTimePeriod TimeIntervalSec
}

cLQd11VoiceCallCounts OBJECT-TYPE
    SYNTAX          Counter32
    UNITS           "calls"
    MAX-ACCESS      read-only
    STATUS          current
    DESCRIPTION
        "This object indicates cumulative number of successful
        VOIP calls placed using this radio." 
    ::= { cLQd11VoiceStatsEntry 1 }

cLQd11CacVoiceCallTimePeriod OBJECT-TYPE
    SYNTAX          TimeIntervalSec
    UNITS           "seconds"
    MAX-ACCESS      read-only
    STATUS          current
    DESCRIPTION
        "This object indicates cumulative call proceed time
        in seconds." 
    ::= { cLQd11VoiceStatsEntry 2 }

--********************************************************************
--*   Per WLAN voice config
--********************************************************************

cLQVoiceWlanConfigTable OBJECT-TYPE
    SYNTAX          SEQUENCE OF CLQVoiceWlanConfigEntry 
    MAX-ACCESS      not-accessible
    STATUS          current
    DESCRIPTION
        "This table contains per WLAN voice related
        configuration. 

        There is a row in this table for every WLAN
        configured through cLWlanConfigTable.  A row is added
        to this table by the agent when a WLAN is created
        by the user through an explicit management action
        initiated from a network management station.
        Similarly a row gets deleted automatically when the
        user deletes the particular WLAN."
    ::= { cLQVoiceWlanConfig 1 }

cLQVoiceWlanConfigEntry OBJECT-TYPE
    SYNTAX          CLQVoiceWlanConfigEntry
    MAX-ACCESS      not-accessible
    STATUS          current
    DESCRIPTION
        "An entry containing information about voice configuration for
        a particular WLAN."
    INDEX           { cLWlanIndex } 
    ::= { cLQVoiceWlanConfigTable 1 }

CLQVoiceWlanConfigEntry ::= SEQUENCE {
        cLQVoiceWlanConfigDetectVoipCallFailure TruthValue
}

cLQVoiceWlanConfigDetectVoipCallFailure OBJECT-TYPE
    SYNTAX          TruthValue
    MAX-ACCESS      read-write
    STATUS          current
    DESCRIPTION
        "If 'true', then the corresponding radios that
        advertise this WLAN, will snoop voice packets 
        to detect call failure and report by sending trap. 
        If 'false', then the corresponding radios 
        that advertise this WLAN, will not detect call failure 
        and hence will not send trap."
    DEFVAL          { false } 
    ::= { cLQVoiceWlanConfigEntry 1 }

--********************************************************************
--*    Client table - voice related objects
--********************************************************************

cLQVoiceClientTable OBJECT-TYPE
    SYNTAX          SEQUENCE OF CLQVoiceClientEntry 
    MAX-ACCESS      not-accessible
    STATUS          current
    DESCRIPTION
        "This table contains voice related client properties.

        There exists a row in this table for each associated
        voice clients.  
        A row is added to this table by the 
        agent when a voice client gets associated.
        Similarly, a row gets deleted automatically when the
        voice client gets disassociated."
    ::= { cLQVoiceClient 1 }

cLQVoiceClientEntry OBJECT-TYPE
    SYNTAX          CLQVoiceClientEntry
    MAX-ACCESS      not-accessible
    STATUS          current
    DESCRIPTION
        "An entry containing voice call management information for a
        particular client."
    INDEX           { cldcClientMacAddress } 
    ::= { cLQVoiceClientTable 1 }

CLQVoiceClientEntry ::= SEQUENCE {
        cLQVoiceClientCallingNumber             SnmpAdminString,
        cLQVoiceClientLastCalledNumber          SnmpAdminString,
        cLQVoiceClientLastCallFailureReasonCode INTEGER
}

cLQVoiceClientCallingNumber OBJECT-TYPE
    SYNTAX          SnmpAdminString
    MAX-ACCESS      read-only
    STATUS          current
    DESCRIPTION
        "This object indicates calling number of this
        voice client" 
    ::= { cLQVoiceClientEntry 1 }

cLQVoiceClientLastCalledNumber OBJECT-TYPE
    SYNTAX          SnmpAdminString
    MAX-ACCESS      read-only
    STATUS          current
    DESCRIPTION
        "This object indicates last called number from this
        voice client" 
    ::= { cLQVoiceClientEntry 2 }

cLQVoiceClientLastCallFailureReasonCode OBJECT-TYPE
    SYNTAX          INTEGER  {
                        unknown(1),
                        normalFailure(2),
                        roamFailure(3),
                        maxLimitExceeded(4),
                        sipPrefCallNoBw(5),
                        badRequest(400),
                        unathorized(401),
                        paymentRequired(402),
                        forbidden(403),
                        notFound(404),
                        methodNotallowed(405),
                        notAcceptable(406),
                        proxyAuthenticationRequired(407),
                        requestTimeout(408),
                        conflict(409),
                        gone(410),
                        lengthRequired(411),
                        requestEntityTooLarge(413),
                        requestURITooLarge(414),
                        unsupportedMdediaType(415),
                        badExtension(420),
                        temporarilyNotAvailable(480),
                        callLegDoesNotExist(481),
                        loopDetected(482),
                        tooManyHops(483),
                        addressIncomplete(484),
                        ambiguous(485),
                        busy(486),
                        internalServerError(500),
                        notImplemented(501),
                        badGateway(502),
                        serviceUnavailable(503),
                        serverTimeout(504),
                        versionNotSupported(505),
                        busyEverywhere(600),
                        decline(603),
                        doesNotExistAnywhere(604),
                        sessionNotAcceptable(606)
                    }
    MAX-ACCESS      read-only
    STATUS          current
    DESCRIPTION
        "This object represents last VOIP failue reason code
        of this voice client.
        These reason codes are taken from SIP standards.

        unknown               - Unknown error

        normalFailure         - Call failed for insufficient bandwidth 


        roamFailure           - SIP call failed during roaming

        maxLimitExceeded      - Maximum SIP call permissible limit 
        was exceeded.

        sipPrefCallNoBw       - SIP Preferred call failed for insufficient 
        bandwidth

        badRequest            - The request could not be understood 
        due to malformed syntax.

        unathorized           - The request requires user 
        authentication.

        paymentRequired       - Reserved for future.

        forbidden             - The server understood the request, 
        but is refusing to fulfill it.

        notFound              - The server has definitive information
        that the user does not exist at the domain specified in the 
        Request-URI.

        methodNotallowed      - The method specified in the 
        Request-Line is understood, but not allowed for the address 
        identified by the Request-URI.

        notAcceptable         - The resource identified by the request 
        is only capable of generating response entities that have 
        content characteristics not acceptable according to the Accept
        header field sent in the request.

        proxyAuthenticationRequired - This code is similar to 401 
        (Unauthorized), but indicates that the client MUST first 
        authenticate itself with the proxy.  

        requestTimeout        - The server could not produce a 
        response within a suitable amount of time, for example, 
        if it could not determine the location of the user in time.

        conflict              - This is used to indicate that the 
        request could not be completed due to a conflict with the 
        current state of the resource.

        gone                  - The requested resource is no longer 
        available at the server and no forwarding address is known.

        lengthRequired        -  The server is refusing to process a 
        request because the request entity-body is larger than the 
        server is willing or able to process.

        requestEntityTooLarge - The server is refusing to process a 
        request because the request entity-body is larger than the 
        server is willing or able to process.

        requestURITooLarge    - The server is refusing to service the
        request because the Request-URI is longer than the server is 
        willing to interpret.

        unsupportedMediaType - The server is refusing to service the 
        request because the message body of the request is in a format 
        not supported by the server for the requested method.

        badExtension          - The server did not understand the 
        protocol extension specified in a Proxy-Require  or Require 
        header field.

        temporarilyNotAvailable - The callee's end system was contacted

        successfully but the callee is currently unavailable.

        callLegDoesNotExist   - This status indicates that the UAS 
        received a request that does not match any existing dialog 
        or transaction.

        loopDetected          - The server has detected a loop.

        tooManyHops           - The server received a request that 
        contains a Max-Forwards header field with the value zero.

        addressIncomplete     - The server received a request with a 
        Request-URI that was incomplete.

        ambiguous             - The Request-URI was ambiguous.

        busy                  - The callee's end system was contacted 
        successfully, but the callee is currently not willing or able 
        to take additional calls at this end system. 

        internalServerError   - The server encountered an unexpected 
        condition that prevented it from fulfilling the request.

        notImplemented        - The server does not support the 
        functionality required to fulfill the request. 

        badGateway            - The server, while acting as a gateway 
        or proxy, received an invalid response from the downstream 
        server it accessed in attempting to fulfill the request.

        serviceUnavailable    - The server is temporarily unable to 
        process the request due to a temporary overloading or 
        maintenance of the server.

        serverTimeout         - The server did not receive a timely 
        response from an external server it accessed in attempting to 
        process the request.

        versionNotSupported    - The server does not support, or 
        refuses to support, the SIP protocol version that was used 
        in the request. 

        busyEverywhere        - The callee's end system was contacted 
        successfully but the callee is busy and does not wish to take 
        the call at this time. 

        decline               - The callee's machine was successfully 
        contacted but the user explicitly does not wish to or cannot 
        participate.

        doesNotExistAnywhere  - The server has authoritative 
        information that the user indicated in the Request-URI 
        does not exist anywhere.

        sessionNotAcceptable         - The user's agent was contacted 
        successfully but some aspects of the session description 
        such as the requested media, bandwidth, or addressing 
        style were not acceptable." 
    ::= { cLQVoiceClientEntry 3 }

--********************************************************************
--*    Client table - Media related objects
--********************************************************************

cLQMediaClientTable OBJECT-TYPE
        SYNTAX     SEQUENCE OF CLQMediaClientEntry
        MAX-ACCESS not-accessible
        STATUS     current
        DESCRIPTION
                "This table represents Media related client
                properties.
                There exists a row in this table for each associated
                Media clients.  A row is added to this table by the
                agent when a client gets associated
                Similarly a row gets deleted automatically when the
                client gets disassociated. "
        ::= { cLQMediaClient  1 }

cLQMediaClientEntry   OBJECT-TYPE
        SYNTAX     CLQMediaClientEntry
        MAX-ACCESS not-accessible
        STATUS     current
        DESCRIPTION
                "Each entry represents a conceptual row in
                cLQMediaClientTable and corresponds to Media
                properties of client."
        INDEX { cLQMStreamName, cLQVMediaClientDestIpAddrType, cLQVMediaClientDestIpAddr, cldcClientMacAddress }
        ::= { cLQMediaClientTable 1 }

CLQMediaClientEntry ::=
        SEQUENCE {
                cLQVMediaClientDestIpAddrType InetAddressType,
                cLQVMediaClientDestIpAddr     InetAddress,
                cLQVMediaClientSrcIpAddrType InetAddressType,
                cLQVMediaClientSrcIpAddr     InetAddress,
                cLQVMediaClientApMacAddress   MacAddress,
                cLQVMediaClientWlanIndex      Unsigned32, 
                cLQVMediaClientRadioType      INTEGER,
                cLQVMediaClientQos            INTEGER,
                cLQVMediaClientDecision       INTEGER
                }


cLQVMediaClientDestIpAddrType    OBJECT-TYPE
       SYNTAX      InetAddressType 
       MAX-ACCESS  not-accessible 
       STATUS      current
       DESCRIPTION
               "This object represents Multicast destination IP address type."
       ::= {  cLQMediaClientEntry 1 }

cLQVMediaClientDestIpAddr    OBJECT-TYPE
       SYNTAX      InetAddress
       MAX-ACCESS  not-accessible
       STATUS      current
       DESCRIPTION
               "This object represents Multicast destination IP address."
       ::= {  cLQMediaClientEntry 2}


cLQVMediaClientSrcIpAddrType    OBJECT-TYPE
       SYNTAX      InetAddressType
       MAX-ACCESS  read-only 
       STATUS      current
       DESCRIPTION
               "This object represents Multicast Source IP address type."
       ::= {  cLQMediaClientEntry 3 }

cLQVMediaClientSrcIpAddr    OBJECT-TYPE
       SYNTAX      InetAddress
       MAX-ACCESS  read-only 
       STATUS      current
       DESCRIPTION
               "This object represents Multicast Source IP address."
       ::= {  cLQMediaClientEntry 4}

cLQVMediaClientApMacAddress OBJECT-TYPE
        SYNTAX     MacAddress
        MAX-ACCESS read-only
        STATUS     current
        DESCRIPTION
                "This object specifies the MAC address of the
                AP for this entry."
       ::= {  cLQMediaClientEntry 5}

cLQVMediaClientWlanIndex OBJECT-TYPE
        SYNTAX     Unsigned32 
        MAX-ACCESS read-only
        STATUS     current
        DESCRIPTION
                "This object uniquely identifies one instance of
                a WLAN on the controller. The value 513-517 indicates
                wired clients."
        ::= {cLQMediaClientEntry 6 }

cLQVMediaClientRadioType OBJECT-TYPE
        SYNTAX     INTEGER{
                   radio80211bg(1),
                   radio80211a(2)
        }
        MAX-ACCESS read-only
        STATUS     current
        DESCRIPTION
                "This object denotes client radio type."
        ::= { cLQMediaClientEntry 7}

cLQVMediaClientQos OBJECT-TYPE
        SYNTAX     INTEGER{
                   besteffort(1),
                   background(2),
                   undefined(3),
                   excellenteffort(4),
                   ctrlload(5),
                   video(6),
                   voice(7),
                   network(8)
        }
        MAX-ACCESS read-only
        STATUS     current
        DESCRIPTION
                "This object represents client QOS."
        DEFVAL { 6 }
        ::= { cLQMediaClientEntry 8}

cLQVMediaClientDecision OBJECT-TYPE
        SYNTAX   INTEGER   {
                              deny(1),
                              admit(2),
                              badClientDeny(3),
                              badClientDemote(4)
                            }
        MAX-ACCESS read-only
        STATUS     current
        DESCRIPTION
          "This object represents the policy
            of this Media client.
         "
        ::= { cLQMediaClientEntry  9 }


cLQMediaClientHistoryTable OBJECT-TYPE
        SYNTAX     SEQUENCE OF CLQMediaClientHistoryEntry
        MAX-ACCESS not-accessible
        STATUS     current
        DESCRIPTION
                "This table represents Media related client
                properties."
        ::= { cLQMediaClient  2 }

cLQMediaClientHistoryEntry   OBJECT-TYPE
        SYNTAX     CLQMediaClientHistoryEntry
        MAX-ACCESS not-accessible
        STATUS     current
        DESCRIPTION
                "Each entry represents a conceptual row in
                cLQMediaClientHistoryTable and corresponds to Media
                properties of client."
        INDEX { cLQVMediaClientHistTimeStamp }
        ::= { cLQMediaClientHistoryTable 1 }

CLQMediaClientHistoryEntry ::=
        SEQUENCE {
                cLQVMediaClientHistTimeStamp      TimeStamp, 
                cLQVMediaClientHistClientMacAddress   MacAddress,
                cLQVMediaClientHistApMacAddress   MacAddress,
                cLQVMediaClientHistSlotId         Unsigned32,
                cLQVMediaClientHistSrcIpAddr      IpAddress,
                cLQVMediaClientHistDestIpAddr     IpAddress,
                cLQVMediaClientHistDecision       INTEGER,
                cLQVMediaClientHistLastFailureReasonCode  INTEGER,
                cLQVMediaClientHistWlanIndex      Unsigned32,
                cLQVMediaClientHistRadioType      INTEGER,
                cLQVMediaClientHistQos            INTEGER,
                cLQVMediaClientHistCfgBw          Unsigned32,
                cLQVMediaClientHistCurrentRate    Unsigned32,
                cLQVMediaClientHistVideoPktSize   Unsigned32,
                cLQVMediaClientHistVideoUtil      Unsigned32,
                cLQVMediaClientHistVoiceUtil      Unsigned32,
                cLQVMediaClientHistChannelUtil    Unsigned32,
                cLQVMediaClientHistQueueUtil      Unsigned32,
                cLQVMediaClientHistVideoPps       Unsigned32,
                cLQVMediaClientHistVideoDelay     Unsigned32,
                cLQVMediaClientHistPktLossDiscard Unsigned32,
                cLQVMediaClientHistPktLossFail    Unsigned32,
                cLQVMediaClientHistNumVideoStreams Unsigned32,
                cLQVMediaClientHistCacEnable      INTEGER,
                cLQVMediaClientHistStreamName     SnmpAdminString,
                cLQVMediaClientHistSrcInetAddrType InetAddressType,
                cLQVMediaClientHistSrcInetAddr    InetAddress,
                cLQVMediaClientHistDestInetAddrType   InetAddressType,
                cLQVMediaClientHistDestInetAddr   InetAddress
                }

cLQVMediaClientHistTimeStamp    OBJECT-TYPE
       SYNTAX     TimeStamp 
       MAX-ACCESS not-accessible
       STATUS      current
       DESCRIPTION
               "This object uniquely identifies one instance of
                 the timestamp in history for which the client
                 admit/deny happens"
       ::= {  cLQMediaClientHistoryEntry 1 }

cLQVMediaClientHistClientMacAddress OBJECT-TYPE
        SYNTAX     MacAddress
        MAX-ACCESS read-only 
        STATUS     current
        DESCRIPTION
                "This object specifies the MAC address of the
                client for this entry."
        ::= { cLQMediaClientHistoryEntry 2  }

cLQVMediaClientHistApMacAddress OBJECT-TYPE
        SYNTAX     MacAddress
        MAX-ACCESS read-only
        STATUS     current
        DESCRIPTION
                "This object specifies the MAC address of the
                AP for this entry."
        ::= { cLQMediaClientHistoryEntry 3  }


cLQVMediaClientHistSlotId OBJECT-TYPE
        SYNTAX     Unsigned32
        MAX-ACCESS read-only
        STATUS     current
        DESCRIPTION
                "This object uniquely identifies the slot id."
        ::= {cLQMediaClientHistoryEntry 4 }

cLQVMediaClientHistSrcIpAddr    OBJECT-TYPE
       SYNTAX      IpAddress
       MAX-ACCESS read-only
       STATUS     deprecated 
       DESCRIPTION
               "This object represents Multicast source IP address."
       ::= {  cLQMediaClientHistoryEntry 5 }

cLQVMediaClientHistDestIpAddr    OBJECT-TYPE
       SYNTAX      IpAddress
       MAX-ACCESS  read-only
       STATUS      deprecated
       DESCRIPTION
               "This object represents Multicast destication IP address."
       ::= {  cLQMediaClientHistoryEntry 6}

cLQVMediaClientHistDecision OBJECT-TYPE
        SYNTAX   INTEGER   {
                              deny(1),
                              admit(2),
                              badClientDeny(3),
                              badClientDemote(4)
                            }
        MAX-ACCESS read-only
        STATUS     current
        DESCRIPTION
          "This object represents the policy  
            of this Media client.
         "
        ::= { cLQMediaClientHistoryEntry  7 }


cLQVMediaClientHistLastFailureReasonCode OBJECT-TYPE
        SYNTAX   INTEGER   {
                             enoughBw(1),
                             notEnoughBw(2),
                             bwViolation(3),
                             radioOverSubscribe(4),
                             badClientLink(5),
                             policyNotAllowed(6),
                             otherErrors(7),
                             clientDemote(8),
                             clientTimeout(9),
                             clientLeave(10)
                            }
        MAX-ACCESS read-only
        STATUS     current
        DESCRIPTION
          "This object represents last failue reason code
            of this Media client.
            enoughBw(1) - Radio can handle additional client traffic.  
            Hence, allowing client admission during RRC admission or Re-RRC phase.
            notEnoughBw(2) - Radio cannot handle additional client traffic. 
            Thus it will delist(put into best effort queue) or deny client. 
            bwViolation(3) - After Re-RRC calculations, it is determined that client 
            has done stream config violation. Thus, it will be delisted or denied.
            radioOverSubscribe(4) -  client will be denied when when radio resources 
            are fully utilized.
            badClientLink(5) - If client traffic is sent at lower data rate or number 
            of retries exceed threshold, it will be classified as bad client.
            policyNotAllowed(6) - Client subscription has violated policy configured.
            otherErrors(7) - During RRC admission or Re-RRC phase, client joining is denied because 
            of abnormal conditions, such as not able to retrieve client data for calculation. 
            clientDemote(8) - During Re-RRC calculation, client is demoted to best-effort queue 
            because the radio is too busy.
            clientTimeout(9) - Client is considered for timeout and removed from databse when 
            no stream update for the client is available before the timer (15mins by default) expires. 
            clientLeave(10) - Client leaves the stream in normal condition.
         "
        ::= { cLQMediaClientHistoryEntry  8 }


cLQVMediaClientHistWlanIndex OBJECT-TYPE
        SYNTAX     Unsigned32 (1..517)
        MAX-ACCESS read-only
        STATUS     current
        DESCRIPTION
                "This object uniquely identifies one instance of
                a WLAN on the controller. The value 513-517 indicates
                wired clients."
        ::= {cLQMediaClientHistoryEntry 9 }

cLQVMediaClientHistRadioType OBJECT-TYPE
        SYNTAX     INTEGER{
                   radio80211bg(1),
                   radio80211a(2)
        }
        MAX-ACCESS read-only
        STATUS     current
        DESCRIPTION
                "This object denotes client radio type."
        ::= { cLQMediaClientHistoryEntry 10}


cLQVMediaClientHistQos OBJECT-TYPE
        SYNTAX     INTEGER{
                   besteffort(1),
                   background(2),
                   undefined(3),
                   excellenteffort(4),
                   ctrlload(5),
                   video(6),
                   voice(7),
                   network(8)
        }
        MAX-ACCESS read-only
        STATUS     current
        DESCRIPTION
                "This object represents client QOS."
        DEFVAL { 6 }
        ::= { cLQMediaClientHistoryEntry 11}


cLQVMediaClientHistCfgBw OBJECT-TYPE
        SYNTAX     Unsigned32
        MAX-ACCESS read-only
        STATUS     current
        DESCRIPTION
                "This object uniquely identifies the configured Stream Bandwidth"
        ::= {cLQMediaClientHistoryEntry 12 }

cLQVMediaClientHistCurrentRate OBJECT-TYPE
        SYNTAX     Unsigned32
        MAX-ACCESS read-only
        STATUS     current
        DESCRIPTION
                "This object uniquely identifies the current rate." 
        ::= {cLQMediaClientHistoryEntry 13 }

cLQVMediaClientHistVideoPktSize OBJECT-TYPE
        SYNTAX     Unsigned32
        MAX-ACCESS read-only
        STATUS     current
        DESCRIPTION
                "This object uniquely identifies the video packet size."
        ::= {cLQMediaClientHistoryEntry 14 }

cLQVMediaClientHistVideoUtil OBJECT-TYPE
        SYNTAX     Unsigned32
        MAX-ACCESS read-only
        STATUS     current
        DESCRIPTION
                "This object uniquely identifies the Video Util."
        ::= {cLQMediaClientHistoryEntry 15 }

cLQVMediaClientHistVoiceUtil OBJECT-TYPE
        SYNTAX     Unsigned32
        MAX-ACCESS read-only
        STATUS     current
        DESCRIPTION
                "This object uniquely identifies the voice util."
        ::= {cLQMediaClientHistoryEntry 16 }

cLQVMediaClientHistChannelUtil OBJECT-TYPE
        SYNTAX     Unsigned32
        MAX-ACCESS read-only
        STATUS     current
        DESCRIPTION
                "This object uniquely identifies the channel util."
        ::= {cLQMediaClientHistoryEntry 17 }

cLQVMediaClientHistQueueUtil OBJECT-TYPE
        SYNTAX     Unsigned32
        MAX-ACCESS read-only
        STATUS     current
        DESCRIPTION
                "This object uniquely identifies the queue util"
        ::= {cLQMediaClientHistoryEntry 18 }

cLQVMediaClientHistVideoPps OBJECT-TYPE
        SYNTAX     Unsigned32
        MAX-ACCESS read-only
        STATUS     current
        DESCRIPTION
                "This object uniquely identifies the Video Pps."
        ::= {cLQMediaClientHistoryEntry 19 }

cLQVMediaClientHistVideoDelay OBJECT-TYPE
        SYNTAX     Unsigned32
        MAX-ACCESS read-only
        STATUS     current
        DESCRIPTION
                "This object uniquely identifies the Video delay severe."
        ::= {cLQMediaClientHistoryEntry 20}

cLQVMediaClientHistPktLossDiscard OBJECT-TYPE
        SYNTAX     Unsigned32
        MAX-ACCESS read-only
        STATUS     current
        DESCRIPTION
                "This object uniquely identifies the packet loss discard."
        ::= {cLQMediaClientHistoryEntry 21 }

cLQVMediaClientHistPktLossFail OBJECT-TYPE
        SYNTAX     Unsigned32
        MAX-ACCESS read-only
        STATUS     current
        DESCRIPTION
                "This object uniquely identifies the packet loss fail" 
        ::= {cLQMediaClientHistoryEntry 22 }

cLQVMediaClientHistNumVideoStreams OBJECT-TYPE
        SYNTAX     Unsigned32
        MAX-ACCESS read-only
        STATUS     current
        DESCRIPTION
                "This object uniquely identifies the number of video streams."
        ::= {cLQMediaClientHistoryEntry 23 }

cLQVMediaClientHistCacEnable OBJECT-TYPE
        SYNTAX   INTEGER   {
                             video(1),
                             voice(2),
                             videoAndVoice(3),
                             none(4)
                            }

        MAX-ACCESS read-only
        STATUS     current
        DESCRIPTION
                "This object uniquely identifies thecac enable state."
        ::= {cLQMediaClientHistoryEntry 24 }

cLQVMediaClientHistStreamName OBJECT-TYPE
        SYNTAX     SnmpAdminString
        MAX-ACCESS read-only 
        STATUS     current
        DESCRIPTION
                "Name of the media stream the client was admitted at the 
        particular timestamp. "
        ::= {cLQMediaClientHistoryEntry 25 }

cLQVMediaClientHistSrcInetAddrType OBJECT-TYPE
    SYNTAX      InetAddressType
    MAX-ACCESS  read-only
    STATUS      current
    DESCRIPTION
          "This object represents Multicast Destination Start Address Type"
    ::= {cLQMediaClientHistoryEntry 26}

cLQVMediaClientHistSrcInetAddr OBJECT-TYPE
    SYNTAX      InetAddress
    MAX-ACCESS  read-only
    STATUS      current
    DESCRIPTION
           "This object represents Multicast Destination Start Address "
    ::= {cLQMediaClientHistoryEntry 27}

cLQVMediaClientHistDestInetAddrType OBJECT-TYPE
    SYNTAX      InetAddressType
    MAX-ACCESS  read-only
    STATUS      current
    DESCRIPTION
    "This object represents Multicast Destination End Address Type"
    ::= {cLQMediaClientHistoryEntry 28}

cLQVMediaClientHistDestInetAddr OBJECT-TYPE
        SYNTAX      InetAddress
        MAX-ACCESS  read-only
        STATUS      current
        DESCRIPTION
                "This object represents Multicast Destination End Address"
        ::= {cLQMediaClientHistoryEntry 29}

cLQMediaMulticastClientTable OBJECT-TYPE
        SYNTAX     SEQUENCE OF CLQMediaMulticastClientEntry
        MAX-ACCESS not-accessible
        STATUS     current
        DESCRIPTION
                "This table represents Media related client
                properties for multicast clients.
                There exists a row in this table for each associated
                Media clients.  A row is added to this table by the
                agent when a client gets associated
                Similarly a row gets deleted automatically when the
                client gets disassociated. "
        ::= { cLQMediaClient  3 }

cLQMediaMulticastClientEntry   OBJECT-TYPE
        SYNTAX     CLQMediaMulticastClientEntry
        MAX-ACCESS not-accessible
        STATUS     current
        DESCRIPTION
                "Each entry represents a conceptual row in
                cLQMediaMulticastClientTable and corresponds to Media
                properties of client."
        INDEX { cLQMStreamName, cLQVMediaClientMCGrpIpAddrType, cLQVMediaClientMCGrpIpAddr, cldcClientMacAddress }
        ::= { cLQMediaMulticastClientTable 1 }

CLQMediaMulticastClientEntry ::=
        SEQUENCE {
                cLQVMediaClientMCGrpIpAddrType InetAddressType,
                cLQVMediaClientMCGrpIpAddr     InetAddress,
                cLQVMediaClientVlanId          Unsigned32,
                cLQVMediaMCClientApName        SnmpAdminString,
                cLQVMediaClientMCUCStatus      SnmpAdminString
                }


cLQVMediaClientMCGrpIpAddrType    OBJECT-TYPE
       SYNTAX      InetAddressType 
       MAX-ACCESS  not-accessible 
       STATUS      current
       DESCRIPTION
               "This object represents Multicast destination IP address type."
       ::= {  cLQMediaMulticastClientEntry 1 }

cLQVMediaClientMCGrpIpAddr    OBJECT-TYPE
       SYNTAX      InetAddress
       MAX-ACCESS  not-accessible
       STATUS      current
       DESCRIPTION
               "This object represents Multicast destination IP address."
       ::= {  cLQMediaMulticastClientEntry 2}

cLQVMediaClientVlanId OBJECT-TYPE
       SYNTAX     Unsigned32
       MAX-ACCESS read-only
       STATUS     current
       DESCRIPTION
                "This object uniquely identifies the VLAN configured for the client."
       ::= {  cLQMediaMulticastClientEntry 3}

cLQVMediaMCClientApName OBJECT-TYPE
        SYNTAX     SnmpAdminString
        MAX-ACCESS read-only
        STATUS     current
        DESCRIPTION
                "This object uniquely identifies the Access Point to
                 which the multicast client is connected."
       ::= {  cLQMediaMulticastClientEntry 4}

cLQVMediaClientMCUCStatus OBJECT-TYPE
        SYNTAX     SnmpAdminString
        MAX-ACCESS read-only
        STATUS     current
        DESCRIPTION
                "This object uniquely identifies whether the multicast client has 
                 Multicast-to-Unicast feature enabled."
       ::= {  cLQMediaMulticastClientEntry 5}

--********************************************************************
--*  SIP CALL admission control configurations
--********************************************************************

cLQd11SipCacConfigTable OBJECT-TYPE
    SYNTAX          SEQUENCE OF CLQd11SipCacConfigEntry 
    MAX-ACCESS      not-accessible
    STATUS          current
    DESCRIPTION
        "This table contains the information about the
        SIP CAC configuration corresponding to
        the dot11 bands of the APs that have joined
        the controller.
        The parameters specify how the SIP call reserves 
        CAC bandwidth."
    ::= { cLQd11SipCacConfig 1 }

cLQd11SipCacConfigEntry OBJECT-TYPE
    SYNTAX          CLQd11SipCacConfigEntry
    MAX-ACCESS      not-accessible
    STATUS          current
    DESCRIPTION
        "An entry containing SIP CAC configuration for a particular type
        of 
        wireless interface."
    INDEX           { cLApDot11IfType } 
    ::= { cLQd11SipCacConfigTable 1 }

CLQd11SipCacConfigEntry ::= SEQUENCE {
        cLQd11SipCacConfigCodecType       INTEGER,
        cLQd11SipCacConfigBw              Unsigned32,
        cLQd11SipCacConfigVoiceSampleSize Unsigned32,
        cLQd11SipCacMaxPossibleVoiceCalls Unsigned32,
        cLQd11SipCacMaxPossibleReservedRoamingCalls Unsigned32
}

cLQd11SipCacConfigCodecType OBJECT-TYPE
    SYNTAX          INTEGER  {
                        userDefined(1),
                        g711(2),
                        g729(3)
                    }
    MAX-ACCESS      read-write
    STATUS          current
    DESCRIPTION
        "This object specifies the configured codec for SIP Cac
        configuration of the dot11 band for the APs associated 
        with this controller. Codec determines the bandwidth to 
        be reserved for voice call.
        userDefined - User defines the bandwidth, 
        cLQd11SipCacConfigBw has to be configured
        g711 - standard Codec G711
        g729 - standard Codec G729"
    DEFVAL          { g711 } 
    ::= { cLQd11SipCacConfigEntry 1 }

cLQd11SipCacConfigBw OBJECT-TYPE
    SYNTAX          Unsigned32
    UNITS           "kbps"
    MAX-ACCESS      read-write
    STATUS          current
    DESCRIPTION
        "This object specifies the configured bandwidth in kbps
        for SIP CAC configuration of the dot11
        band for the APs associated with this controller.

        This is configurable only if cLQd11SipCacConfigCodecType
         is 'userDefined'" 
    ::= { cLQd11SipCacConfigEntry 2 }

cLQd11SipCacConfigVoiceSampleSize OBJECT-TYPE
    SYNTAX          Unsigned32
    UNITS           "milliseconds"
    MAX-ACCESS      read-write
    STATUS          current
    DESCRIPTION
        "This object specifies the configured voice sample size
        in milliseconds for SIP Cac configuration of the dot11 band 
        for the APs associated with this controller." 
    ::= { cLQd11SipCacConfigEntry 3 }

cLQd11SipCacMaxPossibleVoiceCalls OBJECT-TYPE
    SYNTAX Unsigned32
    MAX-ACCESS read-only
    STATUS current
    DESCRIPTION
        " This object represents the maximum possible voice calls 
          that can be made with respect to the current SIP CAC configuration."
 
    ::= { cLQd11SipCacConfigEntry 4 }
 
cLQd11SipCacMaxPossibleReservedRoamingCalls OBJECT-TYPE
    SYNTAX Unsigned32
    MAX-ACCESS read-only
    STATUS current
    DESCRIPTION
        " This object represents the maximum possible reserved roaming calls
          that can be made with respect to the current SIP CAC configuration."
    ::= { cLQd11SipCacConfigEntry 5 }

--********************************************************************
-- Table to represent Media stream config
-- parameters per stream.
--********************************************************************

cLQMStreamTable OBJECT-TYPE
        SYNTAX     SEQUENCE OF CLQMStreamEntry
        MAX-ACCESS not-accessible
        STATUS     current
        DESCRIPTION
                "This table populates the Media stream configuration  "
        ::= { cLQMediaStreamConfig 1}

cLQMStreamEntry OBJECT-TYPE
        SYNTAX     CLQMStreamEntry
        MAX-ACCESS not-accessible
        STATUS     current
        DESCRIPTION
                "Each entry represents a conceptual row in
                cLQd11GprTable and corresponds to the
                GPR configuration on a WLAN. "
        INDEX { cLQMStreamName }
        ::= { cLQMStreamTable 1 }

CLQMStreamEntry ::=
        SEQUENCE {
                cLQMStreamName        SnmpAdminString,
                cLQMStreamRowStatus       RowStatus,
                cLQMStreamDestIPStartAddr IpAddress,
                cLQMStreamDestIPEndAddr   IpAddress,
                cLQMStreamstate           TruthValue,
                cLQMStreamRrcExpBw        Unsigned32,
                cLQMStreamRrcAvgPkt       Unsigned32,
                cLQMStreamReRrc           TruthValue,
                cLQMStreamRrcQos          INTEGER,
                cLQMStreamRrcType         INTEGER,
                cLQMStreamRrcPriority     INTEGER,
                cLQMStreamRrcViolation    INTEGER,
                cLQMStreamRrcPolicy       TruthValue,
		cLQMStreamDestStartInetAddrType InetAddressType,
		cLQMStreamDestStartInetAddr InetAddress,
		cLQMStreamDestEndInetAddrType   InetAddressType,
		cLQMStreamDestEndInetAddr   InetAddress
        }
cLQMStreamName OBJECT-TYPE
        SYNTAX     SnmpAdminString 
        MAX-ACCESS not-accessible 
        STATUS     current
        DESCRIPTION
                "Name of the media stream.Unique identifier for the stream "
        ::= { cLQMStreamEntry 1}

cLQMStreamRowStatus OBJECT-TYPE
        SYNTAX     RowStatus
        MAX-ACCESS read-create
        STATUS     current
        DESCRIPTION
                "This is the status column for this row and used
                to create and delete specific instances of rows
                in this table.
                The following objects are mandatory for successful
                creation of an entry:
                cLQMStreamName,"
                      
        ::= { cLQMStreamEntry 2 }

cLQMStreamDestIPStartAddr  OBJECT-TYPE
        SYNTAX     IpAddress
        MAX-ACCESS read-create 
        STATUS    deprecated 
        DESCRIPTION
                " This object represents Multicast start IP address"
        ::= { cLQMStreamEntry 3 }


cLQMStreamDestIPEndAddr OBJECT-TYPE
        SYNTAX     IpAddress
        MAX-ACCESS read-create
        STATUS     deprecated
        DESCRIPTION
                " This object represents Multicast destination end IP address"
        ::= { cLQMStreamEntry 4 }

cLQMStreamstate OBJECT-TYPE
        SYNTAX     TruthValue
        MAX-ACCESS read-create
        STATUS     current
        DESCRIPTION
                 "This object represents media stream state."
        DEFVAL { false }
        ::= { cLQMStreamEntry 5 }


cLQMStreamRrcExpBw OBJECT-TYPE
        SYNTAX     Unsigned32 (1..35000)
        MAX-ACCESS read-create 
        STATUS     current
        DESCRIPTION
                "This object represents Resource Reservation control bandwidth 
                 utilization"
        DEFVAL { 500 } 
        ::= { cLQMStreamEntry 6}

cLQMStreamRrcAvgPkt OBJECT-TYPE
        SYNTAX     Unsigned32 (100..1500)
        MAX-ACCESS read-create 
        STATUS     current
        DESCRIPTION
                "This object represents RRC Average packet size."
        DEFVAL { 1200 } 
        ::= { cLQMStreamEntry 7}

cLQMStreamReRrc OBJECT-TYPE
        SYNTAX     TruthValue
        MAX-ACCESS read-create 
        STATUS     current
        DESCRIPTION
                "This object represents re-RRC calculations enabled/disabled.
                  A true value represents re-RRC enabled and false value represents
                  Re-RRC disabled"
        DEFVAL { true }
        ::= { cLQMStreamEntry 8 }

cLQMStreamRrcQos OBJECT-TYPE
        SYNTAX     INTEGER{
                   besteffort(1),
                   background(2),
                   undefined(3),
                   excellenteffort(4),
                   ctrlload(5),
                   video(6),
                   voice(7),
                   network(8)
        }
        MAX-ACCESS read-create 
        STATUS     current
        DESCRIPTION
                "This object represents RRC QOS queue information."
        DEFVAL { 6 }
        ::= { cLQMStreamEntry 9}

cLQMStreamRrcType OBJECT-TYPE
        SYNTAX     INTEGER{
                   mc2uc(1),
                   m-only(2),
                   unicast(3),
                   disabled(4)
        }

        MAX-ACCESS read-create 
        STATUS     current
        DESCRIPTION
                "This object represents RRC Media stream type
                mc2uc - multicast to unicast enabled.
                m-only - only multicast enabled.
                unicast - unicast enabled.
                disabled - neither multicast nor unicast enabled."
        DEFVAL { 1 }
        ::= { cLQMStreamEntry 10}

cLQMStreamRrcPriority OBJECT-TYPE
        SYNTAX     INTEGER (1..8) 
        MAX-ACCESS read-create
        STATUS     current
        DESCRIPTION
               "This object represents RRC Priority bit set within media stream "
        DEFVAL { 4 }
        ::= { cLQMStreamEntry 11}

cLQMStreamRrcViolation OBJECT-TYPE
        SYNTAX     INTEGER{
                    fallback(1),
                    drop(2)
        }
        MAX-ACCESS read-create 
        STATUS     current
        DESCRIPTION
                "This object represents RRC Violation. After re-RRC, if media 
                 stream violates profile then whether to stash it into best 
                 effort or drop it "

        DEFVAL { 2 }
        ::= { cLQMStreamEntry 12}

cLQMStreamRrcPolicy OBJECT-TYPE
        SYNTAX     TruthValue
        MAX-ACCESS read-write
        STATUS     current
        DESCRIPTION
                 "This object represents media stream admit/Deny.A true value 
                  represents media stream admit and false value represents
                  media stream deny"
        DEFVAL { false }
        ::= { cLQMStreamEntry 13 }

cLQMStreamDestStartInetAddrType OBJECT-TYPE
    SYNTAX      InetAddressType
    MAX-ACCESS  read-create
    STATUS      current
    DESCRIPTION
          "This object represents Multicast Destination Start Address Type"
    ::= {cLQMStreamEntry 14}

cLQMStreamDestStartInetAddr OBJECT-TYPE
    SYNTAX      InetAddress
    MAX-ACCESS  read-create
    STATUS      current
    DESCRIPTION
           "This object represents Multicast Destination Start Address "
    ::= {cLQMStreamEntry 15}

cLQMStreamDestEndInetAddrType OBJECT-TYPE
    SYNTAX      InetAddressType
    MAX-ACCESS  read-create
    STATUS      current
    DESCRIPTION
    "This object represents Multicast Destination End Address Type"
    ::= {cLQMStreamEntry 16}

cLQMStreamDestEndInetAddr OBJECT-TYPE
        SYNTAX      InetAddress
        MAX-ACCESS  read-create
        STATUS      current
        DESCRIPTION
                "This object represents Multicast Destination End Address"
        ::= {cLQMStreamEntry 17}

cLQMStreamSdpConfig  OBJECT IDENTIFIER ::= { cLQMediaStreamConfig 2 }


cLQMStreamSdpUrl OBJECT-TYPE
         SYNTAX      OCTET STRING (SIZE(0..128))
         MAX-ACCESS  read-write
         STATUS      current
         DESCRIPTION
               "Media Stream Session announcewment message - Session description
                protocol (SDP) URL"  
        ::= { cLQMStreamSdpConfig 1}

cLQMStreamSdpEmail OBJECT-TYPE
         SYNTAX      OCTET STRING (SIZE(0..64))
         MAX-ACCESS  read-write
         STATUS      current
         DESCRIPTION
               "Media Stream Session announcewment message - Session description
                protocol (SDP) Email"
        ::= { cLQMStreamSdpConfig 2}

cLQMStreamSdpPhone OBJECT-TYPE
         SYNTAX      OCTET STRING (SIZE(0..30))
         MAX-ACCESS  read-write
         STATUS      current
         DESCRIPTION
               "Media Stream Session announcewment message - Session description
                protocol (SDP) Phone"
        ::= { cLQMStreamSdpConfig 3}

cLQMStreamSdpNote OBJECT-TYPE
         SYNTAX      OCTET STRING (SIZE(0..128))
         MAX-ACCESS  read-write
         STATUS      current
         DESCRIPTION
               "Media Stream Session announcewment message - Session description
                protocol (SDP) Note"
        ::= { cLQMStreamSdpConfig 4}

cLQMStreamSdpStatus OBJECT-TYPE
         SYNTAX      TruthValue 
         MAX-ACCESS  read-write
         STATUS      current
         DESCRIPTION
               "Media Stream Session announcewment message - Session description
                protocol (SDP) Status"
        ::= { cLQMStreamSdpConfig 5}

cLQMStreamRrcGlobal  OBJECT IDENTIFIER ::= { cLQMediaStreamConfig 3 }

cLQMStreamRrcGlobalState OBJECT-TYPE
        SYNTAX     TruthValue
        MAX-ACCESS read-write
        STATUS     current
        DESCRIPTION
                 "This object represents media stream feature global enable.
                  A 'True' value represents media stream feature enable .
                  A 'False' value represents media stream feature disable." 
        DEFVAL { false }
        ::= { cLQMStreamRrcGlobal 1 }


cLQPreferredCallTable OBJECT-TYPE
        SYNTAX     SEQUENCE OF CLQPreferredCallEntry
        MAX-ACCESS not-accessible
        STATUS     current
        DESCRIPTION
                "This table populates the preferred call configuration  "
        ::= {  cLQPreferredCallConfig 1}

cLQPreferredCallEntry OBJECT-TYPE
        SYNTAX     CLQPreferredCallEntry
        MAX-ACCESS not-accessible
        STATUS     current
        DESCRIPTION
                "Each entry represents a conceptual row in
                cLQPreferredCallTable and corresponds to the
                preferred call of the user. "
        INDEX { cLQPreferredCallIndex }
        ::= { cLQPreferredCallTable 1 }


CLQPreferredCallEntry ::=
        SEQUENCE {
                cLQPreferredCallIndex Unsigned32,
                cLQPreferredCallNumber DisplayString,
                cLQPreferredCallRowStatus RowStatus 
        }


cLQPreferredCallIndex OBJECT-TYPE
        SYNTAX     Unsigned32(1..6) 
        MAX-ACCESS not-accessible 
        STATUS     current
        DESCRIPTION
                "This object represents the index of the  preferred call 
                 configured by the user. When the call comes to any of these 
                 numbers, even if there is no bandwidth available in the 
                 configured voice pool, WLC should facilitate the urgency 
                 of these calls in any way possible without potentially 
                 altering the quality of the existing calls. 
                 This is supported only for those clients which 
                 use SIP based CAC for bandwidth allocation in the WLC."  

        ::= { cLQPreferredCallEntry 1}

cLQPreferredCallNumber OBJECT-TYPE
        SYNTAX     DisplayString(SIZE(0..32)) 
        MAX-ACCESS read-create
        STATUS     current
        DESCRIPTION
                "This object represents the preferred call number
                 configured by the user. When the call comes to any of these
                 numbers, even if there is no bandwidth available in the
                 configured voice pool.
                 WLC should facilitate the urgency of these calls in any way
                 possible without potentially altering the quality of the
                 existing calls. This is supported only for those clients which
                 use SIP based CAC for bandwidth allocation in the WLC."
        ::= { cLQPreferredCallEntry 2}

cLQPreferredCallRowStatus OBJECT-TYPE
        SYNTAX     RowStatus
        MAX-ACCESS read-create
        STATUS     current
        DESCRIPTION
                "This is the status column for this row and used
                to create and delete specific instances of rows
                in this table.
                The following objects are mandatory for successful
                creation of an entry:
                cLQPreferredCallIndex"
        ::= { cLQPreferredCallEntry 3}

cLQoSProfileTable OBJECT-TYPE
        SYNTAX     SEQUENCE OF CLQoSProfileEntry
        MAX-ACCESS not-accessible
        STATUS     current
        DESCRIPTION
                "This table represents the configurable priority related qos 
                  paramaters for the wlan. There exists a row in this table for each 
                qos profile type."
        ::= { cLQoSProfileConfig 1}

cLQoSProfileEntry OBJECT-TYPE
        SYNTAX     CLQoSProfileEntry
        MAX-ACCESS not-accessible
        STATUS     current
        DESCRIPTION
                "Each entry corresponds to one of the existing profile types
                such as  gold, silver, bronze, platinum. "
        INDEX { cLQoSProfileName }
        ::= { cLQoSProfileTable 1 }

CLQoSProfileEntry ::=
        SEQUENCE {
                cLQoSProfileName           		SnmpAdminString,
                cLQoSMaximumPriority       		INTEGER,
                cLQoSUnicastDefPriority    		INTEGER,
                cLQoSMulticastDefPriority  		INTEGER,
                cLQoSClientDSAverageDataRate            Unsigned32,
                cLQoSClientUSAverageDataRate            Unsigned32,
                cLQoSClientDSBurstDataRate              Unsigned32,
                cLQoSClientUSBurstDataRate              Unsigned32,
                cLQoSClientDSAvgRealTimeDataRate        Unsigned32,
                cLQoSClientUSAvgRealTimeDataRate        Unsigned32,
                cLQoSClientDSBurstRealTimeDataRate      Unsigned32,
                cLQoSClientUSBurstRealTimeDataRate      Unsigned32,
                cLQoSSsidDSAverageDataRate              Unsigned32,
                cLQoSSsidUSAverageDataRate              Unsigned32,
                cLQoSSsidDSBurstDataRate                Unsigned32,
                cLQoSSsidUSBurstDataRate                Unsigned32,
                cLQoSSsidDSAvgRealTimeDataRate          Unsigned32,
                cLQoSSsidUSAvgRealTimeDataRate          Unsigned32,
                cLQoSSsidDSBurstRealTimeDataRate        Unsigned32,
                cLQoSSsidUSBurstRealTimeDataRate        Unsigned32
        }
cLQoSProfileName OBJECT-TYPE
        SYNTAX     SnmpAdminString 
        MAX-ACCESS not-accessible 
        STATUS     current
        DESCRIPTION
                "Name of the profile, unique identifier for the profile."
        ::= { cLQoSProfileEntry 1}

cLQoSMaximumPriority  OBJECT-TYPE
        SYNTAX     INTEGER{
                   besteffort(1),
                   background(2),
                   video(3),
                   voice(4) 
        }
        MAX-ACCESS read-write
        STATUS     current
        DESCRIPTION
                " This object specifies the maximum QoS priority of the 
                 WLAN associated with this profile. "
        ::= { cLQoSProfileEntry 2 }

cLQoSUnicastDefPriority OBJECT-TYPE
        SYNTAX     INTEGER{
                   besteffort(1),
                   background(2),
                   video(3),
                   voice(4)
        }
        MAX-ACCESS read-write
        STATUS     current
        DESCRIPTION
                " This object specifies the unicast default QoS priority of the 
                 WLAN associated with this profile "
        ::= { cLQoSProfileEntry 3 }

cLQoSMulticastDefPriority OBJECT-TYPE
        SYNTAX     INTEGER{
                   besteffort(1),
                   background(2),
                   video(3),
                   voice(4)
        }
        MAX-ACCESS read-write
        STATUS     current
        DESCRIPTION
                 "This object specifies the multicast default QoS priority of the 
                 WLAN associated with this profile."
        ::= { cLQoSProfileEntry 4 }

cLQoSClientDSAverageDataRate OBJECT-TYPE
    SYNTAX          Unsigned32
    MAX-ACCESS      read-write
    STATUS          current
    DESCRIPTION
        "This object specifies Average Data Rate per user on downstream.
          Value of 0 indicates the feature is disabled."
    ::= { cLQoSProfileEntry 5 }

cLQoSClientUSAverageDataRate OBJECT-TYPE
    SYNTAX          Unsigned32
    MAX-ACCESS      read-write
    STATUS          current
    DESCRIPTION
        "This object specifies Average Data Rate per user on upstream.
          Value of 0 indicates the feature is disabled."
    ::= { cLQoSProfileEntry 6 }

cLQoSClientDSBurstDataRate OBJECT-TYPE
    SYNTAX          Unsigned32
    MAX-ACCESS      read-write
    STATUS          current
    DESCRIPTION
        "This object specifies Burst Data Rate per user on downstream.
          Value of 0 indicates the feature is disabled."
    ::= { cLQoSProfileEntry 7 }

cLQoSClientUSBurstDataRate OBJECT-TYPE
    SYNTAX          Unsigned32
    MAX-ACCESS      read-write
    STATUS          current
    DESCRIPTION
        "This object specifies Burst Data Rate per user on upstream.
          Value of 0 indicates the feature is disabled."
    ::= { cLQoSProfileEntry 8 }

cLQoSClientDSAvgRealTimeDataRate OBJECT-TYPE
    SYNTAX          Unsigned32
    MAX-ACCESS      read-write
    STATUS          current
    DESCRIPTION
        "This object specifies average real time Data Rate per user on downstream.
          Value of 0 indicates the feature is disabled."
    ::= { cLQoSProfileEntry 9 }

cLQoSClientUSAvgRealTimeDataRate OBJECT-TYPE
    SYNTAX          Unsigned32
    MAX-ACCESS      read-write
    STATUS          current
    DESCRIPTION
        "This object specifies average real time Data Rate per user on upstream.
          Value of 0 indicates the feature is disabled."
    ::= { cLQoSProfileEntry 10 }

cLQoSClientDSBurstRealTimeDataRate OBJECT-TYPE
    SYNTAX          Unsigned32
    MAX-ACCESS      read-write
    STATUS          current
    DESCRIPTION
        "This object specifies burst real time Data Rate per user on downstream.
          Value of 0 indicates the feature is disabled."
    ::= { cLQoSProfileEntry 11 }

cLQoSClientUSBurstRealTimeDataRate OBJECT-TYPE
    SYNTAX          Unsigned32
    MAX-ACCESS      read-write
    STATUS          current
    DESCRIPTION
        "This object specifies burst real time Data Rate per user on upstream.
          Value of 0 indicates the feature is disabled."
    ::= { cLQoSProfileEntry 12 }

cLQoSSsidDSAverageDataRate OBJECT-TYPE
    SYNTAX          Unsigned32
    MAX-ACCESS      read-write
    STATUS          current
    DESCRIPTION
        "This object specifies Average Data Rate per user on downstream.
          Value of 0 indicates the feature is disabled."
    ::= { cLQoSProfileEntry 13 }

cLQoSSsidUSAverageDataRate OBJECT-TYPE
    SYNTAX          Unsigned32
    MAX-ACCESS      read-write
    STATUS          current
    DESCRIPTION
        "This object specifies Average Data Rate per user on upstream.
          Value of 0 indicates the feature is disabled."
    ::= { cLQoSProfileEntry 14 }

cLQoSSsidDSBurstDataRate OBJECT-TYPE
    SYNTAX          Unsigned32
    MAX-ACCESS      read-write
    STATUS          current
    DESCRIPTION
        "This object specifies Burst Data Rate per user on downstream.
          Value of 0 indicates the feature is disabled."
    ::= { cLQoSProfileEntry 15 }

cLQoSSsidUSBurstDataRate OBJECT-TYPE
    SYNTAX          Unsigned32
    MAX-ACCESS      read-write
    STATUS          current
    DESCRIPTION
        "This object specifies Burst Data Rate per user on upstream.
          Value of 0 indicates the feature is disabled."
    ::= { cLQoSProfileEntry 16 }

cLQoSSsidDSAvgRealTimeDataRate OBJECT-TYPE
    SYNTAX          Unsigned32
    MAX-ACCESS      read-write
    STATUS          current
    DESCRIPTION
        "This object specifies average real time Data Rate per user on downstream.
          Value of 0 indicates the feature is disabled."
    ::= { cLQoSProfileEntry 17 }

cLQoSSsidUSAvgRealTimeDataRate OBJECT-TYPE
    SYNTAX          Unsigned32
    MAX-ACCESS      read-write
    STATUS          current
    DESCRIPTION
        "This object specifies average real time Data Rate per user on upstream.
          Value of 0 indicates the feature is disabled."
    ::= { cLQoSProfileEntry 18 }

cLQoSSsidDSBurstRealTimeDataRate OBJECT-TYPE
    SYNTAX          Unsigned32
    MAX-ACCESS      read-write
    STATUS          current
    DESCRIPTION
        "This object specifies burst real time Data Rate per user on downstream.
          Value of 0 indicates the feature is disabled."
    ::= { cLQoSProfileEntry 19 }

cLQoSSsidUSBurstRealTimeDataRate OBJECT-TYPE
    SYNTAX          Unsigned32
    MAX-ACCESS      read-write
    STATUS          current
    DESCRIPTION
        "This object specifies burst real time Data Rate per user on upstream.
          Value of 0 indicates the feature is disabled."
    ::= { cLQoSProfileEntry 20 }

-- *******************************************************************
-- *    SIP Snooping configuration
-- *******************************************************************

cLQoSSipSnoopingPortRangeStart OBJECT-TYPE
    SYNTAX          Unsigned32
    MAX-ACCESS      read-write
    STATUS          current
    DESCRIPTION
        "This is the starting port with respect to SIP snooping 
        feature on controller. If single port has to be used, 
        configure cLQoSSipSnoopingPortRangeStart and 
        cLQoSSipSnoopingPortRangeEnd with same value."
    ::= { cLQoSSipSnoopingConfig  1 }

cLQoSSipSnoopingPortRangeEnd OBJECT-TYPE
    SYNTAX          Unsigned32
    MAX-ACCESS      read-write
    STATUS          current
    DESCRIPTION
        "This is the ending port with respect to SIP snooping 
        feature on controller. If single port has to be used,
        configure cLQoSSipSnoopingPortRangeStart and
        cLQoSSipSnoopingPortRangeEnd with same value. "
    ::= { cLQoSSipSnoopingConfig  2 }


-- ********************************************************************
-- *    NOTIFICATION Control objects
-- ********************************************************************

ciscoLwappVoipCallFailureNotifEnabled OBJECT-TYPE
    SYNTAX          TruthValue
    MAX-ACCESS      read-write
    STATUS          current
    DESCRIPTION
        "The object to control the generation of
        ciscoLwappVoipCallFailureNotif
        notification.

        A value of 'true' indicates that the agent generates
        ciscoLwappVoipCallFailureNotif notification.

        A value of 'false' indicates that the agent doesn't
        generate ciscoLwappVoipCallFailureNotif
        notification." 
    ::= { cLQConfigObjects 1 }

ciscoLwappKtsVoipCallFailureNotifEnabled OBJECT-TYPE
    SYNTAX          TruthValue
    MAX-ACCESS      read-write
    STATUS          current
    DESCRIPTION
        "The object to control the generation of
        ciscoLwappKtsVoipCallFailureNotif
        notification.

        A value of 'true' indicates that the agent generates
        ciscoLwappKtsVoipCallFailureNotif notification.

        A value of 'false' indicates that the agent doesn't
        generate ciscoLwappKtsVoipCallFailureNotif
        notification." 
    ::= { cLQConfigObjects 2 }


--********************************************************************
--*    Notifications 
--********************************************************************
ciscoLwappVoipCallFailureNotif NOTIFICATION-TYPE
    OBJECTS         {
                        cLQVoiceClientLastCallFailureReasonCode,
                        cLQVoiceClientCallingNumber,
                        cLQVoiceClientLastCalledNumber,
                        cLApName,
                        cLApDot11IfType
                    }
    STATUS          current
    DESCRIPTION
        "This notification is generated when ever a VOIP call failure
        occurs."
   ::= { ciscoLwappQosMIBNotifs 1 }

--Gayathri

ciscoLwappMediaMCStreamFailureNotif NOTIFICATION-TYPE
    OBJECTS { 
              cldcClientMacAddress,
              cLQVMediaClientSrcIpAddr,
              cLQVMediaClientSrcIpAddrType,
              cLQVMediaClientDestIpAddr,
              cLQVMediaClientDestIpAddrType,
              cLQVMediaClientHistLastFailureReasonCode,
              cLQVMediaClientHistTimeStamp,
              cLQMStreamName,
              cLApName,
              cLApDot11IfType,
              cLWlanIndex,
              cLQVMediaClientHistCfgBw,
              cLQVMediaClientHistCurrentRate,
              cLQVMediaClientHistVideoPktSize,
              cLQVMediaClientHistVideoUtil,
              cLQVMediaClientHistVoiceUtil,
              cLQVMediaClientHistChannelUtil,
              cLQVMediaClientHistQueueUtil,
              cLQVMediaClientHistVideoPps,
              cLQVMediaClientHistVideoDelay,
              cLQVMediaClientHistPktLossDiscard,
              cLQVMediaClientHistPktLossFail,
              cLQVMediaClientHistNumVideoStreams,
              cLQVMediaClientHistCacEnable

            }
    STATUS current
    DESCRIPTION
        "This notification is generated when ever a Multicast to Unicast 
         Media conversion failure occurs.  AP MAC Address and
         slotID will be sent as index for AP related objects."
    ::= { ciscoLwappQosMIBNotifs  2 }


ciscoLwappMediaMCStreamAdmitNotif NOTIFICATION-TYPE
    OBJECTS { cldcClientMacAddress,
              cLQVMediaClientSrcIpAddr,
              cLQVMediaClientSrcIpAddrType,
              cLQVMediaClientDestIpAddr,
              cLQVMediaClientDestIpAddrType,
              cLQVMediaClientHistLastFailureReasonCode,
              cLQVMediaClientHistTimeStamp,
              cLQMStreamName,
              cLApName,
              cLApDot11IfType,
              cLWlanIndex,
              cLQVMediaClientHistCfgBw,
              cLQVMediaClientHistCurrentRate,
              cLQVMediaClientHistVideoPktSize,
              cLQVMediaClientHistVideoUtil,
              cLQVMediaClientHistVoiceUtil,
              cLQVMediaClientHistChannelUtil,
              cLQVMediaClientHistQueueUtil,
              cLQVMediaClientHistVideoPps,
              cLQVMediaClientHistVideoDelay,
              cLQVMediaClientHistPktLossDiscard,
              cLQVMediaClientHistPktLossFail,
              cLQVMediaClientHistNumVideoStreams,
              cLQVMediaClientHistCacEnable

            }
    STATUS current
    DESCRIPTION
        "This notification is generated when ever a client 
         gets admitted to the stream.  AP MAC Address and
         slotID will be sent as index for AP related objects."
    ::= { ciscoLwappQosMIBNotifs  3 }

ciscoLwappMediaMCStreamDelistNotif NOTIFICATION-TYPE
    OBJECTS { cldcClientMacAddress,
              cLQVMediaClientSrcIpAddr,
              cLQVMediaClientSrcIpAddrType,
              cLQVMediaClientDestIpAddr,
              cLQVMediaClientDestIpAddrType,
              cLQVMediaClientHistLastFailureReasonCode,
              cLQVMediaClientHistTimeStamp,
              cLQMStreamName,
              cLApName,
              cLApDot11IfType,
              cLWlanIndex,
              cLQVMediaClientHistCfgBw,
              cLQVMediaClientHistCurrentRate,
              cLQVMediaClientHistVideoPktSize,
              cLQVMediaClientHistVideoUtil,
              cLQVMediaClientHistVoiceUtil,
              cLQVMediaClientHistChannelUtil,
              cLQVMediaClientHistQueueUtil,
              cLQVMediaClientHistVideoPps,
              cLQVMediaClientHistVideoDelay,
              cLQVMediaClientHistPktLossDiscard,
              cLQVMediaClientHistPktLossFail,
              cLQVMediaClientHistNumVideoStreams,
              cLQVMediaClientHistCacEnable

            }
    STATUS current
    DESCRIPTION
        "This notification is generated when ever a client delists from the 
          stream.  AP MAC Address and slotID will be sent as index for 
          AP related objects."

    ::= { ciscoLwappQosMIBNotifs  4 }

ciscoLwappKtsVoipCallFailureNotif NOTIFICATION-TYPE
    OBJECTS         {
                        cLQVoiceClientLastCallFailureReasonCode,
                        cLApName,
                        cLApDot11IfType
                    }
    STATUS          current
    DESCRIPTION
        "This notification is generated when ever a KTS VOIP call failure
        occurs."
   ::= { ciscoLwappQosMIBNotifs 5 }

--********************************************************************
ciscoLwappQosMIBCompliances OBJECT IDENTIFIER
        ::= { ciscoLwappQosMIBConform 1 }

ciscoLwappQosMIBGroups OBJECT IDENTIFIER
        ::= { ciscoLwappQosMIBConform 2 }

ciscoLwappQosMIBCompliance MODULE-COMPLIANCE
        STATUS     deprecated 
        DESCRIPTION
                "The compliance statement for the SNMP entities that
                implement the ciscoLwappQosMIB module. "
        MODULE MANDATORY-GROUPS {                
                ciscoLwappQosDot11aConfigGroup,
                ciscoLwappQosDot11bConfigGroup,
                ciscoLwappQosDot11WlanConfigGroup,
                ciscoLwappQosDot11CacStatsGroup
        }
        ::= { ciscoLwappQosMIBCompliances 1 }

ciscoLwappQosMIBComplianceRev1 MODULE-COMPLIANCE
        STATUS     deprecated
        DESCRIPTION
                "The compliance statement for the SNMP entities that
                implement the ciscoLwappQosMIB module. "
        MODULE MANDATORY-GROUPS {                
                ciscoLwappQosDot11aConfigGroup,
                ciscoLwappQosDot11bConfigGroup,
                ciscoLwappQosDot11WlanConfigGroup,
                ciscoLwappQosDot11CacStatsGroup,
                ciscoLwappQosDot11aConfigGroupSup1, 
                ciscoLwappQosDot11bConfigGroupSup1
        }
        ::= { ciscoLwappQosMIBCompliances 2 }

ciscoLwappQosMIBComplianceRev2 MODULE-COMPLIANCE
    STATUS          deprecated
    DESCRIPTION
        "Implementation of this group is mandatory only for the
        platforms which implement the ciscoLwappQosMIB module."
    MODULE          -- this module
    MANDATORY-GROUPS {
                        ciscoLwappQosDot11aConfigGroup,
                        ciscoLwappQosDot11bConfigGroup,
                        ciscoLwappQosDot11WlanConfigGroup,
                        ciscoLwappQosDot11CacStatsGroup,
                        ciscoLwappQosDot11aConfigGroupSup1,
                        ciscoLwappQosDot11bConfigGroupSup1,
                        ciscoLwappQosDot11aConfigGroupSup2,
                        ciscoLwappQosDot11bConfigGroupSup2,
                        ciscoLwappQosDot11SipCacStatsGroup,
                        ciscoLwappQosDot11SipConfigGroup,
                        ciscoLwappQosDot11VoiceStatsGroup,
                        ciscoLwappQosDot11VoiceConfigGroup,
                        ciscoLwappQosDot11VoiceNotifGroup,
                        ciscoLwappQosConfigGroup
                    }
    ::= { ciscoLwappQosMIBCompliances 3 }

ciscoLwappQosMIBComplianceRev3 MODULE-COMPLIANCE
    STATUS          current
    DESCRIPTION
        "Implementation of this group is mandatory only for the
        platforms which implement the ciscoLwappQosMIB module."
    MODULE          -- this module
    MANDATORY-GROUPS {
                        ciscoLwappQosDot11aConfigGroup,
                        ciscoLwappQosDot11bConfigGroup,
                        ciscoLwappQosDot11WlanConfigGroup,
                        ciscoLwappQosDot11CacStatsGroup,
                        ciscoLwappQosDot11aConfigGroupSup1,
                        ciscoLwappQosDot11bConfigGroupSup1,
                        ciscoLwappQosDot11aConfigGroupSup2,
                        ciscoLwappQosDot11bConfigGroupSup2,
                        ciscoLwappQosDot11SipCacStatsGroup,
                        ciscoLwappQosDot11SipConfigGroup,
                        ciscoLwappQosDot11VoiceStatsGroup,
                        ciscoLwappQosDot11VoiceConfigGroup,
                        ciscoLwappQosDot11VoiceNotifGroup,
                        ciscoLwappQosConfigGroup,
                        ciscoLwappQosDot11VoiceNotifGroupSup1,
                        ciscoLwappQosConfigGroupSup1
                    }
    ::= { ciscoLwappQosMIBCompliances 4 }


--********************************************************************
--*    Units of conformance  
--********************************************************************

ciscoLwappQosDot11aConfigGroup OBJECT-GROUP
        OBJECTS {
                cLQd11aVoiceAdmCtrlSupport,
                cLQd11aVoiceMaxAdmBandwidth,
                cLQd11aVoiceMaxRoamBandwidth,
                cLQd11aVideoAdmCtrlSupport,
                cLQd11aVideoMaxAdmBandwidth,
                cLQd11aVideoMaxRoamBandwidth,
                cLQd11aGprProbeInterval
        }
        STATUS     current
        DESCRIPTION
                "This collection of objects represents the 
                quality-of-service parameters 802.11a networks. " 
        ::= { ciscoLwappQosMIBGroups 1 }

ciscoLwappQosDot11bConfigGroup OBJECT-GROUP
        OBJECTS {
                cLQd11bVoiceAdmCtrlSupport,
                cLQd11bVoiceMaxAdmBandwidth,
                cLQd11bVoiceMaxRoamBandwidth,
                cLQd11bVideoAdmCtrlSupport,
                cLQd11bVideoMaxAdmBandwidth,
                cLQd11bVideoMaxRoamBandwidth,
                cLQd11bGprProbeInterval
        }
        STATUS     current
        DESCRIPTION
                "This collection of objects represents the 
                quality-of-service parameters 802.11b networks. " 
        ::= { ciscoLwappQosMIBGroups 2 }
  
ciscoLwappQosDot11WlanConfigGroup OBJECT-GROUP
        OBJECTS { 
                cLQd11GprSupport
        }
        STATUS     current
        DESCRIPTION
                "This collection of objects represents the
                quality-of-services parameters on a particular WLAN. "
        ::= { ciscoLwappQosMIBGroups 3 }

ciscoLwappQosDot11CacStatsGroup OBJECT-GROUP
        OBJECTS { 
                cLQd11CacVoiceBwInUse, 
                cLQd11CacVideoBwInUse,
                cLQd11CacVoiceCallsInProgress,
                cLQd11CacRoamVoiceCallsInProg,
                cLQd11CacTotalVoiceCallsAP,
                cLQd11CacTotalRoamCallsAP,
                cLQd11CacVoiceCallsRejectedAP,
                cLQd11CacRoamCallsRejectedAP,
                cLQd11CacRejCallsInsufBw,
                cLQd11CacRejCallsBadParams,
                cLQd11CacRejCallsPhyRate,
                cLQd11CacRejCallsQosPolicy
        }
        STATUS     current
        DESCRIPTION
                "This collection of objects provide the call
                admission control statistics observed on the
                dot11 interfaces of an AP. "
        ::= { ciscoLwappQosMIBGroups 4 }

ciscoLwappQosDot11aConfigGroupSup1 OBJECT-GROUP
        OBJECTS {
                cLQd11aVoiceCtrl, 
                cLQd11aExpeditedBw 
        }
        STATUS     current
        DESCRIPTION
                "This collection of objects represents the 
                quality-of-service parameters 802.11a networks. " 
        ::= { ciscoLwappQosMIBGroups 5 }

ciscoLwappQosDot11bConfigGroupSup1 OBJECT-GROUP
        OBJECTS {
                cLQd11bVoiceCtrl, 
                cLQd11bExpeditedBw 
        }
        STATUS     current
        DESCRIPTION
                "This collection of objects represents the 
                quality-of-service parameters 802.11b networks. " 
        ::= { ciscoLwappQosMIBGroups 6 }

ciscoLwappQosDot11aConfigGroupSup2 OBJECT-GROUP
    OBJECTS         {
                        cLQd11aEdcaProfile,
                        cLQd11aMacOptimization,
                        cLQd11aMaxCallLimit
                    }
    STATUS          current
    DESCRIPTION
        "This collection of objects represents the
        quality-of-service parameters 802.11a networks."
    ::= { ciscoLwappQosMIBGroups 7 }

ciscoLwappQosDot11bConfigGroupSup2 OBJECT-GROUP
    OBJECTS         {
                        cLQd11bEdcaProfile,
                        cLQd11bMacOptimization,
                        cLQd11bMaxCallLimit
                    }
    STATUS          current
    DESCRIPTION
        "This collection of objects represents the
        quality-of-service parameters 802.11b networks."
    ::= { ciscoLwappQosMIBGroups 8 }

ciscoLwappQosDot11SipCacStatsGroup OBJECT-GROUP
    OBJECTS         {
                        cLQd11SipCacNonRoamCallsInProgress,
                        cLQd11SipCacRoamCallsInProg,
                        cLQd11SipCacTotalNonRoamCallsAP,
                        cLQd11SipCacTotalRoamCallsAP,
                        cLQd11SipCacNonRoamCallsRejectedInSuffBw,
                        cLQd11SipCacRoamCallsRejectedInSuffBw,
                        cLQd11SipCacNonRoamCallsRejectedMaxLimit,
                        cLQd11SipCacRoamCallsRejectedMaxLimit,
                        cLQd11SipCacRejCallsQosPolicy
                    }
    STATUS          current
    DESCRIPTION
        "This collection of objects provide the SIP call
        admission control statistics observed on the
        dot11 interfaces of an AP."
    ::= { ciscoLwappQosMIBGroups 9 }

ciscoLwappQosDot11SipConfigGroup OBJECT-GROUP
    OBJECTS         {
                        cLQd11SipCacConfigCodecType,
                        cLQd11SipCacConfigBw,
                        cLQd11SipCacConfigVoiceSampleSize
                    }
    STATUS          current
    DESCRIPTION
        "This collection of objects represents the
        SIP call admission control configuration parameters."
    ::= { ciscoLwappQosMIBGroups 10 }

ciscoLwappQosDot11VoiceStatsGroup OBJECT-GROUP
    OBJECTS         {
                        cLQd11VoiceCallCounts,
                        cLQd11CacVoiceCallTimePeriod
                    }
    STATUS          current
    DESCRIPTION
        "This collection of objects represents the
        Voice statistics parameters."
    ::= { ciscoLwappQosMIBGroups 11 }

ciscoLwappQosDot11VoiceConfigGroup OBJECT-GROUP
    OBJECTS         {
                        cLQVoiceWlanConfigDetectVoipCallFailure,
                        cLQVoiceClientCallingNumber,
                        cLQVoiceClientLastCalledNumber,
                        cLQVoiceClientLastCallFailureReasonCode
                    }
    STATUS          current
    DESCRIPTION
        "This collection of objects represents the
        Voice statistics parameters."
    ::= { ciscoLwappQosMIBGroups 12 }

ciscoLwappQosDot11VoiceNotifGroup NOTIFICATION-GROUP
   NOTIFICATIONS    { ciscoLwappVoipCallFailureNotif }
    STATUS          current
    DESCRIPTION
        "This collection of objects represents the
        Voice notification parameters."
    ::= { ciscoLwappQosMIBGroups 13 }

ciscoLwappQosConfigGroup OBJECT-GROUP
    OBJECTS         { ciscoLwappVoipCallFailureNotifEnabled }
    STATUS          current
    DESCRIPTION
        "This collection of objects represents the
        quality-of-service configuration parameters."
    ::= { ciscoLwappQosMIBGroups 14 }

ciscoLwappQosDot11VoiceNotifGroupSup1 NOTIFICATION-GROUP
   NOTIFICATIONS    { 
                     ciscoLwappKtsVoipCallFailureNotif 
                    }
    STATUS          current
    DESCRIPTION
        "This collection of objects represents the
        Voice notification parameters."
    ::= { ciscoLwappQosMIBGroups 15 }

ciscoLwappQosConfigGroupSup1 OBJECT-GROUP
    OBJECTS         { 
                     ciscoLwappKtsVoipCallFailureNotifEnabled
                    }
    STATUS          current
    DESCRIPTION
        "This collection of objects represents the
        quality-of-service configuration parameters."
    ::= { ciscoLwappQosMIBGroups 16 }

END
