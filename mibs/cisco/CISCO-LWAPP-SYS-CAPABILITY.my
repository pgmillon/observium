-- *****************************************************************
-- CISCO-LWAPP-SYS-MIB.my
-- CISCO-LWAPP-SYS MIB capabilities
--   
-- Aug 2010 Suja Thangaveluchamy
-- Copyright (c) 2006, 2010 by cisco Systems Inc.
-- All rights reserved.
--   
-- *****************************************************************

CISCO-LWAPP-SYS-CAPABILITY DEFINITIONS ::= BEGIN

IMPORTS
    MODULE-IDENTITY
        FROM SNMPv2-SMI
    AGENT-CAPABILITIES
        FROM SNMPv2-CONF
    ciscoAgentCapability
        FROM CISCO-SMI;


ciscoLwappSysCapability MODULE-IDENTITY
    LAST-UPDATED    "201008170000Z"
    ORGANIZATION    "Cisco Systems, Inc."
    CONTACT-INFO
            "Cisco Systems
            Customer Service

            Postal: 170 W Tasman Drive
            San Jose, CA  95134
            USA

            Tel: +1 800 553-NETS

            E-mail: cs-wnbu-snmp@cisco.com"
    DESCRIPTION
        "Agent capabilities for CISCO-LWAPP-SYS-MIB."
    REVISION        "201008170000Z"
    DESCRIPTION
        "Latest version of this MIB module."
    ::= { ciscoAgentCapability 3333 }



ciscoLwappSysCapabilityCUWNSR7V0 AGENT-CAPABILITIES
    PRODUCT-RELEASE "Cisco Unified Wireless Network Software
                     Release 7.0 for Cisco WLAN controllers"
    STATUS           current
    DESCRIPTION
                    "CISCO-LWAPP-SYS-MIB capabilities"

    SUPPORTS        CISCO-LWAPP-SYS-MIB
    INCLUDES        { ciscoLwappSysIgmpConfigGroup }
    VARIATION       cLSysMulticastIGMPSnoopingTimeout
    DESCRIPTION
        "The range of values suppported is from 30 to 7200"

    VARIATION       cLSysMulticastIGMPQueryInterval
    DESCRIPTION
        "The range of values suppported is from 15 to 2400. Default is 60."
    ::= { ciscoLwappSysCapability 1 }

ciscoLwappSysCapabilityCUWNSR7V2 AGENT-CAPABILITIES
    PRODUCT-RELEASE "Cisco Unified Wireless Network Software
                     Release 7.2 for Cisco WLAN controllers"
    STATUS           current
    DESCRIPTION
                    "CISCO-LWAPP-SYS-MIB capabilities"

    SUPPORTS        CISCO-LWAPP-SYS-MIB
    INCLUDES        { ciscoLwappSysStatsConfigGroup }
    VARIATION       clsSysStatsSamplingInterval
    DESCRIPTION
        "The range of values supported is from 2 to 900. Default is 30."

    VARIATION       clsSysStatsAverageInterval
    DESCRIPTION
        "The range of values supported is from 120 to 900. Default is 300."
    ::= { ciscoLwappSysCapability 2 }

END
