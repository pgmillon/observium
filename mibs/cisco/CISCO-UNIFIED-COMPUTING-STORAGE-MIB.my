-- *********************************************************************
-- CISCO-UNIFIED-COMPUTING-STORAGE-MIB.my
-- 
-- MIB representation of the Cisco Unified Computing System
-- STORAGE management information model package
-- 
-- Created June 2013 by Charles Bullis
-- 
-- Copyright (c) 2005-2013 Cisco Systems, Inc. All rights reserved.
-- 
-- *********************************************************************

CISCO-UNIFIED-COMPUTING-STORAGE-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoUnifiedComputingMIBObjects,
    CucsManagedObjectId,
    CucsManagedObjectDn
        FROM CISCO-UNIFIED-COMPUTING-MIB
    CucsAaaConfigState,
    CucsConditionRemoteInvRslt,
    CucsEquipmentOperability,
    CucsEquipmentPowerState,
    CucsEquipmentPresence,
    CucsEquipmentSensorThresholdStatus,
    CucsFabricZoningState,
    CucsFsmCompletion,
    CucsFsmFlags,
    CucsFsmFsmStageStatus,
    CucsFsmLifecycle,
    CucsPolicyPolicyOwner,
    CucsStorageBatteryType,
    CucsStorageConfiguration,
    CucsStorageConnectionProtocol,
    CucsStorageControllerFaultMonitoring,
    CucsStorageControllerId,
    CucsStorageControllerType,
    CucsStorageDisklessAction,
    CucsStorageEpAccess,
    CucsStorageEtherIfVlanType,
    CucsStorageFcZoningType,
    CucsStorageFileSystemStatus,
    CucsStorageIniGroupOperProtocol,
    CucsStorageIniGroupOwner,
    CucsStorageIniGroupProtocol,
    CucsStorageKeyType,
    CucsStorageLocalDiskConfigFlexFlashRAIDReportingState,
    CucsStorageLocalDiskConfigFlexFlashState,
    CucsStorageLocalDiskMode,
    CucsStorageLocalDiskPartitionType,
    CucsStorageLunType,
    CucsStorageOperState,
    CucsStorageProtocol,
    CucsStorageRaidBatteryOperabilityQualifier,
    CucsStorageSystemFsmCurrentFsm,
    CucsStorageSystemFsmStageName,
    CucsStorageSystemFsmTaskItem,
    CucsStorageTargetPath,
    CucsStorageVsanRefSwitchId,
    CucsVnicConfigIssues
        FROM CISCO-UNIFIED-COMPUTING-TC-MIB;

cucsStorageObjects MODULE-IDENTITY
    LAST-UPDATED    "201306240000Z"
    ORGANIZATION    "Cisco Systems Inc."
    CONTACT-INFO
        "Cisco Systems
        Customer Service
        
        Postal: 170 W Tasman Drive
        San Jose, CA  95134
        USA
        
        Tel: +1 800 553 -NETS
        
        E-mail: cs-san@cisco.com, cs-lan-switch-snmp@cisco.com"
    DESCRIPTION
        "MIB representation of the Cisco Unified Computing System
        STORAGE management information model package"
    ::= { ciscoUnifiedComputingMIBObjects 45 }

cucsStorageAuthKeyTable OBJECT-TYPE
    SYNTAX           SEQUENCE OF CucsStorageAuthKeyEntry
    MAX-ACCESS       not-accessible
    STATUS           current
    DESCRIPTION
        "Cisco UCS storage:AuthKey managed object table"
    ::= { cucsStorageObjects 14 }

cucsStorageAuthKeyEntry OBJECT-TYPE
    SYNTAX           CucsStorageAuthKeyEntry
    MAX-ACCESS       not-accessible
    STATUS           current
    DESCRIPTION
        "Entry for the cucsStorageAuthKeyTable table."
    INDEX { cucsStorageAuthKeyInstanceId }
    ::= { cucsStorageAuthKeyTable 1 }

CucsStorageAuthKeyEntry ::= SEQUENCE {
    cucsStorageAuthKeyInstanceId                                     CucsManagedObjectId,
    cucsStorageAuthKeyDn                                             CucsManagedObjectDn,
    cucsStorageAuthKeyRn                                             SnmpAdminString,
    cucsStorageAuthKeyDescr                                          SnmpAdminString,
    cucsStorageAuthKeyIntId                                          SnmpAdminString,
    cucsStorageAuthKeyName                                           SnmpAdminString,
    cucsStorageAuthKeyPassword                                       SnmpAdminString,
    cucsStorageAuthKeyPolicyLevel                                    Gauge32,
    cucsStorageAuthKeyPolicyOwner                                    CucsPolicyPolicyOwner,
    cucsStorageAuthKeyType                                           CucsStorageKeyType,
    cucsStorageAuthKeyUserId                                         SnmpAdminString
}

cucsStorageAuthKeyInstanceId OBJECT-TYPE
    SYNTAX       CucsManagedObjectId
    MAX-ACCESS   not-accessible
    STATUS       current
    DESCRIPTION
        "Instance identifier of the managed object."
    ::= { cucsStorageAuthKeyEntry 1 }

cucsStorageAuthKeyDn OBJECT-TYPE
    SYNTAX       CucsManagedObjectDn
    MAX-ACCESS   read-only
    STATUS       current
    DESCRIPTION
        "Cisco UCS storage:AuthKey:dn managed object property"
    ::= { cucsStorageAuthKeyEntry 2 }

cucsStorageAuthKeyRn OBJECT-TYPE
    SYNTAX       SnmpAdminString
    MAX-ACCESS   read-only
    STATUS       current
    DESCRIPTION
        "Cisco UCS storage:AuthKey:rn managed object property"
    ::= { cucsStorageAuthKeyEntry 3 }

cucsStorageAuthKeyDescr OBJECT-TYPE
    SYNTAX       SnmpAdminString
    MAX-ACCESS   read-only
    STATUS       current
    DESCRIPTION
        "Cisco UCS storage:AuthKey:descr managed object property"
    ::= { cucsStorageAuthKeyEntry 4 }

cucsStorageAuthKeyIntId OBJECT-TYPE
    SYNTAX       SnmpAdminString
    MAX-ACCESS   read-only
    STATUS       current
    DESCRIPTION
        "Cisco UCS storage:AuthKey:intId managed object property"
    ::= { cucsStorageAuthKeyEntry 5 }

cucsStorageAuthKeyName OBJECT-TYPE
    SYNTAX       SnmpAdminString
    MAX-ACCESS   read-only
    STATUS       current
    DESCRIPTION
        "Cisco UCS storage:AuthKey:name managed object property"
    ::= { cucsStorageAuthKeyEntry 6 }

cucsStorageAuthKeyPassword OBJECT-TYPE
    SYNTAX       SnmpAdminString
    MAX-ACCESS   read-only
    STATUS       current
    DESCRIPTION
        "Cisco UCS storage:AuthKey:password managed object property"
    ::= { cucsStorageAuthKeyEntry 7 }

cucsStorageAuthKeyPolicyLevel OBJECT-TYPE
    SYNTAX       Gauge32
    MAX-ACCESS   read-only
    STATUS       current
    DESCRIPTION
        "Cisco UCS storage:AuthKey:policyLevel managed object property"
    ::= { cucsStorageAuthKeyEntry 8 }

cucsStorageAuthKeyPolicyOwner OBJECT-TYPE
    SYNTAX       CucsPolicyPolicyOwner
    MAX-ACCESS   read-only
    STATUS       current
    DESCRIPTION
        "Cisco UCS storage:AuthKey:policyOwner managed object property"
    ::= { cucsStorageAuthKeyEntry 9 }

cucsStorageAuthKeyType OBJECT-TYPE
    SYNTAX       CucsStorageKeyType
    MAX-ACCESS   read-only
    STATUS       current
    DESCRIPTION
        "Cisco UCS storage:AuthKey:type managed object property"
    ::= { cucsStorageAuthKeyEntry 10 }

cucsStorageAuthKeyUserId OBJECT-TYPE
    SYNTAX       SnmpAdminString
    MAX-ACCESS   read-only
    STATUS       current
    DESCRIPTION
        "Cisco UCS storage:AuthKey:userId managed object property"
    ::= { cucsStorageAuthKeyEntry 11 }

cucsStorageConnectionDefTable OBJECT-TYPE
    SYNTAX           SEQUENCE OF CucsStorageConnectionDefEntry
    MAX-ACCESS       not-accessible
    STATUS           current
    DESCRIPTION
        "Cisco UCS storage:ConnectionDef managed object table"
    ::= { cucsStorageObjects 15 }

cucsStorageConnectionDefEntry OBJECT-TYPE
    SYNTAX           CucsStorageConnectionDefEntry
    MAX-ACCESS       not-accessible
    STATUS           current
    DESCRIPTION
        "Entry for the cucsStorageConnectionDefTable table."
    INDEX { cucsStorageConnectionDefInstanceId }
    ::= { cucsStorageConnectionDefTable 1 }

CucsStorageConnectionDefEntry ::= SEQUENCE {
    cucsStorageConnectionDefInstanceId                               CucsManagedObjectId,
    cucsStorageConnectionDefDn                                       CucsManagedObjectDn,
    cucsStorageConnectionDefRn                                       SnmpAdminString,
    cucsStorageConnectionDefDescr                                    SnmpAdminString,
    cucsStorageConnectionDefIntId                                    SnmpAdminString,
    cucsStorageConnectionDefName                                     SnmpAdminString,
    cucsStorageConnectionDefOperState                                CucsStorageOperState,
    cucsStorageConnectionDefPolicyLevel                              Gauge32,
    cucsStorageConnectionDefPolicyOwner                              CucsPolicyPolicyOwner,
    cucsStorageConnectionDefZoningType                               CucsStorageFcZoningType
}

cucsStorageConnectionDefInstanceId OBJECT-TYPE
    SYNTAX       CucsManagedObjectId
    MAX-ACCESS   not-accessible
    STATUS       current
    DESCRIPTION
        "Instance identifier of the managed object."
    ::= { cucsStorageConnectionDefEntry 1 }

cucsStorageConnectionDefDn OBJECT-TYPE
    SYNTAX       CucsManagedObjectDn
    MAX-ACCESS   read-only
    STATUS       current
    DESCRIPTION
        "Cisco UCS storage:ConnectionDef:dn managed object property"
    ::= { cucsStorageConnectionDefEntry 2 }

cucsStorageConnectionDefRn OBJECT-TYPE
    SYNTAX       SnmpAdminString
    MAX-ACCESS   read-only
    STATUS       current
    DESCRIPTION
        "Cisco UCS storage:ConnectionDef:rn managed object property"
    ::= { cucsStorageConnectionDefEntry 3 }

cucsStorageConnectionDefDescr OBJECT-TYPE
    SYNTAX       SnmpAdminString
    MAX-ACCESS   read-only
    STATUS       current
    DESCRIPTION
        "Cisco UCS storage:ConnectionDef:descr managed object property"
    ::= { cucsStorageConnectionDefEntry 4 }

cucsStorageConnectionDefIntId OBJECT-TYPE
    SYNTAX       SnmpAdminString
    MAX-ACCESS   read-only
    STATUS       current
    DESCRIPTION
        "Cisco UCS storage:ConnectionDef:intId managed object property"
    ::= { cucsStorageConnectionDefEntry 5 }

cucsStorageConnectionDefName OBJECT-TYPE
    SYNTAX       SnmpAdminString
    MAX-ACCESS   read-only
    STATUS       current
    DESCRIPTION
        "Cisco UCS storage:ConnectionDef:name managed object property"
    ::= { cucsStorageConnectionDefEntry 6 }

cucsStorageConnectionDefOperState OBJECT-TYPE
    SYNTAX       CucsStorageOperState
    MAX-ACCESS   read-only
    STATUS       current
    DESCRIPTION
        "Cisco UCS storage:ConnectionDef:operState managed
        object property"
    ::= { cucsStorageConnectionDefEntry 7 }

cucsStorageConnectionDefPolicyLevel OBJECT-TYPE
    SYNTAX       Gauge32
    MAX-ACCESS   read-only
    STATUS       current
    DESCRIPTION
        "Cisco UCS storage:ConnectionDef:policyLevel managed
        object property"
    ::= { cucsStorageConnectionDefEntry 8 }

cucsStorageConnectionDefPolicyOwner OBJECT-TYPE
    SYNTAX       CucsPolicyPolicyOwner
    MAX-ACCESS   read-only
    STATUS       current
    DESCRIPTION
        "Cisco UCS storage:ConnectionDef:policyOwner managed
        object property"
    ::= { cucsStorageConnectionDefEntry 9 }

cucsStorageConnectionDefZoningType OBJECT-TYPE
    SYNTAX       CucsStorageFcZoningType
    MAX-ACCESS   read-only
    STATUS       current
    DESCRIPTION
        "Cisco UCS storage:ConnectionDef:zoningType managed
        object property"
    ::= { cucsStorageConnectionDefEntry 10 }

cucsStorageConnectionPolicyTable OBJECT-TYPE
    SYNTAX           SEQUENCE OF CucsStorageConnectionPolicyEntry
    MAX-ACCESS       not-accessible
    STATUS           current
    DESCRIPTION
        "Cisco UCS storage:ConnectionPolicy managed object table"
    ::= { cucsStorageObjects 16 }

cucsStorageConnectionPolicyEntry OBJECT-TYPE
    SYNTAX           CucsStorageConnectionPolicyEntry
    MAX-ACCESS       not-accessible
    STATUS           current
    DESCRIPTION
        "Entry for the cucsStorageConnectionPolicyTable table."
    INDEX { cucsStorageConnectionPolicyInstanceId }
    ::= { cucsStorageConnectionPolicyTable 1 }

CucsStorageConnectionPolicyEntry ::= SEQUENCE {
    cucsStorageConnectionPolicyInstanceId                            CucsManagedObjectId,
    cucsStorageConnectionPolicyDn                                    CucsManagedObjectDn,
    cucsStorageConnectionPolicyRn                                    SnmpAdminString,
    cucsStorageConnectionPolicyDescr                                 SnmpAdminString,
    cucsStorageConnectionPolicyIntId                                 SnmpAdminString,
    cucsStorageConnectionPolicyName                                  SnmpAdminString,
    cucsStorageConnectionPolicyOperState                             CucsStorageOperState,
    cucsStorageConnectionPolicyPolicyLevel                           Gauge32,
    cucsStorageConnectionPolicyPolicyOwner                           CucsPolicyPolicyOwner,
    cucsStorageConnectionPolicyZoningType                            CucsStorageFcZoningType
}

cucsStorageConnectionPolicyInstanceId OBJECT-TYPE
    SYNTAX       CucsManagedObjectId
    MAX-ACCESS   not-accessible
    STATUS       current
    DESCRIPTION
        "Instance identifier of the managed object."
    ::= { cucsStorageConnectionPolicyEntry 1 }

cucsStorageConnectionPolicyDn OBJECT-TYPE
    SYNTAX       CucsManagedObjectDn
    MAX-ACCESS   read-only
    STATUS       current
    DESCRIPTION
        "Cisco UCS storage:ConnectionPolicy:dn managed object property"
    ::= { cucsStorageConnectionPolicyEntry 2 }

cucsStorageConnectionPolicyRn OBJECT-TYPE
    SYNTAX       SnmpAdminString
    MAX-ACCESS   read-only
    STATUS       current
    DESCRIPTION
        "Cisco UCS storage:ConnectionPolicy:rn managed object property"
    ::= { cucsStorageConnectionPolicyEntry 3 }

cucsStorageConnectionPolicyDescr OBJECT-TYPE
    SYNTAX       SnmpAdminString
    MAX-ACCESS   read-only
    STATUS       current
    DESCRIPTION
        "Cisco UCS storage:ConnectionPolicy:descr managed object property"
    ::= { cucsStorageConnectionPolicyEntry 4 }

cucsStorageConnectionPolicyIntId OBJECT-TYPE
    SYNTAX       SnmpAdminString
    MAX-ACCESS   read-only
    STATUS       current
    DESCRIPTION
        "Cisco UCS storage:ConnectionPolicy:intId managed object property"
    ::= { cucsStorageConnectionPolicyEntry 5 }

cucsStorageConnectionPolicyName OBJECT-TYPE
    SYNTAX       SnmpAdminString
    MAX-ACCESS   read-only
    STATUS       current
    DESCRIPTION
        "Cisco UCS storage:ConnectionPolicy:name managed object property"
    ::= { cucsStorageConnectionPolicyEntry 6 }

cucsStorageConnectionPolicyOperState OBJECT-TYPE
    SYNTAX       CucsStorageOperState
    MAX-ACCESS   read-only
    STATUS       current
    DESCRIPTION
        "Cisco UCS storage:ConnectionPolicy:operState managed
        object property"
    ::= { cucsStorageConnectionPolicyEntry 7 }

cucsStorageConnectionPolicyPolicyLevel OBJECT-TYPE
    SYNTAX       Gauge32
    MAX-ACCESS   read-only
    STATUS       current
    DESCRIPTION
        "Cisco UCS storage:ConnectionPolicy:policyLevel
        managed object property"
    ::= { cucsStorageConnectionPolicyEntry 8 }

cucsStorageConnectionPolicyPolicyOwner OBJECT-TYPE
    SYNTAX       CucsPolicyPolicyOwner
    MAX-ACCESS   read-only
    STATUS       current
    DESCRIPTION
        "Cisco UCS storage:ConnectionPolicy:policyOwner
        managed object property"
    ::= { cucsStorageConnectionPolicyEntry 9 }

cucsStorageConnectionPolicyZoningType OBJECT-TYPE
    SYNTAX       CucsStorageFcZoningType
    MAX-ACCESS   read-only
    STATUS       current
    DESCRIPTION
        "Cisco UCS storage:ConnectionPolicy:zoningType
        managed object property"
    ::= { cucsStorageConnectionPolicyEntry 10 }

cucsStorageControllerTable OBJECT-TYPE
    SYNTAX           SEQUENCE OF CucsStorageControllerEntry
    MAX-ACCESS       not-accessible
    STATUS           current
    DESCRIPTION
        "Cisco UCS storage:Controller managed object table"
    ::= { cucsStorageObjects 1 }

cucsStorageControllerEntry OBJECT-TYPE
    SYNTAX           CucsStorageControllerEntry
    MAX-ACCESS       not-accessible
    STATUS           current
    DESCRIPTION
        "Entry for the cucsStorageControllerTable table."
    INDEX { cucsStorageControllerInstanceId }
    ::= { cucsStorageControllerTable 1 }

CucsStorageControllerEntry ::= SEQUENCE {
    cucsStorageControllerInstanceId                                  CucsManagedObjectId,
    cucsStorageControllerDn                                          CucsManagedObjectDn,
    cucsStorageControllerRn                                          SnmpAdminString,
    cucsStorageControllerId                                          CucsStorageControllerId,
    cucsStorageControllerModel                                       SnmpAdminString,
    cucsStorageControllerOperState                                   CucsEquipmentOperability,
    cucsStorageControllerOperability                                 CucsEquipmentOperability,
    cucsStorageControllerPciAddr                                     SnmpAdminString,
    cucsStorageControllerPciSlot                                     SnmpAdminString,
    cucsStorageControllerPerf                                        CucsEquipmentSensorThresholdStatus,
    cucsStorageControllerPower                                       CucsEquipmentPowerState,
    cucsStorageControllerPresence                                    CucsEquipmentPresence,
    cucsStorageControllerRevision                                    SnmpAdminString,
    cucsStorageControllerSerial                                      SnmpAdminString,
    cucsStorageControllerThermal                                     CucsEquipmentSensorThresholdStatus,
    cucsStorageControllerType                                        CucsStorageControllerType,
    cucsStorageControllerVendor                                      SnmpAdminString,
    cucsStorageControllerVoltage                                     CucsEquipmentSensorThresholdStatus,
    cucsStorageControllerRaidSupport                                 SnmpAdminString,
    cucsStorageControllerFaultMonitoring                             CucsStorageControllerFaultMonitoring,
    cucsStorageControllerHwRevision                                  SnmpAdminString,
    cucsStorageControllerDeviceRaidSupport                           SnmpAdminString,
    cucsStorageControllerOperQualifierReason                         SnmpAdminString
}

cucsStorageControllerInstanceId OBJECT-TYPE
    SYNTAX       CucsManagedObjectId
    MAX-ACCESS   not-accessible
    STATUS       current
    DESCRIPTION
        "Instance identifier of the managed object."
    ::= { cucsStorageControllerEntry 1 }

cucsStorageControllerDn OBJECT-TYPE
    SYNTAX       CucsManagedObjectDn
    MAX-ACCESS   read-only
    STATUS       current
    DESCRIPTION
        "Cisco UCS storage:Controller:dn managed object property"
    ::= { cucsStorageControllerEntry 2 }

cucsStorageControllerRn OBJECT-TYPE
    SYNTAX       SnmpAdminString
    MAX-ACCESS   read-only
    STATUS       current
    DESCRIPTION
        "Cisco UCS storage:Controller:rn managed object property"
    ::= { cucsStorageControllerEntry 3 }

cucsStorageControllerId OBJECT-TYPE
    SYNTAX       CucsStorageControllerId
    MAX-ACCESS   read-only
    STATUS       current
    DESCRIPTION
        "Cisco UCS storage:Controller:id managed object property"
    ::= { cucsStorageControllerEntry 4 }

cucsStorageControllerModel OBJECT-TYPE
    SYNTAX       SnmpAdminString
    MAX-ACCESS   read-only
    STATUS       current
    DESCRIPTION
        "Cisco UCS storage:Controller:model managed object property"
    ::= { cucsStorageControllerEntry 5 }

cucsStorageControllerOperState OBJECT-TYPE
    SYNTAX       CucsEquipmentOperability
    MAX-ACCESS   read-only
    STATUS       current
    DESCRIPTION
        "Cisco UCS storage:Controller:operState managed object property"
    ::= { cucsStorageControllerEntry 6 }

cucsStorageControllerOperability OBJECT-TYPE
    SYNTAX       CucsEquipmentOperability
    MAX-ACCESS   read-only
    STATUS       current
    DESCRIPTION
        "Cisco UCS storage:Controller:operability managed object property"
    ::= { cucsStorageControllerEntry 7 }

cucsStorageControllerPciAddr OBJECT-TYPE
    SYNTAX       SnmpAdminString
    MAX-ACCESS   read-only
    STATUS       current
    DESCRIPTION
        "Cisco UCS storage:Controller:pciAddr managed object property"
    ::= { cucsStorageControllerEntry 8 }

cucsStorageControllerPciSlot OBJECT-TYPE
    SYNTAX       SnmpAdminString
    MAX-ACCESS   read-only
    STATUS       current
    DESCRIPTION
        "Cisco UCS storage:Controller:pciSlot managed object property"
    ::= { cucsStorageControllerEntry 9 }

cucsStorageControllerPerf OBJECT-TYPE
    SYNTAX       CucsEquipmentSensorThresholdStatus
    MAX-ACCESS   read-only
    STATUS       current
    DESCRIPTION
        "Cisco UCS storage:Controller:perf managed object property"
    ::= { cucsStorageControllerEntry 10 }

cucsStorageControllerPower OBJECT-TYPE
    SYNTAX       CucsEquipmentPowerState
    MAX-ACCESS   read-only
    STATUS       current
    DESCRIPTION
        "Cisco UCS storage:Controller:power managed object property"
    ::= { cucsStorageControllerEntry 11 }

cucsStorageControllerPresence OBJECT-TYPE
    SYNTAX       CucsEquipmentPresence
    MAX-ACCESS   read-only
    STATUS       current
    DESCRIPTION
        "Cisco UCS storage:Controller:presence managed object property"
    ::= { cucsStorageControllerEntry 12 }

cucsStorageControllerRevision OBJECT-TYPE
    SYNTAX       SnmpAdminString
    MAX-ACCESS   read-only
    STATUS       current
    DESCRIPTION
        "Cisco UCS storage:Controller:revision managed object property"
    ::= { cucsStorageControllerEntry 13 }

cucsStorageControllerSerial OBJECT-TYPE
    SYNTAX       SnmpAdminString
    MAX-ACCESS   read-only
    STATUS       current
    DESCRIPTION
        "Cisco UCS storage:Controller:serial managed object property"
    ::= { cucsStorageControllerEntry 14 }

cucsStorageControllerThermal OBJECT-TYPE
    SYNTAX       CucsEquipmentSensorThresholdStatus
    MAX-ACCESS   read-only
    STATUS       current
    DESCRIPTION
        "Cisco UCS storage:Controller:thermal managed object property"
    ::= { cucsStorageControllerEntry 15 }

cucsStorageControllerType OBJECT-TYPE
    SYNTAX       CucsStorageControllerType
    MAX-ACCESS   read-only
    STATUS       current
    DESCRIPTION
        "Cisco UCS storage:Controller:type managed object property"
    ::= { cucsStorageControllerEntry 16 }

cucsStorageControllerVendor OBJECT-TYPE
    SYNTAX       SnmpAdminString
    MAX-ACCESS   read-only
    STATUS       current
    DESCRIPTION
        "Cisco UCS storage:Controller:vendor managed object property"
    ::= { cucsStorageControllerEntry 17 }

cucsStorageControllerVoltage OBJECT-TYPE
    SYNTAX       CucsEquipmentSensorThresholdStatus
    MAX-ACCESS   read-only
    STATUS       current
    DESCRIPTION
        "Cisco UCS storage:Controller:voltage managed object property"
    ::= { cucsStorageControllerEntry 18 }

cucsStorageControllerRaidSupport OBJECT-TYPE
    SYNTAX       SnmpAdminString
    MAX-ACCESS   read-only
    STATUS       current
    DESCRIPTION
        "Cisco UCS storage:Controller:raidSupport managed object property"
    ::= { cucsStorageControllerEntry 19 }

cucsStorageControllerFaultMonitoring OBJECT-TYPE
    SYNTAX       CucsStorageControllerFaultMonitoring
    MAX-ACCESS   read-only
    STATUS       current
    DESCRIPTION
        "Cisco UCS storage:Controller:faultMonitoring managed
        object property"
    ::= { cucsStorageControllerEntry 20 }

cucsStorageControllerHwRevision OBJECT-TYPE
    SYNTAX       SnmpAdminString
    MAX-ACCESS   read-only
    STATUS       current
    DESCRIPTION
        "Cisco UCS storage:Controller:hwRevision managed object property"
    ::= { cucsStorageControllerEntry 21 }

cucsStorageControllerDeviceRaidSupport OBJECT-TYPE
    SYNTAX       SnmpAdminString
    MAX-ACCESS   read-only
    STATUS       current
    DESCRIPTION
        "Cisco UCS storage:Controller:deviceRaidSupport
        managed object property"
    ::= { cucsStorageControllerEntry 23 }

cucsStorageControllerOperQualifierReason OBJECT-TYPE
    SYNTAX       SnmpAdminString
    MAX-ACCESS   read-only
    STATUS       current
    DESCRIPTION
        "Cisco UCS storage:Controller:operQualifierReason
        managed object property"
    ::= { cucsStorageControllerEntry 24 }

cucsStorageDomainEpTable OBJECT-TYPE
    SYNTAX           SEQUENCE OF CucsStorageDomainEpEntry
    MAX-ACCESS       not-accessible
    STATUS           current
    DESCRIPTION
        "Cisco UCS storage:DomainEp managed object table"
    ::= { cucsStorageObjects 17 }

cucsStorageDomainEpEntry OBJECT-TYPE
    SYNTAX           CucsStorageDomainEpEntry
    MAX-ACCESS       not-accessible
    STATUS           current
    DESCRIPTION
        "Entry for the cucsStorageDomainEpTable table."
    INDEX { cucsStorageDomainEpInstanceId }
    ::= { cucsStorageDomainEpTable 1 }

CucsStorageDomainEpEntry ::= SEQUENCE {
    cucsStorageDomainEpInstanceId                                    CucsManagedObjectId,
    cucsStorageDomainEpDn                                            CucsManagedObjectDn,
    cucsStorageDomainEpRn                                            SnmpAdminString
}

cucsStorageDomainEpInstanceId OBJECT-TYPE
    SYNTAX       CucsManagedObjectId
    MAX-ACCESS   not-accessible
    STATUS       current
    DESCRIPTION
        "Instance identifier of the managed object."
    ::= { cucsStorageDomainEpEntry 1 }

cucsStorageDomainEpDn OBJECT-TYPE
    SYNTAX       CucsManagedObjectDn
    MAX-ACCESS   read-only
    STATUS       current
    DESCRIPTION
        "Cisco UCS storage:DomainEp:dn managed object property"
    ::= { cucsStorageDomainEpEntry 2 }

cucsStorageDomainEpRn OBJECT-TYPE
    SYNTAX       SnmpAdminString
    MAX-ACCESS   read-only
    STATUS       current
    DESCRIPTION
        "Cisco UCS storage:DomainEp:rn managed object property"
    ::= { cucsStorageDomainEpEntry 3 }

cucsStorageDriveTable OBJECT-TYPE
    SYNTAX           SEQUENCE OF CucsStorageDriveEntry
    MAX-ACCESS       not-accessible
    STATUS           current
    DESCRIPTION
        "Cisco UCS storage:Drive managed object table"
    ::= { cucsStorageObjects 2 }

cucsStorageDriveEntry OBJECT-TYPE
    SYNTAX           CucsStorageDriveEntry
    MAX-ACCESS       not-accessible
    STATUS           current
    DESCRIPTION
        "Entry for the cucsStorageDriveTable table."
    INDEX { cucsStorageDriveInstanceId }
    ::= { cucsStorageDriveTable 1 }

CucsStorageDriveEntry ::= SEQUENCE {
    cucsStorageDriveInstanceId                                       CucsManagedObjectId,
    cucsStorageDriveDn                                               CucsManagedObjectDn,
    cucsStorageDriveRn                                               SnmpAdminString,
    cucsStorageDriveId                                               Gauge32,
    cucsStorageDriveModel                                            SnmpAdminString,
    cucsStorageDrivePciAddr                                          SnmpAdminString,
    cucsStorageDriveRevision                                         SnmpAdminString,
    cucsStorageDriveSerial                                           SnmpAdminString,
    cucsStorageDriveVendor                                           SnmpAdminString
}

cucsStorageDriveInstanceId OBJECT-TYPE
    SYNTAX       CucsManagedObjectId
    MAX-ACCESS   not-accessible
    STATUS       current
    DESCRIPTION
        "Instance identifier of the managed object."
    ::= { cucsStorageDriveEntry 1 }

cucsStorageDriveDn OBJECT-TYPE
    SYNTAX       CucsManagedObjectDn
    MAX-ACCESS   read-only
    STATUS       current
    DESCRIPTION
        "Cisco UCS storage:Drive:dn managed object property"
    ::= { cucsStorageDriveEntry 2 }

cucsStorageDriveRn OBJECT-TYPE
    SYNTAX       SnmpAdminString
    MAX-ACCESS   read-only
    STATUS       current
    DESCRIPTION
        "Cisco UCS storage:Drive:rn managed object property"
    ::= { cucsStorageDriveEntry 3 }

cucsStorageDriveId OBJECT-TYPE
    SYNTAX       Gauge32
    MAX-ACCESS   read-only
    STATUS       current
    DESCRIPTION
        "Cisco UCS storage:Drive:id managed object property"
    ::= { cucsStorageDriveEntry 4 }

cucsStorageDriveModel OBJECT-TYPE
    SYNTAX       SnmpAdminString
    MAX-ACCESS   read-only
    STATUS       current
    DESCRIPTION
        "Cisco UCS storage:Drive:model managed object property"
    ::= { cucsStorageDriveEntry 5 }

cucsStorageDrivePciAddr OBJECT-TYPE
    SYNTAX       SnmpAdminString
    MAX-ACCESS   read-only
    STATUS       current
    DESCRIPTION
        "Cisco UCS storage:Drive:pciAddr managed object property"
    ::= { cucsStorageDriveEntry 6 }

cucsStorageDriveRevision OBJECT-TYPE
    SYNTAX       SnmpAdminString
    MAX-ACCESS   read-only
    STATUS       current
    DESCRIPTION
        "Cisco UCS storage:Drive:revision managed object property"
    ::= { cucsStorageDriveEntry 7 }

cucsStorageDriveSerial OBJECT-TYPE
    SYNTAX       SnmpAdminString
    MAX-ACCESS   read-only
    STATUS       current
    DESCRIPTION
        "Cisco UCS storage:Drive:serial managed object property"
    ::= { cucsStorageDriveEntry 8 }

cucsStorageDriveVendor OBJECT-TYPE
    SYNTAX       SnmpAdminString
    MAX-ACCESS   read-only
    STATUS       current
    DESCRIPTION
        "Cisco UCS storage:Drive:vendor managed object property"
    ::= { cucsStorageDriveEntry 9 }

cucsStorageEnclosureTable OBJECT-TYPE
    SYNTAX           SEQUENCE OF CucsStorageEnclosureEntry
    MAX-ACCESS       not-accessible
    STATUS           current
    DESCRIPTION
        "Cisco UCS storage:Enclosure managed object table"
    ::= { cucsStorageObjects 12 }

cucsStorageEnclosureEntry OBJECT-TYPE
    SYNTAX           CucsStorageEnclosureEntry
    MAX-ACCESS       not-accessible
    STATUS           current
    DESCRIPTION
        "Entry for the cucsStorageEnclosureTable table."
    INDEX { cucsStorageEnclosureInstanceId }
    ::= { cucsStorageEnclosureTable 1 }

CucsStorageEnclosureEntry ::= SEQUENCE {
    cucsStorageEnclosureInstanceId                                   CucsManagedObjectId,
    cucsStorageEnclosureDn                                           CucsManagedObjectDn,
    cucsStorageEnclosureRn                                           SnmpAdminString,
    cucsStorageEnclosureId                                           Gauge32,
    cucsStorageEnclosureModel                                        SnmpAdminString,
    cucsStorageEnclosureNumSlots                                     Gauge32,
    cucsStorageEnclosureRevision                                     SnmpAdminString,
    cucsStorageEnclosureSerial                                       SnmpAdminString,
    cucsStorageEnclosureVendor                                       SnmpAdminString,
    cucsStorageEnclosureLc                                           CucsFsmLifecycle
}

cucsStorageEnclosureInstanceId OBJECT-TYPE
    SYNTAX       CucsManagedObjectId
    MAX-ACCESS   not-accessible
    STATUS       current
    DESCRIPTION
        "Instance identifier of the managed object."
    ::= { cucsStorageEnclosureEntry 1 }

cucsStorageEnclosureDn OBJECT-TYPE
    SYNTAX       CucsManagedObjectDn
    MAX-ACCESS   read-only
    STATUS       current
    DESCRIPTION
        "Cisco UCS storage:Enclosure:dn managed object property"
    ::= { cucsStorageEnclosureEntry 2 }

cucsStorageEnclosureRn OBJECT-TYPE
    SYNTAX       SnmpAdminString
    MAX-ACCESS   read-only
    STATUS       current
    DESCRIPTION
        "Cisco UCS storage:Enclosure:rn managed object property"
    ::= { cucsStorageEnclosureEntry 3 }

cucsStorageEnclosureId OBJECT-TYPE
    SYNTAX       Gauge32
    MAX-ACCESS   read-only
    STATUS       current
    DESCRIPTION
        "Cisco UCS storage:Enclosure:id managed object property"
    ::= { cucsStorageEnclosureEntry 4 }

cucsStorageEnclosureModel OBJECT-TYPE
    SYNTAX       SnmpAdminString
    MAX-ACCESS   read-only
    STATUS       current
    DESCRIPTION
        "Cisco UCS storage:Enclosure:model managed object property"
    ::= { cucsStorageEnclosureEntry 5 }

cucsStorageEnclosureNumSlots OBJECT-TYPE
    SYNTAX       Gauge32
    MAX-ACCESS   read-only
    STATUS       current
    DESCRIPTION
        "Cisco UCS storage:Enclosure:numSlots managed object property"
    ::= { cucsStorageEnclosureEntry 6 }

cucsStorageEnclosureRevision OBJECT-TYPE
    SYNTAX       SnmpAdminString
    MAX-ACCESS   read-only
    STATUS       current
    DESCRIPTION
        "Cisco UCS storage:Enclosure:revision managed object property"
    ::= { cucsStorageEnclosureEntry 7 }

cucsStorageEnclosureSerial OBJECT-TYPE
    SYNTAX       SnmpAdminString
    MAX-ACCESS   read-only
    STATUS       current
    DESCRIPTION
        "Cisco UCS storage:Enclosure:serial managed object property"
    ::= { cucsStorageEnclosureEntry 8 }

cucsStorageEnclosureVendor OBJECT-TYPE
    SYNTAX       SnmpAdminString
    MAX-ACCESS   read-only
    STATUS       current
    DESCRIPTION
        "Cisco UCS storage:Enclosure:vendor managed object property"
    ::= { cucsStorageEnclosureEntry 9 }

cucsStorageEnclosureLc OBJECT-TYPE
    SYNTAX       CucsFsmLifecycle
    MAX-ACCESS   read-only
    STATUS       current
    DESCRIPTION
        "Cisco UCS storage:Enclosure:lc managed object property"
    ::= { cucsStorageEnclosureEntry 10 }

cucsStorageEpUserTable OBJECT-TYPE
    SYNTAX           SEQUENCE OF CucsStorageEpUserEntry
    MAX-ACCESS       not-accessible
    STATUS           current
    DESCRIPTION
        "Cisco UCS storage:EpUser managed object table"
    ::= { cucsStorageObjects 18 }

cucsStorageEpUserEntry OBJECT-TYPE
    SYNTAX           CucsStorageEpUserEntry
    MAX-ACCESS       not-accessible
    STATUS           current
    DESCRIPTION
        "Entry for the cucsStorageEpUserTable table."
    INDEX { cucsStorageEpUserInstanceId }
    ::= { cucsStorageEpUserTable 1 }

CucsStorageEpUserEntry ::= SEQUENCE {
    cucsStorageEpUserInstanceId                                      CucsManagedObjectId,
    cucsStorageEpUserDn                                              CucsManagedObjectDn,
    cucsStorageEpUserRn                                              SnmpAdminString,
    cucsStorageEpUserConfigState                                     CucsAaaConfigState,
    cucsStorageEpUserConfigStatusMessage                             SnmpAdminString,
    cucsStorageEpUserDescr                                           SnmpAdminString,
    cucsStorageEpUserDomain                                          SnmpAdminString,
    cucsStorageEpUserName                                            SnmpAdminString,
    cucsStorageEpUserPriv                                            CucsStorageEpAccess,
    cucsStorageEpUserPwd                                             SnmpAdminString,
    cucsStorageEpUserPwdSet                                          TruthValue
}

cucsStorageEpUserInstanceId OBJECT-TYPE
    SYNTAX       CucsManagedObjectId
    MAX-ACCESS   not-accessible
    STATUS       current
    DESCRIPTION
        "Instance identifier of the managed object."
    ::= { cucsStorageEpUserEntry 1 }

cucsStorageEpUserDn OBJECT-TYPE
    SYNTAX       CucsManagedObjectDn
    MAX-ACCESS   read-only
    STATUS       current
    DESCRIPTION
        "Cisco UCS storage:EpUser:dn managed object property"
    ::= { cucsStorageEpUserEntry 2 }

cucsStorageEpUserRn OBJECT-TYPE
    SYNTAX       SnmpAdminString
    MAX-ACCESS   read-only
    STATUS       current
    DESCRIPTION
        "Cisco UCS storage:EpUser:rn managed object property"
    ::= { cucsStorageEpUserEntry 3 }

cucsStorageEpUserConfigState OBJECT-TYPE
    SYNTAX       CucsAaaConfigState
    MAX-ACCESS   read-only
    STATUS       current
    DESCRIPTION
        "Cisco UCS storage:EpUser:configState managed object property"
    ::= { cucsStorageEpUserEntry 4 }

cucsStorageEpUserConfigStatusMessage OBJECT-TYPE
    SYNTAX       SnmpAdminString
    MAX-ACCESS   read-only
    STATUS       current
    DESCRIPTION
        "Cisco UCS storage:EpUser:configStatusMessage managed
        object property"
    ::= { cucsStorageEpUserEntry 5 }

cucsStorageEpUserDescr OBJECT-TYPE
    SYNTAX       SnmpAdminString
    MAX-ACCESS   read-only
    STATUS       current
    DESCRIPTION
        "Cisco UCS storage:EpUser:descr managed object property"
    ::= { cucsStorageEpUserEntry 6 }

cucsStorageEpUserDomain OBJECT-TYPE
    SYNTAX       SnmpAdminString
    MAX-ACCESS   read-only
    STATUS       current
    DESCRIPTION
        "Cisco UCS storage:EpUser:domain managed object property"
    ::= { cucsStorageEpUserEntry 7 }

cucsStorageEpUserName OBJECT-TYPE
    SYNTAX       SnmpAdminString
    MAX-ACCESS   read-only
    STATUS       current
    DESCRIPTION
        "Cisco UCS storage:EpUser:name managed object property"
    ::= { cucsStorageEpUserEntry 8 }

cucsStorageEpUserPriv OBJECT-TYPE
    SYNTAX       CucsStorageEpAccess
    MAX-ACCESS   read-only
    STATUS       current
    DESCRIPTION
        "Cisco UCS storage:EpUser:priv managed object property"
    ::= { cucsStorageEpUserEntry 9 }

cucsStorageEpUserPwd OBJECT-TYPE
    SYNTAX       SnmpAdminString
    MAX-ACCESS   read-only
    STATUS       current
    DESCRIPTION
        "Cisco UCS storage:EpUser:pwd managed object property"
    ::= { cucsStorageEpUserEntry 10 }

cucsStorageEpUserPwdSet OBJECT-TYPE
    SYNTAX       TruthValue
    MAX-ACCESS   read-only
    STATUS       current
    DESCRIPTION
        "Cisco UCS storage:EpUser:pwdSet managed object property"
    ::= { cucsStorageEpUserEntry 11 }

cucsStorageEtherIfTable OBJECT-TYPE
    SYNTAX           SEQUENCE OF CucsStorageEtherIfEntry
    MAX-ACCESS       not-accessible
    STATUS           current
    DESCRIPTION
        "Cisco UCS storage:EtherIf managed object table"
    ::= { cucsStorageObjects 19 }

cucsStorageEtherIfEntry OBJECT-TYPE
    SYNTAX           CucsStorageEtherIfEntry
    MAX-ACCESS       not-accessible
    STATUS           current
    DESCRIPTION
        "Entry for the cucsStorageEtherIfTable table."
    INDEX { cucsStorageEtherIfInstanceId }
    ::= { cucsStorageEtherIfTable 1 }

CucsStorageEtherIfEntry ::= SEQUENCE {
    cucsStorageEtherIfInstanceId                                     CucsManagedObjectId,
    cucsStorageEtherIfDn                                             CucsManagedObjectDn,
    cucsStorageEtherIfRn                                             SnmpAdminString,
    cucsStorageEtherIfName                                           SnmpAdminString,
    cucsStorageEtherIfVlanType                                       CucsStorageEtherIfVlanType
}

cucsStorageEtherIfInstanceId OBJECT-TYPE
    SYNTAX       CucsManagedObjectId
    MAX-ACCESS   not-accessible
    STATUS       current
    DESCRIPTION
        "Instance identifier of the managed object."
    ::= { cucsStorageEtherIfEntry 1 }

cucsStorageEtherIfDn OBJECT-TYPE
    SYNTAX       CucsManagedObjectDn
    MAX-ACCESS   read-only
    STATUS       current
    DESCRIPTION
        "Cisco UCS storage:EtherIf:dn managed object property"
    ::= { cucsStorageEtherIfEntry 2 }

cucsStorageEtherIfRn OBJECT-TYPE
    SYNTAX       SnmpAdminString
    MAX-ACCESS   read-only
    STATUS       current
    DESCRIPTION
        "Cisco UCS storage:EtherIf:rn managed object property"
    ::= { cucsStorageEtherIfEntry 3 }

cucsStorageEtherIfName OBJECT-TYPE
    SYNTAX       SnmpAdminString
    MAX-ACCESS   read-only
    STATUS       current
    DESCRIPTION
        "Cisco UCS storage:EtherIf:name managed object property"
    ::= { cucsStorageEtherIfEntry 4 }

cucsStorageEtherIfVlanType OBJECT-TYPE
    SYNTAX       CucsStorageEtherIfVlanType
    MAX-ACCESS   read-only
    STATUS       current
    DESCRIPTION
        "Cisco UCS storage:EtherIf:vlanType managed object property"
    ::= { cucsStorageEtherIfEntry 5 }

cucsStorageFcIfTable OBJECT-TYPE
    SYNTAX           SEQUENCE OF CucsStorageFcIfEntry
    MAX-ACCESS       not-accessible
    STATUS           current
    DESCRIPTION
        "Cisco UCS storage:FcIf managed object table"
    ::= { cucsStorageObjects 20 }

cucsStorageFcIfEntry OBJECT-TYPE
    SYNTAX           CucsStorageFcIfEntry
    MAX-ACCESS       not-accessible
    STATUS           current
    DESCRIPTION
        "Entry for the cucsStorageFcIfTable table."
    INDEX { cucsStorageFcIfInstanceId }
    ::= { cucsStorageFcIfTable 1 }

CucsStorageFcIfEntry ::= SEQUENCE {
    cucsStorageFcIfInstanceId                                        CucsManagedObjectId,
    cucsStorageFcIfDn                                                CucsManagedObjectDn,
    cucsStorageFcIfRn                                                SnmpAdminString,
    cucsStorageFcIfName                                              SnmpAdminString
}

cucsStorageFcIfInstanceId OBJECT-TYPE
    SYNTAX       CucsManagedObjectId
    MAX-ACCESS   not-accessible
    STATUS       current
    DESCRIPTION
        "Instance identifier of the managed object."
    ::= { cucsStorageFcIfEntry 1 }

cucsStorageFcIfDn OBJECT-TYPE
    SYNTAX       CucsManagedObjectDn
    MAX-ACCESS   read-only
    STATUS       current
    DESCRIPTION
        "Cisco UCS storage:FcIf:dn managed object property"
    ::= { cucsStorageFcIfEntry 2 }

cucsStorageFcIfRn OBJECT-TYPE
    SYNTAX       SnmpAdminString
    MAX-ACCESS   read-only
    STATUS       current
    DESCRIPTION
        "Cisco UCS storage:FcIf:rn managed object property"
    ::= { cucsStorageFcIfEntry 3 }

cucsStorageFcIfName OBJECT-TYPE
    SYNTAX       SnmpAdminString
    MAX-ACCESS   read-only
    STATUS       current
    DESCRIPTION
        "Cisco UCS storage:FcIf:name managed object property"
    ::= { cucsStorageFcIfEntry 4 }

cucsStorageFcTargetEpTable OBJECT-TYPE
    SYNTAX           SEQUENCE OF CucsStorageFcTargetEpEntry
    MAX-ACCESS       not-accessible
    STATUS           current
    DESCRIPTION
        "Cisco UCS storage:FcTargetEp managed object table"
    ::= { cucsStorageObjects 21 }

cucsStorageFcTargetEpEntry OBJECT-TYPE
    SYNTAX           CucsStorageFcTargetEpEntry
    MAX-ACCESS       not-accessible
    STATUS           current
    DESCRIPTION
        "Entry for the cucsStorageFcTargetEpTable table."
    INDEX { cucsStorageFcTargetEpInstanceId }
    ::= { cucsStorageFcTargetEpTable 1 }

CucsStorageFcTargetEpEntry ::= SEQUENCE {
    cucsStorageFcTargetEpInstanceId                                  CucsManagedObjectId,
    cucsStorageFcTargetEpDn                                          CucsManagedObjectDn,
    cucsStorageFcTargetEpRn                                          SnmpAdminString,
    cucsStorageFcTargetEpDescr                                       SnmpAdminString,
    cucsStorageFcTargetEpPath                                        CucsStorageTargetPath,
    cucsStorageFcTargetEpTargetwwpn                                  SnmpAdminString
}

cucsStorageFcTargetEpInstanceId OBJECT-TYPE
    SYNTAX       CucsManagedObjectId
    MAX-ACCESS   not-accessible
    STATUS       current
    DESCRIPTION
        "Instance identifier of the managed object."
    ::= { cucsStorageFcTargetEpEntry 1 }

cucsStorageFcTargetEpDn OBJECT-TYPE
    SYNTAX       CucsManagedObjectDn
    MAX-ACCESS   read-only
    STATUS       current
    DESCRIPTION
        "Cisco UCS storage:FcTargetEp:dn managed object property"
    ::= { cucsStorageFcTargetEpEntry 2 }

cucsStorageFcTargetEpRn OBJECT-TYPE
    SYNTAX       SnmpAdminString
    MAX-ACCESS   read-only
    STATUS       current
    DESCRIPTION
        "Cisco UCS storage:FcTargetEp:rn managed object property"
    ::= { cucsStorageFcTargetEpEntry 3 }

cucsStorageFcTargetEpDescr OBJECT-TYPE
    SYNTAX       SnmpAdminString
    MAX-ACCESS   read-only
    STATUS       current
    DESCRIPTION
        "Cisco UCS storage:FcTargetEp:descr managed object property"
    ::= { cucsStorageFcTargetEpEntry 4 }

cucsStorageFcTargetEpPath OBJECT-TYPE
    SYNTAX       CucsStorageTargetPath
    MAX-ACCESS   read-only
    STATUS       current
    DESCRIPTION
        "Cisco UCS storage:FcTargetEp:path managed object property"
    ::= { cucsStorageFcTargetEpEntry 5 }

cucsStorageFcTargetEpTargetwwpn OBJECT-TYPE
    SYNTAX       SnmpAdminString
    MAX-ACCESS   read-only
    STATUS       current
    DESCRIPTION
        "Cisco UCS storage:FcTargetEp:targetwwpn managed object property"
    ::= { cucsStorageFcTargetEpEntry 6 }

cucsStorageFcTargetIfTable OBJECT-TYPE
    SYNTAX           SEQUENCE OF CucsStorageFcTargetIfEntry
    MAX-ACCESS       not-accessible
    STATUS           current
    DESCRIPTION
        "Cisco UCS storage:FcTargetIf managed object table"
    ::= { cucsStorageObjects 22 }

cucsStorageFcTargetIfEntry OBJECT-TYPE
    SYNTAX           CucsStorageFcTargetIfEntry
    MAX-ACCESS       not-accessible
    STATUS           current
    DESCRIPTION
        "Entry for the cucsStorageFcTargetIfTable table."
    INDEX { cucsStorageFcTargetIfInstanceId }
    ::= { cucsStorageFcTargetIfTable 1 }

CucsStorageFcTargetIfEntry ::= SEQUENCE {
    cucsStorageFcTargetIfInstanceId                                  CucsManagedObjectId,
    cucsStorageFcTargetIfDn                                          CucsManagedObjectDn,
    cucsStorageFcTargetIfRn                                          SnmpAdminString,
    cucsStorageFcTargetIfId                                          Unsigned64,
    cucsStorageFcTargetIfProt                                        CucsStorageProtocol
}

cucsStorageFcTargetIfInstanceId OBJECT-TYPE
    SYNTAX       CucsManagedObjectId
    MAX-ACCESS   not-accessible
    STATUS       current
    DESCRIPTION
        "Instance identifier of the managed object."
    ::= { cucsStorageFcTargetIfEntry 1 }

cucsStorageFcTargetIfDn OBJECT-TYPE
    SYNTAX       CucsManagedObjectDn
    MAX-ACCESS   read-only
    STATUS       current
    DESCRIPTION
        "Cisco UCS storage:FcTargetIf:dn managed object property"
    ::= { cucsStorageFcTargetIfEntry 2 }

cucsStorageFcTargetIfRn OBJECT-TYPE
    SYNTAX       SnmpAdminString
    MAX-ACCESS   read-only
    STATUS       current
    DESCRIPTION
        "Cisco UCS storage:FcTargetIf:rn managed object property"
    ::= { cucsStorageFcTargetIfEntry 3 }

cucsStorageFcTargetIfId OBJECT-TYPE
    SYNTAX       Unsigned64
    MAX-ACCESS   read-only
    STATUS       current
    DESCRIPTION
        "Cisco UCS storage:FcTargetIf:id managed object property"
    ::= { cucsStorageFcTargetIfEntry 4 }

cucsStorageFcTargetIfProt OBJECT-TYPE
    SYNTAX       CucsStorageProtocol
    MAX-ACCESS   read-only
    STATUS       current
    DESCRIPTION
        "Cisco UCS storage:FcTargetIf:prot managed object property"
    ::= { cucsStorageFcTargetIfEntry 5 }

cucsStorageIScsiTargetIfTable OBJECT-TYPE
    SYNTAX           SEQUENCE OF CucsStorageIScsiTargetIfEntry
    MAX-ACCESS       not-accessible
    STATUS           current
    DESCRIPTION
        "Cisco UCS storage:IScsiTargetIf managed object table"
    ::= { cucsStorageObjects 23 }

cucsStorageIScsiTargetIfEntry OBJECT-TYPE
    SYNTAX           CucsStorageIScsiTargetIfEntry
    MAX-ACCESS       not-accessible
    STATUS           current
    DESCRIPTION
        "Entry for the cucsStorageIScsiTargetIfTable table."
    INDEX { cucsStorageIScsiTargetIfInstanceId }
    ::= { cucsStorageIScsiTargetIfTable 1 }

CucsStorageIScsiTargetIfEntry ::= SEQUENCE {
    cucsStorageIScsiTargetIfInstanceId                               CucsManagedObjectId,
    cucsStorageIScsiTargetIfDn                                       CucsManagedObjectDn,
    cucsStorageIScsiTargetIfRn                                       SnmpAdminString,
    cucsStorageIScsiTargetIfName                                     SnmpAdminString,
    cucsStorageIScsiTargetIfProt                                     CucsStorageProtocol
}

cucsStorageIScsiTargetIfInstanceId OBJECT-TYPE
    SYNTAX       CucsManagedObjectId
    MAX-ACCESS   not-accessible
    STATUS       current
    DESCRIPTION
        "Instance identifier of the managed object."
    ::= { cucsStorageIScsiTargetIfEntry 1 }

cucsStorageIScsiTargetIfDn OBJECT-TYPE
    SYNTAX       CucsManagedObjectDn
    MAX-ACCESS   read-only
    STATUS       current
    DESCRIPTION
        "Cisco UCS storage:IScsiTargetIf:dn managed object property"
    ::= { cucsStorageIScsiTargetIfEntry 2 }

cucsStorageIScsiTargetIfRn OBJECT-TYPE
    SYNTAX       SnmpAdminString
    MAX-ACCESS   read-only
    STATUS       current
    DESCRIPTION
        "Cisco UCS storage:IScsiTargetIf:rn managed object property"
    ::= { cucsStorageIScsiTargetIfEntry 3 }

cucsStorageIScsiTargetIfName OBJECT-TYPE
    SYNTAX       SnmpAdminString
    MAX-ACCESS   read-only
    STATUS       current
    DESCRIPTION
        "Cisco UCS storage:IScsiTargetIf:name managed object property"
    ::= { cucsStorageIScsiTargetIfEntry 4 }

cucsStorageIScsiTargetIfProt OBJECT-TYPE
    SYNTAX       CucsStorageProtocol
    MAX-ACCESS   read-only
    STATUS       current
    DESCRIPTION
        "Cisco UCS storage:IScsiTargetIf:prot managed object property"
    ::= { cucsStorageIScsiTargetIfEntry 5 }

cucsStorageIniGroupTable OBJECT-TYPE
    SYNTAX           SEQUENCE OF CucsStorageIniGroupEntry
    MAX-ACCESS       not-accessible
    STATUS           current
    DESCRIPTION
        "Cisco UCS storage:IniGroup managed object table"
    ::= { cucsStorageObjects 24 }

cucsStorageIniGroupEntry OBJECT-TYPE
    SYNTAX           CucsStorageIniGroupEntry
    MAX-ACCESS       not-accessible
    STATUS           current
    DESCRIPTION
        "Entry for the cucsStorageIniGroupTable table."
    INDEX { cucsStorageIniGroupInstanceId }
    ::= { cucsStorageIniGroupTable 1 }

CucsStorageIniGroupEntry ::= SEQUENCE {
    cucsStorageIniGroupInstanceId                                    CucsManagedObjectId,
    cucsStorageIniGroupDn                                            CucsManagedObjectDn,
    cucsStorageIniGroupRn                                            SnmpAdminString,
    cucsStorageIniGroupDescr                                         SnmpAdminString,
    cucsStorageIniGroupGroupPolicyName                               SnmpAdminString,
    cucsStorageIniGroupIntId                                         SnmpAdminString,
    cucsStorageIniGroupName                                          SnmpAdminString,
    cucsStorageIniGroupOperProtocol                                  CucsStorageIniGroupOperProtocol,
    cucsStorageIniGroupOwner                                         CucsStorageIniGroupOwner,
    cucsStorageIniGroupPolicyLevel                                   Gauge32,
    cucsStorageIniGroupPolicyName                                    SnmpAdminString,
    cucsStorageIniGroupPolicyOwner                                   CucsPolicyPolicyOwner,
    cucsStorageIniGroupProtocol                                      CucsStorageIniGroupProtocol,
    cucsStorageIniGroupRmtDiskCfgName                                SnmpAdminString,
    cucsStorageIniGroupOperState                                     CucsStorageOperState
}

cucsStorageIniGroupInstanceId OBJECT-TYPE
    SYNTAX       CucsManagedObjectId
    MAX-ACCESS   not-accessible
    STATUS       current
    DESCRIPTION
        "Instance identifier of the managed object."
    ::= { cucsStorageIniGroupEntry 1 }

cucsStorageIniGroupDn OBJECT-TYPE
    SYNTAX       CucsManagedObjectDn
    MAX-ACCESS   read-only
    STATUS       current
    DESCRIPTION
        "Cisco UCS storage:IniGroup:dn managed object property"
    ::= { cucsStorageIniGroupEntry 2 }

cucsStorageIniGroupRn OBJECT-TYPE
    SYNTAX       SnmpAdminString
    MAX-ACCESS   read-only
    STATUS       current
    DESCRIPTION
        "Cisco UCS storage:IniGroup:rn managed object property"
    ::= { cucsStorageIniGroupEntry 3 }

cucsStorageIniGroupDescr OBJECT-TYPE
    SYNTAX       SnmpAdminString
    MAX-ACCESS   read-only
    STATUS       current
    DESCRIPTION
        "Cisco UCS storage:IniGroup:descr managed object property"
    ::= { cucsStorageIniGroupEntry 4 }

cucsStorageIniGroupGroupPolicyName OBJECT-TYPE
    SYNTAX       SnmpAdminString
    MAX-ACCESS   read-only
    STATUS       current
    DESCRIPTION
        "Cisco UCS storage:IniGroup:groupPolicyName managed
        object property"
    ::= { cucsStorageIniGroupEntry 5 }

cucsStorageIniGroupIntId OBJECT-TYPE
    SYNTAX       SnmpAdminString
    MAX-ACCESS   read-only
    STATUS       current
    DESCRIPTION
        "Cisco UCS storage:IniGroup:intId managed object property"
    ::= { cucsStorageIniGroupEntry 6 }

cucsStorageIniGroupName OBJECT-TYPE
    SYNTAX       SnmpAdminString
    MAX-ACCESS   read-only
    STATUS       current
    DESCRIPTION
        "Cisco UCS storage:IniGroup:name managed object property"
    ::= { cucsStorageIniGroupEntry 7 }

cucsStorageIniGroupOperProtocol OBJECT-TYPE
    SYNTAX       CucsStorageIniGroupOperProtocol
    MAX-ACCESS   read-only
    STATUS       current
    DESCRIPTION
        "Cisco UCS storage:IniGroup:operProtocol managed object property"
    ::= { cucsStorageIniGroupEntry 8 }

cucsStorageIniGroupOwner OBJECT-TYPE
    SYNTAX       CucsStorageIniGroupOwner
    MAX-ACCESS   read-only
    STATUS       current
    DESCRIPTION
        "Cisco UCS storage:IniGroup:owner managed object property"
    ::= { cucsStorageIniGroupEntry 9 }

cucsStorageIniGroupPolicyLevel OBJECT-TYPE
    SYNTAX       Gauge32
    MAX-ACCESS   read-only
    STATUS       current
    DESCRIPTION
        "Cisco UCS storage:IniGroup:policyLevel managed object property"
    ::= { cucsStorageIniGroupEntry 10 }

cucsStorageIniGroupPolicyName OBJECT-TYPE
    SYNTAX       SnmpAdminString
    MAX-ACCESS   read-only
    STATUS       current
    DESCRIPTION
        "Cisco UCS storage:IniGroup:policyName managed object property"
    ::= { cucsStorageIniGroupEntry 11 }

cucsStorageIniGroupPolicyOwner OBJECT-TYPE
    SYNTAX       CucsPolicyPolicyOwner
    MAX-ACCESS   read-only
    STATUS       current
    DESCRIPTION
        "Cisco UCS storage:IniGroup:policyOwner managed object property"
    ::= { cucsStorageIniGroupEntry 12 }

cucsStorageIniGroupProtocol OBJECT-TYPE
    SYNTAX       CucsStorageIniGroupProtocol
    MAX-ACCESS   read-only
    STATUS       current
    DESCRIPTION
        "Cisco UCS storage:IniGroup:protocol managed object property"
    ::= { cucsStorageIniGroupEntry 13 }

cucsStorageIniGroupRmtDiskCfgName OBJECT-TYPE
    SYNTAX       SnmpAdminString
    MAX-ACCESS   read-only
    STATUS       current
    DESCRIPTION
        "Cisco UCS storage:IniGroup:rmtDiskCfgName managed
        object property"
    ::= { cucsStorageIniGroupEntry 14 }

cucsStorageIniGroupOperState OBJECT-TYPE
    SYNTAX       CucsStorageOperState
    MAX-ACCESS   read-only
    STATUS       current
    DESCRIPTION
        "Cisco UCS storage:IniGroup:operState managed object property"
    ::= { cucsStorageIniGroupEntry 15 }

cucsStorageInitiatorTable OBJECT-TYPE
    SYNTAX           SEQUENCE OF CucsStorageInitiatorEntry
    MAX-ACCESS       not-accessible
    STATUS           current
    DESCRIPTION
        "Cisco UCS storage:Initiator managed object table"
    ::= { cucsStorageObjects 25 }

cucsStorageInitiatorEntry OBJECT-TYPE
    SYNTAX           CucsStorageInitiatorEntry
    MAX-ACCESS       not-accessible
    STATUS           current
    DESCRIPTION
        "Entry for the cucsStorageInitiatorTable table."
    INDEX { cucsStorageInitiatorInstanceId }
    ::= { cucsStorageInitiatorTable 1 }

CucsStorageInitiatorEntry ::= SEQUENCE {
    cucsStorageInitiatorInstanceId                                   CucsManagedObjectId,
    cucsStorageInitiatorDn                                           CucsManagedObjectDn,
    cucsStorageInitiatorRn                                           SnmpAdminString,
    cucsStorageInitiatorDescr                                        SnmpAdminString,
    cucsStorageInitiatorIntId                                        SnmpAdminString,
    cucsStorageInitiatorName                                         SnmpAdminString,
    cucsStorageInitiatorOperState                                    CucsStorageOperState,
    cucsStorageInitiatorPolicyLevel                                  Gauge32,
    cucsStorageInitiatorPolicyOwner                                  CucsPolicyPolicyOwner,
    cucsStorageInitiatorDuplicateTarget                              SnmpAdminString
}

cucsStorageInitiatorInstanceId OBJECT-TYPE
    SYNTAX       CucsManagedObjectId
    MAX-ACCESS   not-accessible
    STATUS       current
    DESCRIPTION
        "Instance identifier of the managed object."
    ::= { cucsStorageInitiatorEntry 1 }

cucsStorageInitiatorDn OBJECT-TYPE
    SYNTAX       CucsManagedObjectDn
    MAX-ACCESS   read-only
    STATUS       current
    DESCRIPTION
        "Cisco UCS storage:Initiator:dn managed object property"
    ::= { cucsStorageInitiatorEntry 2 }

cucsStorageInitiatorRn OBJECT-TYPE
    SYNTAX       SnmpAdminString
    MAX-ACCESS   read-only
    STATUS       current
    DESCRIPTION
        "Cisco UCS storage:Initiator:rn managed object property"
    ::= { cucsStorageInitiatorEntry 3 }

cucsStorageInitiatorDescr OBJECT-TYPE
    SYNTAX       SnmpAdminString
    MAX-ACCESS   read-only
    STATUS       current
    DESCRIPTION
        "Cisco UCS storage:Initiator:descr managed object property"
    ::= { cucsStorageInitiatorEntry 4 }

cucsStorageInitiatorIntId OBJECT-TYPE
    SYNTAX       SnmpAdminString
    MAX-ACCESS   read-only
    STATUS       current
    DESCRIPTION
        "Cisco UCS storage:Initiator:intId managed object property"
    ::= { cucsStorageInitiatorEntry 5 }

cucsStorageInitiatorName OBJECT-TYPE
    SYNTAX       SnmpAdminString
    MAX-ACCESS   read-only
    STATUS       current
    DESCRIPTION
        "Cisco UCS storage:Initiator:name managed object property"
    ::= { cucsStorageInitiatorEntry 6 }

cucsStorageInitiatorOperState OBJECT-TYPE
    SYNTAX       CucsStorageOperState
    MAX-ACCESS   read-only
    STATUS       current
    DESCRIPTION
        "Cisco UCS storage:Initiator:operState managed object property"
    ::= { cucsStorageInitiatorEntry 7 }

cucsStorageInitiatorPolicyLevel OBJECT-TYPE
    SYNTAX       Gauge32
    MAX-ACCESS   read-only
    STATUS       current
    DESCRIPTION
        "Cisco UCS storage:Initiator:policyLevel managed object property"
    ::= { cucsStorageInitiatorEntry 8 }

cucsStorageInitiatorPolicyOwner OBJECT-TYPE
    SYNTAX       CucsPolicyPolicyOwner
    MAX-ACCESS   read-only
    STATUS       current
    DESCRIPTION
        "Cisco UCS storage:Initiator:policyOwner managed object property"
    ::= { cucsStorageInitiatorEntry 9 }

cucsStorageInitiatorDuplicateTarget OBJECT-TYPE
    SYNTAX       SnmpAdminString
    MAX-ACCESS   read-only
    STATUS       current
    DESCRIPTION
        "Cisco UCS storage:Initiator:duplicateTarget managed
        object property"
    ::= { cucsStorageInitiatorEntry 10 }

cucsStorageItemTable OBJECT-TYPE
    SYNTAX           SEQUENCE OF CucsStorageItemEntry
    MAX-ACCESS       not-accessible
    STATUS           current
    DESCRIPTION
        "Cisco UCS storage:Item managed object table"
    ::= { cucsStorageObjects 3 }

cucsStorageItemEntry OBJECT-TYPE
    SYNTAX           CucsStorageItemEntry
    MAX-ACCESS       not-accessible
    STATUS           current
    DESCRIPTION
        "Entry for the cucsStorageItemTable table."
    INDEX { cucsStorageItemInstanceId }
    ::= { cucsStorageItemTable 1 }

CucsStorageItemEntry ::= SEQUENCE {
    cucsStorageItemInstanceId                                        CucsManagedObjectId,
    cucsStorageItemDn                                                CucsManagedObjectDn,
    cucsStorageItemRn                                                SnmpAdminString,
    cucsStorageItemName                                              SnmpAdminString,
    cucsStorageItemSize                                              Unsigned64,
    cucsStorageItemUsed                                              Gauge32,
    cucsStorageItemOperState                                         CucsStorageFileSystemStatus
}

cucsStorageItemInstanceId OBJECT-TYPE
    SYNTAX       CucsManagedObjectId
    MAX-ACCESS   not-accessible
    STATUS       current
    DESCRIPTION
        "Instance identifier of the managed object."
    ::= { cucsStorageItemEntry 1 }

cucsStorageItemDn OBJECT-TYPE
    SYNTAX       CucsManagedObjectDn
    MAX-ACCESS   read-only
    STATUS       current
    DESCRIPTION
        "Cisco UCS storage:Item:dn managed object property"
    ::= { cucsStorageItemEntry 2 }

cucsStorageItemRn OBJECT-TYPE
    SYNTAX       SnmpAdminString
    MAX-ACCESS   read-only
    STATUS       current
    DESCRIPTION
        "Cisco UCS storage:Item:rn managed object property"
    ::= { cucsStorageItemEntry 3 }

cucsStorageItemName OBJECT-TYPE
    SYNTAX       SnmpAdminString
    MAX-ACCESS   read-only
    STATUS       current
    DESCRIPTION
        "Cisco UCS storage:Item:name managed object property"
    ::= { cucsStorageItemEntry 4 }

cucsStorageItemSize OBJECT-TYPE
    SYNTAX       Unsigned64
    MAX-ACCESS   read-only
    STATUS       current
    DESCRIPTION
        "Cisco UCS storage:Item:size managed object property"
    ::= { cucsStorageItemEntry 5 }

cucsStorageItemUsed OBJECT-TYPE
    SYNTAX       Gauge32
    MAX-ACCESS   read-only
    STATUS       current
    DESCRIPTION
        "Cisco UCS storage:Item:used managed object property"
    ::= { cucsStorageItemEntry 6 }

cucsStorageItemOperState OBJECT-TYPE
    SYNTAX       CucsStorageFileSystemStatus
    MAX-ACCESS   read-only
    STATUS       current
    DESCRIPTION
        "Cisco UCS storage:Item:operState managed object property"
    ::= { cucsStorageItemEntry 7 }

cucsStorageLocalDiskTable OBJECT-TYPE
    SYNTAX           SEQUENCE OF CucsStorageLocalDiskEntry
    MAX-ACCESS       not-accessible
    STATUS           current
    DESCRIPTION
        "Cisco UCS storage:LocalDisk managed object table"
    ::= { cucsStorageObjects 4 }

cucsStorageLocalDiskEntry OBJECT-TYPE
    SYNTAX           CucsStorageLocalDiskEntry
    MAX-ACCESS       not-accessible
    STATUS           current
    DESCRIPTION
        "Entry for the cucsStorageLocalDiskTable table."
    INDEX { cucsStorageLocalDiskInstanceId }
    ::= { cucsStorageLocalDiskTable 1 }

CucsStorageLocalDiskEntry ::= SEQUENCE {
    cucsStorageLocalDiskInstanceId                                   CucsManagedObjectId,
    cucsStorageLocalDiskDn                                           CucsManagedObjectDn,
    cucsStorageLocalDiskRn                                           SnmpAdminString,
    cucsStorageLocalDiskBlockSize                                    Gauge32,
    cucsStorageLocalDiskConnectionProtocol                           CucsStorageConnectionProtocol,
    cucsStorageLocalDiskId                                           Gauge32,
    cucsStorageLocalDiskModel                                        SnmpAdminString,
    cucsStorageLocalDiskNumberOfBlocks                               Unsigned64,
    cucsStorageLocalDiskOperability                                  CucsEquipmentOperability,
    cucsStorageLocalDiskPresence                                     CucsEquipmentPresence,
    cucsStorageLocalDiskRevision                                     SnmpAdminString,
    cucsStorageLocalDiskSerial                                       SnmpAdminString,
    cucsStorageLocalDiskSize                                         Unsigned64,
    cucsStorageLocalDiskVendor                                       SnmpAdminString,
    cucsStorageLocalDiskLc                                           CucsFsmLifecycle,
    cucsStorageLocalDiskOperQualifierReason                          SnmpAdminString
}

cucsStorageLocalDiskInstanceId OBJECT-TYPE
    SYNTAX       CucsManagedObjectId
    MAX-ACCESS   not-accessible
    STATUS       current
    DESCRIPTION
        "Instance identifier of the managed object."
    ::= { cucsStorageLocalDiskEntry 1 }

cucsStorageLocalDiskDn OBJECT-TYPE
    SYNTAX       CucsManagedObjectDn
    MAX-ACCESS   read-only
    STATUS       current
    DESCRIPTION
        "Cisco UCS storage:LocalDisk:dn managed object property"
    ::= { cucsStorageLocalDiskEntry 2 }

cucsStorageLocalDiskRn OBJECT-TYPE
    SYNTAX       SnmpAdminString
    MAX-ACCESS   read-only
    STATUS       current
    DESCRIPTION
        "Cisco UCS storage:LocalDisk:rn managed object property"
    ::= { cucsStorageLocalDiskEntry 3 }

cucsStorageLocalDiskBlockSize OBJECT-TYPE
    SYNTAX       Gauge32
    MAX-ACCESS   read-only
    STATUS       current
    DESCRIPTION
        "Cisco UCS storage:LocalDisk:blockSize managed object property"
    ::= { cucsStorageLocalDiskEntry 4 }

cucsStorageLocalDiskConnectionProtocol OBJECT-TYPE
    SYNTAX       CucsStorageConnectionProtocol
    MAX-ACCESS   read-only
    STATUS       current
    DESCRIPTION
        "Cisco UCS storage:LocalDisk:connectionProtocol
        managed object property"
    ::= { cucsStorageLocalDiskEntry 5 }

cucsStorageLocalDiskId OBJECT-TYPE
    SYNTAX       Gauge32
    MAX-ACCESS   read-only
    STATUS       current
    DESCRIPTION
        "Cisco UCS storage:LocalDisk:id managed object property"
    ::= { cucsStorageLocalDiskEntry 6 }

cucsStorageLocalDiskModel OBJECT-TYPE
    SYNTAX       SnmpAdminString
    MAX-ACCESS   read-only
    STATUS       current
    DESCRIPTION
        "Cisco UCS storage:LocalDisk:model managed object property"
    ::= { cucsStorageLocalDiskEntry 7 }

cucsStorageLocalDiskNumberOfBlocks OBJECT-TYPE
    SYNTAX       Unsigned64
    MAX-ACCESS   read-only
    STATUS       current
    DESCRIPTION
        "Cisco UCS storage:LocalDisk:numberOfBlocks managed
        object property"
    ::= { cucsStorageLocalDiskEntry 8 }

cucsStorageLocalDiskOperability OBJECT-TYPE
    SYNTAX       CucsEquipmentOperability
    MAX-ACCESS   read-only
    STATUS       current
    DESCRIPTION
        "Cisco UCS storage:LocalDisk:operability managed object property"
    ::= { cucsStorageLocalDiskEntry 9 }

cucsStorageLocalDiskPresence OBJECT-TYPE
    SYNTAX       CucsEquipmentPresence
    MAX-ACCESS   read-only
    STATUS       current
    DESCRIPTION
        "Cisco UCS storage:LocalDisk:presence managed object property"
    ::= { cucsStorageLocalDiskEntry 10 }

cucsStorageLocalDiskRevision OBJECT-TYPE
    SYNTAX       SnmpAdminString
    MAX-ACCESS   read-only
    STATUS       current
    DESCRIPTION
        "Cisco UCS storage:LocalDisk:revision managed object property"
    ::= { cucsStorageLocalDiskEntry 11 }

cucsStorageLocalDiskSerial OBJECT-TYPE
    SYNTAX       SnmpAdminString
    MAX-ACCESS   read-only
    STATUS       current
    DESCRIPTION
        "Cisco UCS storage:LocalDisk:serial managed object property"
    ::= { cucsStorageLocalDiskEntry 12 }

cucsStorageLocalDiskSize OBJECT-TYPE
    SYNTAX       Unsigned64
    MAX-ACCESS   read-only
    STATUS       current
    DESCRIPTION
        "Cisco UCS storage:LocalDisk:size managed object property"
    ::= { cucsStorageLocalDiskEntry 13 }

cucsStorageLocalDiskVendor OBJECT-TYPE
    SYNTAX       SnmpAdminString
    MAX-ACCESS   read-only
    STATUS       current
    DESCRIPTION
        "Cisco UCS storage:LocalDisk:vendor managed object property"
    ::= { cucsStorageLocalDiskEntry 14 }

cucsStorageLocalDiskLc OBJECT-TYPE
    SYNTAX       CucsFsmLifecycle
    MAX-ACCESS   read-only
    STATUS       current
    DESCRIPTION
        "Cisco UCS storage:LocalDisk:lc managed object property"
    ::= { cucsStorageLocalDiskEntry 15 }

cucsStorageLocalDiskOperQualifierReason OBJECT-TYPE
    SYNTAX       SnmpAdminString
    MAX-ACCESS   read-only
    STATUS       current
    DESCRIPTION
        "Cisco UCS storage:LocalDisk:operQualifierReason
        managed object property"
    ::= { cucsStorageLocalDiskEntry 16 }

cucsStorageLocalDiskConfigDefTable OBJECT-TYPE
    SYNTAX           SEQUENCE OF CucsStorageLocalDiskConfigDefEntry
    MAX-ACCESS       not-accessible
    STATUS           current
    DESCRIPTION
        "Cisco UCS storage:LocalDiskConfigDef managed object table"
    ::= { cucsStorageObjects 5 }

cucsStorageLocalDiskConfigDefEntry OBJECT-TYPE
    SYNTAX           CucsStorageLocalDiskConfigDefEntry
    MAX-ACCESS       not-accessible
    STATUS           current
    DESCRIPTION
        "Entry for the cucsStorageLocalDiskConfigDefTable table."
    INDEX { cucsStorageLocalDiskConfigDefInstanceId }
    ::= { cucsStorageLocalDiskConfigDefTable 1 }

CucsStorageLocalDiskConfigDefEntry ::= SEQUENCE {
    cucsStorageLocalDiskConfigDefInstanceId                          CucsManagedObjectId,
    cucsStorageLocalDiskConfigDefDn                                  CucsManagedObjectDn,
    cucsStorageLocalDiskConfigDefRn                                  SnmpAdminString,
    cucsStorageLocalDiskConfigDefDescr                               SnmpAdminString,
    cucsStorageLocalDiskConfigDefIntId                               SnmpAdminString,
    cucsStorageLocalDiskConfigDefMode                                CucsStorageLocalDiskMode,
    cucsStorageLocalDiskConfigDefName                                SnmpAdminString,
    cucsStorageLocalDiskConfigDefProtectConfig                       TruthValue,
    cucsStorageLocalDiskConfigDefPolicyLevel                         Gauge32,
    cucsStorageLocalDiskConfigDefPolicyOwner                         CucsPolicyPolicyOwner,
    cucsStorageLocalDiskConfigDefFlexFlashRAIDReportingState         CucsStorageLocalDiskConfigFlexFlashRAIDReportingState,
    cucsStorageLocalDiskConfigDefFlexFlashState                      CucsStorageLocalDiskConfigFlexFlashState
}

cucsStorageLocalDiskConfigDefInstanceId OBJECT-TYPE
    SYNTAX       CucsManagedObjectId
    MAX-ACCESS   not-accessible
    STATUS       current
    DESCRIPTION
        "Instance identifier of the managed object."
    ::= { cucsStorageLocalDiskConfigDefEntry 1 }

cucsStorageLocalDiskConfigDefDn OBJECT-TYPE
    SYNTAX       CucsManagedObjectDn
    MAX-ACCESS   read-only
    STATUS       current
    DESCRIPTION
        "Cisco UCS storage:LocalDiskConfigDef:dn managed object property"
    ::= { cucsStorageLocalDiskConfigDefEntry 2 }

cucsStorageLocalDiskConfigDefRn OBJECT-TYPE
    SYNTAX       SnmpAdminString
    MAX-ACCESS   read-only
    STATUS       current
    DESCRIPTION
        "Cisco UCS storage:LocalDiskConfigDef:rn managed object property"
    ::= { cucsStorageLocalDiskConfigDefEntry 3 }

cucsStorageLocalDiskConfigDefDescr OBJECT-TYPE
    SYNTAX       SnmpAdminString
    MAX-ACCESS   read-only
    STATUS       current
    DESCRIPTION
        "Cisco UCS storage:LocalDiskConfigDef:descr managed
        object property"
    ::= { cucsStorageLocalDiskConfigDefEntry 4 }

cucsStorageLocalDiskConfigDefIntId OBJECT-TYPE
    SYNTAX       SnmpAdminString
    MAX-ACCESS   read-only
    STATUS       current
    DESCRIPTION
        "Cisco UCS storage:LocalDiskConfigDef:intId managed
        object property"
    ::= { cucsStorageLocalDiskConfigDefEntry 5 }

cucsStorageLocalDiskConfigDefMode OBJECT-TYPE
    SYNTAX       CucsStorageLocalDiskMode
    MAX-ACCESS   read-only
    STATUS       current
    DESCRIPTION
        "Cisco UCS storage:LocalDiskConfigDef:mode managed
        object property"
    ::= { cucsStorageLocalDiskConfigDefEntry 6 }

cucsStorageLocalDiskConfigDefName OBJECT-TYPE
    SYNTAX       SnmpAdminString
    MAX-ACCESS   read-only
    STATUS       current
    DESCRIPTION
        "Cisco UCS storage:LocalDiskConfigDef:name managed
        object property"
    ::= { cucsStorageLocalDiskConfigDefEntry 7 }

cucsStorageLocalDiskConfigDefProtectConfig OBJECT-TYPE
    SYNTAX       TruthValue
    MAX-ACCESS   read-only
    STATUS       current
    DESCRIPTION
        "Cisco UCS storage:LocalDiskConfigDef:protectConfig
        managed object property"
    ::= { cucsStorageLocalDiskConfigDefEntry 8 }

cucsStorageLocalDiskConfigDefPolicyLevel OBJECT-TYPE
    SYNTAX       Gauge32
    MAX-ACCESS   read-only
    STATUS       current
    DESCRIPTION
        "Cisco UCS storage:LocalDiskConfigDef:policyLevel
        managed object property"
    ::= { cucsStorageLocalDiskConfigDefEntry 9 }

cucsStorageLocalDiskConfigDefPolicyOwner OBJECT-TYPE
    SYNTAX       CucsPolicyPolicyOwner
    MAX-ACCESS   read-only
    STATUS       current
    DESCRIPTION
        "Cisco UCS storage:LocalDiskConfigDef:policyOwner
        managed object property"
    ::= { cucsStorageLocalDiskConfigDefEntry 10 }

cucsStorageLocalDiskConfigDefFlexFlashRAIDReportingState OBJECT-TYPE
    SYNTAX       CucsStorageLocalDiskConfigFlexFlashRAIDReportingState
    MAX-ACCESS   read-only
    STATUS       current
    DESCRIPTION
        "Cisco UCS storage:LocalDiskConfigDef:flexFlashRAIDReportingState
        managed object property"
    ::= { cucsStorageLocalDiskConfigDefEntry 11 }

cucsStorageLocalDiskConfigDefFlexFlashState OBJECT-TYPE
    SYNTAX       CucsStorageLocalDiskConfigFlexFlashState
    MAX-ACCESS   read-only
    STATUS       current
    DESCRIPTION
        "Cisco UCS storage:LocalDiskConfigDef:flexFlashState
        managed object property"
    ::= { cucsStorageLocalDiskConfigDefEntry 12 }

cucsStorageLocalDiskConfigPolicyTable OBJECT-TYPE
    SYNTAX           SEQUENCE OF CucsStorageLocalDiskConfigPolicyEntry
    MAX-ACCESS       not-accessible
    STATUS           current
    DESCRIPTION
        "Cisco UCS storage:LocalDiskConfigPolicy managed object table"
    ::= { cucsStorageObjects 6 }

cucsStorageLocalDiskConfigPolicyEntry OBJECT-TYPE
    SYNTAX           CucsStorageLocalDiskConfigPolicyEntry
    MAX-ACCESS       not-accessible
    STATUS           current
    DESCRIPTION
        "Entry for the cucsStorageLocalDiskConfigPolicyTable table."
    INDEX { cucsStorageLocalDiskConfigPolicyInstanceId }
    ::= { cucsStorageLocalDiskConfigPolicyTable 1 }

CucsStorageLocalDiskConfigPolicyEntry ::= SEQUENCE {
    cucsStorageLocalDiskConfigPolicyInstanceId                       CucsManagedObjectId,
    cucsStorageLocalDiskConfigPolicyDn                               CucsManagedObjectDn,
    cucsStorageLocalDiskConfigPolicyRn                               SnmpAdminString,
    cucsStorageLocalDiskConfigPolicyDescr                            SnmpAdminString,
    cucsStorageLocalDiskConfigPolicyIntId                            SnmpAdminString,
    cucsStorageLocalDiskConfigPolicyMode                             CucsStorageLocalDiskMode,
    cucsStorageLocalDiskConfigPolicyName                             SnmpAdminString,
    cucsStorageLocalDiskConfigPolicyProtectConfig                    TruthValue,
    cucsStorageLocalDiskConfigPolicyPolicyLevel                      Gauge32,
    cucsStorageLocalDiskConfigPolicyPolicyOwner                      CucsPolicyPolicyOwner,
    cucsStorageLocalDiskConfigPolicyFlexFlashRAIDReportingState      CucsStorageLocalDiskConfigFlexFlashRAIDReportingState,
    cucsStorageLocalDiskConfigPolicyFlexFlashState                   CucsStorageLocalDiskConfigFlexFlashState
}

cucsStorageLocalDiskConfigPolicyInstanceId OBJECT-TYPE
    SYNTAX       CucsManagedObjectId
    MAX-ACCESS   not-accessible
    STATUS       current
    DESCRIPTION
        "Instance identifier of the managed object."
    ::= { cucsStorageLocalDiskConfigPolicyEntry 1 }

cucsStorageLocalDiskConfigPolicyDn OBJECT-TYPE
    SYNTAX       CucsManagedObjectDn
    MAX-ACCESS   read-only
    STATUS       current
    DESCRIPTION
        "Cisco UCS storage:LocalDiskConfigPolicy:dn managed
        object property"
    ::= { cucsStorageLocalDiskConfigPolicyEntry 2 }

cucsStorageLocalDiskConfigPolicyRn OBJECT-TYPE
    SYNTAX       SnmpAdminString
    MAX-ACCESS   read-only
    STATUS       current
    DESCRIPTION
        "Cisco UCS storage:LocalDiskConfigPolicy:rn managed
        object property"
    ::= { cucsStorageLocalDiskConfigPolicyEntry 3 }

cucsStorageLocalDiskConfigPolicyDescr OBJECT-TYPE
    SYNTAX       SnmpAdminString
    MAX-ACCESS   read-only
    STATUS       current
    DESCRIPTION
        "Cisco UCS storage:LocalDiskConfigPolicy:descr
        managed object property"
    ::= { cucsStorageLocalDiskConfigPolicyEntry 4 }

cucsStorageLocalDiskConfigPolicyIntId OBJECT-TYPE
    SYNTAX       SnmpAdminString
    MAX-ACCESS   read-only
    STATUS       current
    DESCRIPTION
        "Cisco UCS storage:LocalDiskConfigPolicy:intId
        managed object property"
    ::= { cucsStorageLocalDiskConfigPolicyEntry 5 }

cucsStorageLocalDiskConfigPolicyMode OBJECT-TYPE
    SYNTAX       CucsStorageLocalDiskMode
    MAX-ACCESS   read-only
    STATUS       current
    DESCRIPTION
        "Cisco UCS storage:LocalDiskConfigPolicy:mode managed
        object property"
    ::= { cucsStorageLocalDiskConfigPolicyEntry 6 }

cucsStorageLocalDiskConfigPolicyName OBJECT-TYPE
    SYNTAX       SnmpAdminString
    MAX-ACCESS   read-only
    STATUS       current
    DESCRIPTION
        "Cisco UCS storage:LocalDiskConfigPolicy:name managed
        object property"
    ::= { cucsStorageLocalDiskConfigPolicyEntry 7 }

cucsStorageLocalDiskConfigPolicyProtectConfig OBJECT-TYPE
    SYNTAX       TruthValue
    MAX-ACCESS   read-only
    STATUS       current
    DESCRIPTION
        "Cisco UCS storage:LocalDiskConfigPolicy:protectConfig
        managed object property"
    ::= { cucsStorageLocalDiskConfigPolicyEntry 8 }

cucsStorageLocalDiskConfigPolicyPolicyLevel OBJECT-TYPE
    SYNTAX       Gauge32
    MAX-ACCESS   read-only
    STATUS       current
    DESCRIPTION
        "Cisco UCS storage:LocalDiskConfigPolicy:policyLevel
        managed object property"
    ::= { cucsStorageLocalDiskConfigPolicyEntry 9 }

cucsStorageLocalDiskConfigPolicyPolicyOwner OBJECT-TYPE
    SYNTAX       CucsPolicyPolicyOwner
    MAX-ACCESS   read-only
    STATUS       current
    DESCRIPTION
        "Cisco UCS storage:LocalDiskConfigPolicy:policyOwner
        managed object property"
    ::= { cucsStorageLocalDiskConfigPolicyEntry 10 }

cucsStorageLocalDiskConfigPolicyFlexFlashRAIDReportingState OBJECT-TYPE
    SYNTAX       CucsStorageLocalDiskConfigFlexFlashRAIDReportingState
    MAX-ACCESS   read-only
    STATUS       current
    DESCRIPTION
        "Cisco UCS storage:LocalDiskConfigPolicy:flexFlashRAIDReportingSta
        te managed object property"
    ::= { cucsStorageLocalDiskConfigPolicyEntry 11 }

cucsStorageLocalDiskConfigPolicyFlexFlashState OBJECT-TYPE
    SYNTAX       CucsStorageLocalDiskConfigFlexFlashState
    MAX-ACCESS   read-only
    STATUS       current
    DESCRIPTION
        "Cisco UCS storage:LocalDiskConfigPolicy:flexFlashState
        managed object property"
    ::= { cucsStorageLocalDiskConfigPolicyEntry 12 }

cucsStorageLocalDiskPartitionTable OBJECT-TYPE
    SYNTAX           SEQUENCE OF CucsStorageLocalDiskPartitionEntry
    MAX-ACCESS       not-accessible
    STATUS           current
    DESCRIPTION
        "Cisco UCS storage:LocalDiskPartition managed object table"
    ::= { cucsStorageObjects 7 }

cucsStorageLocalDiskPartitionEntry OBJECT-TYPE
    SYNTAX           CucsStorageLocalDiskPartitionEntry
    MAX-ACCESS       not-accessible
    STATUS           current
    DESCRIPTION
        "Entry for the cucsStorageLocalDiskPartitionTable table."
    INDEX { cucsStorageLocalDiskPartitionInstanceId }
    ::= { cucsStorageLocalDiskPartitionTable 1 }

CucsStorageLocalDiskPartitionEntry ::= SEQUENCE {
    cucsStorageLocalDiskPartitionInstanceId                          CucsManagedObjectId,
    cucsStorageLocalDiskPartitionDn                                  CucsManagedObjectDn,
    cucsStorageLocalDiskPartitionRn                                  SnmpAdminString,
    cucsStorageLocalDiskPartitionDescr                               SnmpAdminString,
    cucsStorageLocalDiskPartitionIntId                               SnmpAdminString,
    cucsStorageLocalDiskPartitionName                                SnmpAdminString,
    cucsStorageLocalDiskPartitionOrder                               Gauge32,
    cucsStorageLocalDiskPartitionSize                                Unsigned64,
    cucsStorageLocalDiskPartitionType                                CucsStorageLocalDiskPartitionType,
    cucsStorageLocalDiskPartitionPolicyLevel                         Gauge32,
    cucsStorageLocalDiskPartitionPolicyOwner                         CucsPolicyPolicyOwner
}

cucsStorageLocalDiskPartitionInstanceId OBJECT-TYPE
    SYNTAX       CucsManagedObjectId
    MAX-ACCESS   not-accessible
    STATUS       current
    DESCRIPTION
        "Instance identifier of the managed object."
    ::= { cucsStorageLocalDiskPartitionEntry 1 }

cucsStorageLocalDiskPartitionDn OBJECT-TYPE
    SYNTAX       CucsManagedObjectDn
    MAX-ACCESS   read-only
    STATUS       current
    DESCRIPTION
        "Cisco UCS storage:LocalDiskPartition:dn managed object property"
    ::= { cucsStorageLocalDiskPartitionEntry 2 }

cucsStorageLocalDiskPartitionRn OBJECT-TYPE
    SYNTAX       SnmpAdminString
    MAX-ACCESS   read-only
    STATUS       current
    DESCRIPTION
        "Cisco UCS storage:LocalDiskPartition:rn managed object property"
    ::= { cucsStorageLocalDiskPartitionEntry 3 }

cucsStorageLocalDiskPartitionDescr OBJECT-TYPE
    SYNTAX       SnmpAdminString
    MAX-ACCESS   read-only
    STATUS       current
    DESCRIPTION
        "Cisco UCS storage:LocalDiskPartition:descr managed
        object property"
    ::= { cucsStorageLocalDiskPartitionEntry 4 }

cucsStorageLocalDiskPartitionIntId OBJECT-TYPE
    SYNTAX       SnmpAdminString
    MAX-ACCESS   read-only
    STATUS       current
    DESCRIPTION
        "Cisco UCS storage:LocalDiskPartition:intId managed
        object property"
    ::= { cucsStorageLocalDiskPartitionEntry 5 }

cucsStorageLocalDiskPartitionName OBJECT-TYPE
    SYNTAX       SnmpAdminString
    MAX-ACCESS   read-only
    STATUS       current
    DESCRIPTION
        "Cisco UCS storage:LocalDiskPartition:name managed
        object property"
    ::= { cucsStorageLocalDiskPartitionEntry 6 }

cucsStorageLocalDiskPartitionOrder OBJECT-TYPE
    SYNTAX       Gauge32
    MAX-ACCESS   read-only
    STATUS       current
    DESCRIPTION
        "Cisco UCS storage:LocalDiskPartition:order managed
        object property"
    ::= { cucsStorageLocalDiskPartitionEntry 7 }

cucsStorageLocalDiskPartitionSize OBJECT-TYPE
    SYNTAX       Unsigned64
    MAX-ACCESS   read-only
    STATUS       current
    DESCRIPTION
        "Cisco UCS storage:LocalDiskPartition:size managed
        object property"
    ::= { cucsStorageLocalDiskPartitionEntry 8 }

cucsStorageLocalDiskPartitionType OBJECT-TYPE
    SYNTAX       CucsStorageLocalDiskPartitionType
    MAX-ACCESS   read-only
    STATUS       current
    DESCRIPTION
        "Cisco UCS storage:LocalDiskPartition:type managed
        object property"
    ::= { cucsStorageLocalDiskPartitionEntry 9 }

cucsStorageLocalDiskPartitionPolicyLevel OBJECT-TYPE
    SYNTAX       Gauge32
    MAX-ACCESS   read-only
    STATUS       current
    DESCRIPTION
        "Cisco UCS storage:LocalDiskPartition:policyLevel
        managed object property"
    ::= { cucsStorageLocalDiskPartitionEntry 10 }

cucsStorageLocalDiskPartitionPolicyOwner OBJECT-TYPE
    SYNTAX       CucsPolicyPolicyOwner
    MAX-ACCESS   read-only
    STATUS       current
    DESCRIPTION
        "Cisco UCS storage:LocalDiskPartition:policyOwner
        managed object property"
    ::= { cucsStorageLocalDiskPartitionEntry 11 }

cucsStorageLocalDiskSlotEpTable OBJECT-TYPE
    SYNTAX           SEQUENCE OF CucsStorageLocalDiskSlotEpEntry
    MAX-ACCESS       not-accessible
    STATUS           current
    DESCRIPTION
        "Cisco UCS storage:LocalDiskSlotEp managed object table"
    ::= { cucsStorageObjects 13 }

cucsStorageLocalDiskSlotEpEntry OBJECT-TYPE
    SYNTAX           CucsStorageLocalDiskSlotEpEntry
    MAX-ACCESS       not-accessible
    STATUS           current
    DESCRIPTION
        "Entry for the cucsStorageLocalDiskSlotEpTable table."
    INDEX { cucsStorageLocalDiskSlotEpInstanceId }
    ::= { cucsStorageLocalDiskSlotEpTable 1 }

CucsStorageLocalDiskSlotEpEntry ::= SEQUENCE {
    cucsStorageLocalDiskSlotEpInstanceId                             CucsManagedObjectId,
    cucsStorageLocalDiskSlotEpDn                                     CucsManagedObjectDn,
    cucsStorageLocalDiskSlotEpRn                                     SnmpAdminString,
    cucsStorageLocalDiskSlotEpConfiguration                          CucsStorageConfiguration,
    cucsStorageLocalDiskSlotEpId                                     Gauge32,
    cucsStorageLocalDiskSlotEpOperability                            CucsEquipmentOperability,
    cucsStorageLocalDiskSlotEpPeerDn                                 SnmpAdminString,
    cucsStorageLocalDiskSlotEpPresence                               CucsEquipmentPresence,
    cucsStorageLocalDiskSlotEpOperQualifierReason                    SnmpAdminString
}

cucsStorageLocalDiskSlotEpInstanceId OBJECT-TYPE
    SYNTAX       CucsManagedObjectId
    MAX-ACCESS   not-accessible
    STATUS       current
    DESCRIPTION
        "Instance identifier of the managed object."
    ::= { cucsStorageLocalDiskSlotEpEntry 1 }

cucsStorageLocalDiskSlotEpDn OBJECT-TYPE
    SYNTAX       CucsManagedObjectDn
    MAX-ACCESS   read-only
    STATUS       current
    DESCRIPTION
        "Cisco UCS storage:LocalDiskSlotEp:dn managed object property"
    ::= { cucsStorageLocalDiskSlotEpEntry 2 }

cucsStorageLocalDiskSlotEpRn OBJECT-TYPE
    SYNTAX       SnmpAdminString
    MAX-ACCESS   read-only
    STATUS       current
    DESCRIPTION
        "Cisco UCS storage:LocalDiskSlotEp:rn managed object property"
    ::= { cucsStorageLocalDiskSlotEpEntry 3 }

cucsStorageLocalDiskSlotEpConfiguration OBJECT-TYPE
    SYNTAX       CucsStorageConfiguration
    MAX-ACCESS   read-only
    STATUS       current
    DESCRIPTION
        "Cisco UCS storage:LocalDiskSlotEp:configuration
        managed object property"
    ::= { cucsStorageLocalDiskSlotEpEntry 4 }

cucsStorageLocalDiskSlotEpId OBJECT-TYPE
    SYNTAX       Gauge32
    MAX-ACCESS   read-only
    STATUS       current
    DESCRIPTION
        "Cisco UCS storage:LocalDiskSlotEp:id managed object property"
    ::= { cucsStorageLocalDiskSlotEpEntry 5 }

cucsStorageLocalDiskSlotEpOperability OBJECT-TYPE
    SYNTAX       CucsEquipmentOperability
    MAX-ACCESS   read-only
    STATUS       current
    DESCRIPTION
        "Cisco UCS storage:LocalDiskSlotEp:operability
        managed object property"
    ::= { cucsStorageLocalDiskSlotEpEntry 6 }

cucsStorageLocalDiskSlotEpPeerDn OBJECT-TYPE
    SYNTAX       SnmpAdminString
    MAX-ACCESS   read-only
    STATUS       current
    DESCRIPTION
        "Cisco UCS storage:LocalDiskSlotEp:peerDn managed object property"
    ::= { cucsStorageLocalDiskSlotEpEntry 7 }

cucsStorageLocalDiskSlotEpPresence OBJECT-TYPE
    SYNTAX       CucsEquipmentPresence
    MAX-ACCESS   read-only
    STATUS       current
    DESCRIPTION
        "Cisco UCS storage:LocalDiskSlotEp:presence managed
        object property"
    ::= { cucsStorageLocalDiskSlotEpEntry 8 }

cucsStorageLocalDiskSlotEpOperQualifierReason OBJECT-TYPE
    SYNTAX       SnmpAdminString
    MAX-ACCESS   read-only
    STATUS       current
    DESCRIPTION
        "Cisco UCS storage:LocalDiskSlotEp:operQualifierReason
        managed object property"
    ::= { cucsStorageLocalDiskSlotEpEntry 9 }

cucsStorageLocalLunTable OBJECT-TYPE
    SYNTAX           SEQUENCE OF CucsStorageLocalLunEntry
    MAX-ACCESS       not-accessible
    STATUS           current
    DESCRIPTION
        "Cisco UCS storage:LocalLun managed object table"
    ::= { cucsStorageObjects 8 }

cucsStorageLocalLunEntry OBJECT-TYPE
    SYNTAX           CucsStorageLocalLunEntry
    MAX-ACCESS       not-accessible
    STATUS           current
    DESCRIPTION
        "Entry for the cucsStorageLocalLunTable table."
    INDEX { cucsStorageLocalLunInstanceId }
    ::= { cucsStorageLocalLunTable 1 }

CucsStorageLocalLunEntry ::= SEQUENCE {
    cucsStorageLocalLunInstanceId                                    CucsManagedObjectId,
    cucsStorageLocalLunDn                                            CucsManagedObjectDn,
    cucsStorageLocalLunRn                                            SnmpAdminString,
    cucsStorageLocalLunBlockSize                                     Gauge32,
    cucsStorageLocalLunConnectionProtocol                            CucsStorageConnectionProtocol,
    cucsStorageLocalLunId                                            Gauge32,
    cucsStorageLocalLunModel                                         SnmpAdminString,
    cucsStorageLocalLunNumberOfBlocks                                Unsigned64,
    cucsStorageLocalLunOperability                                   CucsEquipmentOperability,
    cucsStorageLocalLunPresence                                      CucsEquipmentPresence,
    cucsStorageLocalLunRevision                                      SnmpAdminString,
    cucsStorageLocalLunSerial                                        SnmpAdminString,
    cucsStorageLocalLunSize                                          Unsigned64,
    cucsStorageLocalLunType                                          CucsStorageLunType,
    cucsStorageLocalLunVendor                                        SnmpAdminString,
    cucsStorageLocalLunLc                                            CucsFsmLifecycle,
    cucsStorageLocalLunOperQualifierReason                           SnmpAdminString
}

cucsStorageLocalLunInstanceId OBJECT-TYPE
    SYNTAX       CucsManagedObjectId
    MAX-ACCESS   not-accessible
    STATUS       current
    DESCRIPTION
        "Instance identifier of the managed object."
    ::= { cucsStorageLocalLunEntry 1 }

cucsStorageLocalLunDn OBJECT-TYPE
    SYNTAX       CucsManagedObjectDn
    MAX-ACCESS   read-only
    STATUS       current
    DESCRIPTION
        "Cisco UCS storage:LocalLun:dn managed object property"
    ::= { cucsStorageLocalLunEntry 2 }

cucsStorageLocalLunRn OBJECT-TYPE
    SYNTAX       SnmpAdminString
    MAX-ACCESS   read-only
    STATUS       current
    DESCRIPTION
        "Cisco UCS storage:LocalLun:rn managed object property"
    ::= { cucsStorageLocalLunEntry 3 }

cucsStorageLocalLunBlockSize OBJECT-TYPE
    SYNTAX       Gauge32
    MAX-ACCESS   read-only
    STATUS       current
    DESCRIPTION
        "Cisco UCS storage:LocalLun:blockSize managed object property"
    ::= { cucsStorageLocalLunEntry 4 }

cucsStorageLocalLunConnectionProtocol OBJECT-TYPE
    SYNTAX       CucsStorageConnectionProtocol
    MAX-ACCESS   read-only
    STATUS       current
    DESCRIPTION
        "Cisco UCS storage:LocalLun:connectionProtocol
        managed object property"
    ::= { cucsStorageLocalLunEntry 5 }

cucsStorageLocalLunId OBJECT-TYPE
    SYNTAX       Gauge32
    MAX-ACCESS   read-only
    STATUS       current
    DESCRIPTION
        "Cisco UCS storage:LocalLun:id managed object property"
    ::= { cucsStorageLocalLunEntry 6 }

cucsStorageLocalLunModel OBJECT-TYPE
    SYNTAX       SnmpAdminString
    MAX-ACCESS   read-only
    STATUS       current
    DESCRIPTION
        "Cisco UCS storage:LocalLun:model managed object property"
    ::= { cucsStorageLocalLunEntry 7 }

cucsStorageLocalLunNumberOfBlocks OBJECT-TYPE
    SYNTAX       Unsigned64
    MAX-ACCESS   read-only
    STATUS       current
    DESCRIPTION
        "Cisco UCS storage:LocalLun:numberOfBlocks managed
        object property"
    ::= { cucsStorageLocalLunEntry 8 }

cucsStorageLocalLunOperability OBJECT-TYPE
    SYNTAX       CucsEquipmentOperability
    MAX-ACCESS   read-only
    STATUS       current
    DESCRIPTION
        "Cisco UCS storage:LocalLun:operability managed object property"
    ::= { cucsStorageLocalLunEntry 9 }

cucsStorageLocalLunPresence OBJECT-TYPE
    SYNTAX       CucsEquipmentPresence
    MAX-ACCESS   read-only
    STATUS       current
    DESCRIPTION
        "Cisco UCS storage:LocalLun:presence managed object property"
    ::= { cucsStorageLocalLunEntry 10 }

cucsStorageLocalLunRevision OBJECT-TYPE
    SYNTAX       SnmpAdminString
    MAX-ACCESS   read-only
    STATUS       current
    DESCRIPTION
        "Cisco UCS storage:LocalLun:revision managed object property"
    ::= { cucsStorageLocalLunEntry 11 }

cucsStorageLocalLunSerial OBJECT-TYPE
    SYNTAX       SnmpAdminString
    MAX-ACCESS   read-only
    STATUS       current
    DESCRIPTION
        "Cisco UCS storage:LocalLun:serial managed object property"
    ::= { cucsStorageLocalLunEntry 12 }

cucsStorageLocalLunSize OBJECT-TYPE
    SYNTAX       Unsigned64
    MAX-ACCESS   read-only
    STATUS       current
    DESCRIPTION
        "Cisco UCS storage:LocalLun:size managed object property"
    ::= { cucsStorageLocalLunEntry 13 }

cucsStorageLocalLunType OBJECT-TYPE
    SYNTAX       CucsStorageLunType
    MAX-ACCESS   read-only
    STATUS       current
    DESCRIPTION
        "Cisco UCS storage:LocalLun:type managed object property"
    ::= { cucsStorageLocalLunEntry 14 }

cucsStorageLocalLunVendor OBJECT-TYPE
    SYNTAX       SnmpAdminString
    MAX-ACCESS   read-only
    STATUS       current
    DESCRIPTION
        "Cisco UCS storage:LocalLun:vendor managed object property"
    ::= { cucsStorageLocalLunEntry 15 }

cucsStorageLocalLunLc OBJECT-TYPE
    SYNTAX       CucsFsmLifecycle
    MAX-ACCESS   read-only
    STATUS       current
    DESCRIPTION
        "Cisco UCS storage:LocalLun:lc managed object property"
    ::= { cucsStorageLocalLunEntry 16 }

cucsStorageLocalLunOperQualifierReason OBJECT-TYPE
    SYNTAX       SnmpAdminString
    MAX-ACCESS   read-only
    STATUS       current
    DESCRIPTION
        "Cisco UCS storage:LocalLun:operQualifierReason
        managed object property"
    ::= { cucsStorageLocalLunEntry 17 }

cucsStorageLunDiskTable OBJECT-TYPE
    SYNTAX           SEQUENCE OF CucsStorageLunDiskEntry
    MAX-ACCESS       not-accessible
    STATUS           current
    DESCRIPTION
        "Cisco UCS storage:LunDisk managed object table"
    ::= { cucsStorageObjects 9 }

cucsStorageLunDiskEntry OBJECT-TYPE
    SYNTAX           CucsStorageLunDiskEntry
    MAX-ACCESS       not-accessible
    STATUS           current
    DESCRIPTION
        "Entry for the cucsStorageLunDiskTable table."
    INDEX { cucsStorageLunDiskInstanceId }
    ::= { cucsStorageLunDiskTable 1 }

CucsStorageLunDiskEntry ::= SEQUENCE {
    cucsStorageLunDiskInstanceId                                     CucsManagedObjectId,
    cucsStorageLunDiskDn                                             CucsManagedObjectDn,
    cucsStorageLunDiskRn                                             SnmpAdminString,
    cucsStorageLunDiskId                                             Gauge32
}

cucsStorageLunDiskInstanceId OBJECT-TYPE
    SYNTAX       CucsManagedObjectId
    MAX-ACCESS   not-accessible
    STATUS       current
    DESCRIPTION
        "Instance identifier of the managed object."
    ::= { cucsStorageLunDiskEntry 1 }

cucsStorageLunDiskDn OBJECT-TYPE
    SYNTAX       CucsManagedObjectDn
    MAX-ACCESS   read-only
    STATUS       current
    DESCRIPTION
        "Cisco UCS storage:LunDisk:dn managed object property"
    ::= { cucsStorageLunDiskEntry 2 }

cucsStorageLunDiskRn OBJECT-TYPE
    SYNTAX       SnmpAdminString
    MAX-ACCESS   read-only
    STATUS       current
    DESCRIPTION
        "Cisco UCS storage:LunDisk:rn managed object property"
    ::= { cucsStorageLunDiskEntry 3 }

cucsStorageLunDiskId OBJECT-TYPE
    SYNTAX       Gauge32
    MAX-ACCESS   read-only
    STATUS       current
    DESCRIPTION
        "Cisco UCS storage:LunDisk:id managed object property"
    ::= { cucsStorageLunDiskEntry 4 }

cucsStorageNodeEpTable OBJECT-TYPE
    SYNTAX           SEQUENCE OF CucsStorageNodeEpEntry
    MAX-ACCESS       not-accessible
    STATUS           current
    DESCRIPTION
        "Cisco UCS storage:NodeEp managed object table"
    ::= { cucsStorageObjects 26 }

cucsStorageNodeEpEntry OBJECT-TYPE
    SYNTAX           CucsStorageNodeEpEntry
    MAX-ACCESS       not-accessible
    STATUS           current
    DESCRIPTION
        "Entry for the cucsStorageNodeEpTable table."
    INDEX { cucsStorageNodeEpInstanceId }
    ::= { cucsStorageNodeEpTable 1 }

CucsStorageNodeEpEntry ::= SEQUENCE {
    cucsStorageNodeEpInstanceId                                      CucsManagedObjectId,
    cucsStorageNodeEpDn                                              CucsManagedObjectDn,
    cucsStorageNodeEpRn                                              SnmpAdminString,
    cucsStorageNodeEpEpDn                                            SnmpAdminString,
    cucsStorageNodeEpId                                              Gauge32
}

cucsStorageNodeEpInstanceId OBJECT-TYPE
    SYNTAX       CucsManagedObjectId
    MAX-ACCESS   not-accessible
    STATUS       current
    DESCRIPTION
        "Instance identifier of the managed object."
    ::= { cucsStorageNodeEpEntry 1 }

cucsStorageNodeEpDn OBJECT-TYPE
    SYNTAX       CucsManagedObjectDn
    MAX-ACCESS   read-only
    STATUS       current
    DESCRIPTION
        "Cisco UCS storage:NodeEp:dn managed object property"
    ::= { cucsStorageNodeEpEntry 2 }

cucsStorageNodeEpRn OBJECT-TYPE
    SYNTAX       SnmpAdminString
    MAX-ACCESS   read-only
    STATUS       current
    DESCRIPTION
        "Cisco UCS storage:NodeEp:rn managed object property"
    ::= { cucsStorageNodeEpEntry 3 }

cucsStorageNodeEpEpDn OBJECT-TYPE
    SYNTAX       SnmpAdminString
    MAX-ACCESS   read-only
    STATUS       current
    DESCRIPTION
        "Cisco UCS storage:NodeEp:epDn managed object property"
    ::= { cucsStorageNodeEpEntry 4 }

cucsStorageNodeEpId OBJECT-TYPE
    SYNTAX       Gauge32
    MAX-ACCESS   read-only
    STATUS       current
    DESCRIPTION
        "Cisco UCS storage:NodeEp:id managed object property"
    ::= { cucsStorageNodeEpEntry 5 }

cucsStorageQualTable OBJECT-TYPE
    SYNTAX           SEQUENCE OF CucsStorageQualEntry
    MAX-ACCESS       not-accessible
    STATUS           current
    DESCRIPTION
        "Cisco UCS storage:Qual managed object table"
    ::= { cucsStorageObjects 10 }

cucsStorageQualEntry OBJECT-TYPE
    SYNTAX           CucsStorageQualEntry
    MAX-ACCESS       not-accessible
    STATUS           current
    DESCRIPTION
        "Entry for the cucsStorageQualTable table."
    INDEX { cucsStorageQualInstanceId }
    ::= { cucsStorageQualTable 1 }

CucsStorageQualEntry ::= SEQUENCE {
    cucsStorageQualInstanceId                                        CucsManagedObjectId,
    cucsStorageQualDn                                                CucsManagedObjectDn,
    cucsStorageQualRn                                                SnmpAdminString,
    cucsStorageQualBlockSize                                         Gauge32,
    cucsStorageQualMaxCap                                            Unsigned64,
    cucsStorageQualMinCap                                            Unsigned64,
    cucsStorageQualNumberOfBlocks                                    Unsigned64,
    cucsStorageQualPerDiskCap                                        Unsigned64,
    cucsStorageQualUnits                                             Gauge32,
    cucsStorageQualDiskless                                          CucsStorageDisklessAction
}

cucsStorageQualInstanceId OBJECT-TYPE
    SYNTAX       CucsManagedObjectId
    MAX-ACCESS   not-accessible
    STATUS       current
    DESCRIPTION
        "Instance identifier of the managed object."
    ::= { cucsStorageQualEntry 1 }

cucsStorageQualDn OBJECT-TYPE
    SYNTAX       CucsManagedObjectDn
    MAX-ACCESS   read-only
    STATUS       current
    DESCRIPTION
        "Cisco UCS storage:Qual:dn managed object property"
    ::= { cucsStorageQualEntry 2 }

cucsStorageQualRn OBJECT-TYPE
    SYNTAX       SnmpAdminString
    MAX-ACCESS   read-only
    STATUS       current
    DESCRIPTION
        "Cisco UCS storage:Qual:rn managed object property"
    ::= { cucsStorageQualEntry 3 }

cucsStorageQualBlockSize OBJECT-TYPE
    SYNTAX       Gauge32
    MAX-ACCESS   read-only
    STATUS       current
    DESCRIPTION
        "Cisco UCS storage:Qual:blockSize managed object property"
    ::= { cucsStorageQualEntry 4 }

cucsStorageQualMaxCap OBJECT-TYPE
    SYNTAX       Unsigned64
    MAX-ACCESS   read-only
    STATUS       current
    DESCRIPTION
        "Cisco UCS storage:Qual:maxCap managed object property"
    ::= { cucsStorageQualEntry 5 }

cucsStorageQualMinCap OBJECT-TYPE
    SYNTAX       Unsigned64
    MAX-ACCESS   read-only
    STATUS       current
    DESCRIPTION
        "Cisco UCS storage:Qual:minCap managed object property"
    ::= { cucsStorageQualEntry 6 }

cucsStorageQualNumberOfBlocks OBJECT-TYPE
    SYNTAX       Unsigned64
    MAX-ACCESS   read-only
    STATUS       current
    DESCRIPTION
        "Cisco UCS storage:Qual:numberOfBlocks managed object property"
    ::= { cucsStorageQualEntry 7 }

cucsStorageQualPerDiskCap OBJECT-TYPE
    SYNTAX       Unsigned64
    MAX-ACCESS   read-only
    STATUS       current
    DESCRIPTION
        "Cisco UCS storage:Qual:perDiskCap managed object property"
    ::= { cucsStorageQualEntry 8 }

cucsStorageQualUnits OBJECT-TYPE
    SYNTAX       Gauge32
    MAX-ACCESS   read-only
    STATUS       current
    DESCRIPTION
        "Cisco UCS storage:Qual:units managed object property"
    ::= { cucsStorageQualEntry 9 }

cucsStorageQualDiskless OBJECT-TYPE
    SYNTAX       CucsStorageDisklessAction
    MAX-ACCESS   read-only
    STATUS       current
    DESCRIPTION
        "Cisco UCS storage:Qual:diskless managed object property"
    ::= { cucsStorageQualEntry 10 }

cucsStorageRaidBatteryTable OBJECT-TYPE
    SYNTAX           SEQUENCE OF CucsStorageRaidBatteryEntry
    MAX-ACCESS       not-accessible
    STATUS           current
    DESCRIPTION
        "Cisco UCS storage:RaidBattery managed object table"
    ::= { cucsStorageObjects 11 }

cucsStorageRaidBatteryEntry OBJECT-TYPE
    SYNTAX           CucsStorageRaidBatteryEntry
    MAX-ACCESS       not-accessible
    STATUS           current
    DESCRIPTION
        "Entry for the cucsStorageRaidBatteryTable table."
    INDEX { cucsStorageRaidBatteryInstanceId }
    ::= { cucsStorageRaidBatteryTable 1 }

CucsStorageRaidBatteryEntry ::= SEQUENCE {
    cucsStorageRaidBatteryInstanceId                                 CucsManagedObjectId,
    cucsStorageRaidBatteryDn                                         CucsManagedObjectDn,
    cucsStorageRaidBatteryRn                                         SnmpAdminString,
    cucsStorageRaidBatteryBlockSize                                  Gauge32,
    cucsStorageRaidBatteryConnectionProtocol                         CucsStorageConnectionProtocol,
    cucsStorageRaidBatteryId                                         Gauge32,
    cucsStorageRaidBatteryModel                                      SnmpAdminString,
    cucsStorageRaidBatteryNumberOfBlocks                             Unsigned64,
    cucsStorageRaidBatteryOperability                                CucsEquipmentOperability,
    cucsStorageRaidBatteryPresence                                   CucsEquipmentPresence,
    cucsStorageRaidBatteryRevision                                   SnmpAdminString,
    cucsStorageRaidBatterySerial                                     SnmpAdminString,
    cucsStorageRaidBatterySize                                       Unsigned64,
    cucsStorageRaidBatteryVendor                                     SnmpAdminString,
    cucsStorageRaidBatteryOperQualifierReason                        SnmpAdminString,
    cucsStorageRaidBatteryBatteryType                                CucsStorageBatteryType,
    cucsStorageRaidBatteryCapacityPercentage                         Gauge32,
    cucsStorageRaidBatteryOperabilityQualifier                       CucsStorageRaidBatteryOperabilityQualifier,
    cucsStorageRaidBatteryOperabilityQualifierReason                 SnmpAdminString,
    cucsStorageRaidBatteryTemperature                                INTEGER
}

cucsStorageRaidBatteryInstanceId OBJECT-TYPE
    SYNTAX       CucsManagedObjectId
    MAX-ACCESS   not-accessible
    STATUS       current
    DESCRIPTION
        "Instance identifier of the managed object."
    ::= { cucsStorageRaidBatteryEntry 1 }

cucsStorageRaidBatteryDn OBJECT-TYPE
    SYNTAX       CucsManagedObjectDn
    MAX-ACCESS   read-only
    STATUS       current
    DESCRIPTION
        "Cisco UCS storage:RaidBattery:dn managed object property"
    ::= { cucsStorageRaidBatteryEntry 2 }

cucsStorageRaidBatteryRn OBJECT-TYPE
    SYNTAX       SnmpAdminString
    MAX-ACCESS   read-only
    STATUS       current
    DESCRIPTION
        "Cisco UCS storage:RaidBattery:rn managed object property"
    ::= { cucsStorageRaidBatteryEntry 3 }

cucsStorageRaidBatteryBlockSize OBJECT-TYPE
    SYNTAX       Gauge32
    MAX-ACCESS   read-only
    STATUS       current
    DESCRIPTION
        "Cisco UCS storage:RaidBattery:blockSize managed object property"
    ::= { cucsStorageRaidBatteryEntry 4 }

cucsStorageRaidBatteryConnectionProtocol OBJECT-TYPE
    SYNTAX       CucsStorageConnectionProtocol
    MAX-ACCESS   read-only
    STATUS       current
    DESCRIPTION
        "Cisco UCS storage:RaidBattery:connectionProtocol
        managed object property"
    ::= { cucsStorageRaidBatteryEntry 5 }

cucsStorageRaidBatteryId OBJECT-TYPE
    SYNTAX       Gauge32
    MAX-ACCESS   read-only
    STATUS       current
    DESCRIPTION
        "Cisco UCS storage:RaidBattery:id managed object property"
    ::= { cucsStorageRaidBatteryEntry 6 }

cucsStorageRaidBatteryModel OBJECT-TYPE
    SYNTAX       SnmpAdminString
    MAX-ACCESS   read-only
    STATUS       current
    DESCRIPTION
        "Cisco UCS storage:RaidBattery:model managed object property"
    ::= { cucsStorageRaidBatteryEntry 7 }

cucsStorageRaidBatteryNumberOfBlocks OBJECT-TYPE
    SYNTAX       Unsigned64
    MAX-ACCESS   read-only
    STATUS       current
    DESCRIPTION
        "Cisco UCS storage:RaidBattery:numberOfBlocks managed
        object property"
    ::= { cucsStorageRaidBatteryEntry 8 }

cucsStorageRaidBatteryOperability OBJECT-TYPE
    SYNTAX       CucsEquipmentOperability
    MAX-ACCESS   read-only
    STATUS       current
    DESCRIPTION
        "Cisco UCS storage:RaidBattery:operability managed
        object property"
    ::= { cucsStorageRaidBatteryEntry 9 }

cucsStorageRaidBatteryPresence OBJECT-TYPE
    SYNTAX       CucsEquipmentPresence
    MAX-ACCESS   read-only
    STATUS       current
    DESCRIPTION
        "Cisco UCS storage:RaidBattery:presence managed object property"
    ::= { cucsStorageRaidBatteryEntry 10 }

cucsStorageRaidBatteryRevision OBJECT-TYPE
    SYNTAX       SnmpAdminString
    MAX-ACCESS   read-only
    STATUS       current
    DESCRIPTION
        "Cisco UCS storage:RaidBattery:revision managed object property"
    ::= { cucsStorageRaidBatteryEntry 11 }

cucsStorageRaidBatterySerial OBJECT-TYPE
    SYNTAX       SnmpAdminString
    MAX-ACCESS   read-only
    STATUS       current
    DESCRIPTION
        "Cisco UCS storage:RaidBattery:serial managed object property"
    ::= { cucsStorageRaidBatteryEntry 12 }

cucsStorageRaidBatterySize OBJECT-TYPE
    SYNTAX       Unsigned64
    MAX-ACCESS   read-only
    STATUS       current
    DESCRIPTION
        "Cisco UCS storage:RaidBattery:size managed object property"
    ::= { cucsStorageRaidBatteryEntry 13 }

cucsStorageRaidBatteryVendor OBJECT-TYPE
    SYNTAX       SnmpAdminString
    MAX-ACCESS   read-only
    STATUS       current
    DESCRIPTION
        "Cisco UCS storage:RaidBattery:vendor managed object property"
    ::= { cucsStorageRaidBatteryEntry 14 }

cucsStorageRaidBatteryOperQualifierReason OBJECT-TYPE
    SYNTAX       SnmpAdminString
    MAX-ACCESS   read-only
    STATUS       current
    DESCRIPTION
        "Cisco UCS storage:RaidBattery:operQualifierReason
        managed object property"
    ::= { cucsStorageRaidBatteryEntry 15 }

cucsStorageRaidBatteryBatteryType OBJECT-TYPE
    SYNTAX       CucsStorageBatteryType
    MAX-ACCESS   read-only
    STATUS       current
    DESCRIPTION
        "Cisco UCS storage:RaidBattery:batteryType managed
        object property"
    ::= { cucsStorageRaidBatteryEntry 16 }

cucsStorageRaidBatteryCapacityPercentage OBJECT-TYPE
    SYNTAX       Gauge32
    MAX-ACCESS   read-only
    STATUS       current
    DESCRIPTION
        "Cisco UCS storage:RaidBattery:capacityPercentage
        managed object property"
    ::= { cucsStorageRaidBatteryEntry 17 }

cucsStorageRaidBatteryOperabilityQualifier OBJECT-TYPE
    SYNTAX       CucsStorageRaidBatteryOperabilityQualifier
    MAX-ACCESS   read-only
    STATUS       current
    DESCRIPTION
        "Cisco UCS storage:RaidBattery:operabilityQualifier
        managed object property"
    ::= { cucsStorageRaidBatteryEntry 18 }

cucsStorageRaidBatteryOperabilityQualifierReason OBJECT-TYPE
    SYNTAX       SnmpAdminString
    MAX-ACCESS   read-only
    STATUS       current
    DESCRIPTION
        "Cisco UCS storage:RaidBattery:operabilityQualifierReason
        managed object property"
    ::= { cucsStorageRaidBatteryEntry 19 }

cucsStorageRaidBatteryTemperature OBJECT-TYPE
    SYNTAX       INTEGER
    MAX-ACCESS   read-only
    STATUS       current
    DESCRIPTION
        "Cisco UCS storage:RaidBattery:temperature managed
        object property"
    ::= { cucsStorageRaidBatteryEntry 20 }

cucsStorageSystemTable OBJECT-TYPE
    SYNTAX           SEQUENCE OF CucsStorageSystemEntry
    MAX-ACCESS       not-accessible
    STATUS           current
    DESCRIPTION
        "Cisco UCS storage:System managed object table"
    ::= { cucsStorageObjects 27 }

cucsStorageSystemEntry OBJECT-TYPE
    SYNTAX           CucsStorageSystemEntry
    MAX-ACCESS       not-accessible
    STATUS           current
    DESCRIPTION
        "Entry for the cucsStorageSystemTable table."
    INDEX { cucsStorageSystemInstanceId }
    ::= { cucsStorageSystemTable 1 }

CucsStorageSystemEntry ::= SEQUENCE {
    cucsStorageSystemInstanceId                                      CucsManagedObjectId,
    cucsStorageSystemDn                                              CucsManagedObjectDn,
    cucsStorageSystemRn                                              SnmpAdminString,
    cucsStorageSystemFsmDescr                                        SnmpAdminString,
    cucsStorageSystemFsmPrev                                         SnmpAdminString,
    cucsStorageSystemFsmProgr                                        Gauge32,
    cucsStorageSystemFsmRmtInvErrCode                                Gauge32,
    cucsStorageSystemFsmRmtInvErrDescr                               SnmpAdminString,
    cucsStorageSystemFsmRmtInvRslt                                   CucsConditionRemoteInvRslt,
    cucsStorageSystemFsmStageDescr                                   SnmpAdminString,
    cucsStorageSystemFsmStamp                                        DateAndTime,
    cucsStorageSystemFsmStatus                                       SnmpAdminString,
    cucsStorageSystemFsmTry                                          Gauge32,
    cucsStorageSystemId                                              SnmpAdminString,
    cucsStorageSystemName                                            SnmpAdminString
}

cucsStorageSystemInstanceId OBJECT-TYPE
    SYNTAX       CucsManagedObjectId
    MAX-ACCESS   not-accessible
    STATUS       current
    DESCRIPTION
        "Instance identifier of the managed object."
    ::= { cucsStorageSystemEntry 1 }

cucsStorageSystemDn OBJECT-TYPE
    SYNTAX       CucsManagedObjectDn
    MAX-ACCESS   read-only
    STATUS       current
    DESCRIPTION
        "Cisco UCS storage:System:dn managed object property"
    ::= { cucsStorageSystemEntry 2 }

cucsStorageSystemRn OBJECT-TYPE
    SYNTAX       SnmpAdminString
    MAX-ACCESS   read-only
    STATUS       current
    DESCRIPTION
        "Cisco UCS storage:System:rn managed object property"
    ::= { cucsStorageSystemEntry 3 }

cucsStorageSystemFsmDescr OBJECT-TYPE
    SYNTAX       SnmpAdminString
    MAX-ACCESS   read-only
    STATUS       current
    DESCRIPTION
        "Cisco UCS storage:System:fsmDescr managed object property"
    ::= { cucsStorageSystemEntry 4 }

cucsStorageSystemFsmPrev OBJECT-TYPE
    SYNTAX       SnmpAdminString
    MAX-ACCESS   read-only
    STATUS       current
    DESCRIPTION
        "Cisco UCS storage:System:fsmPrev managed object property"
    ::= { cucsStorageSystemEntry 5 }

cucsStorageSystemFsmProgr OBJECT-TYPE
    SYNTAX       Gauge32
    MAX-ACCESS   read-only
    STATUS       current
    DESCRIPTION
        "Cisco UCS storage:System:fsmProgr managed object property"
    ::= { cucsStorageSystemEntry 6 }

cucsStorageSystemFsmRmtInvErrCode OBJECT-TYPE
    SYNTAX       Gauge32
    MAX-ACCESS   read-only
    STATUS       current
    DESCRIPTION
        "Cisco UCS storage:System:fsmRmtInvErrCode managed
        object property"
    ::= { cucsStorageSystemEntry 7 }

cucsStorageSystemFsmRmtInvErrDescr OBJECT-TYPE
    SYNTAX       SnmpAdminString
    MAX-ACCESS   read-only
    STATUS       current
    DESCRIPTION
        "Cisco UCS storage:System:fsmRmtInvErrDescr managed
        object property"
    ::= { cucsStorageSystemEntry 8 }

cucsStorageSystemFsmRmtInvRslt OBJECT-TYPE
    SYNTAX       CucsConditionRemoteInvRslt
    MAX-ACCESS   read-only
    STATUS       current
    DESCRIPTION
        "Cisco UCS storage:System:fsmRmtInvRslt managed object property"
    ::= { cucsStorageSystemEntry 9 }

cucsStorageSystemFsmStageDescr OBJECT-TYPE
    SYNTAX       SnmpAdminString
    MAX-ACCESS   read-only
    STATUS       current
    DESCRIPTION
        "Cisco UCS storage:System:fsmStageDescr managed object property"
    ::= { cucsStorageSystemEntry 10 }

cucsStorageSystemFsmStamp OBJECT-TYPE
    SYNTAX       DateAndTime
    MAX-ACCESS   read-only
    STATUS       current
    DESCRIPTION
        "Cisco UCS storage:System:fsmStamp managed object property"
    ::= { cucsStorageSystemEntry 11 }

cucsStorageSystemFsmStatus OBJECT-TYPE
    SYNTAX       SnmpAdminString
    MAX-ACCESS   read-only
    STATUS       current
    DESCRIPTION
        "Cisco UCS storage:System:fsmStatus managed object property"
    ::= { cucsStorageSystemEntry 12 }

cucsStorageSystemFsmTry OBJECT-TYPE
    SYNTAX       Gauge32
    MAX-ACCESS   read-only
    STATUS       current
    DESCRIPTION
        "Cisco UCS storage:System:fsmTry managed object property"
    ::= { cucsStorageSystemEntry 13 }

cucsStorageSystemId OBJECT-TYPE
    SYNTAX       SnmpAdminString
    MAX-ACCESS   read-only
    STATUS       current
    DESCRIPTION
        "Cisco UCS storage:System:id managed object property"
    ::= { cucsStorageSystemEntry 14 }

cucsStorageSystemName OBJECT-TYPE
    SYNTAX       SnmpAdminString
    MAX-ACCESS   read-only
    STATUS       current
    DESCRIPTION
        "Cisco UCS storage:System:name managed object property"
    ::= { cucsStorageSystemEntry 15 }

cucsStorageSystemFsmTable OBJECT-TYPE
    SYNTAX           SEQUENCE OF CucsStorageSystemFsmEntry
    MAX-ACCESS       not-accessible
    STATUS           current
    DESCRIPTION
        "Cisco UCS storage:SystemFsm managed object table"
    ::= { cucsStorageObjects 28 }

cucsStorageSystemFsmEntry OBJECT-TYPE
    SYNTAX           CucsStorageSystemFsmEntry
    MAX-ACCESS       not-accessible
    STATUS           current
    DESCRIPTION
        "Entry for the cucsStorageSystemFsmTable table."
    INDEX { cucsStorageSystemFsmInstanceId }
    ::= { cucsStorageSystemFsmTable 1 }

CucsStorageSystemFsmEntry ::= SEQUENCE {
    cucsStorageSystemFsmInstanceId                                   CucsManagedObjectId,
    cucsStorageSystemFsmDn                                           CucsManagedObjectDn,
    cucsStorageSystemFsmRn                                           SnmpAdminString,
    cucsStorageSystemFsmCompletionTime                               DateAndTime,
    cucsStorageSystemFsmCurrentFsm                                   CucsStorageSystemFsmCurrentFsm,
    cucsStorageSystemFsmDescr                                        SnmpAdminString,
    cucsStorageSystemFsmFsmStatus                                    CucsFsmFsmStageStatus,
    cucsStorageSystemFsmProgress                                     Gauge32,
    cucsStorageSystemFsmRmtErrCode                                   Gauge32,
    cucsStorageSystemFsmRmtErrDescr                                  SnmpAdminString,
    cucsStorageSystemFsmRmtRslt                                      CucsConditionRemoteInvRslt
}

cucsStorageSystemFsmInstanceId OBJECT-TYPE
    SYNTAX       CucsManagedObjectId
    MAX-ACCESS   not-accessible
    STATUS       current
    DESCRIPTION
        "Instance identifier of the managed object."
    ::= { cucsStorageSystemFsmEntry 1 }

cucsStorageSystemFsmDn OBJECT-TYPE
    SYNTAX       CucsManagedObjectDn
    MAX-ACCESS   read-only
    STATUS       current
    DESCRIPTION
        "Cisco UCS storage:SystemFsm:dn managed object property"
    ::= { cucsStorageSystemFsmEntry 2 }

cucsStorageSystemFsmRn OBJECT-TYPE
    SYNTAX       SnmpAdminString
    MAX-ACCESS   read-only
    STATUS       current
    DESCRIPTION
        "Cisco UCS storage:SystemFsm:rn managed object property"
    ::= { cucsStorageSystemFsmEntry 3 }

cucsStorageSystemFsmCompletionTime OBJECT-TYPE
    SYNTAX       DateAndTime
    MAX-ACCESS   read-only
    STATUS       current
    DESCRIPTION
        "Cisco UCS storage:SystemFsm:completionTime managed
        object property"
    ::= { cucsStorageSystemFsmEntry 4 }

cucsStorageSystemFsmCurrentFsm OBJECT-TYPE
    SYNTAX       CucsStorageSystemFsmCurrentFsm
    MAX-ACCESS   read-only
    STATUS       current
    DESCRIPTION
        "Cisco UCS storage:SystemFsm:currentFsm managed object property"
    ::= { cucsStorageSystemFsmEntry 5 }

cucsStorageSystemFsmDescr OBJECT-TYPE
    SYNTAX       SnmpAdminString
    MAX-ACCESS   read-only
    STATUS       current
    DESCRIPTION
        "Cisco UCS storage:SystemFsm:descr managed object property"
    ::= { cucsStorageSystemFsmEntry 6 }

cucsStorageSystemFsmFsmStatus OBJECT-TYPE
    SYNTAX       CucsFsmFsmStageStatus
    MAX-ACCESS   read-only
    STATUS       current
    DESCRIPTION
        "Cisco UCS storage:SystemFsm:fsmStatus managed object property"
    ::= { cucsStorageSystemFsmEntry 7 }

cucsStorageSystemFsmProgress OBJECT-TYPE
    SYNTAX       Gauge32
    MAX-ACCESS   read-only
    STATUS       current
    DESCRIPTION
        "Cisco UCS storage:SystemFsm:progress managed object property"
    ::= { cucsStorageSystemFsmEntry 8 }

cucsStorageSystemFsmRmtErrCode OBJECT-TYPE
    SYNTAX       Gauge32
    MAX-ACCESS   read-only
    STATUS       current
    DESCRIPTION
        "Cisco UCS storage:SystemFsm:rmtErrCode managed object property"
    ::= { cucsStorageSystemFsmEntry 9 }

cucsStorageSystemFsmRmtErrDescr OBJECT-TYPE
    SYNTAX       SnmpAdminString
    MAX-ACCESS   read-only
    STATUS       current
    DESCRIPTION
        "Cisco UCS storage:SystemFsm:rmtErrDescr managed object property"
    ::= { cucsStorageSystemFsmEntry 10 }

cucsStorageSystemFsmRmtRslt OBJECT-TYPE
    SYNTAX       CucsConditionRemoteInvRslt
    MAX-ACCESS   read-only
    STATUS       current
    DESCRIPTION
        "Cisco UCS storage:SystemFsm:rmtRslt managed object property"
    ::= { cucsStorageSystemFsmEntry 11 }

cucsStorageSystemFsmStageTable OBJECT-TYPE
    SYNTAX           SEQUENCE OF CucsStorageSystemFsmStageEntry
    MAX-ACCESS       not-accessible
    STATUS           current
    DESCRIPTION
        "Cisco UCS storage:SystemFsmStage managed object table"
    ::= { cucsStorageObjects 29 }

cucsStorageSystemFsmStageEntry OBJECT-TYPE
    SYNTAX           CucsStorageSystemFsmStageEntry
    MAX-ACCESS       not-accessible
    STATUS           current
    DESCRIPTION
        "Entry for the cucsStorageSystemFsmStageTable table."
    INDEX { cucsStorageSystemFsmStageInstanceId }
    ::= { cucsStorageSystemFsmStageTable 1 }

CucsStorageSystemFsmStageEntry ::= SEQUENCE {
    cucsStorageSystemFsmStageInstanceId                              CucsManagedObjectId,
    cucsStorageSystemFsmStageDn                                      CucsManagedObjectDn,
    cucsStorageSystemFsmStageRn                                      SnmpAdminString,
    cucsStorageSystemFsmStageDescr                                   SnmpAdminString,
    cucsStorageSystemFsmStageLastUpdateTime                          DateAndTime,
    cucsStorageSystemFsmStageName                                    CucsStorageSystemFsmStageName,
    cucsStorageSystemFsmStageOrder                                   Gauge32,
    cucsStorageSystemFsmStageRetry                                   Gauge32,
    cucsStorageSystemFsmStageStageStatus                             CucsFsmFsmStageStatus
}

cucsStorageSystemFsmStageInstanceId OBJECT-TYPE
    SYNTAX       CucsManagedObjectId
    MAX-ACCESS   not-accessible
    STATUS       current
    DESCRIPTION
        "Instance identifier of the managed object."
    ::= { cucsStorageSystemFsmStageEntry 1 }

cucsStorageSystemFsmStageDn OBJECT-TYPE
    SYNTAX       CucsManagedObjectDn
    MAX-ACCESS   read-only
    STATUS       current
    DESCRIPTION
        "Cisco UCS storage:SystemFsmStage:dn managed object property"
    ::= { cucsStorageSystemFsmStageEntry 2 }

cucsStorageSystemFsmStageRn OBJECT-TYPE
    SYNTAX       SnmpAdminString
    MAX-ACCESS   read-only
    STATUS       current
    DESCRIPTION
        "Cisco UCS storage:SystemFsmStage:rn managed object property"
    ::= { cucsStorageSystemFsmStageEntry 3 }

cucsStorageSystemFsmStageDescr OBJECT-TYPE
    SYNTAX       SnmpAdminString
    MAX-ACCESS   read-only
    STATUS       current
    DESCRIPTION
        "Cisco UCS storage:SystemFsmStage:descr managed object property"
    ::= { cucsStorageSystemFsmStageEntry 4 }

cucsStorageSystemFsmStageLastUpdateTime OBJECT-TYPE
    SYNTAX       DateAndTime
    MAX-ACCESS   read-only
    STATUS       current
    DESCRIPTION
        "Cisco UCS storage:SystemFsmStage:lastUpdateTime
        managed object property"
    ::= { cucsStorageSystemFsmStageEntry 5 }

cucsStorageSystemFsmStageName OBJECT-TYPE
    SYNTAX       CucsStorageSystemFsmStageName
    MAX-ACCESS   read-only
    STATUS       current
    DESCRIPTION
        "Cisco UCS storage:SystemFsmStage:name managed object property"
    ::= { cucsStorageSystemFsmStageEntry 6 }

cucsStorageSystemFsmStageOrder OBJECT-TYPE
    SYNTAX       Gauge32
    MAX-ACCESS   read-only
    STATUS       current
    DESCRIPTION
        "Cisco UCS storage:SystemFsmStage:order managed object property"
    ::= { cucsStorageSystemFsmStageEntry 7 }

cucsStorageSystemFsmStageRetry OBJECT-TYPE
    SYNTAX       Gauge32
    MAX-ACCESS   read-only
    STATUS       current
    DESCRIPTION
        "Cisco UCS storage:SystemFsmStage:retry managed object property"
    ::= { cucsStorageSystemFsmStageEntry 8 }

cucsStorageSystemFsmStageStageStatus OBJECT-TYPE
    SYNTAX       CucsFsmFsmStageStatus
    MAX-ACCESS   read-only
    STATUS       current
    DESCRIPTION
        "Cisco UCS storage:SystemFsmStage:stageStatus managed
        object property"
    ::= { cucsStorageSystemFsmStageEntry 9 }

cucsStorageSystemFsmTaskTable OBJECT-TYPE
    SYNTAX           SEQUENCE OF CucsStorageSystemFsmTaskEntry
    MAX-ACCESS       not-accessible
    STATUS           current
    DESCRIPTION
        "Cisco UCS storage:SystemFsmTask managed object table"
    ::= { cucsStorageObjects 30 }

cucsStorageSystemFsmTaskEntry OBJECT-TYPE
    SYNTAX           CucsStorageSystemFsmTaskEntry
    MAX-ACCESS       not-accessible
    STATUS           current
    DESCRIPTION
        "Entry for the cucsStorageSystemFsmTaskTable table."
    INDEX { cucsStorageSystemFsmTaskInstanceId }
    ::= { cucsStorageSystemFsmTaskTable 1 }

CucsStorageSystemFsmTaskEntry ::= SEQUENCE {
    cucsStorageSystemFsmTaskInstanceId                               CucsManagedObjectId,
    cucsStorageSystemFsmTaskDn                                       CucsManagedObjectDn,
    cucsStorageSystemFsmTaskRn                                       SnmpAdminString,
    cucsStorageSystemFsmTaskCompletion                               CucsFsmCompletion,
    cucsStorageSystemFsmTaskFlags                                    CucsFsmFlags,
    cucsStorageSystemFsmTaskItem                                     CucsStorageSystemFsmTaskItem,
    cucsStorageSystemFsmTaskSeqId                                    Gauge32
}

cucsStorageSystemFsmTaskInstanceId OBJECT-TYPE
    SYNTAX       CucsManagedObjectId
    MAX-ACCESS   not-accessible
    STATUS       current
    DESCRIPTION
        "Instance identifier of the managed object."
    ::= { cucsStorageSystemFsmTaskEntry 1 }

cucsStorageSystemFsmTaskDn OBJECT-TYPE
    SYNTAX       CucsManagedObjectDn
    MAX-ACCESS   read-only
    STATUS       current
    DESCRIPTION
        "Cisco UCS storage:SystemFsmTask:dn managed object property"
    ::= { cucsStorageSystemFsmTaskEntry 2 }

cucsStorageSystemFsmTaskRn OBJECT-TYPE
    SYNTAX       SnmpAdminString
    MAX-ACCESS   read-only
    STATUS       current
    DESCRIPTION
        "Cisco UCS storage:SystemFsmTask:rn managed object property"
    ::= { cucsStorageSystemFsmTaskEntry 3 }

cucsStorageSystemFsmTaskCompletion OBJECT-TYPE
    SYNTAX       CucsFsmCompletion
    MAX-ACCESS   read-only
    STATUS       current
    DESCRIPTION
        "Cisco UCS storage:SystemFsmTask:completion managed
        object property"
    ::= { cucsStorageSystemFsmTaskEntry 4 }

cucsStorageSystemFsmTaskFlags OBJECT-TYPE
    SYNTAX       CucsFsmFlags
    MAX-ACCESS   read-only
    STATUS       current
    DESCRIPTION
        "Cisco UCS storage:SystemFsmTask:flags managed object property"
    ::= { cucsStorageSystemFsmTaskEntry 5 }

cucsStorageSystemFsmTaskItem OBJECT-TYPE
    SYNTAX       CucsStorageSystemFsmTaskItem
    MAX-ACCESS   read-only
    STATUS       current
    DESCRIPTION
        "Cisco UCS storage:SystemFsmTask:item managed object property"
    ::= { cucsStorageSystemFsmTaskEntry 6 }

cucsStorageSystemFsmTaskSeqId OBJECT-TYPE
    SYNTAX       Gauge32
    MAX-ACCESS   read-only
    STATUS       current
    DESCRIPTION
        "Cisco UCS storage:SystemFsmTask:seqId managed object property"
    ::= { cucsStorageSystemFsmTaskEntry 7 }

cucsStorageTransportableFlashModuleTable OBJECT-TYPE
    SYNTAX           SEQUENCE OF CucsStorageTransportableFlashModuleEntry
    MAX-ACCESS       not-accessible
    STATUS           current
    DESCRIPTION
        "Cisco UCS storage:TransportableFlashModule managed object table"
    ::= { cucsStorageObjects 33 }

cucsStorageTransportableFlashModuleEntry OBJECT-TYPE
    SYNTAX           CucsStorageTransportableFlashModuleEntry
    MAX-ACCESS       not-accessible
    STATUS           current
    DESCRIPTION
        "Entry for the cucsStorageTransportableFlashModuleTable table."
    INDEX { cucsStorageTransportableFlashModuleInstanceId }
    ::= { cucsStorageTransportableFlashModuleTable 1 }

CucsStorageTransportableFlashModuleEntry ::= SEQUENCE {
    cucsStorageTransportableFlashModuleInstanceId                    CucsManagedObjectId,
    cucsStorageTransportableFlashModuleDn                            CucsManagedObjectDn,
    cucsStorageTransportableFlashModuleRn                            SnmpAdminString,
    cucsStorageTransportableFlashModuleBlockSize                     Gauge32,
    cucsStorageTransportableFlashModuleConnectionProtocol            CucsStorageConnectionProtocol,
    cucsStorageTransportableFlashModuleId                            Gauge32,
    cucsStorageTransportableFlashModuleModel                         SnmpAdminString,
    cucsStorageTransportableFlashModuleNumberOfBlocks                Unsigned64,
    cucsStorageTransportableFlashModuleOperQualifierReason           SnmpAdminString,
    cucsStorageTransportableFlashModuleOperability                   CucsEquipmentOperability,
    cucsStorageTransportableFlashModulePresence                      CucsEquipmentPresence,
    cucsStorageTransportableFlashModuleRevision                      SnmpAdminString,
    cucsStorageTransportableFlashModuleSerial                        SnmpAdminString,
    cucsStorageTransportableFlashModuleSize                          Unsigned64,
    cucsStorageTransportableFlashModuleVendor                        SnmpAdminString
}

cucsStorageTransportableFlashModuleInstanceId OBJECT-TYPE
    SYNTAX       CucsManagedObjectId
    MAX-ACCESS   not-accessible
    STATUS       current
    DESCRIPTION
        "Instance identifier of the managed object."
    ::= { cucsStorageTransportableFlashModuleEntry 1 }

cucsStorageTransportableFlashModuleDn OBJECT-TYPE
    SYNTAX       CucsManagedObjectDn
    MAX-ACCESS   read-only
    STATUS       current
    DESCRIPTION
        "Cisco UCS storage:TransportableFlashModule:dn
        managed object property"
    ::= { cucsStorageTransportableFlashModuleEntry 2 }

cucsStorageTransportableFlashModuleRn OBJECT-TYPE
    SYNTAX       SnmpAdminString
    MAX-ACCESS   read-only
    STATUS       current
    DESCRIPTION
        "Cisco UCS storage:TransportableFlashModule:rn
        managed object property"
    ::= { cucsStorageTransportableFlashModuleEntry 3 }

cucsStorageTransportableFlashModuleBlockSize OBJECT-TYPE
    SYNTAX       Gauge32
    MAX-ACCESS   read-only
    STATUS       current
    DESCRIPTION
        "Cisco UCS storage:TransportableFlashModule:blockSize
        managed object property"
    ::= { cucsStorageTransportableFlashModuleEntry 4 }

cucsStorageTransportableFlashModuleConnectionProtocol OBJECT-TYPE
    SYNTAX       CucsStorageConnectionProtocol
    MAX-ACCESS   read-only
    STATUS       current
    DESCRIPTION
        "Cisco UCS storage:TransportableFlashModule:connectionProtocol
        managed object property"
    ::= { cucsStorageTransportableFlashModuleEntry 5 }

cucsStorageTransportableFlashModuleId OBJECT-TYPE
    SYNTAX       Gauge32
    MAX-ACCESS   read-only
    STATUS       current
    DESCRIPTION
        "Cisco UCS storage:TransportableFlashModule:id
        managed object property"
    ::= { cucsStorageTransportableFlashModuleEntry 6 }

cucsStorageTransportableFlashModuleModel OBJECT-TYPE
    SYNTAX       SnmpAdminString
    MAX-ACCESS   read-only
    STATUS       current
    DESCRIPTION
        "Cisco UCS storage:TransportableFlashModule:model
        managed object property"
    ::= { cucsStorageTransportableFlashModuleEntry 7 }

cucsStorageTransportableFlashModuleNumberOfBlocks OBJECT-TYPE
    SYNTAX       Unsigned64
    MAX-ACCESS   read-only
    STATUS       current
    DESCRIPTION
        "Cisco UCS storage:TransportableFlashModule:numberOfBlocks
        managed object property"
    ::= { cucsStorageTransportableFlashModuleEntry 8 }

cucsStorageTransportableFlashModuleOperQualifierReason OBJECT-TYPE
    SYNTAX       SnmpAdminString
    MAX-ACCESS   read-only
    STATUS       current
    DESCRIPTION
        "Cisco UCS storage:TransportableFlashModule:operQualifierReason
        managed object property"
    ::= { cucsStorageTransportableFlashModuleEntry 9 }

cucsStorageTransportableFlashModuleOperability OBJECT-TYPE
    SYNTAX       CucsEquipmentOperability
    MAX-ACCESS   read-only
    STATUS       current
    DESCRIPTION
        "Cisco UCS storage:TransportableFlashModule:operability
        managed object property"
    ::= { cucsStorageTransportableFlashModuleEntry 10 }

cucsStorageTransportableFlashModulePresence OBJECT-TYPE
    SYNTAX       CucsEquipmentPresence
    MAX-ACCESS   read-only
    STATUS       current
    DESCRIPTION
        "Cisco UCS storage:TransportableFlashModule:presence
        managed object property"
    ::= { cucsStorageTransportableFlashModuleEntry 11 }

cucsStorageTransportableFlashModuleRevision OBJECT-TYPE
    SYNTAX       SnmpAdminString
    MAX-ACCESS   read-only
    STATUS       current
    DESCRIPTION
        "Cisco UCS storage:TransportableFlashModule:revision
        managed object property"
    ::= { cucsStorageTransportableFlashModuleEntry 12 }

cucsStorageTransportableFlashModuleSerial OBJECT-TYPE
    SYNTAX       SnmpAdminString
    MAX-ACCESS   read-only
    STATUS       current
    DESCRIPTION
        "Cisco UCS storage:TransportableFlashModule:serial
        managed object property"
    ::= { cucsStorageTransportableFlashModuleEntry 13 }

cucsStorageTransportableFlashModuleSize OBJECT-TYPE
    SYNTAX       Unsigned64
    MAX-ACCESS   read-only
    STATUS       current
    DESCRIPTION
        "Cisco UCS storage:TransportableFlashModule:size
        managed object property"
    ::= { cucsStorageTransportableFlashModuleEntry 14 }

cucsStorageTransportableFlashModuleVendor OBJECT-TYPE
    SYNTAX       SnmpAdminString
    MAX-ACCESS   read-only
    STATUS       current
    DESCRIPTION
        "Cisco UCS storage:TransportableFlashModule:vendor
        managed object property"
    ::= { cucsStorageTransportableFlashModuleEntry 15 }

cucsStorageVirtualDriveTable OBJECT-TYPE
    SYNTAX           SEQUENCE OF CucsStorageVirtualDriveEntry
    MAX-ACCESS       not-accessible
    STATUS           current
    DESCRIPTION
        "Cisco UCS storage:VirtualDrive managed object table"
    ::= { cucsStorageObjects 31 }

cucsStorageVirtualDriveEntry OBJECT-TYPE
    SYNTAX           CucsStorageVirtualDriveEntry
    MAX-ACCESS       not-accessible
    STATUS           current
    DESCRIPTION
        "Entry for the cucsStorageVirtualDriveTable table."
    INDEX { cucsStorageVirtualDriveInstanceId }
    ::= { cucsStorageVirtualDriveTable 1 }

CucsStorageVirtualDriveEntry ::= SEQUENCE {
    cucsStorageVirtualDriveInstanceId                                CucsManagedObjectId,
    cucsStorageVirtualDriveDn                                        CucsManagedObjectDn,
    cucsStorageVirtualDriveRn                                        SnmpAdminString,
    cucsStorageVirtualDriveBlockSize                                 Gauge32,
    cucsStorageVirtualDriveConnectionProtocol                        CucsStorageConnectionProtocol,
    cucsStorageVirtualDriveId                                        Gauge32,
    cucsStorageVirtualDriveModel                                     SnmpAdminString,
    cucsStorageVirtualDriveNumberOfBlocks                            Unsigned64,
    cucsStorageVirtualDriveOperQualifierReason                       SnmpAdminString,
    cucsStorageVirtualDriveOperability                               CucsEquipmentOperability,
    cucsStorageVirtualDrivePresence                                  CucsEquipmentPresence,
    cucsStorageVirtualDriveRevision                                  SnmpAdminString,
    cucsStorageVirtualDriveSerial                                    SnmpAdminString,
    cucsStorageVirtualDriveSize                                      Unsigned64,
    cucsStorageVirtualDriveType                                      CucsStorageLunType,
    cucsStorageVirtualDriveVendor                                    SnmpAdminString
}

cucsStorageVirtualDriveInstanceId OBJECT-TYPE
    SYNTAX       CucsManagedObjectId
    MAX-ACCESS   not-accessible
    STATUS       current
    DESCRIPTION
        "Instance identifier of the managed object."
    ::= { cucsStorageVirtualDriveEntry 1 }

cucsStorageVirtualDriveDn OBJECT-TYPE
    SYNTAX       CucsManagedObjectDn
    MAX-ACCESS   read-only
    STATUS       current
    DESCRIPTION
        "Cisco UCS storage:VirtualDrive:dn managed object property"
    ::= { cucsStorageVirtualDriveEntry 2 }

cucsStorageVirtualDriveRn OBJECT-TYPE
    SYNTAX       SnmpAdminString
    MAX-ACCESS   read-only
    STATUS       current
    DESCRIPTION
        "Cisco UCS storage:VirtualDrive:rn managed object property"
    ::= { cucsStorageVirtualDriveEntry 3 }

cucsStorageVirtualDriveBlockSize OBJECT-TYPE
    SYNTAX       Gauge32
    MAX-ACCESS   read-only
    STATUS       current
    DESCRIPTION
        "Cisco UCS storage:VirtualDrive:blockSize managed object property"
    ::= { cucsStorageVirtualDriveEntry 4 }

cucsStorageVirtualDriveConnectionProtocol OBJECT-TYPE
    SYNTAX       CucsStorageConnectionProtocol
    MAX-ACCESS   read-only
    STATUS       current
    DESCRIPTION
        "Cisco UCS storage:VirtualDrive:connectionProtocol
        managed object property"
    ::= { cucsStorageVirtualDriveEntry 5 }

cucsStorageVirtualDriveId OBJECT-TYPE
    SYNTAX       Gauge32
    MAX-ACCESS   read-only
    STATUS       current
    DESCRIPTION
        "Cisco UCS storage:VirtualDrive:id managed object property"
    ::= { cucsStorageVirtualDriveEntry 6 }

cucsStorageVirtualDriveModel OBJECT-TYPE
    SYNTAX       SnmpAdminString
    MAX-ACCESS   read-only
    STATUS       current
    DESCRIPTION
        "Cisco UCS storage:VirtualDrive:model managed object property"
    ::= { cucsStorageVirtualDriveEntry 7 }

cucsStorageVirtualDriveNumberOfBlocks OBJECT-TYPE
    SYNTAX       Unsigned64
    MAX-ACCESS   read-only
    STATUS       current
    DESCRIPTION
        "Cisco UCS storage:VirtualDrive:numberOfBlocks
        managed object property"
    ::= { cucsStorageVirtualDriveEntry 8 }

cucsStorageVirtualDriveOperQualifierReason OBJECT-TYPE
    SYNTAX       SnmpAdminString
    MAX-ACCESS   read-only
    STATUS       current
    DESCRIPTION
        "Cisco UCS storage:VirtualDrive:operQualifierReason
        managed object property"
    ::= { cucsStorageVirtualDriveEntry 9 }

cucsStorageVirtualDriveOperability OBJECT-TYPE
    SYNTAX       CucsEquipmentOperability
    MAX-ACCESS   read-only
    STATUS       current
    DESCRIPTION
        "Cisco UCS storage:VirtualDrive:operability managed
        object property"
    ::= { cucsStorageVirtualDriveEntry 10 }

cucsStorageVirtualDrivePresence OBJECT-TYPE
    SYNTAX       CucsEquipmentPresence
    MAX-ACCESS   read-only
    STATUS       current
    DESCRIPTION
        "Cisco UCS storage:VirtualDrive:presence managed object property"
    ::= { cucsStorageVirtualDriveEntry 11 }

cucsStorageVirtualDriveRevision OBJECT-TYPE
    SYNTAX       SnmpAdminString
    MAX-ACCESS   read-only
    STATUS       current
    DESCRIPTION
        "Cisco UCS storage:VirtualDrive:revision managed object property"
    ::= { cucsStorageVirtualDriveEntry 12 }

cucsStorageVirtualDriveSerial OBJECT-TYPE
    SYNTAX       SnmpAdminString
    MAX-ACCESS   read-only
    STATUS       current
    DESCRIPTION
        "Cisco UCS storage:VirtualDrive:serial managed object property"
    ::= { cucsStorageVirtualDriveEntry 13 }

cucsStorageVirtualDriveSize OBJECT-TYPE
    SYNTAX       Unsigned64
    MAX-ACCESS   read-only
    STATUS       current
    DESCRIPTION
        "Cisco UCS storage:VirtualDrive:size managed object property"
    ::= { cucsStorageVirtualDriveEntry 14 }

cucsStorageVirtualDriveType OBJECT-TYPE
    SYNTAX       CucsStorageLunType
    MAX-ACCESS   read-only
    STATUS       current
    DESCRIPTION
        "Cisco UCS storage:VirtualDrive:type managed object property"
    ::= { cucsStorageVirtualDriveEntry 15 }

cucsStorageVirtualDriveVendor OBJECT-TYPE
    SYNTAX       SnmpAdminString
    MAX-ACCESS   read-only
    STATUS       current
    DESCRIPTION
        "Cisco UCS storage:VirtualDrive:vendor managed object property"
    ::= { cucsStorageVirtualDriveEntry 16 }

cucsStorageVsanRefTable OBJECT-TYPE
    SYNTAX           SEQUENCE OF CucsStorageVsanRefEntry
    MAX-ACCESS       not-accessible
    STATUS           current
    DESCRIPTION
        "Cisco UCS storage:VsanRef managed object table"
    ::= { cucsStorageObjects 32 }

cucsStorageVsanRefEntry OBJECT-TYPE
    SYNTAX           CucsStorageVsanRefEntry
    MAX-ACCESS       not-accessible
    STATUS           current
    DESCRIPTION
        "Entry for the cucsStorageVsanRefTable table."
    INDEX { cucsStorageVsanRefInstanceId }
    ::= { cucsStorageVsanRefTable 1 }

CucsStorageVsanRefEntry ::= SEQUENCE {
    cucsStorageVsanRefInstanceId                                     CucsManagedObjectId,
    cucsStorageVsanRefDn                                             CucsManagedObjectDn,
    cucsStorageVsanRefRn                                             SnmpAdminString,
    cucsStorageVsanRefConfigQualifier                                CucsVnicConfigIssues,
    cucsStorageVsanRefName                                           SnmpAdminString,
    cucsStorageVsanRefOperVnetDn                                     SnmpAdminString,
    cucsStorageVsanRefOperVnetName                                   SnmpAdminString,
    cucsStorageVsanRefSwitchId                                       CucsStorageVsanRefSwitchId,
    cucsStorageVsanRefVnet                                           Gauge32,
    cucsStorageVsanRefZoningState                                    CucsFabricZoningState
}

cucsStorageVsanRefInstanceId OBJECT-TYPE
    SYNTAX       CucsManagedObjectId
    MAX-ACCESS   not-accessible
    STATUS       current
    DESCRIPTION
        "Instance identifier of the managed object."
    ::= { cucsStorageVsanRefEntry 1 }

cucsStorageVsanRefDn OBJECT-TYPE
    SYNTAX       CucsManagedObjectDn
    MAX-ACCESS   read-only
    STATUS       current
    DESCRIPTION
        "Cisco UCS storage:VsanRef:dn managed object property"
    ::= { cucsStorageVsanRefEntry 2 }

cucsStorageVsanRefRn OBJECT-TYPE
    SYNTAX       SnmpAdminString
    MAX-ACCESS   read-only
    STATUS       current
    DESCRIPTION
        "Cisco UCS storage:VsanRef:rn managed object property"
    ::= { cucsStorageVsanRefEntry 3 }

cucsStorageVsanRefConfigQualifier OBJECT-TYPE
    SYNTAX       CucsVnicConfigIssues
    MAX-ACCESS   read-only
    STATUS       current
    DESCRIPTION
        "Cisco UCS storage:VsanRef:configQualifier managed
        object property"
    ::= { cucsStorageVsanRefEntry 4 }

cucsStorageVsanRefName OBJECT-TYPE
    SYNTAX       SnmpAdminString
    MAX-ACCESS   read-only
    STATUS       current
    DESCRIPTION
        "Cisco UCS storage:VsanRef:name managed object property"
    ::= { cucsStorageVsanRefEntry 5 }

cucsStorageVsanRefOperVnetDn OBJECT-TYPE
    SYNTAX       SnmpAdminString
    MAX-ACCESS   read-only
    STATUS       current
    DESCRIPTION
        "Cisco UCS storage:VsanRef:operVnetDn managed object property"
    ::= { cucsStorageVsanRefEntry 6 }

cucsStorageVsanRefOperVnetName OBJECT-TYPE
    SYNTAX       SnmpAdminString
    MAX-ACCESS   read-only
    STATUS       current
    DESCRIPTION
        "Cisco UCS storage:VsanRef:operVnetName managed object property"
    ::= { cucsStorageVsanRefEntry 7 }

cucsStorageVsanRefSwitchId OBJECT-TYPE
    SYNTAX       CucsStorageVsanRefSwitchId
    MAX-ACCESS   read-only
    STATUS       current
    DESCRIPTION
        "Cisco UCS storage:VsanRef:switchId managed object property"
    ::= { cucsStorageVsanRefEntry 8 }

cucsStorageVsanRefVnet OBJECT-TYPE
    SYNTAX       Gauge32
    MAX-ACCESS   read-only
    STATUS       current
    DESCRIPTION
        "Cisco UCS storage:VsanRef:vnet managed object property"
    ::= { cucsStorageVsanRefEntry 9 }

cucsStorageVsanRefZoningState OBJECT-TYPE
    SYNTAX       CucsFabricZoningState
    MAX-ACCESS   read-only
    STATUS       current
    DESCRIPTION
        "Cisco UCS storage:VsanRef:zoningState managed object property"
    ::= { cucsStorageVsanRefEntry 10 }

END
