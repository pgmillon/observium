-- *********************************************************************
-- CISCO-UNIFIED-COMPUTING-EQUIPMENT-MIB.my
-- 
-- MIB representation of the Cisco Unified Computing System
-- EQUIPMENT management information model package
-- 
-- Created June 2013 by Charles Bullis
-- 
-- Copyright (c) 2005-2013 Cisco Systems, Inc. All rights reserved.
-- 
-- *********************************************************************

CISCO-UNIFIED-COMPUTING-EQUIPMENT-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoUnifiedComputingMIBObjects,
    CucsManagedObjectId,
    CucsManagedObjectDn
        FROM CISCO-UNIFIED-COMPUTING-MIB
    CucsComputeLinkAggregationCap,
    CucsComputeMemoryUnitConstraintType,
    CucsConditionRemoteInvRslt,
    CucsConditionSeverity,
    CucsEquipmentAdminPowerState,
    CucsEquipmentAirflowDirection,
    CucsEquipmentAsicType,
    CucsEquipmentBeaconLedFsmCurrentFsm,
    CucsEquipmentBeaconLedFsmStageName,
    CucsEquipmentBeaconLedFsmTaskItem,
    CucsEquipmentBeaconLedState,
    CucsEquipmentBiosUpdateMethod,
    CucsEquipmentChassisAdminState,
    CucsEquipmentChassisConfigProgressIndicator,
    CucsEquipmentChassisConfigState,
    CucsEquipmentChassisFsmCurrentFsm,
    CucsEquipmentChassisFsmStageName,
    CucsEquipmentChassisFsmTaskItem,
    CucsEquipmentChassisId,
    CucsEquipmentChassisIssues,
    CucsEquipmentChassisPowerOperState,
    CucsEquipmentChassisStatsHistThresholded,
    CucsEquipmentChassisStatsThresholded,
    CucsEquipmentCommStatus,
    CucsEquipmentConnectionStatus,
    CucsEquipmentDiscoveryCapOperPowerRequirement,
    CucsEquipmentDiscoveryState,
    CucsEquipmentFanId,
    CucsEquipmentFanModule,
    CucsEquipmentFanModuleId,
    CucsEquipmentFanModuleStatsHistThresholded,
    CucsEquipmentFanModuleStatsThresholded,
    CucsEquipmentFanModuleTray,
    CucsEquipmentFanStatsHistThresholded,
    CucsEquipmentFanStatsThresholded,
    CucsEquipmentFanTray,
    CucsEquipmentFexCapProviderRole,
    CucsEquipmentFexEnvStatsHistThresholded,
    CucsEquipmentFexEnvStatsThresholded,
    CucsEquipmentFexFsmCurrentFsm,
    CucsEquipmentFexFsmStageName,
    CucsEquipmentFexFsmTaskItem,
    CucsEquipmentFexId,
    CucsEquipmentFexPowerSummaryHistThresholded,
    CucsEquipmentFexPowerSummaryThresholded,
    CucsEquipmentFexPsuInputStatsHistThresholded,
    CucsEquipmentFexPsuInputStatsThresholded,
    CucsEquipmentHealthLedState,
    CucsEquipmentIOCardFsmCurrentFsm,
    CucsEquipmentIOCardFsmStageName,
    CucsEquipmentIOCardFsmTaskItem,
    CucsEquipmentIOCardId,
    CucsEquipmentIOCardIssues,
    CucsEquipmentIOCardStatsHistThresholded,
    CucsEquipmentIOCardStatsThresholded,
    CucsEquipmentInternalFanType,
    CucsEquipmentIsSupported,
    CucsEquipmentLedColor,
    CucsEquipmentLedLocatorState,
    CucsEquipmentLedOperState,
    CucsEquipmentLocatorLedFsmCurrentFsm,
    CucsEquipmentLocatorLedFsmStageName,
    CucsEquipmentLocatorLedFsmTaskItem,
    CucsEquipmentMemoryUnitDiscoveryModifierAction,
    CucsEquipmentMethod,
    CucsEquipmentNetworkElementFanStatsHistThresholded,
    CucsEquipmentNetworkElementFanStatsThresholded,
    CucsEquipmentOperability,
    CucsEquipmentPOSTRecoverability,
    CucsEquipmentPictureType,
    CucsEquipmentPowerState,
    CucsEquipmentPresence,
    CucsEquipmentPsuId,
    CucsEquipmentPsuInputStatsHistThresholded,
    CucsEquipmentPsuInputStatsThresholded,
    CucsEquipmentPsuOutputStatsHistThresholded,
    CucsEquipmentPsuOutputStatsThresholded,
    CucsEquipmentPsuStateQualifier,
    CucsEquipmentPsuStatsHistThresholded,
    CucsEquipmentPsuStatsThresholded,
    CucsEquipmentPsuType,
    CucsEquipmentRackUnitFanStatsHistThresholded,
    CucsEquipmentRackUnitFanStatsThresholded,
    CucsEquipmentRackUnitPsuStatsHistThresholded,
    CucsEquipmentRackUnitPsuStatsThresholded,
    CucsEquipmentRemovalConditions,
    CucsEquipmentResetOn,
    CucsEquipmentSecureBios,
    CucsEquipmentSensorThresholdStatus,
    CucsEquipmentSlotArrayLocation,
    CucsEquipmentSlotArrayOrientation,
    CucsEquipmentSlotArraySelector,
    CucsEquipmentSlotSpanOrientation,
    CucsEquipmentStorageMethod,
    CucsEquipmentUnifiedPortAlgorithm,
    CucsEquipmentXcvrId,
    CucsEquipmentXcvrType,
    CucsFsmCompletion,
    CucsFsmFlags,
    CucsFsmFsmStageStatus,
    CucsLicenseState,
    CucsMgmtUpgradeStatus,
    CucsNetworkSide,
    CucsNetworkSwitchId,
    CucsPolicyPolicyOwner,
    CucsPortEthSpeed,
    CucsPortGroupType,
    CucsPortSpeed,
    CucsStorageControllerForm,
    CucsStorageLocalDiskMode,
    CucsStorageTechnology
        FROM CISCO-UNIFIED-COMPUTING-TC-MIB;

cucsEquipmentObjects MODULE-IDENTITY
    LAST-UPDATED    "201306240000Z"
    ORGANIZATION    "Cisco Systems Inc."
    CONTACT-INFO
        "Cisco Systems
        Customer Service
        
        Postal: 170 W Tasman Drive
        San Jose, CA  95134
        USA
        
        Tel: +1 800 553 -NETS
        
        E-mail: cs-san@cisco.com, cs-lan-switch-snmp@cisco.com"
    DESCRIPTION
        "MIB representation of the Cisco Unified Computing System
        EQUIPMENT management information model package"
    ::= { ciscoUnifiedComputingMIBObjects 15 }

cucsEquipmentAdaptorConnDefTable OBJECT-TYPE
    SYNTAX           SEQUENCE OF CucsEquipmentAdaptorConnDefEntry
    MAX-ACCESS       not-accessible
    STATUS           current
    DESCRIPTION
        "Cisco UCS equipment:AdaptorConnDef managed object table"
    ::= { cucsEquipmentObjects 95 }

cucsEquipmentAdaptorConnDefEntry OBJECT-TYPE
    SYNTAX           CucsEquipmentAdaptorConnDefEntry
    MAX-ACCESS       not-accessible
    STATUS           current
    DESCRIPTION
        "Entry for the cucsEquipmentAdaptorConnDefTable table."
    INDEX { cucsEquipmentAdaptorConnDefInstanceId }
    ::= { cucsEquipmentAdaptorConnDefTable 1 }

CucsEquipmentAdaptorConnDefEntry ::= SEQUENCE {
    cucsEquipmentAdaptorConnDefInstanceId                            CucsManagedObjectId,
    cucsEquipmentAdaptorConnDefDn                                    CucsManagedObjectDn,
    cucsEquipmentAdaptorConnDefRn                                    SnmpAdminString,
    cucsEquipmentAdaptorConnDefAdaptorEp                             Gauge32,
    cucsEquipmentAdaptorConnDefDescr                                 SnmpAdminString,
    cucsEquipmentAdaptorConnDefIntId                                 SnmpAdminString,
    cucsEquipmentAdaptorConnDefIomEp                                 Gauge32,
    cucsEquipmentAdaptorConnDefName                                  SnmpAdminString,
    cucsEquipmentAdaptorConnDefPolicyLevel                           Gauge32,
    cucsEquipmentAdaptorConnDefPolicyOwner                           CucsPolicyPolicyOwner
}

cucsEquipmentAdaptorConnDefInstanceId OBJECT-TYPE
    SYNTAX       CucsManagedObjectId
    MAX-ACCESS   not-accessible
    STATUS       current
    DESCRIPTION
        "Instance identifier of the managed object."
    ::= { cucsEquipmentAdaptorConnDefEntry 1 }

cucsEquipmentAdaptorConnDefDn OBJECT-TYPE
    SYNTAX       CucsManagedObjectDn
    MAX-ACCESS   read-only
    STATUS       current
    DESCRIPTION
        "Cisco UCS equipment:AdaptorConnDef:dn managed object property"
    ::= { cucsEquipmentAdaptorConnDefEntry 2 }

cucsEquipmentAdaptorConnDefRn OBJECT-TYPE
    SYNTAX       SnmpAdminString
    MAX-ACCESS   read-only
    STATUS       current
    DESCRIPTION
        "Cisco UCS equipment:AdaptorConnDef:rn managed object property"
    ::= { cucsEquipmentAdaptorConnDefEntry 3 }

cucsEquipmentAdaptorConnDefAdaptorEp OBJECT-TYPE
    SYNTAX       Gauge32
    MAX-ACCESS   read-only
    STATUS       current
    DESCRIPTION
        "Cisco UCS equipment:AdaptorConnDef:adaptorEp managed
        object property"
    ::= { cucsEquipmentAdaptorConnDefEntry 4 }

cucsEquipmentAdaptorConnDefDescr OBJECT-TYPE
    SYNTAX       SnmpAdminString
    MAX-ACCESS   read-only
    STATUS       current
    DESCRIPTION
        "Cisco UCS equipment:AdaptorConnDef:descr managed object property"
    ::= { cucsEquipmentAdaptorConnDefEntry 5 }

cucsEquipmentAdaptorConnDefIntId OBJECT-TYPE
    SYNTAX       SnmpAdminString
    MAX-ACCESS   read-only
    STATUS       current
    DESCRIPTION
        "Cisco UCS equipment:AdaptorConnDef:intId managed object property"
    ::= { cucsEquipmentAdaptorConnDefEntry 6 }

cucsEquipmentAdaptorConnDefIomEp OBJECT-TYPE
    SYNTAX       Gauge32
    MAX-ACCESS   read-only
    STATUS       current
    DESCRIPTION
        "Cisco UCS equipment:AdaptorConnDef:iomEp managed object property"
    ::= { cucsEquipmentAdaptorConnDefEntry 7 }

cucsEquipmentAdaptorConnDefName OBJECT-TYPE
    SYNTAX       SnmpAdminString
    MAX-ACCESS   read-only
    STATUS       current
    DESCRIPTION
        "Cisco UCS equipment:AdaptorConnDef:name managed object property"
    ::= { cucsEquipmentAdaptorConnDefEntry 8 }

cucsEquipmentAdaptorConnDefPolicyLevel OBJECT-TYPE
    SYNTAX       Gauge32
    MAX-ACCESS   read-only
    STATUS       current
    DESCRIPTION
        "Cisco UCS equipment:AdaptorConnDef:policyLevel
        managed object property"
    ::= { cucsEquipmentAdaptorConnDefEntry 9 }

cucsEquipmentAdaptorConnDefPolicyOwner OBJECT-TYPE
    SYNTAX       CucsPolicyPolicyOwner
    MAX-ACCESS   read-only
    STATUS       current
    DESCRIPTION
        "Cisco UCS equipment:AdaptorConnDef:policyOwner
        managed object property"
    ::= { cucsEquipmentAdaptorConnDefEntry 10 }

cucsEquipmentAdaptorDefTable OBJECT-TYPE
    SYNTAX           SEQUENCE OF CucsEquipmentAdaptorDefEntry
    MAX-ACCESS       not-accessible
    STATUS           current
    DESCRIPTION
        "Cisco UCS equipment:AdaptorDef managed object table"
    ::= { cucsEquipmentObjects 1 }

cucsEquipmentAdaptorDefEntry OBJECT-TYPE
    SYNTAX           CucsEquipmentAdaptorDefEntry
    MAX-ACCESS       not-accessible
    STATUS           current
    DESCRIPTION
        "Entry for the cucsEquipmentAdaptorDefTable table."
    INDEX { cucsEquipmentAdaptorDefInstanceId }
    ::= { cucsEquipmentAdaptorDefTable 1 }

CucsEquipmentAdaptorDefEntry ::= SEQUENCE {
    cucsEquipmentAdaptorDefInstanceId                                CucsManagedObjectId,
    cucsEquipmentAdaptorDefDn                                        CucsManagedObjectDn,
    cucsEquipmentAdaptorDefRn                                        SnmpAdminString,
    cucsEquipmentAdaptorDefDescr                                     SnmpAdminString,
    cucsEquipmentAdaptorDefEthernetPortSpeed                         Unsigned64,
    cucsEquipmentAdaptorDefFibreChannelPortSpeed                     Unsigned64,
    cucsEquipmentAdaptorDefIntId                                     SnmpAdminString,
    cucsEquipmentAdaptorDefName                                      SnmpAdminString,
    cucsEquipmentAdaptorDefPolicyLevel                               Gauge32,
    cucsEquipmentAdaptorDefPolicyOwner                               CucsPolicyPolicyOwner
}

cucsEquipmentAdaptorDefInstanceId OBJECT-TYPE
    SYNTAX       CucsManagedObjectId
    MAX-ACCESS   not-accessible
    STATUS       current
    DESCRIPTION
        "Instance identifier of the managed object."
    ::= { cucsEquipmentAdaptorDefEntry 1 }

cucsEquipmentAdaptorDefDn OBJECT-TYPE
    SYNTAX       CucsManagedObjectDn
    MAX-ACCESS   read-only
    STATUS       current
    DESCRIPTION
        "Cisco UCS equipment:AdaptorDef:dn managed object property"
    ::= { cucsEquipmentAdaptorDefEntry 2 }

cucsEquipmentAdaptorDefRn OBJECT-TYPE
    SYNTAX       SnmpAdminString
    MAX-ACCESS   read-only
    STATUS       current
    DESCRIPTION
        "Cisco UCS equipment:AdaptorDef:rn managed object property"
    ::= { cucsEquipmentAdaptorDefEntry 3 }

cucsEquipmentAdaptorDefDescr OBJECT-TYPE
    SYNTAX       SnmpAdminString
    MAX-ACCESS   read-only
    STATUS       current
    DESCRIPTION
        "Cisco UCS equipment:AdaptorDef:descr managed object property"
    ::= { cucsEquipmentAdaptorDefEntry 4 }

cucsEquipmentAdaptorDefEthernetPortSpeed OBJECT-TYPE
    SYNTAX       Unsigned64
    MAX-ACCESS   read-only
    STATUS       current
    DESCRIPTION
        "Cisco UCS equipment:AdaptorDef:ethernetPortSpeed
        managed object property"
    ::= { cucsEquipmentAdaptorDefEntry 5 }

cucsEquipmentAdaptorDefFibreChannelPortSpeed OBJECT-TYPE
    SYNTAX       Unsigned64
    MAX-ACCESS   read-only
    STATUS       current
    DESCRIPTION
        "Cisco UCS equipment:AdaptorDef:fibreChannelPortSpeed
        managed object property"
    ::= { cucsEquipmentAdaptorDefEntry 6 }

cucsEquipmentAdaptorDefIntId OBJECT-TYPE
    SYNTAX       SnmpAdminString
    MAX-ACCESS   read-only
    STATUS       current
    DESCRIPTION
        "Cisco UCS equipment:AdaptorDef:intId managed object property"
    ::= { cucsEquipmentAdaptorDefEntry 7 }

cucsEquipmentAdaptorDefName OBJECT-TYPE
    SYNTAX       SnmpAdminString
    MAX-ACCESS   read-only
    STATUS       current
    DESCRIPTION
        "Cisco UCS equipment:AdaptorDef:name managed object property"
    ::= { cucsEquipmentAdaptorDefEntry 8 }

cucsEquipmentAdaptorDefPolicyLevel OBJECT-TYPE
    SYNTAX       Gauge32
    MAX-ACCESS   read-only
    STATUS       current
    DESCRIPTION
        "Cisco UCS equipment:AdaptorDef:policyLevel managed
        object property"
    ::= { cucsEquipmentAdaptorDefEntry 9 }

cucsEquipmentAdaptorDefPolicyOwner OBJECT-TYPE
    SYNTAX       CucsPolicyPolicyOwner
    MAX-ACCESS   read-only
    STATUS       current
    DESCRIPTION
        "Cisco UCS equipment:AdaptorDef:policyOwner managed
        object property"
    ::= { cucsEquipmentAdaptorDefEntry 10 }

cucsEquipmentBaseBoardCapProviderTable OBJECT-TYPE
    SYNTAX           SEQUENCE OF CucsEquipmentBaseBoardCapProviderEntry
    MAX-ACCESS       not-accessible
    STATUS           current
    DESCRIPTION
        "Cisco UCS equipment:BaseBoardCapProvider managed object table"
    ::= { cucsEquipmentObjects 2 }

cucsEquipmentBaseBoardCapProviderEntry OBJECT-TYPE
    SYNTAX           CucsEquipmentBaseBoardCapProviderEntry
    MAX-ACCESS       not-accessible
    STATUS           current
    DESCRIPTION
        "Entry for the cucsEquipmentBaseBoardCapProviderTable table."
    INDEX { cucsEquipmentBaseBoardCapProviderInstanceId }
    ::= { cucsEquipmentBaseBoardCapProviderTable 1 }

CucsEquipmentBaseBoardCapProviderEntry ::= SEQUENCE {
    cucsEquipmentBaseBoardCapProviderInstanceId                      CucsManagedObjectId,
    cucsEquipmentBaseBoardCapProviderDn                              CucsManagedObjectDn,
    cucsEquipmentBaseBoardCapProviderRn                              SnmpAdminString,
    cucsEquipmentBaseBoardCapProviderDeprecated                      TruthValue,
    cucsEquipmentBaseBoardCapProviderGencount                        Gauge32,
    cucsEquipmentBaseBoardCapProviderMgmtPlaneVer                    SnmpAdminString,
    cucsEquipmentBaseBoardCapProviderModel                           SnmpAdminString,
    cucsEquipmentBaseBoardCapProviderRevision                        SnmpAdminString,
    cucsEquipmentBaseBoardCapProviderVendor                          SnmpAdminString,
    cucsEquipmentBaseBoardCapProviderPromCardType                    Gauge32,
    cucsEquipmentBaseBoardCapProviderDeleted                         TruthValue,
    cucsEquipmentBaseBoardCapProviderElementLoadFailures             Gauge32,
    cucsEquipmentBaseBoardCapProviderElementsLoaded                  Gauge32,
    cucsEquipmentBaseBoardCapProviderLoadErrors                      Gauge32,
    cucsEquipmentBaseBoardCapProviderLoadWarnings                    Gauge32
}

cucsEquipmentBaseBoardCapProviderInstanceId OBJECT-TYPE
    SYNTAX       CucsManagedObjectId
    MAX-ACCESS   not-accessible
    STATUS       current
    DESCRIPTION
        "Instance identifier of the managed object."
    ::= { cucsEquipmentBaseBoardCapProviderEntry 1 }

cucsEquipmentBaseBoardCapProviderDn OBJECT-TYPE
    SYNTAX       CucsManagedObjectDn
    MAX-ACCESS   read-only
    STATUS       current
    DESCRIPTION
        "Cisco UCS equipment:BaseBoardCapProvider:dn managed
        object property"
    ::= { cucsEquipmentBaseBoardCapProviderEntry 2 }

cucsEquipmentBaseBoardCapProviderRn OBJECT-TYPE
    SYNTAX       SnmpAdminString
    MAX-ACCESS   read-only
    STATUS       current
    DESCRIPTION
        "Cisco UCS equipment:BaseBoardCapProvider:rn managed
        object property"
    ::= { cucsEquipmentBaseBoardCapProviderEntry 3 }

cucsEquipmentBaseBoardCapProviderDeprecated OBJECT-TYPE
    SYNTAX       TruthValue
    MAX-ACCESS   read-only
    STATUS       current
    DESCRIPTION
        "Cisco UCS equipment:BaseBoardCapProvider:deprecated
        managed object property"
    ::= { cucsEquipmentBaseBoardCapProviderEntry 4 }

cucsEquipmentBaseBoardCapProviderGencount OBJECT-TYPE
    SYNTAX       Gauge32
    MAX-ACCESS   read-only
    STATUS       current
    DESCRIPTION
        "Cisco UCS equipment:BaseBoardCapProvider:gencount
        managed object property"
    ::= { cucsEquipmentBaseBoardCapProviderEntry 5 }

cucsEquipmentBaseBoardCapProviderMgmtPlaneVer OBJECT-TYPE
    SYNTAX       SnmpAdminString
    MAX-ACCESS   read-only
    STATUS       current
    DESCRIPTION
        "Cisco UCS equipment:BaseBoardCapProvider:mgmtPlaneVer
        managed object property"
    ::= { cucsEquipmentBaseBoardCapProviderEntry 6 }

cucsEquipmentBaseBoardCapProviderModel OBJECT-TYPE
    SYNTAX       SnmpAdminString
    MAX-ACCESS   read-only
    STATUS       current
    DESCRIPTION
        "Cisco UCS equipment:BaseBoardCapProvider:model
        managed object property"
    ::= { cucsEquipmentBaseBoardCapProviderEntry 7 }

cucsEquipmentBaseBoardCapProviderRevision OBJECT-TYPE
    SYNTAX       SnmpAdminString
    MAX-ACCESS   read-only
    STATUS       current
    DESCRIPTION
        "Cisco UCS equipment:BaseBoardCapProvider:revision
        managed object property"
    ::= { cucsEquipmentBaseBoardCapProviderEntry 8 }

cucsEquipmentBaseBoardCapProviderVendor OBJECT-TYPE
    SYNTAX       SnmpAdminString
    MAX-ACCESS   read-only
    STATUS       current
    DESCRIPTION
        "Cisco UCS equipment:BaseBoardCapProvider:vendor
        managed object property"
    ::= { cucsEquipmentBaseBoardCapProviderEntry 9 }

cucsEquipmentBaseBoardCapProviderPromCardType OBJECT-TYPE
    SYNTAX       Gauge32
    MAX-ACCESS   read-only
    STATUS       current
    DESCRIPTION
        "Cisco UCS equipment:BaseBoardCapProvider:promCardType
        managed object property"
    ::= { cucsEquipmentBaseBoardCapProviderEntry 10 }

cucsEquipmentBaseBoardCapProviderDeleted OBJECT-TYPE
    SYNTAX       TruthValue
    MAX-ACCESS   read-only
    STATUS       current
    DESCRIPTION
        "Cisco UCS equipment:BaseBoardCapProvider:deleted
        managed object property"
    ::= { cucsEquipmentBaseBoardCapProviderEntry 11 }

cucsEquipmentBaseBoardCapProviderElementLoadFailures OBJECT-TYPE
    SYNTAX       Gauge32
    MAX-ACCESS   read-only
    STATUS       current
    DESCRIPTION
        "Cisco UCS equipment:BaseBoardCapProvider:elementLoadFailures
        managed object property"
    ::= { cucsEquipmentBaseBoardCapProviderEntry 12 }

cucsEquipmentBaseBoardCapProviderElementsLoaded OBJECT-TYPE
    SYNTAX       Gauge32
    MAX-ACCESS   read-only
    STATUS       current
    DESCRIPTION
        "Cisco UCS equipment:BaseBoardCapProvider:elementsLoaded
        managed object property"
    ::= { cucsEquipmentBaseBoardCapProviderEntry 13 }

cucsEquipmentBaseBoardCapProviderLoadErrors OBJECT-TYPE
    SYNTAX       Gauge32
    MAX-ACCESS   read-only
    STATUS       current
    DESCRIPTION
        "Cisco UCS equipment:BaseBoardCapProvider:loadErrors
        managed object property"
    ::= { cucsEquipmentBaseBoardCapProviderEntry 14 }

cucsEquipmentBaseBoardCapProviderLoadWarnings OBJECT-TYPE
    SYNTAX       Gauge32
    MAX-ACCESS   read-only
    STATUS       current
    DESCRIPTION
        "Cisco UCS equipment:BaseBoardCapProvider:loadWarnings
        managed object property"
    ::= { cucsEquipmentBaseBoardCapProviderEntry 15 }

cucsEquipmentBeaconCapProviderTable OBJECT-TYPE
    SYNTAX           SEQUENCE OF CucsEquipmentBeaconCapProviderEntry
    MAX-ACCESS       not-accessible
    STATUS           current
    DESCRIPTION
        "Cisco UCS equipment:BeaconCapProvider managed object table"
    ::= { cucsEquipmentObjects 81 }

cucsEquipmentBeaconCapProviderEntry OBJECT-TYPE
    SYNTAX           CucsEquipmentBeaconCapProviderEntry
    MAX-ACCESS       not-accessible
    STATUS           current
    DESCRIPTION
        "Entry for the cucsEquipmentBeaconCapProviderTable table."
    INDEX { cucsEquipmentBeaconCapProviderInstanceId }
    ::= { cucsEquipmentBeaconCapProviderTable 1 }

CucsEquipmentBeaconCapProviderEntry ::= SEQUENCE {
    cucsEquipmentBeaconCapProviderInstanceId                         CucsManagedObjectId,
    cucsEquipmentBeaconCapProviderDn                                 CucsManagedObjectDn,
    cucsEquipmentBeaconCapProviderRn                                 SnmpAdminString,
    cucsEquipmentBeaconCapProviderDescr                              SnmpAdminString,
    cucsEquipmentBeaconCapProviderIntId                              SnmpAdminString,
    cucsEquipmentBeaconCapProviderName                               SnmpAdminString,
    cucsEquipmentBeaconCapProviderPortModeBeacon                     TruthValue,
    cucsEquipmentBeaconCapProviderPolicyLevel                        Gauge32,
    cucsEquipmentBeaconCapProviderPolicyOwner                        CucsPolicyPolicyOwner
}

cucsEquipmentBeaconCapProviderInstanceId OBJECT-TYPE
    SYNTAX       CucsManagedObjectId
    MAX-ACCESS   not-accessible
    STATUS       current
    DESCRIPTION
        "Instance identifier of the managed object."
    ::= { cucsEquipmentBeaconCapProviderEntry 1 }

cucsEquipmentBeaconCapProviderDn OBJECT-TYPE
    SYNTAX       CucsManagedObjectDn
    MAX-ACCESS   read-only
    STATUS       current
    DESCRIPTION
        "Cisco UCS equipment:BeaconCapProvider:dn managed object property"
    ::= { cucsEquipmentBeaconCapProviderEntry 2 }

cucsEquipmentBeaconCapProviderRn OBJECT-TYPE
    SYNTAX       SnmpAdminString
    MAX-ACCESS   read-only
    STATUS       current
    DESCRIPTION
        "Cisco UCS equipment:BeaconCapProvider:rn managed object property"
    ::= { cucsEquipmentBeaconCapProviderEntry 3 }

cucsEquipmentBeaconCapProviderDescr OBJECT-TYPE
    SYNTAX       SnmpAdminString
    MAX-ACCESS   read-only
    STATUS       current
    DESCRIPTION
        "Cisco UCS equipment:BeaconCapProvider:descr managed
        object property"
    ::= { cucsEquipmentBeaconCapProviderEntry 4 }

cucsEquipmentBeaconCapProviderIntId OBJECT-TYPE
    SYNTAX       SnmpAdminString
    MAX-ACCESS   read-only
    STATUS       current
    DESCRIPTION
        "Cisco UCS equipment:BeaconCapProvider:intId managed
        object property"
    ::= { cucsEquipmentBeaconCapProviderEntry 5 }

cucsEquipmentBeaconCapProviderName OBJECT-TYPE
    SYNTAX       SnmpAdminString
    MAX-ACCESS   read-only
    STATUS       current
    DESCRIPTION
        "Cisco UCS equipment:BeaconCapProvider:name managed
        object property"
    ::= { cucsEquipmentBeaconCapProviderEntry 6 }

cucsEquipmentBeaconCapProviderPortModeBeacon OBJECT-TYPE
    SYNTAX       TruthValue
    MAX-ACCESS   read-only
    STATUS       current
    DESCRIPTION
        "Cisco UCS equipment:BeaconCapProvider:portModeBeacon
        managed object property"
    ::= { cucsEquipmentBeaconCapProviderEntry 7 }

cucsEquipmentBeaconCapProviderPolicyLevel OBJECT-TYPE
    SYNTAX       Gauge32
    MAX-ACCESS   read-only
    STATUS       current
    DESCRIPTION
        "Cisco UCS equipment:BeaconCapProvider:policyLevel
        managed object property"
    ::= { cucsEquipmentBeaconCapProviderEntry 8 }

cucsEquipmentBeaconCapProviderPolicyOwner OBJECT-TYPE
    SYNTAX       CucsPolicyPolicyOwner
    MAX-ACCESS   read-only
    STATUS       current
    DESCRIPTION
        "Cisco UCS equipment:BeaconCapProvider:policyOwner
        managed object property"
    ::= { cucsEquipmentBeaconCapProviderEntry 9 }

cucsEquipmentBeaconLedTable OBJECT-TYPE
    SYNTAX           SEQUENCE OF CucsEquipmentBeaconLedEntry
    MAX-ACCESS       not-accessible
    STATUS           current
    DESCRIPTION
        "Cisco UCS equipment:BeaconLed managed object table"
    ::= { cucsEquipmentObjects 82 }

cucsEquipmentBeaconLedEntry OBJECT-TYPE
    SYNTAX           CucsEquipmentBeaconLedEntry
    MAX-ACCESS       not-accessible
    STATUS           current
    DESCRIPTION
        "Entry for the cucsEquipmentBeaconLedTable table."
    INDEX { cucsEquipmentBeaconLedInstanceId }
    ::= { cucsEquipmentBeaconLedTable 1 }

CucsEquipmentBeaconLedEntry ::= SEQUENCE {
    cucsEquipmentBeaconLedInstanceId                                 CucsManagedObjectId,
    cucsEquipmentBeaconLedDn                                         CucsManagedObjectDn,
    cucsEquipmentBeaconLedRn                                         SnmpAdminString,
    cucsEquipmentBeaconLedAdminState                                 CucsEquipmentBeaconLedState,
    cucsEquipmentBeaconLedColor                                      CucsEquipmentLedColor,
    cucsEquipmentBeaconLedFsmDescr                                   SnmpAdminString,
    cucsEquipmentBeaconLedFsmPrev                                    SnmpAdminString,
    cucsEquipmentBeaconLedFsmProgr                                   Gauge32,
    cucsEquipmentBeaconLedFsmRmtInvErrCode                           Gauge32,
    cucsEquipmentBeaconLedFsmRmtInvErrDescr                          SnmpAdminString,
    cucsEquipmentBeaconLedFsmRmtInvRslt                              CucsConditionRemoteInvRslt,
    cucsEquipmentBeaconLedFsmStageDescr                              SnmpAdminString,
    cucsEquipmentBeaconLedFsmStamp                                   DateAndTime,
    cucsEquipmentBeaconLedFsmStatus                                  SnmpAdminString,
    cucsEquipmentBeaconLedFsmTry                                     Gauge32,
    cucsEquipmentBeaconLedId                                         Gauge32,
    cucsEquipmentBeaconLedName                                       SnmpAdminString,
    cucsEquipmentBeaconLedOperState                                  CucsEquipmentLedOperState
}

cucsEquipmentBeaconLedInstanceId OBJECT-TYPE
    SYNTAX       CucsManagedObjectId
    MAX-ACCESS   not-accessible
    STATUS       current
    DESCRIPTION
        "Instance identifier of the managed object."
    ::= { cucsEquipmentBeaconLedEntry 1 }

cucsEquipmentBeaconLedDn OBJECT-TYPE
    SYNTAX       CucsManagedObjectDn
    MAX-ACCESS   read-only
    STATUS       current
    DESCRIPTION
        "Cisco UCS equipment:BeaconLed:dn managed object property"
    ::= { cucsEquipmentBeaconLedEntry 2 }

cucsEquipmentBeaconLedRn OBJECT-TYPE
    SYNTAX       SnmpAdminString
    MAX-ACCESS   read-only
    STATUS       current
    DESCRIPTION
        "Cisco UCS equipment:BeaconLed:rn managed object property"
    ::= { cucsEquipmentBeaconLedEntry 3 }

cucsEquipmentBeaconLedAdminState OBJECT-TYPE
    SYNTAX       CucsEquipmentBeaconLedState
    MAX-ACCESS   read-only
    STATUS       current
    DESCRIPTION
        "Cisco UCS equipment:BeaconLed:adminState managed object property"
    ::= { cucsEquipmentBeaconLedEntry 4 }

cucsEquipmentBeaconLedColor OBJECT-TYPE
    SYNTAX       CucsEquipmentLedColor
    MAX-ACCESS   read-only
    STATUS       current
    DESCRIPTION
        "Cisco UCS equipment:BeaconLed:color managed object property"
    ::= { cucsEquipmentBeaconLedEntry 5 }

cucsEquipmentBeaconLedFsmDescr OBJECT-TYPE
    SYNTAX       SnmpAdminString
    MAX-ACCESS   read-only
    STATUS       current
    DESCRIPTION
        "Cisco UCS equipment:BeaconLed:fsmDescr managed object property"
    ::= { cucsEquipmentBeaconLedEntry 6 }

cucsEquipmentBeaconLedFsmPrev OBJECT-TYPE
    SYNTAX       SnmpAdminString
    MAX-ACCESS   read-only
    STATUS       current
    DESCRIPTION
        "Cisco UCS equipment:BeaconLed:fsmPrev managed object property"
    ::= { cucsEquipmentBeaconLedEntry 7 }

cucsEquipmentBeaconLedFsmProgr OBJECT-TYPE
    SYNTAX       Gauge32
    MAX-ACCESS   read-only
    STATUS       current
    DESCRIPTION
        "Cisco UCS equipment:BeaconLed:fsmProgr managed object property"
    ::= { cucsEquipmentBeaconLedEntry 8 }

cucsEquipmentBeaconLedFsmRmtInvErrCode OBJECT-TYPE
    SYNTAX       Gauge32
    MAX-ACCESS   read-only
    STATUS       current
    DESCRIPTION
        "Cisco UCS equipment:BeaconLed:fsmRmtInvErrCode
        managed object property"
    ::= { cucsEquipmentBeaconLedEntry 9 }

cucsEquipmentBeaconLedFsmRmtInvErrDescr OBJECT-TYPE
    SYNTAX       SnmpAdminString
    MAX-ACCESS   read-only
    STATUS       current
    DESCRIPTION
        "Cisco UCS equipment:BeaconLed:fsmRmtInvErrDescr
        managed object property"
    ::= { cucsEquipmentBeaconLedEntry 10 }

cucsEquipmentBeaconLedFsmRmtInvRslt OBJECT-TYPE
    SYNTAX       CucsConditionRemoteInvRslt
    MAX-ACCESS   read-only
    STATUS       current
    DESCRIPTION
        "Cisco UCS equipment:BeaconLed:fsmRmtInvRslt managed
        object property"
    ::= { cucsEquipmentBeaconLedEntry 11 }

cucsEquipmentBeaconLedFsmStageDescr OBJECT-TYPE
    SYNTAX       SnmpAdminString
    MAX-ACCESS   read-only
    STATUS       current
    DESCRIPTION
        "Cisco UCS equipment:BeaconLed:fsmStageDescr managed
        object property"
    ::= { cucsEquipmentBeaconLedEntry 12 }

cucsEquipmentBeaconLedFsmStamp OBJECT-TYPE
    SYNTAX       DateAndTime
    MAX-ACCESS   read-only
    STATUS       current
    DESCRIPTION
        "Cisco UCS equipment:BeaconLed:fsmStamp managed object property"
    ::= { cucsEquipmentBeaconLedEntry 13 }

cucsEquipmentBeaconLedFsmStatus OBJECT-TYPE
    SYNTAX       SnmpAdminString
    MAX-ACCESS   read-only
    STATUS       current
    DESCRIPTION
        "Cisco UCS equipment:BeaconLed:fsmStatus managed object property"
    ::= { cucsEquipmentBeaconLedEntry 14 }

cucsEquipmentBeaconLedFsmTry OBJECT-TYPE
    SYNTAX       Gauge32
    MAX-ACCESS   read-only
    STATUS       current
    DESCRIPTION
        "Cisco UCS equipment:BeaconLed:fsmTry managed object property"
    ::= { cucsEquipmentBeaconLedEntry 15 }

cucsEquipmentBeaconLedId OBJECT-TYPE
    SYNTAX       Gauge32
    MAX-ACCESS   read-only
    STATUS       current
    DESCRIPTION
        "Cisco UCS equipment:BeaconLed:id managed object property"
    ::= { cucsEquipmentBeaconLedEntry 16 }

cucsEquipmentBeaconLedName OBJECT-TYPE
    SYNTAX       SnmpAdminString
    MAX-ACCESS   read-only
    STATUS       current
    DESCRIPTION
        "Cisco UCS equipment:BeaconLed:name managed object property"
    ::= { cucsEquipmentBeaconLedEntry 17 }

cucsEquipmentBeaconLedOperState OBJECT-TYPE
    SYNTAX       CucsEquipmentLedOperState
    MAX-ACCESS   read-only
    STATUS       current
    DESCRIPTION
        "Cisco UCS equipment:BeaconLed:operState managed object property"
    ::= { cucsEquipmentBeaconLedEntry 18 }

cucsEquipmentBeaconLedFsmTable OBJECT-TYPE
    SYNTAX           SEQUENCE OF CucsEquipmentBeaconLedFsmEntry
    MAX-ACCESS       not-accessible
    STATUS           current
    DESCRIPTION
        "Cisco UCS equipment:BeaconLedFsm managed object table"
    ::= { cucsEquipmentObjects 103 }

cucsEquipmentBeaconLedFsmEntry OBJECT-TYPE
    SYNTAX           CucsEquipmentBeaconLedFsmEntry
    MAX-ACCESS       not-accessible
    STATUS           current
    DESCRIPTION
        "Entry for the cucsEquipmentBeaconLedFsmTable table."
    INDEX { cucsEquipmentBeaconLedFsmInstanceId }
    ::= { cucsEquipmentBeaconLedFsmTable 1 }

CucsEquipmentBeaconLedFsmEntry ::= SEQUENCE {
    cucsEquipmentBeaconLedFsmInstanceId                              CucsManagedObjectId,
    cucsEquipmentBeaconLedFsmDn                                      CucsManagedObjectDn,
    cucsEquipmentBeaconLedFsmRn                                      SnmpAdminString,
    cucsEquipmentBeaconLedFsmCompletionTime                          DateAndTime,
    cucsEquipmentBeaconLedFsmCurrentFsm                              CucsEquipmentBeaconLedFsmCurrentFsm,
    cucsEquipmentBeaconLedFsmDescr                                   SnmpAdminString,
    cucsEquipmentBeaconLedFsmFsmStatus                               CucsFsmFsmStageStatus,
    cucsEquipmentBeaconLedFsmProgress                                Gauge32,
    cucsEquipmentBeaconLedFsmRmtErrCode                              Gauge32,
    cucsEquipmentBeaconLedFsmRmtErrDescr                             SnmpAdminString,
    cucsEquipmentBeaconLedFsmRmtRslt                                 CucsConditionRemoteInvRslt
}

cucsEquipmentBeaconLedFsmInstanceId OBJECT-TYPE
    SYNTAX       CucsManagedObjectId
    MAX-ACCESS   not-accessible
    STATUS       current
    DESCRIPTION
        "Instance identifier of the managed object."
    ::= { cucsEquipmentBeaconLedFsmEntry 1 }

cucsEquipmentBeaconLedFsmDn OBJECT-TYPE
    SYNTAX       CucsManagedObjectDn
    MAX-ACCESS   read-only
    STATUS       current
    DESCRIPTION
        "Cisco UCS equipment:BeaconLedFsm:dn managed object property"
    ::= { cucsEquipmentBeaconLedFsmEntry 2 }

cucsEquipmentBeaconLedFsmRn OBJECT-TYPE
    SYNTAX       SnmpAdminString
    MAX-ACCESS   read-only
    STATUS       current
    DESCRIPTION
        "Cisco UCS equipment:BeaconLedFsm:rn managed object property"
    ::= { cucsEquipmentBeaconLedFsmEntry 3 }

cucsEquipmentBeaconLedFsmCompletionTime OBJECT-TYPE
    SYNTAX       DateAndTime
    MAX-ACCESS   read-only
    STATUS       current
    DESCRIPTION
        "Cisco UCS equipment:BeaconLedFsm:completionTime
        managed object property"
    ::= { cucsEquipmentBeaconLedFsmEntry 4 }

cucsEquipmentBeaconLedFsmCurrentFsm OBJECT-TYPE
    SYNTAX       CucsEquipmentBeaconLedFsmCurrentFsm
    MAX-ACCESS   read-only
    STATUS       current
    DESCRIPTION
        "Cisco UCS equipment:BeaconLedFsm:currentFsm managed
        object property"
    ::= { cucsEquipmentBeaconLedFsmEntry 5 }

cucsEquipmentBeaconLedFsmDescr OBJECT-TYPE
    SYNTAX       SnmpAdminString
    MAX-ACCESS   read-only
    STATUS       current
    DESCRIPTION
        "Cisco UCS equipment:BeaconLedFsm:descr managed object property"
    ::= { cucsEquipmentBeaconLedFsmEntry 6 }

cucsEquipmentBeaconLedFsmFsmStatus OBJECT-TYPE
    SYNTAX       CucsFsmFsmStageStatus
    MAX-ACCESS   read-only
    STATUS       current
    DESCRIPTION
        "Cisco UCS equipment:BeaconLedFsm:fsmStatus managed
        object property"
    ::= { cucsEquipmentBeaconLedFsmEntry 7 }

cucsEquipmentBeaconLedFsmProgress OBJECT-TYPE
    SYNTAX       Gauge32
    MAX-ACCESS   read-only
    STATUS       current
    DESCRIPTION
        "Cisco UCS equipment:BeaconLedFsm:progress managed
        object property"
    ::= { cucsEquipmentBeaconLedFsmEntry 8 }

cucsEquipmentBeaconLedFsmRmtErrCode OBJECT-TYPE
    SYNTAX       Gauge32
    MAX-ACCESS   read-only
    STATUS       current
    DESCRIPTION
        "Cisco UCS equipment:BeaconLedFsm:rmtErrCode managed
        object property"
    ::= { cucsEquipmentBeaconLedFsmEntry 9 }

cucsEquipmentBeaconLedFsmRmtErrDescr OBJECT-TYPE
    SYNTAX       SnmpAdminString
    MAX-ACCESS   read-only
    STATUS       current
    DESCRIPTION
        "Cisco UCS equipment:BeaconLedFsm:rmtErrDescr managed
        object property"
    ::= { cucsEquipmentBeaconLedFsmEntry 10 }

cucsEquipmentBeaconLedFsmRmtRslt OBJECT-TYPE
    SYNTAX       CucsConditionRemoteInvRslt
    MAX-ACCESS   read-only
    STATUS       current
    DESCRIPTION
        "Cisco UCS equipment:BeaconLedFsm:rmtRslt managed object property"
    ::= { cucsEquipmentBeaconLedFsmEntry 11 }

cucsEquipmentBeaconLedFsmStageTable OBJECT-TYPE
    SYNTAX           SEQUENCE OF CucsEquipmentBeaconLedFsmStageEntry
    MAX-ACCESS       not-accessible
    STATUS           current
    DESCRIPTION
        "Cisco UCS equipment:BeaconLedFsmStage managed object table"
    ::= { cucsEquipmentObjects 104 }

cucsEquipmentBeaconLedFsmStageEntry OBJECT-TYPE
    SYNTAX           CucsEquipmentBeaconLedFsmStageEntry
    MAX-ACCESS       not-accessible
    STATUS           current
    DESCRIPTION
        "Entry for the cucsEquipmentBeaconLedFsmStageTable table."
    INDEX { cucsEquipmentBeaconLedFsmStageInstanceId }
    ::= { cucsEquipmentBeaconLedFsmStageTable 1 }

CucsEquipmentBeaconLedFsmStageEntry ::= SEQUENCE {
    cucsEquipmentBeaconLedFsmStageInstanceId                         CucsManagedObjectId,
    cucsEquipmentBeaconLedFsmStageDn                                 CucsManagedObjectDn,
    cucsEquipmentBeaconLedFsmStageRn                                 SnmpAdminString,
    cucsEquipmentBeaconLedFsmStageDescr                              SnmpAdminString,
    cucsEquipmentBeaconLedFsmStageLastUpdateTime                     DateAndTime,
    cucsEquipmentBeaconLedFsmStageName                               CucsEquipmentBeaconLedFsmStageName,
    cucsEquipmentBeaconLedFsmStageOrder                              Gauge32,
    cucsEquipmentBeaconLedFsmStageRetry                              Gauge32,
    cucsEquipmentBeaconLedFsmStageStageStatus                        CucsFsmFsmStageStatus
}

cucsEquipmentBeaconLedFsmStageInstanceId OBJECT-TYPE
    SYNTAX       CucsManagedObjectId
    MAX-ACCESS   not-accessible
    STATUS       current
    DESCRIPTION
        "Instance identifier of the managed object."
    ::= { cucsEquipmentBeaconLedFsmStageEntry 1 }

cucsEquipmentBeaconLedFsmStageDn OBJECT-TYPE
    SYNTAX       CucsManagedObjectDn
    MAX-ACCESS   read-only
    STATUS       current
    DESCRIPTION
        "Cisco UCS equipment:BeaconLedFsmStage:dn managed object property"
    ::= { cucsEquipmentBeaconLedFsmStageEntry 2 }

cucsEquipmentBeaconLedFsmStageRn OBJECT-TYPE
    SYNTAX       SnmpAdminString
    MAX-ACCESS   read-only
    STATUS       current
    DESCRIPTION
        "Cisco UCS equipment:BeaconLedFsmStage:rn managed object property"
    ::= { cucsEquipmentBeaconLedFsmStageEntry 3 }

cucsEquipmentBeaconLedFsmStageDescr OBJECT-TYPE
    SYNTAX       SnmpAdminString
    MAX-ACCESS   read-only
    STATUS       current
    DESCRIPTION
        "Cisco UCS equipment:BeaconLedFsmStage:descr managed
        object property"
    ::= { cucsEquipmentBeaconLedFsmStageEntry 4 }

cucsEquipmentBeaconLedFsmStageLastUpdateTime OBJECT-TYPE
    SYNTAX       DateAndTime
    MAX-ACCESS   read-only
    STATUS       current
    DESCRIPTION
        "Cisco UCS equipment:BeaconLedFsmStage:lastUpdateTime
        managed object property"
    ::= { cucsEquipmentBeaconLedFsmStageEntry 5 }

cucsEquipmentBeaconLedFsmStageName OBJECT-TYPE
    SYNTAX       CucsEquipmentBeaconLedFsmStageName
    MAX-ACCESS   read-only
    STATUS       current
    DESCRIPTION
        "Cisco UCS equipment:BeaconLedFsmStage:name managed
        object property"
    ::= { cucsEquipmentBeaconLedFsmStageEntry 6 }

cucsEquipmentBeaconLedFsmStageOrder OBJECT-TYPE
    SYNTAX       Gauge32
    MAX-ACCESS   read-only
    STATUS       current
    DESCRIPTION
        "Cisco UCS equipment:BeaconLedFsmStage:order managed
        object property"
    ::= { cucsEquipmentBeaconLedFsmStageEntry 7 }

cucsEquipmentBeaconLedFsmStageRetry OBJECT-TYPE
    SYNTAX       Gauge32
    MAX-ACCESS   read-only
    STATUS       current
    DESCRIPTION
        "Cisco UCS equipment:BeaconLedFsmStage:retry managed
        object property"
    ::= { cucsEquipmentBeaconLedFsmStageEntry 8 }

cucsEquipmentBeaconLedFsmStageStageStatus OBJECT-TYPE
    SYNTAX       CucsFsmFsmStageStatus
    MAX-ACCESS   read-only
    STATUS       current
    DESCRIPTION
        "Cisco UCS equipment:BeaconLedFsmStage:stageStatus
        managed object property"
    ::= { cucsEquipmentBeaconLedFsmStageEntry 9 }

cucsEquipmentBeaconLedFsmTaskTable OBJECT-TYPE
    SYNTAX           SEQUENCE OF CucsEquipmentBeaconLedFsmTaskEntry
    MAX-ACCESS       not-accessible
    STATUS           current
    DESCRIPTION
        "Cisco UCS equipment:BeaconLedFsmTask managed object table"
    ::= { cucsEquipmentObjects 83 }

cucsEquipmentBeaconLedFsmTaskEntry OBJECT-TYPE
    SYNTAX           CucsEquipmentBeaconLedFsmTaskEntry
    MAX-ACCESS       not-accessible
    STATUS           current
    DESCRIPTION
        "Entry for the cucsEquipmentBeaconLedFsmTaskTable table."
    INDEX { cucsEquipmentBeaconLedFsmTaskInstanceId }
    ::= { cucsEquipmentBeaconLedFsmTaskTable 1 }

CucsEquipmentBeaconLedFsmTaskEntry ::= SEQUENCE {
    cucsEquipmentBeaconLedFsmTaskInstanceId                          CucsManagedObjectId,
    cucsEquipmentBeaconLedFsmTaskDn                                  CucsManagedObjectDn,
    cucsEquipmentBeaconLedFsmTaskRn                                  SnmpAdminString,
    cucsEquipmentBeaconLedFsmTaskCompletion                          CucsFsmCompletion,
    cucsEquipmentBeaconLedFsmTaskFlags                               CucsFsmFlags,
    cucsEquipmentBeaconLedFsmTaskItem                                CucsEquipmentBeaconLedFsmTaskItem,
    cucsEquipmentBeaconLedFsmTaskSeqId                               Gauge32
}

cucsEquipmentBeaconLedFsmTaskInstanceId OBJECT-TYPE
    SYNTAX       CucsManagedObjectId
    MAX-ACCESS   not-accessible
    STATUS       current
    DESCRIPTION
        "Instance identifier of the managed object."
    ::= { cucsEquipmentBeaconLedFsmTaskEntry 1 }

cucsEquipmentBeaconLedFsmTaskDn OBJECT-TYPE
    SYNTAX       CucsManagedObjectDn
    MAX-ACCESS   read-only
    STATUS       current
    DESCRIPTION
        "Cisco UCS equipment:BeaconLedFsmTask:dn managed object property"
    ::= { cucsEquipmentBeaconLedFsmTaskEntry 2 }

cucsEquipmentBeaconLedFsmTaskRn OBJECT-TYPE
    SYNTAX       SnmpAdminString
    MAX-ACCESS   read-only
    STATUS       current
    DESCRIPTION
        "Cisco UCS equipment:BeaconLedFsmTask:rn managed object property"
    ::= { cucsEquipmentBeaconLedFsmTaskEntry 3 }

cucsEquipmentBeaconLedFsmTaskCompletion OBJECT-TYPE
    SYNTAX       CucsFsmCompletion
    MAX-ACCESS   read-only
    STATUS       current
    DESCRIPTION
        "Cisco UCS equipment:BeaconLedFsmTask:completion
        managed object property"
    ::= { cucsEquipmentBeaconLedFsmTaskEntry 4 }

cucsEquipmentBeaconLedFsmTaskFlags OBJECT-TYPE
    SYNTAX       CucsFsmFlags
    MAX-ACCESS   read-only
    STATUS       current
    DESCRIPTION
        "Cisco UCS equipment:BeaconLedFsmTask:flags managed
        object property"
    ::= { cucsEquipmentBeaconLedFsmTaskEntry 5 }

cucsEquipmentBeaconLedFsmTaskItem OBJECT-TYPE
    SYNTAX       CucsEquipmentBeaconLedFsmTaskItem
    MAX-ACCESS   read-only
    STATUS       current
    DESCRIPTION
        "Cisco UCS equipment:BeaconLedFsmTask:item managed
        object property"
    ::= { cucsEquipmentBeaconLedFsmTaskEntry 6 }

cucsEquipmentBeaconLedFsmTaskSeqId OBJECT-TYPE
    SYNTAX       Gauge32
    MAX-ACCESS   read-only
    STATUS       current
    DESCRIPTION
        "Cisco UCS equipment:BeaconLedFsmTask:seqId managed
        object property"
    ::= { cucsEquipmentBeaconLedFsmTaskEntry 7 }

cucsEquipmentBiosDefTable OBJECT-TYPE
    SYNTAX           SEQUENCE OF CucsEquipmentBiosDefEntry
    MAX-ACCESS       not-accessible
    STATUS           current
    DESCRIPTION
        "Cisco UCS equipment:BiosDef managed object table"
    ::= { cucsEquipmentObjects 96 }

cucsEquipmentBiosDefEntry OBJECT-TYPE
    SYNTAX           CucsEquipmentBiosDefEntry
    MAX-ACCESS       not-accessible
    STATUS           current
    DESCRIPTION
        "Entry for the cucsEquipmentBiosDefTable table."
    INDEX { cucsEquipmentBiosDefInstanceId }
    ::= { cucsEquipmentBiosDefTable 1 }

CucsEquipmentBiosDefEntry ::= SEQUENCE {
    cucsEquipmentBiosDefInstanceId                                   CucsManagedObjectId,
    cucsEquipmentBiosDefDn                                           CucsManagedObjectDn,
    cucsEquipmentBiosDefRn                                           SnmpAdminString,
    cucsEquipmentBiosDefDescr                                        SnmpAdminString,
    cucsEquipmentBiosDefIntId                                        SnmpAdminString,
    cucsEquipmentBiosDefName                                         SnmpAdminString,
    cucsEquipmentBiosDefResetOn                                      CucsEquipmentResetOn,
    cucsEquipmentBiosDefSecureBios                                   CucsEquipmentSecureBios,
    cucsEquipmentBiosDefStorageMethod                                CucsEquipmentStorageMethod,
    cucsEquipmentBiosDefUpdateMethod                                 CucsEquipmentBiosUpdateMethod,
    cucsEquipmentBiosDefPolicyLevel                                  Gauge32,
    cucsEquipmentBiosDefPolicyOwner                                  CucsPolicyPolicyOwner
}

cucsEquipmentBiosDefInstanceId OBJECT-TYPE
    SYNTAX       CucsManagedObjectId
    MAX-ACCESS   not-accessible
    STATUS       current
    DESCRIPTION
        "Instance identifier of the managed object."
    ::= { cucsEquipmentBiosDefEntry 1 }

cucsEquipmentBiosDefDn OBJECT-TYPE
    SYNTAX       CucsManagedObjectDn
    MAX-ACCESS   read-only
    STATUS       current
    DESCRIPTION
        "Cisco UCS equipment:BiosDef:dn managed object property"
    ::= { cucsEquipmentBiosDefEntry 2 }

cucsEquipmentBiosDefRn OBJECT-TYPE
    SYNTAX       SnmpAdminString
    MAX-ACCESS   read-only
    STATUS       current
    DESCRIPTION
        "Cisco UCS equipment:BiosDef:rn managed object property"
    ::= { cucsEquipmentBiosDefEntry 3 }

cucsEquipmentBiosDefDescr OBJECT-TYPE
    SYNTAX       SnmpAdminString
    MAX-ACCESS   read-only
    STATUS       current
    DESCRIPTION
        "Cisco UCS equipment:BiosDef:descr managed object property"
    ::= { cucsEquipmentBiosDefEntry 4 }

cucsEquipmentBiosDefIntId OBJECT-TYPE
    SYNTAX       SnmpAdminString
    MAX-ACCESS   read-only
    STATUS       current
    DESCRIPTION
        "Cisco UCS equipment:BiosDef:intId managed object property"
    ::= { cucsEquipmentBiosDefEntry 5 }

cucsEquipmentBiosDefName OBJECT-TYPE
    SYNTAX       SnmpAdminString
    MAX-ACCESS   read-only
    STATUS       current
    DESCRIPTION
        "Cisco UCS equipment:BiosDef:name managed object property"
    ::= { cucsEquipmentBiosDefEntry 6 }

cucsEquipmentBiosDefResetOn OBJECT-TYPE
    SYNTAX       CucsEquipmentResetOn
    MAX-ACCESS   read-only
    STATUS       current
    DESCRIPTION
        "Cisco UCS equipment:BiosDef:resetOn managed object property"
    ::= { cucsEquipmentBiosDefEntry 7 }

cucsEquipmentBiosDefSecureBios OBJECT-TYPE
    SYNTAX       CucsEquipmentSecureBios
    MAX-ACCESS   read-only
    STATUS       current
    DESCRIPTION
        "Cisco UCS equipment:BiosDef:secureBios managed object property"
    ::= { cucsEquipmentBiosDefEntry 8 }

cucsEquipmentBiosDefStorageMethod OBJECT-TYPE
    SYNTAX       CucsEquipmentStorageMethod
    MAX-ACCESS   read-only
    STATUS       current
    DESCRIPTION
        "Cisco UCS equipment:BiosDef:storageMethod managed
        object property"
    ::= { cucsEquipmentBiosDefEntry 9 }

cucsEquipmentBiosDefUpdateMethod OBJECT-TYPE
    SYNTAX       CucsEquipmentBiosUpdateMethod
    MAX-ACCESS   read-only
    STATUS       current
    DESCRIPTION
        "Cisco UCS equipment:BiosDef:updateMethod managed object property"
    ::= { cucsEquipmentBiosDefEntry 10 }

cucsEquipmentBiosDefPolicyLevel OBJECT-TYPE
    SYNTAX       Gauge32
    MAX-ACCESS   read-only
    STATUS       current
    DESCRIPTION
        "Cisco UCS equipment:BiosDef:policyLevel managed object property"
    ::= { cucsEquipmentBiosDefEntry 11 }

cucsEquipmentBiosDefPolicyOwner OBJECT-TYPE
    SYNTAX       CucsPolicyPolicyOwner
    MAX-ACCESS   read-only
    STATUS       current
    DESCRIPTION
        "Cisco UCS equipment:BiosDef:policyOwner managed object property"
    ::= { cucsEquipmentBiosDefEntry 12 }

cucsEquipmentBladeAGLibraryTable OBJECT-TYPE
    SYNTAX           SEQUENCE OF CucsEquipmentBladeAGLibraryEntry
    MAX-ACCESS       not-accessible
    STATUS           current
    DESCRIPTION
        "Cisco UCS equipment:BladeAGLibrary managed object table"
    ::= { cucsEquipmentObjects 73 }

cucsEquipmentBladeAGLibraryEntry OBJECT-TYPE
    SYNTAX           CucsEquipmentBladeAGLibraryEntry
    MAX-ACCESS       not-accessible
    STATUS           current
    DESCRIPTION
        "Entry for the cucsEquipmentBladeAGLibraryTable table."
    INDEX { cucsEquipmentBladeAGLibraryInstanceId }
    ::= { cucsEquipmentBladeAGLibraryTable 1 }

CucsEquipmentBladeAGLibraryEntry ::= SEQUENCE {
    cucsEquipmentBladeAGLibraryInstanceId                            CucsManagedObjectId,
    cucsEquipmentBladeAGLibraryDn                                    CucsManagedObjectDn,
    cucsEquipmentBladeAGLibraryRn                                    SnmpAdminString,
    cucsEquipmentBladeAGLibraryDescr                                 SnmpAdminString,
    cucsEquipmentBladeAGLibraryIntId                                 SnmpAdminString,
    cucsEquipmentBladeAGLibraryName                                  SnmpAdminString,
    cucsEquipmentBladeAGLibraryPolicyLevel                           Gauge32,
    cucsEquipmentBladeAGLibraryPolicyOwner                           CucsPolicyPolicyOwner
}

cucsEquipmentBladeAGLibraryInstanceId OBJECT-TYPE
    SYNTAX       CucsManagedObjectId
    MAX-ACCESS   not-accessible
    STATUS       current
    DESCRIPTION
        "Instance identifier of the managed object."
    ::= { cucsEquipmentBladeAGLibraryEntry 1 }

cucsEquipmentBladeAGLibraryDn OBJECT-TYPE
    SYNTAX       CucsManagedObjectDn
    MAX-ACCESS   read-only
    STATUS       current
    DESCRIPTION
        "Cisco UCS equipment:BladeAGLibrary:dn managed object property"
    ::= { cucsEquipmentBladeAGLibraryEntry 2 }

cucsEquipmentBladeAGLibraryRn OBJECT-TYPE
    SYNTAX       SnmpAdminString
    MAX-ACCESS   read-only
    STATUS       current
    DESCRIPTION
        "Cisco UCS equipment:BladeAGLibrary:rn managed object property"
    ::= { cucsEquipmentBladeAGLibraryEntry 3 }

cucsEquipmentBladeAGLibraryDescr OBJECT-TYPE
    SYNTAX       SnmpAdminString
    MAX-ACCESS   read-only
    STATUS       current
    DESCRIPTION
        "Cisco UCS equipment:BladeAGLibrary:descr managed object property"
    ::= { cucsEquipmentBladeAGLibraryEntry 4 }

cucsEquipmentBladeAGLibraryIntId OBJECT-TYPE
    SYNTAX       SnmpAdminString
    MAX-ACCESS   read-only
    STATUS       current
    DESCRIPTION
        "Cisco UCS equipment:BladeAGLibrary:intId managed object property"
    ::= { cucsEquipmentBladeAGLibraryEntry 5 }

cucsEquipmentBladeAGLibraryName OBJECT-TYPE
    SYNTAX       SnmpAdminString
    MAX-ACCESS   read-only
    STATUS       current
    DESCRIPTION
        "Cisco UCS equipment:BladeAGLibrary:name managed object property"
    ::= { cucsEquipmentBladeAGLibraryEntry 6 }

cucsEquipmentBladeAGLibraryPolicyLevel OBJECT-TYPE
    SYNTAX       Gauge32
    MAX-ACCESS   read-only
    STATUS       current
    DESCRIPTION
        "Cisco UCS equipment:BladeAGLibrary:policyLevel
        managed object property"
    ::= { cucsEquipmentBladeAGLibraryEntry 7 }

cucsEquipmentBladeAGLibraryPolicyOwner OBJECT-TYPE
    SYNTAX       CucsPolicyPolicyOwner
    MAX-ACCESS   read-only
    STATUS       current
    DESCRIPTION
        "Cisco UCS equipment:BladeAGLibrary:policyOwner
        managed object property"
    ::= { cucsEquipmentBladeAGLibraryEntry 8 }

cucsEquipmentBladeBiosCapProviderTable OBJECT-TYPE
    SYNTAX           SEQUENCE OF CucsEquipmentBladeBiosCapProviderEntry
    MAX-ACCESS       not-accessible
    STATUS           current
    DESCRIPTION
        "Cisco UCS equipment:BladeBiosCapProvider managed object table"
    ::= { cucsEquipmentObjects 3 }

cucsEquipmentBladeBiosCapProviderEntry OBJECT-TYPE
    SYNTAX           CucsEquipmentBladeBiosCapProviderEntry
    MAX-ACCESS       not-accessible
    STATUS           current
    DESCRIPTION
        "Entry for the cucsEquipmentBladeBiosCapProviderTable table."
    INDEX { cucsEquipmentBladeBiosCapProviderInstanceId }
    ::= { cucsEquipmentBladeBiosCapProviderTable 1 }

CucsEquipmentBladeBiosCapProviderEntry ::= SEQUENCE {
    cucsEquipmentBladeBiosCapProviderInstanceId                      CucsManagedObjectId,
    cucsEquipmentBladeBiosCapProviderDn                              CucsManagedObjectDn,
    cucsEquipmentBladeBiosCapProviderRn                              SnmpAdminString,
    cucsEquipmentBladeBiosCapProviderDeprecated                      TruthValue,
    cucsEquipmentBladeBiosCapProviderGencount                        Gauge32,
    cucsEquipmentBladeBiosCapProviderMgmtPlaneVer                    SnmpAdminString,
    cucsEquipmentBladeBiosCapProviderModel                           SnmpAdminString,
    cucsEquipmentBladeBiosCapProviderRevision                        SnmpAdminString,
    cucsEquipmentBladeBiosCapProviderVendor                          SnmpAdminString,
    cucsEquipmentBladeBiosCapProviderProductName                     SnmpAdminString,
    cucsEquipmentBladeBiosCapProviderPromCardType                    Gauge32,
    cucsEquipmentBladeBiosCapProviderDeleted                         TruthValue,
    cucsEquipmentBladeBiosCapProviderElementLoadFailures             Gauge32,
    cucsEquipmentBladeBiosCapProviderElementsLoaded                  Gauge32,
    cucsEquipmentBladeBiosCapProviderLoadErrors                      Gauge32,
    cucsEquipmentBladeBiosCapProviderLoadWarnings                    Gauge32
}

cucsEquipmentBladeBiosCapProviderInstanceId OBJECT-TYPE
    SYNTAX       CucsManagedObjectId
    MAX-ACCESS   not-accessible
    STATUS       current
    DESCRIPTION
        "Instance identifier of the managed object."
    ::= { cucsEquipmentBladeBiosCapProviderEntry 1 }

cucsEquipmentBladeBiosCapProviderDn OBJECT-TYPE
    SYNTAX       CucsManagedObjectDn
    MAX-ACCESS   read-only
    STATUS       current
    DESCRIPTION
        "Cisco UCS equipment:BladeBiosCapProvider:dn managed
        object property"
    ::= { cucsEquipmentBladeBiosCapProviderEntry 2 }

cucsEquipmentBladeBiosCapProviderRn OBJECT-TYPE
    SYNTAX       SnmpAdminString
    MAX-ACCESS   read-only
    STATUS       current
    DESCRIPTION
        "Cisco UCS equipment:BladeBiosCapProvider:rn managed
        object property"
    ::= { cucsEquipmentBladeBiosCapProviderEntry 3 }

cucsEquipmentBladeBiosCapProviderDeprecated OBJECT-TYPE
    SYNTAX       TruthValue
    MAX-ACCESS   read-only
    STATUS       current
    DESCRIPTION
        "Cisco UCS equipment:BladeBiosCapProvider:deprecated
        managed object property"
    ::= { cucsEquipmentBladeBiosCapProviderEntry 4 }

cucsEquipmentBladeBiosCapProviderGencount OBJECT-TYPE
    SYNTAX       Gauge32
    MAX-ACCESS   read-only
    STATUS       current
    DESCRIPTION
        "Cisco UCS equipment:BladeBiosCapProvider:gencount
        managed object property"
    ::= { cucsEquipmentBladeBiosCapProviderEntry 5 }

cucsEquipmentBladeBiosCapProviderMgmtPlaneVer OBJECT-TYPE
    SYNTAX       SnmpAdminString
    MAX-ACCESS   read-only
    STATUS       current
    DESCRIPTION
        "Cisco UCS equipment:BladeBiosCapProvider:mgmtPlaneVer
        managed object property"
    ::= { cucsEquipmentBladeBiosCapProviderEntry 6 }

cucsEquipmentBladeBiosCapProviderModel OBJECT-TYPE
    SYNTAX       SnmpAdminString
    MAX-ACCESS   read-only
    STATUS       current
    DESCRIPTION
        "Cisco UCS equipment:BladeBiosCapProvider:model
        managed object property"
    ::= { cucsEquipmentBladeBiosCapProviderEntry 7 }

cucsEquipmentBladeBiosCapProviderRevision OBJECT-TYPE
    SYNTAX       SnmpAdminString
    MAX-ACCESS   read-only
    STATUS       current
    DESCRIPTION
        "Cisco UCS equipment:BladeBiosCapProvider:revision
        managed object property"
    ::= { cucsEquipmentBladeBiosCapProviderEntry 8 }

cucsEquipmentBladeBiosCapProviderVendor OBJECT-TYPE
    SYNTAX       SnmpAdminString
    MAX-ACCESS   read-only
    STATUS       current
    DESCRIPTION
        "Cisco UCS equipment:BladeBiosCapProvider:vendor
        managed object property"
    ::= { cucsEquipmentBladeBiosCapProviderEntry 9 }

cucsEquipmentBladeBiosCapProviderProductName OBJECT-TYPE
    SYNTAX       SnmpAdminString
    MAX-ACCESS   read-only
    STATUS       current
    DESCRIPTION
        "Cisco UCS equipment:BladeBiosCapProvider:productName
        managed object property"
    ::= { cucsEquipmentBladeBiosCapProviderEntry 10 }

cucsEquipmentBladeBiosCapProviderPromCardType OBJECT-TYPE
    SYNTAX       Gauge32
    MAX-ACCESS   read-only
    STATUS       current
    DESCRIPTION
        "Cisco UCS equipment:BladeBiosCapProvider:promCardType
        managed object property"
    ::= { cucsEquipmentBladeBiosCapProviderEntry 11 }

cucsEquipmentBladeBiosCapProviderDeleted OBJECT-TYPE
    SYNTAX       TruthValue
    MAX-ACCESS   read-only
    STATUS       current
    DESCRIPTION
        "Cisco UCS equipment:BladeBiosCapProvider:deleted
        managed object property"
    ::= { cucsEquipmentBladeBiosCapProviderEntry 12 }

cucsEquipmentBladeBiosCapProviderElementLoadFailures OBJECT-TYPE
    SYNTAX       Gauge32
    MAX-ACCESS   read-only
    STATUS       current
    DESCRIPTION
        "Cisco UCS equipment:BladeBiosCapProvider:elementLoadFailures
        managed object property"
    ::= { cucsEquipmentBladeBiosCapProviderEntry 13 }

cucsEquipmentBladeBiosCapProviderElementsLoaded OBJECT-TYPE
    SYNTAX       Gauge32
    MAX-ACCESS   read-only
    STATUS       current
    DESCRIPTION
        "Cisco UCS equipment:BladeBiosCapProvider:elementsLoaded
        managed object property"
    ::= { cucsEquipmentBladeBiosCapProviderEntry 14 }

cucsEquipmentBladeBiosCapProviderLoadErrors OBJECT-TYPE
    SYNTAX       Gauge32
    MAX-ACCESS   read-only
    STATUS       current
    DESCRIPTION
        "Cisco UCS equipment:BladeBiosCapProvider:loadErrors
        managed object property"
    ::= { cucsEquipmentBladeBiosCapProviderEntry 15 }

cucsEquipmentBladeBiosCapProviderLoadWarnings OBJECT-TYPE
    SYNTAX       Gauge32
    MAX-ACCESS   read-only
    STATUS       current
    DESCRIPTION
        "Cisco UCS equipment:BladeBiosCapProvider:loadWarnings
        managed object property"
    ::= { cucsEquipmentBladeBiosCapProviderEntry 16 }

cucsEquipmentBladeCapProviderTable OBJECT-TYPE
    SYNTAX           SEQUENCE OF CucsEquipmentBladeCapProviderEntry
    MAX-ACCESS       not-accessible
    STATUS           current
    DESCRIPTION
        "Cisco UCS equipment:BladeCapProvider managed object table"
    ::= { cucsEquipmentObjects 4 }

cucsEquipmentBladeCapProviderEntry OBJECT-TYPE
    SYNTAX           CucsEquipmentBladeCapProviderEntry
    MAX-ACCESS       not-accessible
    STATUS           current
    DESCRIPTION
        "Entry for the cucsEquipmentBladeCapProviderTable table."
    INDEX { cucsEquipmentBladeCapProviderInstanceId }
    ::= { cucsEquipmentBladeCapProviderTable 1 }

CucsEquipmentBladeCapProviderEntry ::= SEQUENCE {
    cucsEquipmentBladeCapProviderInstanceId                          CucsManagedObjectId,
    cucsEquipmentBladeCapProviderDn                                  CucsManagedObjectDn,
    cucsEquipmentBladeCapProviderRn                                  SnmpAdminString,
    cucsEquipmentBladeCapProviderDeprecated                          TruthValue,
    cucsEquipmentBladeCapProviderGencount                            Gauge32,
    cucsEquipmentBladeCapProviderMgmtPlaneVer                        SnmpAdminString,
    cucsEquipmentBladeCapProviderModel                               SnmpAdminString,
    cucsEquipmentBladeCapProviderRevision                            SnmpAdminString,
    cucsEquipmentBladeCapProviderVendor                              SnmpAdminString,
    cucsEquipmentBladeCapProviderPromCardType                        Gauge32,
    cucsEquipmentBladeCapProviderDeleted                             TruthValue,
    cucsEquipmentBladeCapProviderElementLoadFailures                 Gauge32,
    cucsEquipmentBladeCapProviderElementsLoaded                      Gauge32,
    cucsEquipmentBladeCapProviderLoadErrors                          Gauge32,
    cucsEquipmentBladeCapProviderLoadWarnings                        Gauge32
}

cucsEquipmentBladeCapProviderInstanceId OBJECT-TYPE
    SYNTAX       CucsManagedObjectId
    MAX-ACCESS   not-accessible
    STATUS       current
    DESCRIPTION
        "Instance identifier of the managed object."
    ::= { cucsEquipmentBladeCapProviderEntry 1 }

cucsEquipmentBladeCapProviderDn OBJECT-TYPE
    SYNTAX       CucsManagedObjectDn
    MAX-ACCESS   read-only
    STATUS       current
    DESCRIPTION
        "Cisco UCS equipment:BladeCapProvider:dn managed object property"
    ::= { cucsEquipmentBladeCapProviderEntry 2 }

cucsEquipmentBladeCapProviderRn OBJECT-TYPE
    SYNTAX       SnmpAdminString
    MAX-ACCESS   read-only
    STATUS       current
    DESCRIPTION
        "Cisco UCS equipment:BladeCapProvider:rn managed object property"
    ::= { cucsEquipmentBladeCapProviderEntry 3 }

cucsEquipmentBladeCapProviderDeprecated OBJECT-TYPE
    SYNTAX       TruthValue
    MAX-ACCESS   read-only
    STATUS       current
    DESCRIPTION
        "Cisco UCS equipment:BladeCapProvider:deprecated
        managed object property"
    ::= { cucsEquipmentBladeCapProviderEntry 4 }

cucsEquipmentBladeCapProviderGencount OBJECT-TYPE
    SYNTAX       Gauge32
    MAX-ACCESS   read-only
    STATUS       current
    DESCRIPTION
        "Cisco UCS equipment:BladeCapProvider:gencount
        managed object property"
    ::= { cucsEquipmentBladeCapProviderEntry 5 }

cucsEquipmentBladeCapProviderMgmtPlaneVer OBJECT-TYPE
    SYNTAX       SnmpAdminString
    MAX-ACCESS   read-only
    STATUS       current
    DESCRIPTION
        "Cisco UCS equipment:BladeCapProvider:mgmtPlaneVer
        managed object property"
    ::= { cucsEquipmentBladeCapProviderEntry 6 }

cucsEquipmentBladeCapProviderModel OBJECT-TYPE
    SYNTAX       SnmpAdminString
    MAX-ACCESS   read-only
    STATUS       current
    DESCRIPTION
        "Cisco UCS equipment:BladeCapProvider:model managed
        object property"
    ::= { cucsEquipmentBladeCapProviderEntry 7 }

cucsEquipmentBladeCapProviderRevision OBJECT-TYPE
    SYNTAX       SnmpAdminString
    MAX-ACCESS   read-only
    STATUS       current
    DESCRIPTION
        "Cisco UCS equipment:BladeCapProvider:revision
        managed object property"
    ::= { cucsEquipmentBladeCapProviderEntry 8 }

cucsEquipmentBladeCapProviderVendor OBJECT-TYPE
    SYNTAX       SnmpAdminString
    MAX-ACCESS   read-only
    STATUS       current
    DESCRIPTION
        "Cisco UCS equipment:BladeCapProvider:vendor managed
        object property"
    ::= { cucsEquipmentBladeCapProviderEntry 9 }

cucsEquipmentBladeCapProviderPromCardType OBJECT-TYPE
    SYNTAX       Gauge32
    MAX-ACCESS   read-only
    STATUS       current
    DESCRIPTION
        "Cisco UCS equipment:BladeCapProvider:promCardType
        managed object property"
    ::= { cucsEquipmentBladeCapProviderEntry 10 }

cucsEquipmentBladeCapProviderDeleted OBJECT-TYPE
    SYNTAX       TruthValue
    MAX-ACCESS   read-only
    STATUS       current
    DESCRIPTION
        "Cisco UCS equipment:BladeCapProvider:deleted managed
        object property"
    ::= { cucsEquipmentBladeCapProviderEntry 11 }

cucsEquipmentBladeCapProviderElementLoadFailures OBJECT-TYPE
    SYNTAX       Gauge32
    MAX-ACCESS   read-only
    STATUS       current
    DESCRIPTION
        "Cisco UCS equipment:BladeCapProvider:elementLoadFailures
        managed object property"
    ::= { cucsEquipmentBladeCapProviderEntry 12 }

cucsEquipmentBladeCapProviderElementsLoaded OBJECT-TYPE
    SYNTAX       Gauge32
    MAX-ACCESS   read-only
    STATUS       current
    DESCRIPTION
        "Cisco UCS equipment:BladeCapProvider:elementsLoaded
        managed object property"
    ::= { cucsEquipmentBladeCapProviderEntry 13 }

cucsEquipmentBladeCapProviderLoadErrors OBJECT-TYPE
    SYNTAX       Gauge32
    MAX-ACCESS   read-only
    STATUS       current
    DESCRIPTION
        "Cisco UCS equipment:BladeCapProvider:loadErrors
        managed object property"
    ::= { cucsEquipmentBladeCapProviderEntry 14 }

cucsEquipmentBladeCapProviderLoadWarnings OBJECT-TYPE
    SYNTAX       Gauge32
    MAX-ACCESS   read-only
    STATUS       current
    DESCRIPTION
        "Cisco UCS equipment:BladeCapProvider:loadWarnings
        managed object property"
    ::= { cucsEquipmentBladeCapProviderEntry 15 }

cucsEquipmentBladeConnDefTable OBJECT-TYPE
    SYNTAX           SEQUENCE OF CucsEquipmentBladeConnDefEntry
    MAX-ACCESS       not-accessible
    STATUS           current
    DESCRIPTION
        "Cisco UCS equipment:BladeConnDef managed object table"
    ::= { cucsEquipmentObjects 97 }

cucsEquipmentBladeConnDefEntry OBJECT-TYPE
    SYNTAX           CucsEquipmentBladeConnDefEntry
    MAX-ACCESS       not-accessible
    STATUS           current
    DESCRIPTION
        "Entry for the cucsEquipmentBladeConnDefTable table."
    INDEX { cucsEquipmentBladeConnDefInstanceId }
    ::= { cucsEquipmentBladeConnDefTable 1 }

CucsEquipmentBladeConnDefEntry ::= SEQUENCE {
    cucsEquipmentBladeConnDefInstanceId                              CucsManagedObjectId,
    cucsEquipmentBladeConnDefDn                                      CucsManagedObjectDn,
    cucsEquipmentBladeConnDefRn                                      SnmpAdminString,
    cucsEquipmentBladeConnDefAdaptorFamily                           SnmpAdminString,
    cucsEquipmentBladeConnDefAdaptorSlotNumber                       Gauge32,
    cucsEquipmentBladeConnDefAdaptorSlotSpan                         Gauge32,
    cucsEquipmentBladeConnDefAdaptorType                             SnmpAdminString,
    cucsEquipmentBladeConnDefDescr                                   SnmpAdminString,
    cucsEquipmentBladeConnDefIntId                                   SnmpAdminString,
    cucsEquipmentBladeConnDefName                                    SnmpAdminString,
    cucsEquipmentBladeConnDefParentAdaptorSlotNum                    Gauge32,
    cucsEquipmentBladeConnDefSwitchPortMuxOffset                     Gauge32,
    cucsEquipmentBladeConnDefPolicyLevel                             Gauge32,
    cucsEquipmentBladeConnDefPolicyOwner                             CucsPolicyPolicyOwner
}

cucsEquipmentBladeConnDefInstanceId OBJECT-TYPE
    SYNTAX       CucsManagedObjectId
    MAX-ACCESS   not-accessible
    STATUS       current
    DESCRIPTION
        "Instance identifier of the managed object."
    ::= { cucsEquipmentBladeConnDefEntry 1 }

cucsEquipmentBladeConnDefDn OBJECT-TYPE
    SYNTAX       CucsManagedObjectDn
    MAX-ACCESS   read-only
    STATUS       current
    DESCRIPTION
        "Cisco UCS equipment:BladeConnDef:dn managed object property"
    ::= { cucsEquipmentBladeConnDefEntry 2 }

cucsEquipmentBladeConnDefRn OBJECT-TYPE
    SYNTAX       SnmpAdminString
    MAX-ACCESS   read-only
    STATUS       current
    DESCRIPTION
        "Cisco UCS equipment:BladeConnDef:rn managed object property"
    ::= { cucsEquipmentBladeConnDefEntry 3 }

cucsEquipmentBladeConnDefAdaptorFamily OBJECT-TYPE
    SYNTAX       SnmpAdminString
    MAX-ACCESS   read-only
    STATUS       current
    DESCRIPTION
        "Cisco UCS equipment:BladeConnDef:adaptorFamily
        managed object property"
    ::= { cucsEquipmentBladeConnDefEntry 4 }

cucsEquipmentBladeConnDefAdaptorSlotNumber OBJECT-TYPE
    SYNTAX       Gauge32
    MAX-ACCESS   read-only
    STATUS       current
    DESCRIPTION
        "Cisco UCS equipment:BladeConnDef:adaptorSlotNumber
        managed object property"
    ::= { cucsEquipmentBladeConnDefEntry 5 }

cucsEquipmentBladeConnDefAdaptorSlotSpan OBJECT-TYPE
    SYNTAX       Gauge32
    MAX-ACCESS   read-only
    STATUS       current
    DESCRIPTION
        "Cisco UCS equipment:BladeConnDef:adaptorSlotSpan
        managed object property"
    ::= { cucsEquipmentBladeConnDefEntry 6 }

cucsEquipmentBladeConnDefAdaptorType OBJECT-TYPE
    SYNTAX       SnmpAdminString
    MAX-ACCESS   read-only
    STATUS       current
    DESCRIPTION
        "Cisco UCS equipment:BladeConnDef:adaptorType managed
        object property"
    ::= { cucsEquipmentBladeConnDefEntry 7 }

cucsEquipmentBladeConnDefDescr OBJECT-TYPE
    SYNTAX       SnmpAdminString
    MAX-ACCESS   read-only
    STATUS       current
    DESCRIPTION
        "Cisco UCS equipment:BladeConnDef:descr managed object property"
    ::= { cucsEquipmentBladeConnDefEntry 8 }

cucsEquipmentBladeConnDefIntId OBJECT-TYPE
    SYNTAX       SnmpAdminString
    MAX-ACCESS   read-only
    STATUS       current
    DESCRIPTION
        "Cisco UCS equipment:BladeConnDef:intId managed object property"
    ::= { cucsEquipmentBladeConnDefEntry 9 }

cucsEquipmentBladeConnDefName OBJECT-TYPE
    SYNTAX       SnmpAdminString
    MAX-ACCESS   read-only
    STATUS       current
    DESCRIPTION
        "Cisco UCS equipment:BladeConnDef:name managed object property"
    ::= { cucsEquipmentBladeConnDefEntry 10 }

cucsEquipmentBladeConnDefParentAdaptorSlotNum OBJECT-TYPE
    SYNTAX       Gauge32
    MAX-ACCESS   read-only
    STATUS       current
    DESCRIPTION
        "Cisco UCS equipment:BladeConnDef:parentAdaptorSlotNum
        managed object property"
    ::= { cucsEquipmentBladeConnDefEntry 11 }

cucsEquipmentBladeConnDefSwitchPortMuxOffset OBJECT-TYPE
    SYNTAX       Gauge32
    MAX-ACCESS   read-only
    STATUS       current
    DESCRIPTION
        "Cisco UCS equipment:BladeConnDef:switchPortMuxOffset
        managed object property"
    ::= { cucsEquipmentBladeConnDefEntry 12 }

cucsEquipmentBladeConnDefPolicyLevel OBJECT-TYPE
    SYNTAX       Gauge32
    MAX-ACCESS   read-only
    STATUS       current
    DESCRIPTION
        "Cisco UCS equipment:BladeConnDef:policyLevel managed
        object property"
    ::= { cucsEquipmentBladeConnDefEntry 13 }

cucsEquipmentBladeConnDefPolicyOwner OBJECT-TYPE
    SYNTAX       CucsPolicyPolicyOwner
    MAX-ACCESS   read-only
    STATUS       current
    DESCRIPTION
        "Cisco UCS equipment:BladeConnDef:policyOwner managed
        object property"
    ::= { cucsEquipmentBladeConnDefEntry 14 }

cucsEquipmentBladeIOMConnDefTable OBJECT-TYPE
    SYNTAX           SEQUENCE OF CucsEquipmentBladeIOMConnDefEntry
    MAX-ACCESS       not-accessible
    STATUS           current
    DESCRIPTION
        "Cisco UCS equipment:BladeIOMConnDef managed object table"
    ::= { cucsEquipmentObjects 98 }

cucsEquipmentBladeIOMConnDefEntry OBJECT-TYPE
    SYNTAX           CucsEquipmentBladeIOMConnDefEntry
    MAX-ACCESS       not-accessible
    STATUS           current
    DESCRIPTION
        "Entry for the cucsEquipmentBladeIOMConnDefTable table."
    INDEX { cucsEquipmentBladeIOMConnDefInstanceId }
    ::= { cucsEquipmentBladeIOMConnDefTable 1 }

CucsEquipmentBladeIOMConnDefEntry ::= SEQUENCE {
    cucsEquipmentBladeIOMConnDefInstanceId                           CucsManagedObjectId,
    cucsEquipmentBladeIOMConnDefDn                                   CucsManagedObjectDn,
    cucsEquipmentBladeIOMConnDefRn                                   SnmpAdminString,
    cucsEquipmentBladeIOMConnDefDescr                                SnmpAdminString,
    cucsEquipmentBladeIOMConnDefIntId                                SnmpAdminString,
    cucsEquipmentBladeIOMConnDefIocardType                           SnmpAdminString,
    cucsEquipmentBladeIOMConnDefName                                 SnmpAdminString,
    cucsEquipmentBladeIOMConnDefPortBandwidth                        CucsPortEthSpeed,
    cucsEquipmentBladeIOMConnDefPolicyLevel                          Gauge32,
    cucsEquipmentBladeIOMConnDefPolicyOwner                          CucsPolicyPolicyOwner
}

cucsEquipmentBladeIOMConnDefInstanceId OBJECT-TYPE
    SYNTAX       CucsManagedObjectId
    MAX-ACCESS   not-accessible
    STATUS       current
    DESCRIPTION
        "Instance identifier of the managed object."
    ::= { cucsEquipmentBladeIOMConnDefEntry 1 }

cucsEquipmentBladeIOMConnDefDn OBJECT-TYPE
    SYNTAX       CucsManagedObjectDn
    MAX-ACCESS   read-only
    STATUS       current
    DESCRIPTION
        "Cisco UCS equipment:BladeIOMConnDef:dn managed object property"
    ::= { cucsEquipmentBladeIOMConnDefEntry 2 }

cucsEquipmentBladeIOMConnDefRn OBJECT-TYPE
    SYNTAX       SnmpAdminString
    MAX-ACCESS   read-only
    STATUS       current
    DESCRIPTION
        "Cisco UCS equipment:BladeIOMConnDef:rn managed object property"
    ::= { cucsEquipmentBladeIOMConnDefEntry 3 }

cucsEquipmentBladeIOMConnDefDescr OBJECT-TYPE
    SYNTAX       SnmpAdminString
    MAX-ACCESS   read-only
    STATUS       current
    DESCRIPTION
        "Cisco UCS equipment:BladeIOMConnDef:descr managed
        object property"
    ::= { cucsEquipmentBladeIOMConnDefEntry 4 }

cucsEquipmentBladeIOMConnDefIntId OBJECT-TYPE
    SYNTAX       SnmpAdminString
    MAX-ACCESS   read-only
    STATUS       current
    DESCRIPTION
        "Cisco UCS equipment:BladeIOMConnDef:intId managed
        object property"
    ::= { cucsEquipmentBladeIOMConnDefEntry 5 }

cucsEquipmentBladeIOMConnDefIocardType OBJECT-TYPE
    SYNTAX       SnmpAdminString
    MAX-ACCESS   read-only
    STATUS       current
    DESCRIPTION
        "Cisco UCS equipment:BladeIOMConnDef:iocardType
        managed object property"
    ::= { cucsEquipmentBladeIOMConnDefEntry 6 }

cucsEquipmentBladeIOMConnDefName OBJECT-TYPE
    SYNTAX       SnmpAdminString
    MAX-ACCESS   read-only
    STATUS       current
    DESCRIPTION
        "Cisco UCS equipment:BladeIOMConnDef:name managed object property"
    ::= { cucsEquipmentBladeIOMConnDefEntry 7 }

cucsEquipmentBladeIOMConnDefPortBandwidth OBJECT-TYPE
    SYNTAX       CucsPortEthSpeed
    MAX-ACCESS   read-only
    STATUS       current
    DESCRIPTION
        "Cisco UCS equipment:BladeIOMConnDef:portBandwidth
        managed object property"
    ::= { cucsEquipmentBladeIOMConnDefEntry 8 }

cucsEquipmentBladeIOMConnDefPolicyLevel OBJECT-TYPE
    SYNTAX       Gauge32
    MAX-ACCESS   read-only
    STATUS       current
    DESCRIPTION
        "Cisco UCS equipment:BladeIOMConnDef:policyLevel
        managed object property"
    ::= { cucsEquipmentBladeIOMConnDefEntry 9 }

cucsEquipmentBladeIOMConnDefPolicyOwner OBJECT-TYPE
    SYNTAX       CucsPolicyPolicyOwner
    MAX-ACCESS   read-only
    STATUS       current
    DESCRIPTION
        "Cisco UCS equipment:BladeIOMConnDef:policyOwner
        managed object property"
    ::= { cucsEquipmentBladeIOMConnDefEntry 10 }

cucsEquipmentBoardControllerDefTable OBJECT-TYPE
    SYNTAX           SEQUENCE OF CucsEquipmentBoardControllerDefEntry
    MAX-ACCESS       not-accessible
    STATUS           current
    DESCRIPTION
        "Cisco UCS equipment:BoardControllerDef managed object table"
    ::= { cucsEquipmentObjects 5 }

cucsEquipmentBoardControllerDefEntry OBJECT-TYPE
    SYNTAX           CucsEquipmentBoardControllerDefEntry
    MAX-ACCESS       not-accessible
    STATUS           current
    DESCRIPTION
        "Entry for the cucsEquipmentBoardControllerDefTable table."
    INDEX { cucsEquipmentBoardControllerDefInstanceId }
    ::= { cucsEquipmentBoardControllerDefTable 1 }

CucsEquipmentBoardControllerDefEntry ::= SEQUENCE {
    cucsEquipmentBoardControllerDefInstanceId                        CucsManagedObjectId,
    cucsEquipmentBoardControllerDefDn                                CucsManagedObjectDn,
    cucsEquipmentBoardControllerDefRn                                SnmpAdminString,
    cucsEquipmentBoardControllerDefDescr                             SnmpAdminString,
    cucsEquipmentBoardControllerDefIntId                             SnmpAdminString,
    cucsEquipmentBoardControllerDefName                              SnmpAdminString,
    cucsEquipmentBoardControllerDefPolicyLevel                       Gauge32,
    cucsEquipmentBoardControllerDefPolicyOwner                       CucsPolicyPolicyOwner
}

cucsEquipmentBoardControllerDefInstanceId OBJECT-TYPE
    SYNTAX       CucsManagedObjectId
    MAX-ACCESS   not-accessible
    STATUS       current
    DESCRIPTION
        "Instance identifier of the managed object."
    ::= { cucsEquipmentBoardControllerDefEntry 1 }

cucsEquipmentBoardControllerDefDn OBJECT-TYPE
    SYNTAX       CucsManagedObjectDn
    MAX-ACCESS   read-only
    STATUS       current
    DESCRIPTION
        "Cisco UCS equipment:BoardControllerDef:dn managed
        object property"
    ::= { cucsEquipmentBoardControllerDefEntry 2 }

cucsEquipmentBoardControllerDefRn OBJECT-TYPE
    SYNTAX       SnmpAdminString
    MAX-ACCESS   read-only
    STATUS       current
    DESCRIPTION
        "Cisco UCS equipment:BoardControllerDef:rn managed
        object property"
    ::= { cucsEquipmentBoardControllerDefEntry 3 }

cucsEquipmentBoardControllerDefDescr OBJECT-TYPE
    SYNTAX       SnmpAdminString
    MAX-ACCESS   read-only
    STATUS       current
    DESCRIPTION
        "Cisco UCS equipment:BoardControllerDef:descr managed
        object property"
    ::= { cucsEquipmentBoardControllerDefEntry 4 }

cucsEquipmentBoardControllerDefIntId OBJECT-TYPE
    SYNTAX       SnmpAdminString
    MAX-ACCESS   read-only
    STATUS       current
    DESCRIPTION
        "Cisco UCS equipment:BoardControllerDef:intId managed
        object property"
    ::= { cucsEquipmentBoardControllerDefEntry 5 }

cucsEquipmentBoardControllerDefName OBJECT-TYPE
    SYNTAX       SnmpAdminString
    MAX-ACCESS   read-only
    STATUS       current
    DESCRIPTION
        "Cisco UCS equipment:BoardControllerDef:name managed
        object property"
    ::= { cucsEquipmentBoardControllerDefEntry 6 }

cucsEquipmentBoardControllerDefPolicyLevel OBJECT-TYPE
    SYNTAX       Gauge32
    MAX-ACCESS   read-only
    STATUS       current
    DESCRIPTION
        "Cisco UCS equipment:BoardControllerDef:policyLevel
        managed object property"
    ::= { cucsEquipmentBoardControllerDefEntry 7 }

cucsEquipmentBoardControllerDefPolicyOwner OBJECT-TYPE
    SYNTAX       CucsPolicyPolicyOwner
    MAX-ACCESS   read-only
    STATUS       current
    DESCRIPTION
        "Cisco UCS equipment:BoardControllerDef:policyOwner
        managed object property"
    ::= { cucsEquipmentBoardControllerDefEntry 8 }

cucsEquipmentCatalogCapProviderTable OBJECT-TYPE
    SYNTAX           SEQUENCE OF CucsEquipmentCatalogCapProviderEntry
    MAX-ACCESS       not-accessible
    STATUS           current
    DESCRIPTION
        "Cisco UCS equipment:CatalogCapProvider managed object table"
    ::= { cucsEquipmentObjects 6 }

cucsEquipmentCatalogCapProviderEntry OBJECT-TYPE
    SYNTAX           CucsEquipmentCatalogCapProviderEntry
    MAX-ACCESS       not-accessible
    STATUS           current
    DESCRIPTION
        "Entry for the cucsEquipmentCatalogCapProviderTable table."
    INDEX { cucsEquipmentCatalogCapProviderInstanceId }
    ::= { cucsEquipmentCatalogCapProviderTable 1 }

CucsEquipmentCatalogCapProviderEntry ::= SEQUENCE {
    cucsEquipmentCatalogCapProviderInstanceId                        CucsManagedObjectId,
    cucsEquipmentCatalogCapProviderDn                                CucsManagedObjectDn,
    cucsEquipmentCatalogCapProviderRn                                SnmpAdminString,
    cucsEquipmentCatalogCapProviderDeprecated                        TruthValue,
    cucsEquipmentCatalogCapProviderGencount                          Gauge32,
    cucsEquipmentCatalogCapProviderMgmtPlaneVer                      SnmpAdminString,
    cucsEquipmentCatalogCapProviderModel                             SnmpAdminString,
    cucsEquipmentCatalogCapProviderRevision                          SnmpAdminString,
    cucsEquipmentCatalogCapProviderVendor                            SnmpAdminString,
    cucsEquipmentCatalogCapProviderPromCardType                      Gauge32,
    cucsEquipmentCatalogCapProviderDeleted                           TruthValue,
    cucsEquipmentCatalogCapProviderElementLoadFailures               Gauge32,
    cucsEquipmentCatalogCapProviderElementsLoaded                    Gauge32,
    cucsEquipmentCatalogCapProviderLoadErrors                        Gauge32,
    cucsEquipmentCatalogCapProviderLoadWarnings                      Gauge32
}

cucsEquipmentCatalogCapProviderInstanceId OBJECT-TYPE
    SYNTAX       CucsManagedObjectId
    MAX-ACCESS   not-accessible
    STATUS       current
    DESCRIPTION
        "Instance identifier of the managed object."
    ::= { cucsEquipmentCatalogCapProviderEntry 1 }

cucsEquipmentCatalogCapProviderDn OBJECT-TYPE
    SYNTAX       CucsManagedObjectDn
    MAX-ACCESS   read-only
    STATUS       current
    DESCRIPTION
        "Cisco UCS equipment:CatalogCapProvider:dn managed
        object property"
    ::= { cucsEquipmentCatalogCapProviderEntry 2 }

cucsEquipmentCatalogCapProviderRn OBJECT-TYPE
    SYNTAX       SnmpAdminString
    MAX-ACCESS   read-only
    STATUS       current
    DESCRIPTION
        "Cisco UCS equipment:CatalogCapProvider:rn managed
        object property"
    ::= { cucsEquipmentCatalogCapProviderEntry 3 }

cucsEquipmentCatalogCapProviderDeprecated OBJECT-TYPE
    SYNTAX       TruthValue
    MAX-ACCESS   read-only
    STATUS       current
    DESCRIPTION
        "Cisco UCS equipment:CatalogCapProvider:deprecated
        managed object property"
    ::= { cucsEquipmentCatalogCapProviderEntry 4 }

cucsEquipmentCatalogCapProviderGencount OBJECT-TYPE
    SYNTAX       Gauge32
    MAX-ACCESS   read-only
    STATUS       current
    DESCRIPTION
        "Cisco UCS equipment:CatalogCapProvider:gencount
        managed object property"
    ::= { cucsEquipmentCatalogCapProviderEntry 5 }

cucsEquipmentCatalogCapProviderMgmtPlaneVer OBJECT-TYPE
    SYNTAX       SnmpAdminString
    MAX-ACCESS   read-only
    STATUS       current
    DESCRIPTION
        "Cisco UCS equipment:CatalogCapProvider:mgmtPlaneVer
        managed object property"
    ::= { cucsEquipmentCatalogCapProviderEntry 6 }

cucsEquipmentCatalogCapProviderModel OBJECT-TYPE
    SYNTAX       SnmpAdminString
    MAX-ACCESS   read-only
    STATUS       current
    DESCRIPTION
        "Cisco UCS equipment:CatalogCapProvider:model managed
        object property"
    ::= { cucsEquipmentCatalogCapProviderEntry 7 }

cucsEquipmentCatalogCapProviderRevision OBJECT-TYPE
    SYNTAX       SnmpAdminString
    MAX-ACCESS   read-only
    STATUS       current
    DESCRIPTION
        "Cisco UCS equipment:CatalogCapProvider:revision
        managed object property"
    ::= { cucsEquipmentCatalogCapProviderEntry 8 }

cucsEquipmentCatalogCapProviderVendor OBJECT-TYPE
    SYNTAX       SnmpAdminString
    MAX-ACCESS   read-only
    STATUS       current
    DESCRIPTION
        "Cisco UCS equipment:CatalogCapProvider:vendor
        managed object property"
    ::= { cucsEquipmentCatalogCapProviderEntry 9 }

cucsEquipmentCatalogCapProviderPromCardType OBJECT-TYPE
    SYNTAX       Gauge32
    MAX-ACCESS   read-only
    STATUS       current
    DESCRIPTION
        "Cisco UCS equipment:CatalogCapProvider:promCardType
        managed object property"
    ::= { cucsEquipmentCatalogCapProviderEntry 10 }

cucsEquipmentCatalogCapProviderDeleted OBJECT-TYPE
    SYNTAX       TruthValue
    MAX-ACCESS   read-only
    STATUS       current
    DESCRIPTION
        "Cisco UCS equipment:CatalogCapProvider:deleted
        managed object property"
    ::= { cucsEquipmentCatalogCapProviderEntry 11 }

cucsEquipmentCatalogCapProviderElementLoadFailures OBJECT-TYPE
    SYNTAX       Gauge32
    MAX-ACCESS   read-only
    STATUS       current
    DESCRIPTION
        "Cisco UCS equipment:CatalogCapProvider:elementLoadFailures
        managed object property"
    ::= { cucsEquipmentCatalogCapProviderEntry 12 }

cucsEquipmentCatalogCapProviderElementsLoaded OBJECT-TYPE
    SYNTAX       Gauge32
    MAX-ACCESS   read-only
    STATUS       current
    DESCRIPTION
        "Cisco UCS equipment:CatalogCapProvider:elementsLoaded
        managed object property"
    ::= { cucsEquipmentCatalogCapProviderEntry 13 }

cucsEquipmentCatalogCapProviderLoadErrors OBJECT-TYPE
    SYNTAX       Gauge32
    MAX-ACCESS   read-only
    STATUS       current
    DESCRIPTION
        "Cisco UCS equipment:CatalogCapProvider:loadErrors
        managed object property"
    ::= { cucsEquipmentCatalogCapProviderEntry 14 }

cucsEquipmentCatalogCapProviderLoadWarnings OBJECT-TYPE
    SYNTAX       Gauge32
    MAX-ACCESS   read-only
    STATUS       current
    DESCRIPTION
        "Cisco UCS equipment:CatalogCapProvider:loadWarnings
        managed object property"
    ::= { cucsEquipmentCatalogCapProviderEntry 15 }

cucsEquipmentChassisTable OBJECT-TYPE
    SYNTAX           SEQUENCE OF CucsEquipmentChassisEntry
    MAX-ACCESS       not-accessible
    STATUS           current
    DESCRIPTION
        "Cisco UCS equipment:Chassis managed object table"
    ::= { cucsEquipmentObjects 7 }

cucsEquipmentChassisEntry OBJECT-TYPE
    SYNTAX           CucsEquipmentChassisEntry
    MAX-ACCESS       not-accessible
    STATUS           current
    DESCRIPTION
        "Entry for the cucsEquipmentChassisTable table."
    INDEX { cucsEquipmentChassisInstanceId }
    ::= { cucsEquipmentChassisTable 1 }

CucsEquipmentChassisEntry ::= SEQUENCE {
    cucsEquipmentChassisInstanceId                                   CucsManagedObjectId,
    cucsEquipmentChassisDn                                           CucsManagedObjectDn,
    cucsEquipmentChassisRn                                           SnmpAdminString,
    cucsEquipmentChassisAdminState                                   CucsEquipmentChassisAdminState,
    cucsEquipmentChassisConfigState                                  CucsEquipmentChassisConfigState,
    cucsEquipmentChassisConnPath                                     CucsEquipmentConnectionStatus,
    cucsEquipmentChassisConnStatus                                   CucsEquipmentConnectionStatus,
    cucsEquipmentChassisFabricEpDn                                   SnmpAdminString,
    cucsEquipmentChassisFltAggr                                      Unsigned64,
    cucsEquipmentChassisFsmDescr                                     SnmpAdminString,
    cucsEquipmentChassisFsmPrev                                      SnmpAdminString,
    cucsEquipmentChassisFsmProgr                                     Gauge32,
    cucsEquipmentChassisFsmRmtInvErrCode                             Gauge32,
    cucsEquipmentChassisFsmRmtInvErrDescr                            SnmpAdminString,
    cucsEquipmentChassisFsmRmtInvRslt                                CucsConditionRemoteInvRslt,
    cucsEquipmentChassisFsmStageDescr                                SnmpAdminString,
    cucsEquipmentChassisFsmStamp                                     DateAndTime,
    cucsEquipmentChassisFsmStatus                                    SnmpAdminString,
    cucsEquipmentChassisFsmTry                                       Gauge32,
    cucsEquipmentChassisId                                           CucsEquipmentChassisId,
    cucsEquipmentChassisLcTs                                         DateAndTime,
    cucsEquipmentChassisLicGP                                        Unsigned64,
    cucsEquipmentChassisLicState                                     CucsLicenseState,
    cucsEquipmentChassisManagingInst                                 CucsNetworkSwitchId,
    cucsEquipmentChassisModel                                        SnmpAdminString,
    cucsEquipmentChassisOperQualifier                                CucsEquipmentChassisIssues,
    cucsEquipmentChassisOperState                                    CucsEquipmentOperability,
    cucsEquipmentChassisOperability                                  CucsEquipmentOperability,
    cucsEquipmentChassisPower                                        CucsEquipmentChassisPowerOperState,
    cucsEquipmentChassisPresence                                     CucsEquipmentPresence,
    cucsEquipmentChassisRevision                                     SnmpAdminString,
    cucsEquipmentChassisSerial                                       SnmpAdminString,
    cucsEquipmentChassisThermal                                      CucsEquipmentSensorThresholdStatus,
    cucsEquipmentChassisUsrLbl                                       SnmpAdminString,
    cucsEquipmentChassisVendor                                       SnmpAdminString,
    cucsEquipmentChassisVersionHolder                                TruthValue,
    cucsEquipmentChassisAckProgressIndicator                         CucsEquipmentChassisConfigProgressIndicator,
    cucsEquipmentChassisSeepromOperState                             CucsEquipmentOperability,
    cucsEquipmentChassisMfgTime                                      DateAndTime,
    cucsEquipmentChassisThermalStateQualifier                        SnmpAdminString,
    cucsEquipmentChassisOperQualifierReason                          SnmpAdminString
}

cucsEquipmentChassisInstanceId OBJECT-TYPE
    SYNTAX       CucsManagedObjectId
    MAX-ACCESS   not-accessible
    STATUS       current
    DESCRIPTION
        "Instance identifier of the managed object."
    ::= { cucsEquipmentChassisEntry 1 }

cucsEquipmentChassisDn OBJECT-TYPE
    SYNTAX       CucsManagedObjectDn
    MAX-ACCESS   read-only
    STATUS       current
    DESCRIPTION
        "Cisco UCS equipment:Chassis:dn managed object property"
    ::= { cucsEquipmentChassisEntry 2 }

cucsEquipmentChassisRn OBJECT-TYPE
    SYNTAX       SnmpAdminString
    MAX-ACCESS   read-only
    STATUS       current
    DESCRIPTION
        "Cisco UCS equipment:Chassis:rn managed object property"
    ::= { cucsEquipmentChassisEntry 3 }

cucsEquipmentChassisAdminState OBJECT-TYPE
    SYNTAX       CucsEquipmentChassisAdminState
    MAX-ACCESS   read-only
    STATUS       current
    DESCRIPTION
        "Cisco UCS equipment:Chassis:adminState managed object property"
    ::= { cucsEquipmentChassisEntry 4 }

cucsEquipmentChassisConfigState OBJECT-TYPE
    SYNTAX       CucsEquipmentChassisConfigState
    MAX-ACCESS   read-only
    STATUS       current
    DESCRIPTION
        "Cisco UCS equipment:Chassis:configState managed object property"
    ::= { cucsEquipmentChassisEntry 5 }

cucsEquipmentChassisConnPath OBJECT-TYPE
    SYNTAX       CucsEquipmentConnectionStatus
    MAX-ACCESS   read-only
    STATUS       current
    DESCRIPTION
        "Cisco UCS equipment:Chassis:connPath managed object property"
    ::= { cucsEquipmentChassisEntry 6 }

cucsEquipmentChassisConnStatus OBJECT-TYPE
    SYNTAX       CucsEquipmentConnectionStatus
    MAX-ACCESS   read-only
    STATUS       current
    DESCRIPTION
        "Cisco UCS equipment:Chassis:connStatus managed object property"
    ::= { cucsEquipmentChassisEntry 7 }

cucsEquipmentChassisFabricEpDn OBJECT-TYPE
    SYNTAX       SnmpAdminString
    MAX-ACCESS   read-only
    STATUS       current
    DESCRIPTION
        "Cisco UCS equipment:Chassis:fabricEpDn managed object property"
    ::= { cucsEquipmentChassisEntry 8 }

cucsEquipmentChassisFltAggr OBJECT-TYPE
    SYNTAX       Unsigned64
    MAX-ACCESS   read-only
    STATUS       current
    DESCRIPTION
        "Cisco UCS equipment:Chassis:fltAggr managed object property"
    ::= { cucsEquipmentChassisEntry 9 }

cucsEquipmentChassisFsmDescr OBJECT-TYPE
    SYNTAX       SnmpAdminString
    MAX-ACCESS   read-only
    STATUS       current
    DESCRIPTION
        "Cisco UCS equipment:Chassis:fsmDescr managed object property"
    ::= { cucsEquipmentChassisEntry 10 }

cucsEquipmentChassisFsmPrev OBJECT-TYPE
    SYNTAX       SnmpAdminString
    MAX-ACCESS   read-only
    STATUS       current
    DESCRIPTION
        "Cisco UCS equipment:Chassis:fsmPrev managed object property"
    ::= { cucsEquipmentChassisEntry 11 }

cucsEquipmentChassisFsmProgr OBJECT-TYPE
    SYNTAX       Gauge32
    MAX-ACCESS   read-only
    STATUS       current
    DESCRIPTION
        "Cisco UCS equipment:Chassis:fsmProgr managed object property"
    ::= { cucsEquipmentChassisEntry 12 }

cucsEquipmentChassisFsmRmtInvErrCode OBJECT-TYPE
    SYNTAX       Gauge32
    MAX-ACCESS   read-only
    STATUS       current
    DESCRIPTION
        "Cisco UCS equipment:Chassis:fsmRmtInvErrCode managed
        object property"
    ::= { cucsEquipmentChassisEntry 13 }

cucsEquipmentChassisFsmRmtInvErrDescr OBJECT-TYPE
    SYNTAX       SnmpAdminString
    MAX-ACCESS   read-only
    STATUS       current
    DESCRIPTION
        "Cisco UCS equipment:Chassis:fsmRmtInvErrDescr
        managed object property"
    ::= { cucsEquipmentChassisEntry 14 }

cucsEquipmentChassisFsmRmtInvRslt OBJECT-TYPE
    SYNTAX       CucsConditionRemoteInvRslt
    MAX-ACCESS   read-only
    STATUS       current
    DESCRIPTION
        "Cisco UCS equipment:Chassis:fsmRmtInvRslt managed
        object property"
    ::= { cucsEquipmentChassisEntry 15 }

cucsEquipmentChassisFsmStageDescr OBJECT-TYPE
    SYNTAX       SnmpAdminString
    MAX-ACCESS   read-only
    STATUS       current
    DESCRIPTION
        "Cisco UCS equipment:Chassis:fsmStageDescr managed
        object property"
    ::= { cucsEquipmentChassisEntry 16 }

cucsEquipmentChassisFsmStamp OBJECT-TYPE
    SYNTAX       DateAndTime
    MAX-ACCESS   read-only
    STATUS       current
    DESCRIPTION
        "Cisco UCS equipment:Chassis:fsmStamp managed object property"
    ::= { cucsEquipmentChassisEntry 17 }

cucsEquipmentChassisFsmStatus OBJECT-TYPE
    SYNTAX       SnmpAdminString
    MAX-ACCESS   read-only
    STATUS       current
    DESCRIPTION
        "Cisco UCS equipment:Chassis:fsmStatus managed object property"
    ::= { cucsEquipmentChassisEntry 18 }

cucsEquipmentChassisFsmTry OBJECT-TYPE
    SYNTAX       Gauge32
    MAX-ACCESS   read-only
    STATUS       current
    DESCRIPTION
        "Cisco UCS equipment:Chassis:fsmTry managed object property"
    ::= { cucsEquipmentChassisEntry 19 }

cucsEquipmentChassisId OBJECT-TYPE
    SYNTAX       CucsEquipmentChassisId
    MAX-ACCESS   read-only
    STATUS       current
    DESCRIPTION
        "Cisco UCS equipment:Chassis:id managed object property"
    ::= { cucsEquipmentChassisEntry 20 }

cucsEquipmentChassisLcTs OBJECT-TYPE
    SYNTAX       DateAndTime
    MAX-ACCESS   read-only
    STATUS       current
    DESCRIPTION
        "Cisco UCS equipment:Chassis:lcTs managed object property"
    ::= { cucsEquipmentChassisEntry 21 }

cucsEquipmentChassisLicGP OBJECT-TYPE
    SYNTAX       Unsigned64
    MAX-ACCESS   read-only
    STATUS       current
    DESCRIPTION
        "Cisco UCS equipment:Chassis:licGP managed object property"
    ::= { cucsEquipmentChassisEntry 22 }

cucsEquipmentChassisLicState OBJECT-TYPE
    SYNTAX       CucsLicenseState
    MAX-ACCESS   read-only
    STATUS       current
    DESCRIPTION
        "Cisco UCS equipment:Chassis:licState managed object property"
    ::= { cucsEquipmentChassisEntry 23 }

cucsEquipmentChassisManagingInst OBJECT-TYPE
    SYNTAX       CucsNetworkSwitchId
    MAX-ACCESS   read-only
    STATUS       current
    DESCRIPTION
        "Cisco UCS equipment:Chassis:managingInst managed object property"
    ::= { cucsEquipmentChassisEntry 24 }

cucsEquipmentChassisModel OBJECT-TYPE
    SYNTAX       SnmpAdminString
    MAX-ACCESS   read-only
    STATUS       current
    DESCRIPTION
        "Cisco UCS equipment:Chassis:model managed object property"
    ::= { cucsEquipmentChassisEntry 25 }

cucsEquipmentChassisOperQualifier OBJECT-TYPE
    SYNTAX       CucsEquipmentChassisIssues
    MAX-ACCESS   read-only
    STATUS       current
    DESCRIPTION
        "Cisco UCS equipment:Chassis:operQualifier managed
        object property"
    ::= { cucsEquipmentChassisEntry 26 }

cucsEquipmentChassisOperState OBJECT-TYPE
    SYNTAX       CucsEquipmentOperability
    MAX-ACCESS   read-only
    STATUS       current
    DESCRIPTION
        "Cisco UCS equipment:Chassis:operState managed object property"
    ::= { cucsEquipmentChassisEntry 27 }

cucsEquipmentChassisOperability OBJECT-TYPE
    SYNTAX       CucsEquipmentOperability
    MAX-ACCESS   read-only
    STATUS       current
    DESCRIPTION
        "Cisco UCS equipment:Chassis:operability managed object property"
    ::= { cucsEquipmentChassisEntry 28 }

cucsEquipmentChassisPower OBJECT-TYPE
    SYNTAX       CucsEquipmentChassisPowerOperState
    MAX-ACCESS   read-only
    STATUS       current
    DESCRIPTION
        "Cisco UCS equipment:Chassis:power managed object property"
    ::= { cucsEquipmentChassisEntry 29 }

cucsEquipmentChassisPresence OBJECT-TYPE
    SYNTAX       CucsEquipmentPresence
    MAX-ACCESS   read-only
    STATUS       current
    DESCRIPTION
        "Cisco UCS equipment:Chassis:presence managed object property"
    ::= { cucsEquipmentChassisEntry 30 }

cucsEquipmentChassisRevision OBJECT-TYPE
    SYNTAX       SnmpAdminString
    MAX-ACCESS   read-only
    STATUS       current
    DESCRIPTION
        "Cisco UCS equipment:Chassis:revision managed object property"
    ::= { cucsEquipmentChassisEntry 31 }

cucsEquipmentChassisSerial OBJECT-TYPE
    SYNTAX       SnmpAdminString
    MAX-ACCESS   read-only
    STATUS       current
    DESCRIPTION
        "Cisco UCS equipment:Chassis:serial managed object property"
    ::= { cucsEquipmentChassisEntry 32 }

cucsEquipmentChassisThermal OBJECT-TYPE
    SYNTAX       CucsEquipmentSensorThresholdStatus
    MAX-ACCESS   read-only
    STATUS       current
    DESCRIPTION
        "Cisco UCS equipment:Chassis:thermal managed object property"
    ::= { cucsEquipmentChassisEntry 33 }

cucsEquipmentChassisUsrLbl OBJECT-TYPE
    SYNTAX       SnmpAdminString
    MAX-ACCESS   read-only
    STATUS       current
    DESCRIPTION
        "Cisco UCS equipment:Chassis:usrLbl managed object property"
    ::= { cucsEquipmentChassisEntry 34 }

cucsEquipmentChassisVendor OBJECT-TYPE
    SYNTAX       SnmpAdminString
    MAX-ACCESS   read-only
    STATUS       current
    DESCRIPTION
        "Cisco UCS equipment:Chassis:vendor managed object property"
    ::= { cucsEquipmentChassisEntry 35 }

cucsEquipmentChassisVersionHolder OBJECT-TYPE
    SYNTAX       TruthValue
    MAX-ACCESS   read-only
    STATUS       current
    DESCRIPTION
        "Cisco UCS equipment:Chassis:versionHolder managed
        object property"
    ::= { cucsEquipmentChassisEntry 36 }

cucsEquipmentChassisAckProgressIndicator OBJECT-TYPE
    SYNTAX       CucsEquipmentChassisConfigProgressIndicator
    MAX-ACCESS   read-only
    STATUS       current
    DESCRIPTION
        "Cisco UCS equipment:Chassis:ackProgressIndicator
        managed object property"
    ::= { cucsEquipmentChassisEntry 37 }

cucsEquipmentChassisSeepromOperState OBJECT-TYPE
    SYNTAX       CucsEquipmentOperability
    MAX-ACCESS   read-only
    STATUS       current
    DESCRIPTION
        "Cisco UCS equipment:Chassis:seepromOperState managed
        object property"
    ::= { cucsEquipmentChassisEntry 38 }

cucsEquipmentChassisMfgTime OBJECT-TYPE
    SYNTAX       DateAndTime
    MAX-ACCESS   read-only
    STATUS       current
    DESCRIPTION
        "Cisco UCS equipment:Chassis:mfgTime managed object property"
    ::= { cucsEquipmentChassisEntry 39 }

cucsEquipmentChassisThermalStateQualifier OBJECT-TYPE
    SYNTAX       SnmpAdminString
    MAX-ACCESS   read-only
    STATUS       current
    DESCRIPTION
        "Cisco UCS equipment:Chassis:thermalStateQualifier
        managed object property"
    ::= { cucsEquipmentChassisEntry 40 }

cucsEquipmentChassisOperQualifierReason OBJECT-TYPE
    SYNTAX       SnmpAdminString
    MAX-ACCESS   read-only
    STATUS       current
    DESCRIPTION
        "Cisco UCS equipment:Chassis:operQualifierReason
        managed object property"
    ::= { cucsEquipmentChassisEntry 41 }

cucsEquipmentChassisCapProviderTable OBJECT-TYPE
    SYNTAX           SEQUENCE OF CucsEquipmentChassisCapProviderEntry
    MAX-ACCESS       not-accessible
    STATUS           current
    DESCRIPTION
        "Cisco UCS equipment:ChassisCapProvider managed object table"
    ::= { cucsEquipmentObjects 8 }

cucsEquipmentChassisCapProviderEntry OBJECT-TYPE
    SYNTAX           CucsEquipmentChassisCapProviderEntry
    MAX-ACCESS       not-accessible
    STATUS           current
    DESCRIPTION
        "Entry for the cucsEquipmentChassisCapProviderTable table."
    INDEX { cucsEquipmentChassisCapProviderInstanceId }
    ::= { cucsEquipmentChassisCapProviderTable 1 }

CucsEquipmentChassisCapProviderEntry ::= SEQUENCE {
    cucsEquipmentChassisCapProviderInstanceId                        CucsManagedObjectId,
    cucsEquipmentChassisCapProviderDn                                CucsManagedObjectDn,
    cucsEquipmentChassisCapProviderRn                                SnmpAdminString,
    cucsEquipmentChassisCapProviderDeprecated                        TruthValue,
    cucsEquipmentChassisCapProviderGencount                          Gauge32,
    cucsEquipmentChassisCapProviderMgmtPlaneVer                      SnmpAdminString,
    cucsEquipmentChassisCapProviderModel                             SnmpAdminString,
    cucsEquipmentChassisCapProviderRevision                          SnmpAdminString,
    cucsEquipmentChassisCapProviderVendor                            SnmpAdminString,
    cucsEquipmentChassisCapProviderPromCardType                      Gauge32,
    cucsEquipmentChassisCapProviderDeleted                           TruthValue,
    cucsEquipmentChassisCapProviderElementLoadFailures               Gauge32,
    cucsEquipmentChassisCapProviderElementsLoaded                    Gauge32,
    cucsEquipmentChassisCapProviderLoadErrors                        Gauge32,
    cucsEquipmentChassisCapProviderLoadWarnings                      Gauge32
}

cucsEquipmentChassisCapProviderInstanceId OBJECT-TYPE
    SYNTAX       CucsManagedObjectId
    MAX-ACCESS   not-accessible
    STATUS       current
    DESCRIPTION
        "Instance identifier of the managed object."
    ::= { cucsEquipmentChassisCapProviderEntry 1 }

cucsEquipmentChassisCapProviderDn OBJECT-TYPE
    SYNTAX       CucsManagedObjectDn
    MAX-ACCESS   read-only
    STATUS       current
    DESCRIPTION
        "Cisco UCS equipment:ChassisCapProvider:dn managed
        object property"
    ::= { cucsEquipmentChassisCapProviderEntry 2 }

cucsEquipmentChassisCapProviderRn OBJECT-TYPE
    SYNTAX       SnmpAdminString
    MAX-ACCESS   read-only
    STATUS       current
    DESCRIPTION
        "Cisco UCS equipment:ChassisCapProvider:rn managed
        object property"
    ::= { cucsEquipmentChassisCapProviderEntry 3 }

cucsEquipmentChassisCapProviderDeprecated OBJECT-TYPE
    SYNTAX       TruthValue
    MAX-ACCESS   read-only
    STATUS       current
    DESCRIPTION
        "Cisco UCS equipment:ChassisCapProvider:deprecated
        managed object property"
    ::= { cucsEquipmentChassisCapProviderEntry 4 }

cucsEquipmentChassisCapProviderGencount OBJECT-TYPE
    SYNTAX       Gauge32
    MAX-ACCESS   read-only
    STATUS       current
    DESCRIPTION
        "Cisco UCS equipment:ChassisCapProvider:gencount
        managed object property"
    ::= { cucsEquipmentChassisCapProviderEntry 5 }

cucsEquipmentChassisCapProviderMgmtPlaneVer OBJECT-TYPE
    SYNTAX       SnmpAdminString
    MAX-ACCESS   read-only
    STATUS       current
    DESCRIPTION
        "Cisco UCS equipment:ChassisCapProvider:mgmtPlaneVer
        managed object property"
    ::= { cucsEquipmentChassisCapProviderEntry 6 }

cucsEquipmentChassisCapProviderModel OBJECT-TYPE
    SYNTAX       SnmpAdminString
    MAX-ACCESS   read-only
    STATUS       current
    DESCRIPTION
        "Cisco UCS equipment:ChassisCapProvider:model managed
        object property"
    ::= { cucsEquipmentChassisCapProviderEntry 7 }

cucsEquipmentChassisCapProviderRevision OBJECT-TYPE
    SYNTAX       SnmpAdminString
    MAX-ACCESS   read-only
    STATUS       current
    DESCRIPTION
        "Cisco UCS equipment:ChassisCapProvider:revision
        managed object property"
    ::= { cucsEquipmentChassisCapProviderEntry 8 }

cucsEquipmentChassisCapProviderVendor OBJECT-TYPE
    SYNTAX       SnmpAdminString
    MAX-ACCESS   read-only
    STATUS       current
    DESCRIPTION
        "Cisco UCS equipment:ChassisCapProvider:vendor
        managed object property"
    ::= { cucsEquipmentChassisCapProviderEntry 9 }

cucsEquipmentChassisCapProviderPromCardType OBJECT-TYPE
    SYNTAX       Gauge32
    MAX-ACCESS   read-only
    STATUS       current
    DESCRIPTION
        "Cisco UCS equipment:ChassisCapProvider:promCardType
        managed object property"
    ::= { cucsEquipmentChassisCapProviderEntry 10 }

cucsEquipmentChassisCapProviderDeleted OBJECT-TYPE
    SYNTAX       TruthValue
    MAX-ACCESS   read-only
    STATUS       current
    DESCRIPTION
        "Cisco UCS equipment:ChassisCapProvider:deleted
        managed object property"
    ::= { cucsEquipmentChassisCapProviderEntry 11 }

cucsEquipmentChassisCapProviderElementLoadFailures OBJECT-TYPE
    SYNTAX       Gauge32
    MAX-ACCESS   read-only
    STATUS       current
    DESCRIPTION
        "Cisco UCS equipment:ChassisCapProvider:elementLoadFailures
        managed object property"
    ::= { cucsEquipmentChassisCapProviderEntry 12 }

cucsEquipmentChassisCapProviderElementsLoaded OBJECT-TYPE
    SYNTAX       Gauge32
    MAX-ACCESS   read-only
    STATUS       current
    DESCRIPTION
        "Cisco UCS equipment:ChassisCapProvider:elementsLoaded
        managed object property"
    ::= { cucsEquipmentChassisCapProviderEntry 13 }

cucsEquipmentChassisCapProviderLoadErrors OBJECT-TYPE
    SYNTAX       Gauge32
    MAX-ACCESS   read-only
    STATUS       current
    DESCRIPTION
        "Cisco UCS equipment:ChassisCapProvider:loadErrors
        managed object property"
    ::= { cucsEquipmentChassisCapProviderEntry 14 }

cucsEquipmentChassisCapProviderLoadWarnings OBJECT-TYPE
    SYNTAX       Gauge32
    MAX-ACCESS   read-only
    STATUS       current
    DESCRIPTION
        "Cisco UCS equipment:ChassisCapProvider:loadWarnings
        managed object property"
    ::= { cucsEquipmentChassisCapProviderEntry 15 }

cucsEquipmentChassisFsmTable OBJECT-TYPE
    SYNTAX           SEQUENCE OF CucsEquipmentChassisFsmEntry
    MAX-ACCESS       not-accessible
    STATUS           current
    DESCRIPTION
        "Cisco UCS equipment:ChassisFsm managed object table"
    ::= { cucsEquipmentObjects 105 }

cucsEquipmentChassisFsmEntry OBJECT-TYPE
    SYNTAX           CucsEquipmentChassisFsmEntry
    MAX-ACCESS       not-accessible
    STATUS           current
    DESCRIPTION
        "Entry for the cucsEquipmentChassisFsmTable table."
    INDEX { cucsEquipmentChassisFsmInstanceId }
    ::= { cucsEquipmentChassisFsmTable 1 }

CucsEquipmentChassisFsmEntry ::= SEQUENCE {
    cucsEquipmentChassisFsmInstanceId                                CucsManagedObjectId,
    cucsEquipmentChassisFsmDn                                        CucsManagedObjectDn,
    cucsEquipmentChassisFsmRn                                        SnmpAdminString,
    cucsEquipmentChassisFsmCompletionTime                            DateAndTime,
    cucsEquipmentChassisFsmCurrentFsm                                CucsEquipmentChassisFsmCurrentFsm,
    cucsEquipmentChassisFsmDescr                                     SnmpAdminString,
    cucsEquipmentChassisFsmFsmStatus                                 CucsFsmFsmStageStatus,
    cucsEquipmentChassisFsmProgress                                  Gauge32,
    cucsEquipmentChassisFsmRmtErrCode                                Gauge32,
    cucsEquipmentChassisFsmRmtErrDescr                               SnmpAdminString,
    cucsEquipmentChassisFsmRmtRslt                                   CucsConditionRemoteInvRslt
}

cucsEquipmentChassisFsmInstanceId OBJECT-TYPE
    SYNTAX       CucsManagedObjectId
    MAX-ACCESS   not-accessible
    STATUS       current
    DESCRIPTION
        "Instance identifier of the managed object."
    ::= { cucsEquipmentChassisFsmEntry 1 }

cucsEquipmentChassisFsmDn OBJECT-TYPE
    SYNTAX       CucsManagedObjectDn
    MAX-ACCESS   read-only
    STATUS       current
    DESCRIPTION
        "Cisco UCS equipment:ChassisFsm:dn managed object property"
    ::= { cucsEquipmentChassisFsmEntry 2 }

cucsEquipmentChassisFsmRn OBJECT-TYPE
    SYNTAX       SnmpAdminString
    MAX-ACCESS   read-only
    STATUS       current
    DESCRIPTION
        "Cisco UCS equipment:ChassisFsm:rn managed object property"
    ::= { cucsEquipmentChassisFsmEntry 3 }

cucsEquipmentChassisFsmCompletionTime OBJECT-TYPE
    SYNTAX       DateAndTime
    MAX-ACCESS   read-only
    STATUS       current
    DESCRIPTION
        "Cisco UCS equipment:ChassisFsm:completionTime
        managed object property"
    ::= { cucsEquipmentChassisFsmEntry 4 }

cucsEquipmentChassisFsmCurrentFsm OBJECT-TYPE
    SYNTAX       CucsEquipmentChassisFsmCurrentFsm
    MAX-ACCESS   read-only
    STATUS       current
    DESCRIPTION
        "Cisco UCS equipment:ChassisFsm:currentFsm managed
        object property"
    ::= { cucsEquipmentChassisFsmEntry 5 }

cucsEquipmentChassisFsmDescr OBJECT-TYPE
    SYNTAX       SnmpAdminString
    MAX-ACCESS   read-only
    STATUS       current
    DESCRIPTION
        "Cisco UCS equipment:ChassisFsm:descr managed object property"
    ::= { cucsEquipmentChassisFsmEntry 6 }

cucsEquipmentChassisFsmFsmStatus OBJECT-TYPE
    SYNTAX       CucsFsmFsmStageStatus
    MAX-ACCESS   read-only
    STATUS       current
    DESCRIPTION
        "Cisco UCS equipment:ChassisFsm:fsmStatus managed object property"
    ::= { cucsEquipmentChassisFsmEntry 7 }

cucsEquipmentChassisFsmProgress OBJECT-TYPE
    SYNTAX       Gauge32
    MAX-ACCESS   read-only
    STATUS       current
    DESCRIPTION
        "Cisco UCS equipment:ChassisFsm:progress managed object property"
    ::= { cucsEquipmentChassisFsmEntry 8 }

cucsEquipmentChassisFsmRmtErrCode OBJECT-TYPE
    SYNTAX       Gauge32
    MAX-ACCESS   read-only
    STATUS       current
    DESCRIPTION
        "Cisco UCS equipment:ChassisFsm:rmtErrCode managed
        object property"
    ::= { cucsEquipmentChassisFsmEntry 9 }

cucsEquipmentChassisFsmRmtErrDescr OBJECT-TYPE
    SYNTAX       SnmpAdminString
    MAX-ACCESS   read-only
    STATUS       current
    DESCRIPTION
        "Cisco UCS equipment:ChassisFsm:rmtErrDescr managed
        object property"
    ::= { cucsEquipmentChassisFsmEntry 10 }

cucsEquipmentChassisFsmRmtRslt OBJECT-TYPE
    SYNTAX       CucsConditionRemoteInvRslt
    MAX-ACCESS   read-only
    STATUS       current
    DESCRIPTION
        "Cisco UCS equipment:ChassisFsm:rmtRslt managed object property"
    ::= { cucsEquipmentChassisFsmEntry 11 }

cucsEquipmentChassisFsmStageTable OBJECT-TYPE
    SYNTAX           SEQUENCE OF CucsEquipmentChassisFsmStageEntry
    MAX-ACCESS       not-accessible
    STATUS           current
    DESCRIPTION
        "Cisco UCS equipment:ChassisFsmStage managed object table"
    ::= { cucsEquipmentObjects 106 }

cucsEquipmentChassisFsmStageEntry OBJECT-TYPE
    SYNTAX           CucsEquipmentChassisFsmStageEntry
    MAX-ACCESS       not-accessible
    STATUS           current
    DESCRIPTION
        "Entry for the cucsEquipmentChassisFsmStageTable table."
    INDEX { cucsEquipmentChassisFsmStageInstanceId }
    ::= { cucsEquipmentChassisFsmStageTable 1 }

CucsEquipmentChassisFsmStageEntry ::= SEQUENCE {
    cucsEquipmentChassisFsmStageInstanceId                           CucsManagedObjectId,
    cucsEquipmentChassisFsmStageDn                                   CucsManagedObjectDn,
    cucsEquipmentChassisFsmStageRn                                   SnmpAdminString,
    cucsEquipmentChassisFsmStageDescr                                SnmpAdminString,
    cucsEquipmentChassisFsmStageLastUpdateTime                       DateAndTime,
    cucsEquipmentChassisFsmStageName                                 CucsEquipmentChassisFsmStageName,
    cucsEquipmentChassisFsmStageOrder                                Gauge32,
    cucsEquipmentChassisFsmStageRetry                                Gauge32,
    cucsEquipmentChassisFsmStageStageStatus                          CucsFsmFsmStageStatus
}

cucsEquipmentChassisFsmStageInstanceId OBJECT-TYPE
    SYNTAX       CucsManagedObjectId
    MAX-ACCESS   not-accessible
    STATUS       current
    DESCRIPTION
        "Instance identifier of the managed object."
    ::= { cucsEquipmentChassisFsmStageEntry 1 }

cucsEquipmentChassisFsmStageDn OBJECT-TYPE
    SYNTAX       CucsManagedObjectDn
    MAX-ACCESS   read-only
    STATUS       current
    DESCRIPTION
        "Cisco UCS equipment:ChassisFsmStage:dn managed object property"
    ::= { cucsEquipmentChassisFsmStageEntry 2 }

cucsEquipmentChassisFsmStageRn OBJECT-TYPE
    SYNTAX       SnmpAdminString
    MAX-ACCESS   read-only
    STATUS       current
    DESCRIPTION
        "Cisco UCS equipment:ChassisFsmStage:rn managed object property"
    ::= { cucsEquipmentChassisFsmStageEntry 3 }

cucsEquipmentChassisFsmStageDescr OBJECT-TYPE
    SYNTAX       SnmpAdminString
    MAX-ACCESS   read-only
    STATUS       current
    DESCRIPTION
        "Cisco UCS equipment:ChassisFsmStage:descr managed
        object property"
    ::= { cucsEquipmentChassisFsmStageEntry 4 }

cucsEquipmentChassisFsmStageLastUpdateTime OBJECT-TYPE
    SYNTAX       DateAndTime
    MAX-ACCESS   read-only
    STATUS       current
    DESCRIPTION
        "Cisco UCS equipment:ChassisFsmStage:lastUpdateTime
        managed object property"
    ::= { cucsEquipmentChassisFsmStageEntry 5 }

cucsEquipmentChassisFsmStageName OBJECT-TYPE
    SYNTAX       CucsEquipmentChassisFsmStageName
    MAX-ACCESS   read-only
    STATUS       current
    DESCRIPTION
        "Cisco UCS equipment:ChassisFsmStage:name managed object property"
    ::= { cucsEquipmentChassisFsmStageEntry 6 }

cucsEquipmentChassisFsmStageOrder OBJECT-TYPE
    SYNTAX       Gauge32
    MAX-ACCESS   read-only
    STATUS       current
    DESCRIPTION
        "Cisco UCS equipment:ChassisFsmStage:order managed
        object property"
    ::= { cucsEquipmentChassisFsmStageEntry 7 }

cucsEquipmentChassisFsmStageRetry OBJECT-TYPE
    SYNTAX       Gauge32
    MAX-ACCESS   read-only
    STATUS       current
    DESCRIPTION
        "Cisco UCS equipment:ChassisFsmStage:retry managed
        object property"
    ::= { cucsEquipmentChassisFsmStageEntry 8 }

cucsEquipmentChassisFsmStageStageStatus OBJECT-TYPE
    SYNTAX       CucsFsmFsmStageStatus
    MAX-ACCESS   read-only
    STATUS       current
    DESCRIPTION
        "Cisco UCS equipment:ChassisFsmStage:stageStatus
        managed object property"
    ::= { cucsEquipmentChassisFsmStageEntry 9 }

cucsEquipmentChassisFsmTaskTable OBJECT-TYPE
    SYNTAX           SEQUENCE OF CucsEquipmentChassisFsmTaskEntry
    MAX-ACCESS       not-accessible
    STATUS           current
    DESCRIPTION
        "Cisco UCS equipment:ChassisFsmTask managed object table"
    ::= { cucsEquipmentObjects 9 }

cucsEquipmentChassisFsmTaskEntry OBJECT-TYPE
    SYNTAX           CucsEquipmentChassisFsmTaskEntry
    MAX-ACCESS       not-accessible
    STATUS           current
    DESCRIPTION
        "Entry for the cucsEquipmentChassisFsmTaskTable table."
    INDEX { cucsEquipmentChassisFsmTaskInstanceId }
    ::= { cucsEquipmentChassisFsmTaskTable 1 }

CucsEquipmentChassisFsmTaskEntry ::= SEQUENCE {
    cucsEquipmentChassisFsmTaskInstanceId                            CucsManagedObjectId,
    cucsEquipmentChassisFsmTaskDn                                    CucsManagedObjectDn,
    cucsEquipmentChassisFsmTaskRn                                    SnmpAdminString,
    cucsEquipmentChassisFsmTaskCompletion                            CucsFsmCompletion,
    cucsEquipmentChassisFsmTaskFlags                                 CucsFsmFlags,
    cucsEquipmentChassisFsmTaskItem                                  CucsEquipmentChassisFsmTaskItem,
    cucsEquipmentChassisFsmTaskSeqId                                 Gauge32
}

cucsEquipmentChassisFsmTaskInstanceId OBJECT-TYPE
    SYNTAX       CucsManagedObjectId
    MAX-ACCESS   not-accessible
    STATUS       current
    DESCRIPTION
        "Instance identifier of the managed object."
    ::= { cucsEquipmentChassisFsmTaskEntry 1 }

cucsEquipmentChassisFsmTaskDn OBJECT-TYPE
    SYNTAX       CucsManagedObjectDn
    MAX-ACCESS   read-only
    STATUS       current
    DESCRIPTION
        "Cisco UCS equipment:ChassisFsmTask:dn managed object property"
    ::= { cucsEquipmentChassisFsmTaskEntry 2 }

cucsEquipmentChassisFsmTaskRn OBJECT-TYPE
    SYNTAX       SnmpAdminString
    MAX-ACCESS   read-only
    STATUS       current
    DESCRIPTION
        "Cisco UCS equipment:ChassisFsmTask:rn managed object property"
    ::= { cucsEquipmentChassisFsmTaskEntry 3 }

cucsEquipmentChassisFsmTaskCompletion OBJECT-TYPE
    SYNTAX       CucsFsmCompletion
    MAX-ACCESS   read-only
    STATUS       current
    DESCRIPTION
        "Cisco UCS equipment:ChassisFsmTask:completion
        managed object property"
    ::= { cucsEquipmentChassisFsmTaskEntry 4 }

cucsEquipmentChassisFsmTaskFlags OBJECT-TYPE
    SYNTAX       CucsFsmFlags
    MAX-ACCESS   read-only
    STATUS       current
    DESCRIPTION
        "Cisco UCS equipment:ChassisFsmTask:flags managed object property"
    ::= { cucsEquipmentChassisFsmTaskEntry 5 }

cucsEquipmentChassisFsmTaskItem OBJECT-TYPE
    SYNTAX       CucsEquipmentChassisFsmTaskItem
    MAX-ACCESS   read-only
    STATUS       current
    DESCRIPTION
        "Cisco UCS equipment:ChassisFsmTask:item managed object property"
    ::= { cucsEquipmentChassisFsmTaskEntry 6 }

cucsEquipmentChassisFsmTaskSeqId OBJECT-TYPE
    SYNTAX       Gauge32
    MAX-ACCESS   read-only
    STATUS       current
    DESCRIPTION
        "Cisco UCS equipment:ChassisFsmTask:seqId managed object property"
    ::= { cucsEquipmentChassisFsmTaskEntry 7 }

cucsEquipmentChassisStatsTable OBJECT-TYPE
    SYNTAX           SEQUENCE OF CucsEquipmentChassisStatsEntry
    MAX-ACCESS       not-accessible
    STATUS           current
    DESCRIPTION
        "Cisco UCS equipment:ChassisStats managed object table"
    ::= { cucsEquipmentObjects 10 }

cucsEquipmentChassisStatsEntry OBJECT-TYPE
    SYNTAX           CucsEquipmentChassisStatsEntry
    MAX-ACCESS       not-accessible
    STATUS           current
    DESCRIPTION
        "Entry for the cucsEquipmentChassisStatsTable table."
    INDEX { cucsEquipmentChassisStatsInstanceId }
    ::= { cucsEquipmentChassisStatsTable 1 }

CucsEquipmentChassisStatsEntry ::= SEQUENCE {
    cucsEquipmentChassisStatsInstanceId                              CucsManagedObjectId,
    cucsEquipmentChassisStatsDn                                      CucsManagedObjectDn,
    cucsEquipmentChassisStatsRn                                      SnmpAdminString,
    cucsEquipmentChassisStatsInputPower                              INTEGER,
    cucsEquipmentChassisStatsInputPowerAvg                           INTEGER,
    cucsEquipmentChassisStatsInputPowerMax                           INTEGER,
    cucsEquipmentChassisStatsInputPowerMin                           INTEGER,
    cucsEquipmentChassisStatsIntervals                               Gauge32,
    cucsEquipmentChassisStatsOutputPower                             INTEGER,
    cucsEquipmentChassisStatsOutputPowerAvg                          INTEGER,
    cucsEquipmentChassisStatsOutputPowerMax                          INTEGER,
    cucsEquipmentChassisStatsOutputPowerMin                          INTEGER,
    cucsEquipmentChassisStatsSuspect                                 TruthValue,
    cucsEquipmentChassisStatsThresholded                             CucsEquipmentChassisStatsThresholded,
    cucsEquipmentChassisStatsTimeCollected                           DateAndTime,
    cucsEquipmentChassisStatsUpdate                                  Gauge32
}

cucsEquipmentChassisStatsInstanceId OBJECT-TYPE
    SYNTAX       CucsManagedObjectId
    MAX-ACCESS   not-accessible
    STATUS       current
    DESCRIPTION
        "Instance identifier of the managed object."
    ::= { cucsEquipmentChassisStatsEntry 1 }

cucsEquipmentChassisStatsDn OBJECT-TYPE
    SYNTAX       CucsManagedObjectDn
    MAX-ACCESS   read-only
    STATUS       current
    DESCRIPTION
        "Cisco UCS equipment:ChassisStats:dn managed object property"
    ::= { cucsEquipmentChassisStatsEntry 2 }

cucsEquipmentChassisStatsRn OBJECT-TYPE
    SYNTAX       SnmpAdminString
    MAX-ACCESS   read-only
    STATUS       current
    DESCRIPTION
        "Cisco UCS equipment:ChassisStats:rn managed object property"
    ::= { cucsEquipmentChassisStatsEntry 3 }

cucsEquipmentChassisStatsInputPower OBJECT-TYPE
    SYNTAX       INTEGER
    MAX-ACCESS   read-only
    STATUS       current
    DESCRIPTION
        "Cisco UCS equipment:ChassisStats:inputPower managed
        object property"
    ::= { cucsEquipmentChassisStatsEntry 4 }

cucsEquipmentChassisStatsInputPowerAvg OBJECT-TYPE
    SYNTAX       INTEGER
    MAX-ACCESS   read-only
    STATUS       current
    DESCRIPTION
        "Cisco UCS equipment:ChassisStats:inputPowerAvg
        managed object property"
    ::= { cucsEquipmentChassisStatsEntry 5 }

cucsEquipmentChassisStatsInputPowerMax OBJECT-TYPE
    SYNTAX       INTEGER
    MAX-ACCESS   read-only
    STATUS       current
    DESCRIPTION
        "Cisco UCS equipment:ChassisStats:inputPowerMax
        managed object property"
    ::= { cucsEquipmentChassisStatsEntry 6 }

cucsEquipmentChassisStatsInputPowerMin OBJECT-TYPE
    SYNTAX       INTEGER
    MAX-ACCESS   read-only
    STATUS       current
    DESCRIPTION
        "Cisco UCS equipment:ChassisStats:inputPowerMin
        managed object property"
    ::= { cucsEquipmentChassisStatsEntry 7 }

cucsEquipmentChassisStatsIntervals OBJECT-TYPE
    SYNTAX       Gauge32
    MAX-ACCESS   read-only
    STATUS       current
    DESCRIPTION
        "Cisco UCS equipment:ChassisStats:intervals managed
        object property"
    ::= { cucsEquipmentChassisStatsEntry 8 }

cucsEquipmentChassisStatsOutputPower OBJECT-TYPE
    SYNTAX       INTEGER
    MAX-ACCESS   read-only
    STATUS       current
    DESCRIPTION
        "Cisco UCS equipment:ChassisStats:outputPower managed
        object property"
    ::= { cucsEquipmentChassisStatsEntry 9 }

cucsEquipmentChassisStatsOutputPowerAvg OBJECT-TYPE
    SYNTAX       INTEGER
    MAX-ACCESS   read-only
    STATUS       current
    DESCRIPTION
        "Cisco UCS equipment:ChassisStats:outputPowerAvg
        managed object property"
    ::= { cucsEquipmentChassisStatsEntry 10 }

cucsEquipmentChassisStatsOutputPowerMax OBJECT-TYPE
    SYNTAX       INTEGER
    MAX-ACCESS   read-only
    STATUS       current
    DESCRIPTION
        "Cisco UCS equipment:ChassisStats:outputPowerMax
        managed object property"
    ::= { cucsEquipmentChassisStatsEntry 11 }

cucsEquipmentChassisStatsOutputPowerMin OBJECT-TYPE
    SYNTAX       INTEGER
    MAX-ACCESS   read-only
    STATUS       current
    DESCRIPTION
        "Cisco UCS equipment:ChassisStats:outputPowerMin
        managed object property"
    ::= { cucsEquipmentChassisStatsEntry 12 }

cucsEquipmentChassisStatsSuspect OBJECT-TYPE
    SYNTAX       TruthValue
    MAX-ACCESS   read-only
    STATUS       current
    DESCRIPTION
        "Cisco UCS equipment:ChassisStats:suspect managed object property"
    ::= { cucsEquipmentChassisStatsEntry 13 }

cucsEquipmentChassisStatsThresholded OBJECT-TYPE
    SYNTAX       CucsEquipmentChassisStatsThresholded
    MAX-ACCESS   read-only
    STATUS       current
    DESCRIPTION
        "Cisco UCS equipment:ChassisStats:thresholded managed
        object property"
    ::= { cucsEquipmentChassisStatsEntry 14 }

cucsEquipmentChassisStatsTimeCollected OBJECT-TYPE
    SYNTAX       DateAndTime
    MAX-ACCESS   read-only
    STATUS       current
    DESCRIPTION
        "Cisco UCS equipment:ChassisStats:timeCollected
        managed object property"
    ::= { cucsEquipmentChassisStatsEntry 15 }

cucsEquipmentChassisStatsUpdate OBJECT-TYPE
    SYNTAX       Gauge32
    MAX-ACCESS   read-only
    STATUS       current
    DESCRIPTION
        "Cisco UCS equipment:ChassisStats:update managed object property"
    ::= { cucsEquipmentChassisStatsEntry 16 }

cucsEquipmentChassisStatsHistTable OBJECT-TYPE
    SYNTAX           SEQUENCE OF CucsEquipmentChassisStatsHistEntry
    MAX-ACCESS       not-accessible
    STATUS           current
    DESCRIPTION
        "Cisco UCS equipment:ChassisStatsHist managed object table"
    ::= { cucsEquipmentObjects 11 }

cucsEquipmentChassisStatsHistEntry OBJECT-TYPE
    SYNTAX           CucsEquipmentChassisStatsHistEntry
    MAX-ACCESS       not-accessible
    STATUS           current
    DESCRIPTION
        "Entry for the cucsEquipmentChassisStatsHistTable table."
    INDEX { cucsEquipmentChassisStatsHistInstanceId }
    ::= { cucsEquipmentChassisStatsHistTable 1 }

CucsEquipmentChassisStatsHistEntry ::= SEQUENCE {
    cucsEquipmentChassisStatsHistInstanceId                          CucsManagedObjectId,
    cucsEquipmentChassisStatsHistDn                                  CucsManagedObjectDn,
    cucsEquipmentChassisStatsHistRn                                  SnmpAdminString,
    cucsEquipmentChassisStatsHistId                                  Unsigned64,
    cucsEquipmentChassisStatsHistInputPower                          INTEGER,
    cucsEquipmentChassisStatsHistInputPowerAvg                       INTEGER,
    cucsEquipmentChassisStatsHistInputPowerMax                       INTEGER,
    cucsEquipmentChassisStatsHistInputPowerMin                       INTEGER,
    cucsEquipmentChassisStatsHistMostRecent                          TruthValue,
    cucsEquipmentChassisStatsHistOutputPower                         INTEGER,
    cucsEquipmentChassisStatsHistOutputPowerAvg                      INTEGER,
    cucsEquipmentChassisStatsHistOutputPowerMax                      INTEGER,
    cucsEquipmentChassisStatsHistOutputPowerMin                      INTEGER,
    cucsEquipmentChassisStatsHistSuspect                             TruthValue,
    cucsEquipmentChassisStatsHistThresholded                         CucsEquipmentChassisStatsHistThresholded,
    cucsEquipmentChassisStatsHistTimeCollected                       DateAndTime
}

cucsEquipmentChassisStatsHistInstanceId OBJECT-TYPE
    SYNTAX       CucsManagedObjectId
    MAX-ACCESS   not-accessible
    STATUS       current
    DESCRIPTION
        "Instance identifier of the managed object."
    ::= { cucsEquipmentChassisStatsHistEntry 1 }

cucsEquipmentChassisStatsHistDn OBJECT-TYPE
    SYNTAX       CucsManagedObjectDn
    MAX-ACCESS   read-only
    STATUS       current
    DESCRIPTION
        "Cisco UCS equipment:ChassisStatsHist:dn managed object property"
    ::= { cucsEquipmentChassisStatsHistEntry 2 }

cucsEquipmentChassisStatsHistRn OBJECT-TYPE
    SYNTAX       SnmpAdminString
    MAX-ACCESS   read-only
    STATUS       current
    DESCRIPTION
        "Cisco UCS equipment:ChassisStatsHist:rn managed object property"
    ::= { cucsEquipmentChassisStatsHistEntry 3 }

cucsEquipmentChassisStatsHistId OBJECT-TYPE
    SYNTAX       Unsigned64
    MAX-ACCESS   read-only
    STATUS       current
    DESCRIPTION
        "Cisco UCS equipment:ChassisStatsHist:id managed object property"
    ::= { cucsEquipmentChassisStatsHistEntry 4 }

cucsEquipmentChassisStatsHistInputPower OBJECT-TYPE
    SYNTAX       INTEGER
    MAX-ACCESS   read-only
    STATUS       current
    DESCRIPTION
        "Cisco UCS equipment:ChassisStatsHist:inputPower
        managed object property"
    ::= { cucsEquipmentChassisStatsHistEntry 5 }

cucsEquipmentChassisStatsHistInputPowerAvg OBJECT-TYPE
    SYNTAX       INTEGER
    MAX-ACCESS   read-only
    STATUS       current
    DESCRIPTION
        "Cisco UCS equipment:ChassisStatsHist:inputPowerAvg
        managed object property"
    ::= { cucsEquipmentChassisStatsHistEntry 6 }

cucsEquipmentChassisStatsHistInputPowerMax OBJECT-TYPE
    SYNTAX       INTEGER
    MAX-ACCESS   read-only
    STATUS       current
    DESCRIPTION
        "Cisco UCS equipment:ChassisStatsHist:inputPowerMax
        managed object property"
    ::= { cucsEquipmentChassisStatsHistEntry 7 }

cucsEquipmentChassisStatsHistInputPowerMin OBJECT-TYPE
    SYNTAX       INTEGER
    MAX-ACCESS   read-only
    STATUS       current
    DESCRIPTION
        "Cisco UCS equipment:ChassisStatsHist:inputPowerMin
        managed object property"
    ::= { cucsEquipmentChassisStatsHistEntry 8 }

cucsEquipmentChassisStatsHistMostRecent OBJECT-TYPE
    SYNTAX       TruthValue
    MAX-ACCESS   read-only
    STATUS       current
    DESCRIPTION
        "Cisco UCS equipment:ChassisStatsHist:mostRecent
        managed object property"
    ::= { cucsEquipmentChassisStatsHistEntry 9 }

cucsEquipmentChassisStatsHistOutputPower OBJECT-TYPE
    SYNTAX       INTEGER
    MAX-ACCESS   read-only
    STATUS       current
    DESCRIPTION
        "Cisco UCS equipment:ChassisStatsHist:outputPower
        managed object property"
    ::= { cucsEquipmentChassisStatsHistEntry 10 }

cucsEquipmentChassisStatsHistOutputPowerAvg OBJECT-TYPE
    SYNTAX       INTEGER
    MAX-ACCESS   read-only
    STATUS       current
    DESCRIPTION
        "Cisco UCS equipment:ChassisStatsHist:outputPowerAvg
        managed object property"
    ::= { cucsEquipmentChassisStatsHistEntry 11 }

cucsEquipmentChassisStatsHistOutputPowerMax OBJECT-TYPE
    SYNTAX       INTEGER
    MAX-ACCESS   read-only
    STATUS       current
    DESCRIPTION
        "Cisco UCS equipment:ChassisStatsHist:outputPowerMax
        managed object property"
    ::= { cucsEquipmentChassisStatsHistEntry 12 }

cucsEquipmentChassisStatsHistOutputPowerMin OBJECT-TYPE
    SYNTAX       INTEGER
    MAX-ACCESS   read-only
    STATUS       current
    DESCRIPTION
        "Cisco UCS equipment:ChassisStatsHist:outputPowerMin
        managed object property"
    ::= { cucsEquipmentChassisStatsHistEntry 13 }

cucsEquipmentChassisStatsHistSuspect OBJECT-TYPE
    SYNTAX       TruthValue
    MAX-ACCESS   read-only
    STATUS       current
    DESCRIPTION
        "Cisco UCS equipment:ChassisStatsHist:suspect managed
        object property"
    ::= { cucsEquipmentChassisStatsHistEntry 14 }

cucsEquipmentChassisStatsHistThresholded OBJECT-TYPE
    SYNTAX       CucsEquipmentChassisStatsHistThresholded
    MAX-ACCESS   read-only
    STATUS       current
    DESCRIPTION
        "Cisco UCS equipment:ChassisStatsHist:thresholded
        managed object property"
    ::= { cucsEquipmentChassisStatsHistEntry 15 }

cucsEquipmentChassisStatsHistTimeCollected OBJECT-TYPE
    SYNTAX       DateAndTime
    MAX-ACCESS   read-only
    STATUS       current
    DESCRIPTION
        "Cisco UCS equipment:ChassisStatsHist:timeCollected
        managed object property"
    ::= { cucsEquipmentChassisStatsHistEntry 16 }

cucsEquipmentDbgPluginCapProviderTable OBJECT-TYPE
    SYNTAX           SEQUENCE OF CucsEquipmentDbgPluginCapProviderEntry
    MAX-ACCESS       not-accessible
    STATUS           current
    DESCRIPTION
        "Cisco UCS equipment:DbgPluginCapProvider managed object table"
    ::= { cucsEquipmentObjects 77 }

cucsEquipmentDbgPluginCapProviderEntry OBJECT-TYPE
    SYNTAX           CucsEquipmentDbgPluginCapProviderEntry
    MAX-ACCESS       not-accessible
    STATUS           current
    DESCRIPTION
        "Entry for the cucsEquipmentDbgPluginCapProviderTable table."
    INDEX { cucsEquipmentDbgPluginCapProviderInstanceId }
    ::= { cucsEquipmentDbgPluginCapProviderTable 1 }

CucsEquipmentDbgPluginCapProviderEntry ::= SEQUENCE {
    cucsEquipmentDbgPluginCapProviderInstanceId                      CucsManagedObjectId,
    cucsEquipmentDbgPluginCapProviderDn                              CucsManagedObjectDn,
    cucsEquipmentDbgPluginCapProviderRn                              SnmpAdminString,
    cucsEquipmentDbgPluginCapProviderDeleted                         TruthValue,
    cucsEquipmentDbgPluginCapProviderDeprecated                      TruthValue,
    cucsEquipmentDbgPluginCapProviderGencount                        Gauge32,
    cucsEquipmentDbgPluginCapProviderMgmtPlaneVer                    SnmpAdminString,
    cucsEquipmentDbgPluginCapProviderModel                           SnmpAdminString,
    cucsEquipmentDbgPluginCapProviderPromCardType                    Gauge32,
    cucsEquipmentDbgPluginCapProviderRevision                        SnmpAdminString,
    cucsEquipmentDbgPluginCapProviderVendor                          SnmpAdminString,
    cucsEquipmentDbgPluginCapProviderElementLoadFailures             Gauge32,
    cucsEquipmentDbgPluginCapProviderElementsLoaded                  Gauge32,
    cucsEquipmentDbgPluginCapProviderLoadErrors                      Gauge32,
    cucsEquipmentDbgPluginCapProviderLoadWarnings                    Gauge32
}

cucsEquipmentDbgPluginCapProviderInstanceId OBJECT-TYPE
    SYNTAX       CucsManagedObjectId
    MAX-ACCESS   not-accessible
    STATUS       current
    DESCRIPTION
        "Instance identifier of the managed object."
    ::= { cucsEquipmentDbgPluginCapProviderEntry 1 }

cucsEquipmentDbgPluginCapProviderDn OBJECT-TYPE
    SYNTAX       CucsManagedObjectDn
    MAX-ACCESS   read-only
    STATUS       current
    DESCRIPTION
        "Cisco UCS equipment:DbgPluginCapProvider:dn managed
        object property"
    ::= { cucsEquipmentDbgPluginCapProviderEntry 2 }

cucsEquipmentDbgPluginCapProviderRn OBJECT-TYPE
    SYNTAX       SnmpAdminString
    MAX-ACCESS   read-only
    STATUS       current
    DESCRIPTION
        "Cisco UCS equipment:DbgPluginCapProvider:rn managed
        object property"
    ::= { cucsEquipmentDbgPluginCapProviderEntry 3 }

cucsEquipmentDbgPluginCapProviderDeleted OBJECT-TYPE
    SYNTAX       TruthValue
    MAX-ACCESS   read-only
    STATUS       current
    DESCRIPTION
        "Cisco UCS equipment:DbgPluginCapProvider:deleted
        managed object property"
    ::= { cucsEquipmentDbgPluginCapProviderEntry 4 }

cucsEquipmentDbgPluginCapProviderDeprecated OBJECT-TYPE
    SYNTAX       TruthValue
    MAX-ACCESS   read-only
    STATUS       current
    DESCRIPTION
        "Cisco UCS equipment:DbgPluginCapProvider:deprecated
        managed object property"
    ::= { cucsEquipmentDbgPluginCapProviderEntry 5 }

cucsEquipmentDbgPluginCapProviderGencount OBJECT-TYPE
    SYNTAX       Gauge32
    MAX-ACCESS   read-only
    STATUS       current
    DESCRIPTION
        "Cisco UCS equipment:DbgPluginCapProvider:gencount
        managed object property"
    ::= { cucsEquipmentDbgPluginCapProviderEntry 6 }

cucsEquipmentDbgPluginCapProviderMgmtPlaneVer OBJECT-TYPE
    SYNTAX       SnmpAdminString
    MAX-ACCESS   read-only
    STATUS       current
    DESCRIPTION
        "Cisco UCS equipment:DbgPluginCapProvider:mgmtPlaneVer
        managed object property"
    ::= { cucsEquipmentDbgPluginCapProviderEntry 7 }

cucsEquipmentDbgPluginCapProviderModel OBJECT-TYPE
    SYNTAX       SnmpAdminString
    MAX-ACCESS   read-only
    STATUS       current
    DESCRIPTION
        "Cisco UCS equipment:DbgPluginCapProvider:model
        managed object property"
    ::= { cucsEquipmentDbgPluginCapProviderEntry 8 }

cucsEquipmentDbgPluginCapProviderPromCardType OBJECT-TYPE
    SYNTAX       Gauge32
    MAX-ACCESS   read-only
    STATUS       current
    DESCRIPTION
        "Cisco UCS equipment:DbgPluginCapProvider:promCardType
        managed object property"
    ::= { cucsEquipmentDbgPluginCapProviderEntry 9 }

cucsEquipmentDbgPluginCapProviderRevision OBJECT-TYPE
    SYNTAX       SnmpAdminString
    MAX-ACCESS   read-only
    STATUS       current
    DESCRIPTION
        "Cisco UCS equipment:DbgPluginCapProvider:revision
        managed object property"
    ::= { cucsEquipmentDbgPluginCapProviderEntry 10 }

cucsEquipmentDbgPluginCapProviderVendor OBJECT-TYPE
    SYNTAX       SnmpAdminString
    MAX-ACCESS   read-only
    STATUS       current
    DESCRIPTION
        "Cisco UCS equipment:DbgPluginCapProvider:vendor
        managed object property"
    ::= { cucsEquipmentDbgPluginCapProviderEntry 11 }

cucsEquipmentDbgPluginCapProviderElementLoadFailures OBJECT-TYPE
    SYNTAX       Gauge32
    MAX-ACCESS   read-only
    STATUS       current
    DESCRIPTION
        "Cisco UCS equipment:DbgPluginCapProvider:elementLoadFailures
        managed object property"
    ::= { cucsEquipmentDbgPluginCapProviderEntry 12 }

cucsEquipmentDbgPluginCapProviderElementsLoaded OBJECT-TYPE
    SYNTAX       Gauge32
    MAX-ACCESS   read-only
    STATUS       current
    DESCRIPTION
        "Cisco UCS equipment:DbgPluginCapProvider:elementsLoaded
        managed object property"
    ::= { cucsEquipmentDbgPluginCapProviderEntry 13 }

cucsEquipmentDbgPluginCapProviderLoadErrors OBJECT-TYPE
    SYNTAX       Gauge32
    MAX-ACCESS   read-only
    STATUS       current
    DESCRIPTION
        "Cisco UCS equipment:DbgPluginCapProvider:loadErrors
        managed object property"
    ::= { cucsEquipmentDbgPluginCapProviderEntry 14 }

cucsEquipmentDbgPluginCapProviderLoadWarnings OBJECT-TYPE
    SYNTAX       Gauge32
    MAX-ACCESS   read-only
    STATUS       current
    DESCRIPTION
        "Cisco UCS equipment:DbgPluginCapProvider:loadWarnings
        managed object property"
    ::= { cucsEquipmentDbgPluginCapProviderEntry 15 }

cucsEquipmentDimmEntryTable OBJECT-TYPE
    SYNTAX           SEQUENCE OF CucsEquipmentDimmEntryEntry
    MAX-ACCESS       not-accessible
    STATUS           current
    DESCRIPTION
        "Cisco UCS equipment:DimmEntry managed object table"
    ::= { cucsEquipmentObjects 99 }

cucsEquipmentDimmEntryEntry OBJECT-TYPE
    SYNTAX           CucsEquipmentDimmEntryEntry
    MAX-ACCESS       not-accessible
    STATUS           current
    DESCRIPTION
        "Entry for the cucsEquipmentDimmEntryTable table."
    INDEX { cucsEquipmentDimmEntryInstanceId }
    ::= { cucsEquipmentDimmEntryTable 1 }

CucsEquipmentDimmEntryEntry ::= SEQUENCE {
    cucsEquipmentDimmEntryInstanceId                                 CucsManagedObjectId,
    cucsEquipmentDimmEntryDn                                         CucsManagedObjectDn,
    cucsEquipmentDimmEntryRn                                         SnmpAdminString,
    cucsEquipmentDimmEntryId                                         Gauge32,
    cucsEquipmentDimmEntrySmbiosname                                 SnmpAdminString
}

cucsEquipmentDimmEntryInstanceId OBJECT-TYPE
    SYNTAX       CucsManagedObjectId
    MAX-ACCESS   not-accessible
    STATUS       current
    DESCRIPTION
        "Instance identifier of the managed object."
    ::= { cucsEquipmentDimmEntryEntry 1 }

cucsEquipmentDimmEntryDn OBJECT-TYPE
    SYNTAX       CucsManagedObjectDn
    MAX-ACCESS   read-only
    STATUS       current
    DESCRIPTION
        "Cisco UCS equipment:DimmEntry:dn managed object property"
    ::= { cucsEquipmentDimmEntryEntry 2 }

cucsEquipmentDimmEntryRn OBJECT-TYPE
    SYNTAX       SnmpAdminString
    MAX-ACCESS   read-only
    STATUS       current
    DESCRIPTION
        "Cisco UCS equipment:DimmEntry:rn managed object property"
    ::= { cucsEquipmentDimmEntryEntry 3 }

cucsEquipmentDimmEntryId OBJECT-TYPE
    SYNTAX       Gauge32
    MAX-ACCESS   read-only
    STATUS       current
    DESCRIPTION
        "Cisco UCS equipment:DimmEntry:id managed object property"
    ::= { cucsEquipmentDimmEntryEntry 4 }

cucsEquipmentDimmEntrySmbiosname OBJECT-TYPE
    SYNTAX       SnmpAdminString
    MAX-ACCESS   read-only
    STATUS       current
    DESCRIPTION
        "Cisco UCS equipment:DimmEntry:smbiosname managed object property"
    ::= { cucsEquipmentDimmEntryEntry 5 }

cucsEquipmentDimmMappingTable OBJECT-TYPE
    SYNTAX           SEQUENCE OF CucsEquipmentDimmMappingEntry
    MAX-ACCESS       not-accessible
    STATUS           current
    DESCRIPTION
        "Cisco UCS equipment:DimmMapping managed object table"
    ::= { cucsEquipmentObjects 100 }

cucsEquipmentDimmMappingEntry OBJECT-TYPE
    SYNTAX           CucsEquipmentDimmMappingEntry
    MAX-ACCESS       not-accessible
    STATUS           current
    DESCRIPTION
        "Entry for the cucsEquipmentDimmMappingTable table."
    INDEX { cucsEquipmentDimmMappingInstanceId }
    ::= { cucsEquipmentDimmMappingTable 1 }

CucsEquipmentDimmMappingEntry ::= SEQUENCE {
    cucsEquipmentDimmMappingInstanceId                               CucsManagedObjectId,
    cucsEquipmentDimmMappingDn                                       CucsManagedObjectDn,
    cucsEquipmentDimmMappingRn                                       SnmpAdminString,
    cucsEquipmentDimmMappingDescr                                    SnmpAdminString,
    cucsEquipmentDimmMappingIntId                                    SnmpAdminString,
    cucsEquipmentDimmMappingName                                     SnmpAdminString,
    cucsEquipmentDimmMappingPolicyLevel                              Gauge32,
    cucsEquipmentDimmMappingPolicyOwner                              CucsPolicyPolicyOwner
}

cucsEquipmentDimmMappingInstanceId OBJECT-TYPE
    SYNTAX       CucsManagedObjectId
    MAX-ACCESS   not-accessible
    STATUS       current
    DESCRIPTION
        "Instance identifier of the managed object."
    ::= { cucsEquipmentDimmMappingEntry 1 }

cucsEquipmentDimmMappingDn OBJECT-TYPE
    SYNTAX       CucsManagedObjectDn
    MAX-ACCESS   read-only
    STATUS       current
    DESCRIPTION
        "Cisco UCS equipment:DimmMapping:dn managed object property"
    ::= { cucsEquipmentDimmMappingEntry 2 }

cucsEquipmentDimmMappingRn OBJECT-TYPE
    SYNTAX       SnmpAdminString
    MAX-ACCESS   read-only
    STATUS       current
    DESCRIPTION
        "Cisco UCS equipment:DimmMapping:rn managed object property"
    ::= { cucsEquipmentDimmMappingEntry 3 }

cucsEquipmentDimmMappingDescr OBJECT-TYPE
    SYNTAX       SnmpAdminString
    MAX-ACCESS   read-only
    STATUS       current
    DESCRIPTION
        "Cisco UCS equipment:DimmMapping:descr managed object property"
    ::= { cucsEquipmentDimmMappingEntry 4 }

cucsEquipmentDimmMappingIntId OBJECT-TYPE
    SYNTAX       SnmpAdminString
    MAX-ACCESS   read-only
    STATUS       current
    DESCRIPTION
        "Cisco UCS equipment:DimmMapping:intId managed object property"
    ::= { cucsEquipmentDimmMappingEntry 5 }

cucsEquipmentDimmMappingName OBJECT-TYPE
    SYNTAX       SnmpAdminString
    MAX-ACCESS   read-only
    STATUS       current
    DESCRIPTION
        "Cisco UCS equipment:DimmMapping:name managed object property"
    ::= { cucsEquipmentDimmMappingEntry 6 }

cucsEquipmentDimmMappingPolicyLevel OBJECT-TYPE
    SYNTAX       Gauge32
    MAX-ACCESS   read-only
    STATUS       current
    DESCRIPTION
        "Cisco UCS equipment:DimmMapping:policyLevel managed
        object property"
    ::= { cucsEquipmentDimmMappingEntry 7 }

cucsEquipmentDimmMappingPolicyOwner OBJECT-TYPE
    SYNTAX       CucsPolicyPolicyOwner
    MAX-ACCESS   read-only
    STATUS       current
    DESCRIPTION
        "Cisco UCS equipment:DimmMapping:policyOwner managed
        object property"
    ::= { cucsEquipmentDimmMappingEntry 8 }

cucsEquipmentDiscoveryCapTable OBJECT-TYPE
    SYNTAX           SEQUENCE OF CucsEquipmentDiscoveryCapEntry
    MAX-ACCESS       not-accessible
    STATUS           current
    DESCRIPTION
        "Cisco UCS equipment:DiscoveryCap managed object table"
    ::= { cucsEquipmentObjects 79 }

cucsEquipmentDiscoveryCapEntry OBJECT-TYPE
    SYNTAX           CucsEquipmentDiscoveryCapEntry
    MAX-ACCESS       not-accessible
    STATUS           current
    DESCRIPTION
        "Entry for the cucsEquipmentDiscoveryCapTable table."
    INDEX { cucsEquipmentDiscoveryCapInstanceId }
    ::= { cucsEquipmentDiscoveryCapTable 1 }

CucsEquipmentDiscoveryCapEntry ::= SEQUENCE {
    cucsEquipmentDiscoveryCapInstanceId                              CucsManagedObjectId,
    cucsEquipmentDiscoveryCapDn                                      CucsManagedObjectDn,
    cucsEquipmentDiscoveryCapRn                                      SnmpAdminString,
    cucsEquipmentDiscoveryCapOperPowerRequirement                    CucsEquipmentDiscoveryCapOperPowerRequirement
}

cucsEquipmentDiscoveryCapInstanceId OBJECT-TYPE
    SYNTAX       CucsManagedObjectId
    MAX-ACCESS   not-accessible
    STATUS       current
    DESCRIPTION
        "Instance identifier of the managed object."
    ::= { cucsEquipmentDiscoveryCapEntry 1 }

cucsEquipmentDiscoveryCapDn OBJECT-TYPE
    SYNTAX       CucsManagedObjectDn
    MAX-ACCESS   read-only
    STATUS       current
    DESCRIPTION
        "Cisco UCS equipment:DiscoveryCap:dn managed object property"
    ::= { cucsEquipmentDiscoveryCapEntry 2 }

cucsEquipmentDiscoveryCapRn OBJECT-TYPE
    SYNTAX       SnmpAdminString
    MAX-ACCESS   read-only
    STATUS       current
    DESCRIPTION
        "Cisco UCS equipment:DiscoveryCap:rn managed object property"
    ::= { cucsEquipmentDiscoveryCapEntry 3 }

cucsEquipmentDiscoveryCapOperPowerRequirement OBJECT-TYPE
    SYNTAX       CucsEquipmentDiscoveryCapOperPowerRequirement
    MAX-ACCESS   read-only
    STATUS       current
    DESCRIPTION
        "Cisco UCS equipment:DiscoveryCap:operPowerRequirement
        managed object property"
    ::= { cucsEquipmentDiscoveryCapEntry 4 }

cucsEquipmentFanTable OBJECT-TYPE
    SYNTAX           SEQUENCE OF CucsEquipmentFanEntry
    MAX-ACCESS       not-accessible
    STATUS           current
    DESCRIPTION
        "Cisco UCS equipment:Fan managed object table"
    ::= { cucsEquipmentObjects 12 }

cucsEquipmentFanEntry OBJECT-TYPE
    SYNTAX           CucsEquipmentFanEntry
    MAX-ACCESS       not-accessible
    STATUS           current
    DESCRIPTION
        "Entry for the cucsEquipmentFanTable table."
    INDEX { cucsEquipmentFanInstanceId }
    ::= { cucsEquipmentFanTable 1 }

CucsEquipmentFanEntry ::= SEQUENCE {
    cucsEquipmentFanInstanceId                                       CucsManagedObjectId,
    cucsEquipmentFanDn                                               CucsManagedObjectDn,
    cucsEquipmentFanRn                                               SnmpAdminString,
    cucsEquipmentFanFltAggr                                          Unsigned64,
    cucsEquipmentFanId                                               CucsEquipmentFanId,
    cucsEquipmentFanIntType                                          CucsEquipmentInternalFanType,
    cucsEquipmentFanModel                                            SnmpAdminString,
    cucsEquipmentFanModule                                           CucsEquipmentFanModule,
    cucsEquipmentFanOperState                                        CucsEquipmentOperability,
    cucsEquipmentFanOperability                                      CucsEquipmentOperability,
    cucsEquipmentFanPerf                                             CucsEquipmentSensorThresholdStatus,
    cucsEquipmentFanPower                                            CucsEquipmentPowerState,
    cucsEquipmentFanPresence                                         CucsEquipmentPresence,
    cucsEquipmentFanRevision                                         SnmpAdminString,
    cucsEquipmentFanSerial                                           SnmpAdminString,
    cucsEquipmentFanThermal                                          CucsEquipmentSensorThresholdStatus,
    cucsEquipmentFanTray                                             CucsEquipmentFanTray,
    cucsEquipmentFanVendor                                           SnmpAdminString,
    cucsEquipmentFanVoltage                                          CucsEquipmentSensorThresholdStatus,
    cucsEquipmentFanOperQualifierReason                              SnmpAdminString
}

cucsEquipmentFanInstanceId OBJECT-TYPE
    SYNTAX       CucsManagedObjectId
    MAX-ACCESS   not-accessible
    STATUS       current
    DESCRIPTION
        "Instance identifier of the managed object."
    ::= { cucsEquipmentFanEntry 1 }

cucsEquipmentFanDn OBJECT-TYPE
    SYNTAX       CucsManagedObjectDn
    MAX-ACCESS   read-only
    STATUS       current
    DESCRIPTION
        "Cisco UCS equipment:Fan:dn managed object property"
    ::= { cucsEquipmentFanEntry 2 }

cucsEquipmentFanRn OBJECT-TYPE
    SYNTAX       SnmpAdminString
    MAX-ACCESS   read-only
    STATUS       current
    DESCRIPTION
        "Cisco UCS equipment:Fan:rn managed object property"
    ::= { cucsEquipmentFanEntry 3 }

cucsEquipmentFanFltAggr OBJECT-TYPE
    SYNTAX       Unsigned64
    MAX-ACCESS   read-only
    STATUS       current
    DESCRIPTION
        "Cisco UCS equipment:Fan:fltAggr managed object property"
    ::= { cucsEquipmentFanEntry 4 }

cucsEquipmentFanId OBJECT-TYPE
    SYNTAX       CucsEquipmentFanId
    MAX-ACCESS   read-only
    STATUS       current
    DESCRIPTION
        "Cisco UCS equipment:Fan:id managed object property"
    ::= { cucsEquipmentFanEntry 5 }

cucsEquipmentFanIntType OBJECT-TYPE
    SYNTAX       CucsEquipmentInternalFanType
    MAX-ACCESS   read-only
    STATUS       current
    DESCRIPTION
        "Cisco UCS equipment:Fan:intType managed object property"
    ::= { cucsEquipmentFanEntry 6 }

cucsEquipmentFanModel OBJECT-TYPE
    SYNTAX       SnmpAdminString
    MAX-ACCESS   read-only
    STATUS       current
    DESCRIPTION
        "Cisco UCS equipment:Fan:model managed object property"
    ::= { cucsEquipmentFanEntry 7 }

cucsEquipmentFanModule OBJECT-TYPE
    SYNTAX       CucsEquipmentFanModule
    MAX-ACCESS   read-only
    STATUS       current
    DESCRIPTION
        "Cisco UCS equipment:Fan:module managed object property"
    ::= { cucsEquipmentFanEntry 8 }

cucsEquipmentFanOperState OBJECT-TYPE
    SYNTAX       CucsEquipmentOperability
    MAX-ACCESS   read-only
    STATUS       current
    DESCRIPTION
        "Cisco UCS equipment:Fan:operState managed object property"
    ::= { cucsEquipmentFanEntry 9 }

cucsEquipmentFanOperability OBJECT-TYPE
    SYNTAX       CucsEquipmentOperability
    MAX-ACCESS   read-only
    STATUS       current
    DESCRIPTION
        "Cisco UCS equipment:Fan:operability managed object property"
    ::= { cucsEquipmentFanEntry 10 }

cucsEquipmentFanPerf OBJECT-TYPE
    SYNTAX       CucsEquipmentSensorThresholdStatus
    MAX-ACCESS   read-only
    STATUS       current
    DESCRIPTION
        "Cisco UCS equipment:Fan:perf managed object property"
    ::= { cucsEquipmentFanEntry 11 }

cucsEquipmentFanPower OBJECT-TYPE
    SYNTAX       CucsEquipmentPowerState
    MAX-ACCESS   read-only
    STATUS       current
    DESCRIPTION
        "Cisco UCS equipment:Fan:power managed object property"
    ::= { cucsEquipmentFanEntry 12 }

cucsEquipmentFanPresence OBJECT-TYPE
    SYNTAX       CucsEquipmentPresence
    MAX-ACCESS   read-only
    STATUS       current
    DESCRIPTION
        "Cisco UCS equipment:Fan:presence managed object property"
    ::= { cucsEquipmentFanEntry 13 }

cucsEquipmentFanRevision OBJECT-TYPE
    SYNTAX       SnmpAdminString
    MAX-ACCESS   read-only
    STATUS       current
    DESCRIPTION
        "Cisco UCS equipment:Fan:revision managed object property"
    ::= { cucsEquipmentFanEntry 14 }

cucsEquipmentFanSerial OBJECT-TYPE
    SYNTAX       SnmpAdminString
    MAX-ACCESS   read-only
    STATUS       current
    DESCRIPTION
        "Cisco UCS equipment:Fan:serial managed object property"
    ::= { cucsEquipmentFanEntry 15 }

cucsEquipmentFanThermal OBJECT-TYPE
    SYNTAX       CucsEquipmentSensorThresholdStatus
    MAX-ACCESS   read-only
    STATUS       current
    DESCRIPTION
        "Cisco UCS equipment:Fan:thermal managed object property"
    ::= { cucsEquipmentFanEntry 16 }

cucsEquipmentFanTray OBJECT-TYPE
    SYNTAX       CucsEquipmentFanTray
    MAX-ACCESS   read-only
    STATUS       current
    DESCRIPTION
        "Cisco UCS equipment:Fan:tray managed object property"
    ::= { cucsEquipmentFanEntry 17 }

cucsEquipmentFanVendor OBJECT-TYPE
    SYNTAX       SnmpAdminString
    MAX-ACCESS   read-only
    STATUS       current
    DESCRIPTION
        "Cisco UCS equipment:Fan:vendor managed object property"
    ::= { cucsEquipmentFanEntry 18 }

cucsEquipmentFanVoltage OBJECT-TYPE
    SYNTAX       CucsEquipmentSensorThresholdStatus
    MAX-ACCESS   read-only
    STATUS       current
    DESCRIPTION
        "Cisco UCS equipment:Fan:voltage managed object property"
    ::= { cucsEquipmentFanEntry 19 }

cucsEquipmentFanOperQualifierReason OBJECT-TYPE
    SYNTAX       SnmpAdminString
    MAX-ACCESS   read-only
    STATUS       current
    DESCRIPTION
        "Cisco UCS equipment:Fan:operQualifierReason managed
        object property"
    ::= { cucsEquipmentFanEntry 20 }

cucsEquipmentFanModuleTable OBJECT-TYPE
    SYNTAX           SEQUENCE OF CucsEquipmentFanModuleEntry
    MAX-ACCESS       not-accessible
    STATUS           current
    DESCRIPTION
        "Cisco UCS equipment:FanModule managed object table"
    ::= { cucsEquipmentObjects 13 }

cucsEquipmentFanModuleEntry OBJECT-TYPE
    SYNTAX           CucsEquipmentFanModuleEntry
    MAX-ACCESS       not-accessible
    STATUS           current
    DESCRIPTION
        "Entry for the cucsEquipmentFanModuleTable table."
    INDEX { cucsEquipmentFanModuleInstanceId }
    ::= { cucsEquipmentFanModuleTable 1 }

CucsEquipmentFanModuleEntry ::= SEQUENCE {
    cucsEquipmentFanModuleInstanceId                                 CucsManagedObjectId,
    cucsEquipmentFanModuleDn                                         CucsManagedObjectDn,
    cucsEquipmentFanModuleRn                                         SnmpAdminString,
    cucsEquipmentFanModuleFltAggr                                    Unsigned64,
    cucsEquipmentFanModuleId                                         CucsEquipmentFanModuleId,
    cucsEquipmentFanModuleModel                                      SnmpAdminString,
    cucsEquipmentFanModuleOperState                                  CucsEquipmentOperability,
    cucsEquipmentFanModuleOperability                                CucsEquipmentOperability,
    cucsEquipmentFanModulePerf                                       CucsEquipmentSensorThresholdStatus,
    cucsEquipmentFanModulePower                                      CucsEquipmentPowerState,
    cucsEquipmentFanModulePresence                                   CucsEquipmentPresence,
    cucsEquipmentFanModuleRevision                                   SnmpAdminString,
    cucsEquipmentFanModuleSerial                                     SnmpAdminString,
    cucsEquipmentFanModuleThermal                                    CucsEquipmentSensorThresholdStatus,
    cucsEquipmentFanModuleTray                                       CucsEquipmentFanModuleTray,
    cucsEquipmentFanModuleVendor                                     SnmpAdminString,
    cucsEquipmentFanModuleVoltage                                    CucsEquipmentSensorThresholdStatus,
    cucsEquipmentFanModuleMfgTime                                    DateAndTime,
    cucsEquipmentFanModuleOperQualifierReason                        SnmpAdminString
}

cucsEquipmentFanModuleInstanceId OBJECT-TYPE
    SYNTAX       CucsManagedObjectId
    MAX-ACCESS   not-accessible
    STATUS       current
    DESCRIPTION
        "Instance identifier of the managed object."
    ::= { cucsEquipmentFanModuleEntry 1 }

cucsEquipmentFanModuleDn OBJECT-TYPE
    SYNTAX       CucsManagedObjectDn
    MAX-ACCESS   read-only
    STATUS       current
    DESCRIPTION
        "Cisco UCS equipment:FanModule:dn managed object property"
    ::= { cucsEquipmentFanModuleEntry 2 }

cucsEquipmentFanModuleRn OBJECT-TYPE
    SYNTAX       SnmpAdminString
    MAX-ACCESS   read-only
    STATUS       current
    DESCRIPTION
        "Cisco UCS equipment:FanModule:rn managed object property"
    ::= { cucsEquipmentFanModuleEntry 3 }

cucsEquipmentFanModuleFltAggr OBJECT-TYPE
    SYNTAX       Unsigned64
    MAX-ACCESS   read-only
    STATUS       current
    DESCRIPTION
        "Cisco UCS equipment:FanModule:fltAggr managed object property"
    ::= { cucsEquipmentFanModuleEntry 4 }

cucsEquipmentFanModuleId OBJECT-TYPE
    SYNTAX       CucsEquipmentFanModuleId
    MAX-ACCESS   read-only
    STATUS       current
    DESCRIPTION
        "Cisco UCS equipment:FanModule:id managed object property"
    ::= { cucsEquipmentFanModuleEntry 5 }

cucsEquipmentFanModuleModel OBJECT-TYPE
    SYNTAX       SnmpAdminString
    MAX-ACCESS   read-only
    STATUS       current
    DESCRIPTION
        "Cisco UCS equipment:FanModule:model managed object property"
    ::= { cucsEquipmentFanModuleEntry 6 }

cucsEquipmentFanModuleOperState OBJECT-TYPE
    SYNTAX       CucsEquipmentOperability
    MAX-ACCESS   read-only
    STATUS       current
    DESCRIPTION
        "Cisco UCS equipment:FanModule:operState managed object property"
    ::= { cucsEquipmentFanModuleEntry 7 }

cucsEquipmentFanModuleOperability OBJECT-TYPE
    SYNTAX       CucsEquipmentOperability
    MAX-ACCESS   read-only
    STATUS       current
    DESCRIPTION
        "Cisco UCS equipment:FanModule:operability managed
        object property"
    ::= { cucsEquipmentFanModuleEntry 8 }

cucsEquipmentFanModulePerf OBJECT-TYPE
    SYNTAX       CucsEquipmentSensorThresholdStatus
    MAX-ACCESS   read-only
    STATUS       current
    DESCRIPTION
        "Cisco UCS equipment:FanModule:perf managed object property"
    ::= { cucsEquipmentFanModuleEntry 9 }

cucsEquipmentFanModulePower OBJECT-TYPE
    SYNTAX       CucsEquipmentPowerState
    MAX-ACCESS   read-only
    STATUS       current
    DESCRIPTION
        "Cisco UCS equipment:FanModule:power managed object property"
    ::= { cucsEquipmentFanModuleEntry 10 }

cucsEquipmentFanModulePresence OBJECT-TYPE
    SYNTAX       CucsEquipmentPresence
    MAX-ACCESS   read-only
    STATUS       current
    DESCRIPTION
        "Cisco UCS equipment:FanModule:presence managed object property"
    ::= { cucsEquipmentFanModuleEntry 11 }

cucsEquipmentFanModuleRevision OBJECT-TYPE
    SYNTAX       SnmpAdminString
    MAX-ACCESS   read-only
    STATUS       current
    DESCRIPTION
        "Cisco UCS equipment:FanModule:revision managed object property"
    ::= { cucsEquipmentFanModuleEntry 12 }

cucsEquipmentFanModuleSerial OBJECT-TYPE
    SYNTAX       SnmpAdminString
    MAX-ACCESS   read-only
    STATUS       current
    DESCRIPTION
        "Cisco UCS equipment:FanModule:serial managed object property"
    ::= { cucsEquipmentFanModuleEntry 13 }

cucsEquipmentFanModuleThermal OBJECT-TYPE
    SYNTAX       CucsEquipmentSensorThresholdStatus
    MAX-ACCESS   read-only
    STATUS       current
    DESCRIPTION
        "Cisco UCS equipment:FanModule:thermal managed object property"
    ::= { cucsEquipmentFanModuleEntry 14 }

cucsEquipmentFanModuleTray OBJECT-TYPE
    SYNTAX       CucsEquipmentFanModuleTray
    MAX-ACCESS   read-only
    STATUS       current
    DESCRIPTION
        "Cisco UCS equipment:FanModule:tray managed object property"
    ::= { cucsEquipmentFanModuleEntry 15 }

cucsEquipmentFanModuleVendor OBJECT-TYPE
    SYNTAX       SnmpAdminString
    MAX-ACCESS   read-only
    STATUS       current
    DESCRIPTION
        "Cisco UCS equipment:FanModule:vendor managed object property"
    ::= { cucsEquipmentFanModuleEntry 16 }

cucsEquipmentFanModuleVoltage OBJECT-TYPE
    SYNTAX       CucsEquipmentSensorThresholdStatus
    MAX-ACCESS   read-only
    STATUS       current
    DESCRIPTION
        "Cisco UCS equipment:FanModule:voltage managed object property"
    ::= { cucsEquipmentFanModuleEntry 17 }

cucsEquipmentFanModuleMfgTime OBJECT-TYPE
    SYNTAX       DateAndTime
    MAX-ACCESS   read-only
    STATUS       current
    DESCRIPTION
        "Cisco UCS equipment:FanModule:mfgTime managed object property"
    ::= { cucsEquipmentFanModuleEntry 18 }

cucsEquipmentFanModuleOperQualifierReason OBJECT-TYPE
    SYNTAX       SnmpAdminString
    MAX-ACCESS   read-only
    STATUS       current
    DESCRIPTION
        "Cisco UCS equipment:FanModule:operQualifierReason
        managed object property"
    ::= { cucsEquipmentFanModuleEntry 19 }

cucsEquipmentFanModuleCapProviderTable OBJECT-TYPE
    SYNTAX           SEQUENCE OF CucsEquipmentFanModuleCapProviderEntry
    MAX-ACCESS       not-accessible
    STATUS           current
    DESCRIPTION
        "Cisco UCS equipment:FanModuleCapProvider managed object table"
    ::= { cucsEquipmentObjects 14 }

cucsEquipmentFanModuleCapProviderEntry OBJECT-TYPE
    SYNTAX           CucsEquipmentFanModuleCapProviderEntry
    MAX-ACCESS       not-accessible
    STATUS           current
    DESCRIPTION
        "Entry for the cucsEquipmentFanModuleCapProviderTable table."
    INDEX { cucsEquipmentFanModuleCapProviderInstanceId }
    ::= { cucsEquipmentFanModuleCapProviderTable 1 }

CucsEquipmentFanModuleCapProviderEntry ::= SEQUENCE {
    cucsEquipmentFanModuleCapProviderInstanceId                      CucsManagedObjectId,
    cucsEquipmentFanModuleCapProviderDn                              CucsManagedObjectDn,
    cucsEquipmentFanModuleCapProviderRn                              SnmpAdminString,
    cucsEquipmentFanModuleCapProviderDeprecated                      TruthValue,
    cucsEquipmentFanModuleCapProviderGencount                        Gauge32,
    cucsEquipmentFanModuleCapProviderMgmtPlaneVer                    SnmpAdminString,
    cucsEquipmentFanModuleCapProviderModel                           SnmpAdminString,
    cucsEquipmentFanModuleCapProviderRevision                        SnmpAdminString,
    cucsEquipmentFanModuleCapProviderVendor                          SnmpAdminString,
    cucsEquipmentFanModuleCapProviderPromCardType                    Gauge32,
    cucsEquipmentFanModuleCapProviderDeleted                         TruthValue,
    cucsEquipmentFanModuleCapProviderElementLoadFailures             Gauge32,
    cucsEquipmentFanModuleCapProviderElementsLoaded                  Gauge32,
    cucsEquipmentFanModuleCapProviderLoadErrors                      Gauge32,
    cucsEquipmentFanModuleCapProviderLoadWarnings                    Gauge32
}

cucsEquipmentFanModuleCapProviderInstanceId OBJECT-TYPE
    SYNTAX       CucsManagedObjectId
    MAX-ACCESS   not-accessible
    STATUS       current
    DESCRIPTION
        "Instance identifier of the managed object."
    ::= { cucsEquipmentFanModuleCapProviderEntry 1 }

cucsEquipmentFanModuleCapProviderDn OBJECT-TYPE
    SYNTAX       CucsManagedObjectDn
    MAX-ACCESS   read-only
    STATUS       current
    DESCRIPTION
        "Cisco UCS equipment:FanModuleCapProvider:dn managed
        object property"
    ::= { cucsEquipmentFanModuleCapProviderEntry 2 }

cucsEquipmentFanModuleCapProviderRn OBJECT-TYPE
    SYNTAX       SnmpAdminString
    MAX-ACCESS   read-only
    STATUS       current
    DESCRIPTION
        "Cisco UCS equipment:FanModuleCapProvider:rn managed
        object property"
    ::= { cucsEquipmentFanModuleCapProviderEntry 3 }

cucsEquipmentFanModuleCapProviderDeprecated OBJECT-TYPE
    SYNTAX       TruthValue
    MAX-ACCESS   read-only
    STATUS       current
    DESCRIPTION
        "Cisco UCS equipment:FanModuleCapProvider:deprecated
        managed object property"
    ::= { cucsEquipmentFanModuleCapProviderEntry 4 }

cucsEquipmentFanModuleCapProviderGencount OBJECT-TYPE
    SYNTAX       Gauge32
    MAX-ACCESS   read-only
    STATUS       current
    DESCRIPTION
        "Cisco UCS equipment:FanModuleCapProvider:gencount
        managed object property"
    ::= { cucsEquipmentFanModuleCapProviderEntry 5 }

cucsEquipmentFanModuleCapProviderMgmtPlaneVer OBJECT-TYPE
    SYNTAX       SnmpAdminString
    MAX-ACCESS   read-only
    STATUS       current
    DESCRIPTION
        "Cisco UCS equipment:FanModuleCapProvider:mgmtPlaneVer
        managed object property"
    ::= { cucsEquipmentFanModuleCapProviderEntry 6 }

cucsEquipmentFanModuleCapProviderModel OBJECT-TYPE
    SYNTAX       SnmpAdminString
    MAX-ACCESS   read-only
    STATUS       current
    DESCRIPTION
        "Cisco UCS equipment:FanModuleCapProvider:model
        managed object property"
    ::= { cucsEquipmentFanModuleCapProviderEntry 7 }

cucsEquipmentFanModuleCapProviderRevision OBJECT-TYPE
    SYNTAX       SnmpAdminString
    MAX-ACCESS   read-only
    STATUS       current
    DESCRIPTION
        "Cisco UCS equipment:FanModuleCapProvider:revision
        managed object property"
    ::= { cucsEquipmentFanModuleCapProviderEntry 8 }

cucsEquipmentFanModuleCapProviderVendor OBJECT-TYPE
    SYNTAX       SnmpAdminString
    MAX-ACCESS   read-only
    STATUS       current
    DESCRIPTION
        "Cisco UCS equipment:FanModuleCapProvider:vendor
        managed object property"
    ::= { cucsEquipmentFanModuleCapProviderEntry 9 }

cucsEquipmentFanModuleCapProviderPromCardType OBJECT-TYPE
    SYNTAX       Gauge32
    MAX-ACCESS   read-only
    STATUS       current
    DESCRIPTION
        "Cisco UCS equipment:FanModuleCapProvider:promCardType
        managed object property"
    ::= { cucsEquipmentFanModuleCapProviderEntry 10 }

cucsEquipmentFanModuleCapProviderDeleted OBJECT-TYPE
    SYNTAX       TruthValue
    MAX-ACCESS   read-only
    STATUS       current
    DESCRIPTION
        "Cisco UCS equipment:FanModuleCapProvider:deleted
        managed object property"
    ::= { cucsEquipmentFanModuleCapProviderEntry 11 }

cucsEquipmentFanModuleCapProviderElementLoadFailures OBJECT-TYPE
    SYNTAX       Gauge32
    MAX-ACCESS   read-only
    STATUS       current
    DESCRIPTION
        "Cisco UCS equipment:FanModuleCapProvider:elementLoadFailures
        managed object property"
    ::= { cucsEquipmentFanModuleCapProviderEntry 12 }

cucsEquipmentFanModuleCapProviderElementsLoaded OBJECT-TYPE
    SYNTAX       Gauge32
    MAX-ACCESS   read-only
    STATUS       current
    DESCRIPTION
        "Cisco UCS equipment:FanModuleCapProvider:elementsLoaded
        managed object property"
    ::= { cucsEquipmentFanModuleCapProviderEntry 13 }

cucsEquipmentFanModuleCapProviderLoadErrors OBJECT-TYPE
    SYNTAX       Gauge32
    MAX-ACCESS   read-only
    STATUS       current
    DESCRIPTION
        "Cisco UCS equipment:FanModuleCapProvider:loadErrors
        managed object property"
    ::= { cucsEquipmentFanModuleCapProviderEntry 14 }

cucsEquipmentFanModuleCapProviderLoadWarnings OBJECT-TYPE
    SYNTAX       Gauge32
    MAX-ACCESS   read-only
    STATUS       current
    DESCRIPTION
        "Cisco UCS equipment:FanModuleCapProvider:loadWarnings
        managed object property"
    ::= { cucsEquipmentFanModuleCapProviderEntry 15 }

cucsEquipmentFanModuleDefTable OBJECT-TYPE
    SYNTAX           SEQUENCE OF CucsEquipmentFanModuleDefEntry
    MAX-ACCESS       not-accessible
    STATUS           current
    DESCRIPTION
        "Cisco UCS equipment:FanModuleDef managed object table"
    ::= { cucsEquipmentObjects 84 }

cucsEquipmentFanModuleDefEntry OBJECT-TYPE
    SYNTAX           CucsEquipmentFanModuleDefEntry
    MAX-ACCESS       not-accessible
    STATUS           current
    DESCRIPTION
        "Entry for the cucsEquipmentFanModuleDefTable table."
    INDEX { cucsEquipmentFanModuleDefInstanceId }
    ::= { cucsEquipmentFanModuleDefTable 1 }

CucsEquipmentFanModuleDefEntry ::= SEQUENCE {
    cucsEquipmentFanModuleDefInstanceId                              CucsManagedObjectId,
    cucsEquipmentFanModuleDefDn                                      CucsManagedObjectDn,
    cucsEquipmentFanModuleDefRn                                      SnmpAdminString,
    cucsEquipmentFanModuleDefDescr                                   SnmpAdminString,
    cucsEquipmentFanModuleDefFanCapacity                             Gauge32,
    cucsEquipmentFanModuleDefIntId                                   SnmpAdminString,
    cucsEquipmentFanModuleDefName                                    SnmpAdminString,
    cucsEquipmentFanModuleDefPolicyLevel                             Gauge32,
    cucsEquipmentFanModuleDefPolicyOwner                             CucsPolicyPolicyOwner
}

cucsEquipmentFanModuleDefInstanceId OBJECT-TYPE
    SYNTAX       CucsManagedObjectId
    MAX-ACCESS   not-accessible
    STATUS       current
    DESCRIPTION
        "Instance identifier of the managed object."
    ::= { cucsEquipmentFanModuleDefEntry 1 }

cucsEquipmentFanModuleDefDn OBJECT-TYPE
    SYNTAX       CucsManagedObjectDn
    MAX-ACCESS   read-only
    STATUS       current
    DESCRIPTION
        "Cisco UCS equipment:FanModuleDef:dn managed object property"
    ::= { cucsEquipmentFanModuleDefEntry 2 }

cucsEquipmentFanModuleDefRn OBJECT-TYPE
    SYNTAX       SnmpAdminString
    MAX-ACCESS   read-only
    STATUS       current
    DESCRIPTION
        "Cisco UCS equipment:FanModuleDef:rn managed object property"
    ::= { cucsEquipmentFanModuleDefEntry 3 }

cucsEquipmentFanModuleDefDescr OBJECT-TYPE
    SYNTAX       SnmpAdminString
    MAX-ACCESS   read-only
    STATUS       current
    DESCRIPTION
        "Cisco UCS equipment:FanModuleDef:descr managed object property"
    ::= { cucsEquipmentFanModuleDefEntry 4 }

cucsEquipmentFanModuleDefFanCapacity OBJECT-TYPE
    SYNTAX       Gauge32
    MAX-ACCESS   read-only
    STATUS       current
    DESCRIPTION
        "Cisco UCS equipment:FanModuleDef:fanCapacity managed
        object property"
    ::= { cucsEquipmentFanModuleDefEntry 5 }

cucsEquipmentFanModuleDefIntId OBJECT-TYPE
    SYNTAX       SnmpAdminString
    MAX-ACCESS   read-only
    STATUS       current
    DESCRIPTION
        "Cisco UCS equipment:FanModuleDef:intId managed object property"
    ::= { cucsEquipmentFanModuleDefEntry 6 }

cucsEquipmentFanModuleDefName OBJECT-TYPE
    SYNTAX       SnmpAdminString
    MAX-ACCESS   read-only
    STATUS       current
    DESCRIPTION
        "Cisco UCS equipment:FanModuleDef:name managed object property"
    ::= { cucsEquipmentFanModuleDefEntry 7 }

cucsEquipmentFanModuleDefPolicyLevel OBJECT-TYPE
    SYNTAX       Gauge32
    MAX-ACCESS   read-only
    STATUS       current
    DESCRIPTION
        "Cisco UCS equipment:FanModuleDef:policyLevel managed
        object property"
    ::= { cucsEquipmentFanModuleDefEntry 8 }

cucsEquipmentFanModuleDefPolicyOwner OBJECT-TYPE
    SYNTAX       CucsPolicyPolicyOwner
    MAX-ACCESS   read-only
    STATUS       current
    DESCRIPTION
        "Cisco UCS equipment:FanModuleDef:policyOwner managed
        object property"
    ::= { cucsEquipmentFanModuleDefEntry 9 }

cucsEquipmentFanModuleStatsTable OBJECT-TYPE
    SYNTAX           SEQUENCE OF CucsEquipmentFanModuleStatsEntry
    MAX-ACCESS       not-accessible
    STATUS           current
    DESCRIPTION
        "Cisco UCS equipment:FanModuleStats managed object table"
    ::= { cucsEquipmentObjects 15 }

cucsEquipmentFanModuleStatsEntry OBJECT-TYPE
    SYNTAX           CucsEquipmentFanModuleStatsEntry
    MAX-ACCESS       not-accessible
    STATUS           current
    DESCRIPTION
        "Entry for the cucsEquipmentFanModuleStatsTable table."
    INDEX { cucsEquipmentFanModuleStatsInstanceId }
    ::= { cucsEquipmentFanModuleStatsTable 1 }

CucsEquipmentFanModuleStatsEntry ::= SEQUENCE {
    cucsEquipmentFanModuleStatsInstanceId                            CucsManagedObjectId,
    cucsEquipmentFanModuleStatsDn                                    CucsManagedObjectDn,
    cucsEquipmentFanModuleStatsRn                                    SnmpAdminString,
    cucsEquipmentFanModuleStatsAmbientTemp                           INTEGER,
    cucsEquipmentFanModuleStatsAmbientTempAvg                        INTEGER,
    cucsEquipmentFanModuleStatsAmbientTempMax                        INTEGER,
    cucsEquipmentFanModuleStatsAmbientTempMin                        INTEGER,
    cucsEquipmentFanModuleStatsIntervals                             Gauge32,
    cucsEquipmentFanModuleStatsSuspect                               TruthValue,
    cucsEquipmentFanModuleStatsThresholded                           CucsEquipmentFanModuleStatsThresholded,
    cucsEquipmentFanModuleStatsTimeCollected                         DateAndTime,
    cucsEquipmentFanModuleStatsUpdate                                Gauge32
}

cucsEquipmentFanModuleStatsInstanceId OBJECT-TYPE
    SYNTAX       CucsManagedObjectId
    MAX-ACCESS   not-accessible
    STATUS       current
    DESCRIPTION
        "Instance identifier of the managed object."
    ::= { cucsEquipmentFanModuleStatsEntry 1 }

cucsEquipmentFanModuleStatsDn OBJECT-TYPE
    SYNTAX       CucsManagedObjectDn
    MAX-ACCESS   read-only
    STATUS       current
    DESCRIPTION
        "Cisco UCS equipment:FanModuleStats:dn managed object property"
    ::= { cucsEquipmentFanModuleStatsEntry 2 }

cucsEquipmentFanModuleStatsRn OBJECT-TYPE
    SYNTAX       SnmpAdminString
    MAX-ACCESS   read-only
    STATUS       current
    DESCRIPTION
        "Cisco UCS equipment:FanModuleStats:rn managed object property"
    ::= { cucsEquipmentFanModuleStatsEntry 3 }

cucsEquipmentFanModuleStatsAmbientTemp OBJECT-TYPE
    SYNTAX       INTEGER
    MAX-ACCESS   read-only
    STATUS       current
    DESCRIPTION
        "Cisco UCS equipment:FanModuleStats:ambientTemp
        managed object property"
    ::= { cucsEquipmentFanModuleStatsEntry 4 }

cucsEquipmentFanModuleStatsAmbientTempAvg OBJECT-TYPE
    SYNTAX       INTEGER
    MAX-ACCESS   read-only
    STATUS       current
    DESCRIPTION
        "Cisco UCS equipment:FanModuleStats:ambientTempAvg
        managed object property"
    ::= { cucsEquipmentFanModuleStatsEntry 5 }

cucsEquipmentFanModuleStatsAmbientTempMax OBJECT-TYPE
    SYNTAX       INTEGER
    MAX-ACCESS   read-only
    STATUS       current
    DESCRIPTION
        "Cisco UCS equipment:FanModuleStats:ambientTempMax
        managed object property"
    ::= { cucsEquipmentFanModuleStatsEntry 6 }

cucsEquipmentFanModuleStatsAmbientTempMin OBJECT-TYPE
    SYNTAX       INTEGER
    MAX-ACCESS   read-only
    STATUS       current
    DESCRIPTION
        "Cisco UCS equipment:FanModuleStats:ambientTempMin
        managed object property"
    ::= { cucsEquipmentFanModuleStatsEntry 7 }

cucsEquipmentFanModuleStatsIntervals OBJECT-TYPE
    SYNTAX       Gauge32
    MAX-ACCESS   read-only
    STATUS       current
    DESCRIPTION
        "Cisco UCS equipment:FanModuleStats:intervals managed
        object property"
    ::= { cucsEquipmentFanModuleStatsEntry 8 }

cucsEquipmentFanModuleStatsSuspect OBJECT-TYPE
    SYNTAX       TruthValue
    MAX-ACCESS   read-only
    STATUS       current
    DESCRIPTION
        "Cisco UCS equipment:FanModuleStats:suspect managed
        object property"
    ::= { cucsEquipmentFanModuleStatsEntry 9 }

cucsEquipmentFanModuleStatsThresholded OBJECT-TYPE
    SYNTAX       CucsEquipmentFanModuleStatsThresholded
    MAX-ACCESS   read-only
    STATUS       current
    DESCRIPTION
        "Cisco UCS equipment:FanModuleStats:thresholded
        managed object property"
    ::= { cucsEquipmentFanModuleStatsEntry 10 }

cucsEquipmentFanModuleStatsTimeCollected OBJECT-TYPE
    SYNTAX       DateAndTime
    MAX-ACCESS   read-only
    STATUS       current
    DESCRIPTION
        "Cisco UCS equipment:FanModuleStats:timeCollected
        managed object property"
    ::= { cucsEquipmentFanModuleStatsEntry 11 }

cucsEquipmentFanModuleStatsUpdate OBJECT-TYPE
    SYNTAX       Gauge32
    MAX-ACCESS   read-only
    STATUS       current
    DESCRIPTION
        "Cisco UCS equipment:FanModuleStats:update managed
        object property"
    ::= { cucsEquipmentFanModuleStatsEntry 12 }

cucsEquipmentFanModuleStatsHistTable OBJECT-TYPE
    SYNTAX           SEQUENCE OF CucsEquipmentFanModuleStatsHistEntry
    MAX-ACCESS       not-accessible
    STATUS           current
    DESCRIPTION
        "Cisco UCS equipment:FanModuleStatsHist managed object table"
    ::= { cucsEquipmentObjects 16 }

cucsEquipmentFanModuleStatsHistEntry OBJECT-TYPE
    SYNTAX           CucsEquipmentFanModuleStatsHistEntry
    MAX-ACCESS       not-accessible
    STATUS           current
    DESCRIPTION
        "Entry for the cucsEquipmentFanModuleStatsHistTable table."
    INDEX { cucsEquipmentFanModuleStatsHistInstanceId }
    ::= { cucsEquipmentFanModuleStatsHistTable 1 }

CucsEquipmentFanModuleStatsHistEntry ::= SEQUENCE {
    cucsEquipmentFanModuleStatsHistInstanceId                        CucsManagedObjectId,
    cucsEquipmentFanModuleStatsHistDn                                CucsManagedObjectDn,
    cucsEquipmentFanModuleStatsHistRn                                SnmpAdminString,
    cucsEquipmentFanModuleStatsHistAmbientTemp                       INTEGER,
    cucsEquipmentFanModuleStatsHistAmbientTempAvg                    INTEGER,
    cucsEquipmentFanModuleStatsHistAmbientTempMax                    INTEGER,
    cucsEquipmentFanModuleStatsHistAmbientTempMin                    INTEGER,
    cucsEquipmentFanModuleStatsHistId                                Unsigned64,
    cucsEquipmentFanModuleStatsHistMostRecent                        TruthValue,
    cucsEquipmentFanModuleStatsHistSuspect                           TruthValue,
    cucsEquipmentFanModuleStatsHistThresholded                       CucsEquipmentFanModuleStatsHistThresholded,
    cucsEquipmentFanModuleStatsHistTimeCollected                     DateAndTime
}

cucsEquipmentFanModuleStatsHistInstanceId OBJECT-TYPE
    SYNTAX       CucsManagedObjectId
    MAX-ACCESS   not-accessible
    STATUS       current
    DESCRIPTION
        "Instance identifier of the managed object."
    ::= { cucsEquipmentFanModuleStatsHistEntry 1 }

cucsEquipmentFanModuleStatsHistDn OBJECT-TYPE
    SYNTAX       CucsManagedObjectDn
    MAX-ACCESS   read-only
    STATUS       current
    DESCRIPTION
        "Cisco UCS equipment:FanModuleStatsHist:dn managed
        object property"
    ::= { cucsEquipmentFanModuleStatsHistEntry 2 }

cucsEquipmentFanModuleStatsHistRn OBJECT-TYPE
    SYNTAX       SnmpAdminString
    MAX-ACCESS   read-only
    STATUS       current
    DESCRIPTION
        "Cisco UCS equipment:FanModuleStatsHist:rn managed
        object property"
    ::= { cucsEquipmentFanModuleStatsHistEntry 3 }

cucsEquipmentFanModuleStatsHistAmbientTemp OBJECT-TYPE
    SYNTAX       INTEGER
    MAX-ACCESS   read-only
    STATUS       current
    DESCRIPTION
        "Cisco UCS equipment:FanModuleStatsHist:ambientTemp
        managed object property"
    ::= { cucsEquipmentFanModuleStatsHistEntry 4 }

cucsEquipmentFanModuleStatsHistAmbientTempAvg OBJECT-TYPE
    SYNTAX       INTEGER
    MAX-ACCESS   read-only
    STATUS       current
    DESCRIPTION
        "Cisco UCS equipment:FanModuleStatsHist:ambientTempAvg
        managed object property"
    ::= { cucsEquipmentFanModuleStatsHistEntry 5 }

cucsEquipmentFanModuleStatsHistAmbientTempMax OBJECT-TYPE
    SYNTAX       INTEGER
    MAX-ACCESS   read-only
    STATUS       current
    DESCRIPTION
        "Cisco UCS equipment:FanModuleStatsHist:ambientTempMax
        managed object property"
    ::= { cucsEquipmentFanModuleStatsHistEntry 6 }

cucsEquipmentFanModuleStatsHistAmbientTempMin OBJECT-TYPE
    SYNTAX       INTEGER
    MAX-ACCESS   read-only
    STATUS       current
    DESCRIPTION
        "Cisco UCS equipment:FanModuleStatsHist:ambientTempMin
        managed object property"
    ::= { cucsEquipmentFanModuleStatsHistEntry 7 }

cucsEquipmentFanModuleStatsHistId OBJECT-TYPE
    SYNTAX       Unsigned64
    MAX-ACCESS   read-only
    STATUS       current
    DESCRIPTION
        "Cisco UCS equipment:FanModuleStatsHist:id managed
        object property"
    ::= { cucsEquipmentFanModuleStatsHistEntry 8 }

cucsEquipmentFanModuleStatsHistMostRecent OBJECT-TYPE
    SYNTAX       TruthValue
    MAX-ACCESS   read-only
    STATUS       current
    DESCRIPTION
        "Cisco UCS equipment:FanModuleStatsHist:mostRecent
        managed object property"
    ::= { cucsEquipmentFanModuleStatsHistEntry 9 }

cucsEquipmentFanModuleStatsHistSuspect OBJECT-TYPE
    SYNTAX       TruthValue
    MAX-ACCESS   read-only
    STATUS       current
    DESCRIPTION
        "Cisco UCS equipment:FanModuleStatsHist:suspect
        managed object property"
    ::= { cucsEquipmentFanModuleStatsHistEntry 10 }

cucsEquipmentFanModuleStatsHistThresholded OBJECT-TYPE
    SYNTAX       CucsEquipmentFanModuleStatsHistThresholded
    MAX-ACCESS   read-only
    STATUS       current
    DESCRIPTION
        "Cisco UCS equipment:FanModuleStatsHist:thresholded
        managed object property"
    ::= { cucsEquipmentFanModuleStatsHistEntry 11 }

cucsEquipmentFanModuleStatsHistTimeCollected OBJECT-TYPE
    SYNTAX       DateAndTime
    MAX-ACCESS   read-only
    STATUS       current
    DESCRIPTION
        "Cisco UCS equipment:FanModuleStatsHist:timeCollected
        managed object property"
    ::= { cucsEquipmentFanModuleStatsHistEntry 12 }

cucsEquipmentFanStatsTable OBJECT-TYPE
    SYNTAX           SEQUENCE OF CucsEquipmentFanStatsEntry
    MAX-ACCESS       not-accessible
    STATUS           current
    DESCRIPTION
        "Cisco UCS equipment:FanStats managed object table"
    ::= { cucsEquipmentObjects 17 }

cucsEquipmentFanStatsEntry OBJECT-TYPE
    SYNTAX           CucsEquipmentFanStatsEntry
    MAX-ACCESS       not-accessible
    STATUS           current
    DESCRIPTION
        "Entry for the cucsEquipmentFanStatsTable table."
    INDEX { cucsEquipmentFanStatsInstanceId }
    ::= { cucsEquipmentFanStatsTable 1 }

CucsEquipmentFanStatsEntry ::= SEQUENCE {
    cucsEquipmentFanStatsInstanceId                                  CucsManagedObjectId,
    cucsEquipmentFanStatsDn                                          CucsManagedObjectDn,
    cucsEquipmentFanStatsRn                                          SnmpAdminString,
    cucsEquipmentFanStatsIntervals                                   Gauge32,
    cucsEquipmentFanStatsSpeed                                       Gauge32,
    cucsEquipmentFanStatsSpeedAvg                                    Gauge32,
    cucsEquipmentFanStatsSpeedMax                                    Gauge32,
    cucsEquipmentFanStatsSpeedMin                                    Gauge32,
    cucsEquipmentFanStatsSuspect                                     TruthValue,
    cucsEquipmentFanStatsThresholded                                 CucsEquipmentFanStatsThresholded,
    cucsEquipmentFanStatsTimeCollected                               DateAndTime,
    cucsEquipmentFanStatsUpdate                                      Gauge32
}

cucsEquipmentFanStatsInstanceId OBJECT-TYPE
    SYNTAX       CucsManagedObjectId
    MAX-ACCESS   not-accessible
    STATUS       current
    DESCRIPTION
        "Instance identifier of the managed object."
    ::= { cucsEquipmentFanStatsEntry 1 }

cucsEquipmentFanStatsDn OBJECT-TYPE
    SYNTAX       CucsManagedObjectDn
    MAX-ACCESS   read-only
    STATUS       current
    DESCRIPTION
        "Cisco UCS equipment:FanStats:dn managed object property"
    ::= { cucsEquipmentFanStatsEntry 2 }

cucsEquipmentFanStatsRn OBJECT-TYPE
    SYNTAX       SnmpAdminString
    MAX-ACCESS   read-only
    STATUS       current
    DESCRIPTION
        "Cisco UCS equipment:FanStats:rn managed object property"
    ::= { cucsEquipmentFanStatsEntry 3 }

cucsEquipmentFanStatsIntervals OBJECT-TYPE
    SYNTAX       Gauge32
    MAX-ACCESS   read-only
    STATUS       current
    DESCRIPTION
        "Cisco UCS equipment:FanStats:intervals managed object property"
    ::= { cucsEquipmentFanStatsEntry 4 }

cucsEquipmentFanStatsSpeed OBJECT-TYPE
    SYNTAX       Gauge32
    MAX-ACCESS   read-only
    STATUS       current
    DESCRIPTION
        "Cisco UCS equipment:FanStats:speed managed object property"
    ::= { cucsEquipmentFanStatsEntry 5 }

cucsEquipmentFanStatsSpeedAvg OBJECT-TYPE
    SYNTAX       Gauge32
    MAX-ACCESS   read-only
    STATUS       current
    DESCRIPTION
        "Cisco UCS equipment:FanStats:speedAvg managed object property"
    ::= { cucsEquipmentFanStatsEntry 6 }

cucsEquipmentFanStatsSpeedMax OBJECT-TYPE
    SYNTAX       Gauge32
    MAX-ACCESS   read-only
    STATUS       current
    DESCRIPTION
        "Cisco UCS equipment:FanStats:speedMax managed object property"
    ::= { cucsEquipmentFanStatsEntry 7 }

cucsEquipmentFanStatsSpeedMin OBJECT-TYPE
    SYNTAX       Gauge32
    MAX-ACCESS   read-only
    STATUS       current
    DESCRIPTION
        "Cisco UCS equipment:FanStats:speedMin managed object property"
    ::= { cucsEquipmentFanStatsEntry 8 }

cucsEquipmentFanStatsSuspect OBJECT-TYPE
    SYNTAX       TruthValue
    MAX-ACCESS   read-only
    STATUS       current
    DESCRIPTION
        "Cisco UCS equipment:FanStats:suspect managed object property"
    ::= { cucsEquipmentFanStatsEntry 9 }

cucsEquipmentFanStatsThresholded OBJECT-TYPE
    SYNTAX       CucsEquipmentFanStatsThresholded
    MAX-ACCESS   read-only
    STATUS       current
    DESCRIPTION
        "Cisco UCS equipment:FanStats:thresholded managed object property"
    ::= { cucsEquipmentFanStatsEntry 10 }

cucsEquipmentFanStatsTimeCollected OBJECT-TYPE
    SYNTAX       DateAndTime
    MAX-ACCESS   read-only
    STATUS       current
    DESCRIPTION
        "Cisco UCS equipment:FanStats:timeCollected managed
        object property"
    ::= { cucsEquipmentFanStatsEntry 11 }

cucsEquipmentFanStatsUpdate OBJECT-TYPE
    SYNTAX       Gauge32
    MAX-ACCESS   read-only
    STATUS       current
    DESCRIPTION
        "Cisco UCS equipment:FanStats:update managed object property"
    ::= { cucsEquipmentFanStatsEntry 12 }

cucsEquipmentFanStatsHistTable OBJECT-TYPE
    SYNTAX           SEQUENCE OF CucsEquipmentFanStatsHistEntry
    MAX-ACCESS       not-accessible
    STATUS           current
    DESCRIPTION
        "Cisco UCS equipment:FanStatsHist managed object table"
    ::= { cucsEquipmentObjects 18 }

cucsEquipmentFanStatsHistEntry OBJECT-TYPE
    SYNTAX           CucsEquipmentFanStatsHistEntry
    MAX-ACCESS       not-accessible
    STATUS           current
    DESCRIPTION
        "Entry for the cucsEquipmentFanStatsHistTable table."
    INDEX { cucsEquipmentFanStatsHistInstanceId }
    ::= { cucsEquipmentFanStatsHistTable 1 }

CucsEquipmentFanStatsHistEntry ::= SEQUENCE {
    cucsEquipmentFanStatsHistInstanceId                              CucsManagedObjectId,
    cucsEquipmentFanStatsHistDn                                      CucsManagedObjectDn,
    cucsEquipmentFanStatsHistRn                                      SnmpAdminString,
    cucsEquipmentFanStatsHistId                                      Unsigned64,
    cucsEquipmentFanStatsHistMostRecent                              TruthValue,
    cucsEquipmentFanStatsHistSpeed                                   Gauge32,
    cucsEquipmentFanStatsHistSpeedAvg                                Gauge32,
    cucsEquipmentFanStatsHistSpeedMax                                Gauge32,
    cucsEquipmentFanStatsHistSpeedMin                                Gauge32,
    cucsEquipmentFanStatsHistSuspect                                 TruthValue,
    cucsEquipmentFanStatsHistThresholded                             CucsEquipmentFanStatsHistThresholded,
    cucsEquipmentFanStatsHistTimeCollected                           DateAndTime
}

cucsEquipmentFanStatsHistInstanceId OBJECT-TYPE
    SYNTAX       CucsManagedObjectId
    MAX-ACCESS   not-accessible
    STATUS       current
    DESCRIPTION
        "Instance identifier of the managed object."
    ::= { cucsEquipmentFanStatsHistEntry 1 }

cucsEquipmentFanStatsHistDn OBJECT-TYPE
    SYNTAX       CucsManagedObjectDn
    MAX-ACCESS   read-only
    STATUS       current
    DESCRIPTION
        "Cisco UCS equipment:FanStatsHist:dn managed object property"
    ::= { cucsEquipmentFanStatsHistEntry 2 }

cucsEquipmentFanStatsHistRn OBJECT-TYPE
    SYNTAX       SnmpAdminString
    MAX-ACCESS   read-only
    STATUS       current
    DESCRIPTION
        "Cisco UCS equipment:FanStatsHist:rn managed object property"
    ::= { cucsEquipmentFanStatsHistEntry 3 }

cucsEquipmentFanStatsHistId OBJECT-TYPE
    SYNTAX       Unsigned64
    MAX-ACCESS   read-only
    STATUS       current
    DESCRIPTION
        "Cisco UCS equipment:FanStatsHist:id managed object property"
    ::= { cucsEquipmentFanStatsHistEntry 4 }

cucsEquipmentFanStatsHistMostRecent OBJECT-TYPE
    SYNTAX       TruthValue
    MAX-ACCESS   read-only
    STATUS       current
    DESCRIPTION
        "Cisco UCS equipment:FanStatsHist:mostRecent managed
        object property"
    ::= { cucsEquipmentFanStatsHistEntry 5 }

cucsEquipmentFanStatsHistSpeed OBJECT-TYPE
    SYNTAX       Gauge32
    MAX-ACCESS   read-only
    STATUS       current
    DESCRIPTION
        "Cisco UCS equipment:FanStatsHist:speed managed object property"
    ::= { cucsEquipmentFanStatsHistEntry 6 }

cucsEquipmentFanStatsHistSpeedAvg OBJECT-TYPE
    SYNTAX       Gauge32
    MAX-ACCESS   read-only
    STATUS       current
    DESCRIPTION
        "Cisco UCS equipment:FanStatsHist:speedAvg managed
        object property"
    ::= { cucsEquipmentFanStatsHistEntry 7 }

cucsEquipmentFanStatsHistSpeedMax OBJECT-TYPE
    SYNTAX       Gauge32
    MAX-ACCESS   read-only
    STATUS       current
    DESCRIPTION
        "Cisco UCS equipment:FanStatsHist:speedMax managed
        object property"
    ::= { cucsEquipmentFanStatsHistEntry 8 }

cucsEquipmentFanStatsHistSpeedMin OBJECT-TYPE
    SYNTAX       Gauge32
    MAX-ACCESS   read-only
    STATUS       current
    DESCRIPTION
        "Cisco UCS equipment:FanStatsHist:speedMin managed
        object property"
    ::= { cucsEquipmentFanStatsHistEntry 9 }

cucsEquipmentFanStatsHistSuspect OBJECT-TYPE
    SYNTAX       TruthValue
    MAX-ACCESS   read-only
    STATUS       current
    DESCRIPTION
        "Cisco UCS equipment:FanStatsHist:suspect managed object property"
    ::= { cucsEquipmentFanStatsHistEntry 10 }

cucsEquipmentFanStatsHistThresholded OBJECT-TYPE
    SYNTAX       CucsEquipmentFanStatsHistThresholded
    MAX-ACCESS   read-only
    STATUS       current
    DESCRIPTION
        "Cisco UCS equipment:FanStatsHist:thresholded managed
        object property"
    ::= { cucsEquipmentFanStatsHistEntry 11 }

cucsEquipmentFanStatsHistTimeCollected OBJECT-TYPE
    SYNTAX       DateAndTime
    MAX-ACCESS   read-only
    STATUS       current
    DESCRIPTION
        "Cisco UCS equipment:FanStatsHist:timeCollected
        managed object property"
    ::= { cucsEquipmentFanStatsHistEntry 12 }

cucsEquipmentFexTable OBJECT-TYPE
    SYNTAX           SEQUENCE OF CucsEquipmentFexEntry
    MAX-ACCESS       not-accessible
    STATUS           current
    DESCRIPTION
        "Cisco UCS equipment:Fex managed object table"
    ::= { cucsEquipmentObjects 19 }

cucsEquipmentFexEntry OBJECT-TYPE
    SYNTAX           CucsEquipmentFexEntry
    MAX-ACCESS       not-accessible
    STATUS           current
    DESCRIPTION
        "Entry for the cucsEquipmentFexTable table."
    INDEX { cucsEquipmentFexInstanceId }
    ::= { cucsEquipmentFexTable 1 }

CucsEquipmentFexEntry ::= SEQUENCE {
    cucsEquipmentFexInstanceId                                       CucsManagedObjectId,
    cucsEquipmentFexDn                                               CucsManagedObjectDn,
    cucsEquipmentFexRn                                               SnmpAdminString,
    cucsEquipmentFexAdminPowerState                                  CucsEquipmentAdminPowerState,
    cucsEquipmentFexAdminState                                       CucsEquipmentChassisAdminState,
    cucsEquipmentFexConfigState                                      CucsEquipmentChassisConfigState,
    cucsEquipmentFexFltAggr                                          Unsigned64,
    cucsEquipmentFexFsmDescr                                         SnmpAdminString,
    cucsEquipmentFexFsmPrev                                          SnmpAdminString,
    cucsEquipmentFexFsmProgr                                         Gauge32,
    cucsEquipmentFexFsmRmtInvErrCode                                 Gauge32,
    cucsEquipmentFexFsmRmtInvErrDescr                                SnmpAdminString,
    cucsEquipmentFexFsmRmtInvRslt                                    CucsConditionRemoteInvRslt,
    cucsEquipmentFexFsmStageDescr                                    SnmpAdminString,
    cucsEquipmentFexFsmStamp                                         DateAndTime,
    cucsEquipmentFexFsmStatus                                        SnmpAdminString,
    cucsEquipmentFexFsmTry                                           Gauge32,
    cucsEquipmentFexId                                               CucsEquipmentFexId,
    cucsEquipmentFexModel                                            SnmpAdminString,
    cucsEquipmentFexOperQualifier                                    CucsEquipmentChassisIssues,
    cucsEquipmentFexOperState                                        CucsEquipmentOperability,
    cucsEquipmentFexOperability                                      CucsEquipmentOperability,
    cucsEquipmentFexPower                                            CucsEquipmentPowerState,
    cucsEquipmentFexPresence                                         CucsEquipmentPresence,
    cucsEquipmentFexRevision                                         SnmpAdminString,
    cucsEquipmentFexSerial                                           SnmpAdminString,
    cucsEquipmentFexThermal                                          CucsEquipmentSensorThresholdStatus,
    cucsEquipmentFexUsrLbl                                           SnmpAdminString,
    cucsEquipmentFexVendor                                           SnmpAdminString,
    cucsEquipmentFexVoltage                                          CucsEquipmentSensorThresholdStatus,
    cucsEquipmentFexSwitchId                                         CucsNetworkSwitchId,
    cucsEquipmentFexLicGP                                            Unsigned64,
    cucsEquipmentFexLicState                                         CucsLicenseState,
    cucsEquipmentFexOperQualifierReason                              SnmpAdminString
}

cucsEquipmentFexInstanceId OBJECT-TYPE
    SYNTAX       CucsManagedObjectId
    MAX-ACCESS   not-accessible
    STATUS       current
    DESCRIPTION
        "Instance identifier of the managed object."
    ::= { cucsEquipmentFexEntry 1 }

cucsEquipmentFexDn OBJECT-TYPE
    SYNTAX       CucsManagedObjectDn
    MAX-ACCESS   read-only
    STATUS       current
    DESCRIPTION
        "Cisco UCS equipment:Fex:dn managed object property"
    ::= { cucsEquipmentFexEntry 2 }

cucsEquipmentFexRn OBJECT-TYPE
    SYNTAX       SnmpAdminString
    MAX-ACCESS   read-only
    STATUS       current
    DESCRIPTION
        "Cisco UCS equipment:Fex:rn managed object property"
    ::= { cucsEquipmentFexEntry 3 }

cucsEquipmentFexAdminPowerState OBJECT-TYPE
    SYNTAX       CucsEquipmentAdminPowerState
    MAX-ACCESS   read-only
    STATUS       current
    DESCRIPTION
        "Cisco UCS equipment:Fex:adminPowerState managed object property"
    ::= { cucsEquipmentFexEntry 4 }

cucsEquipmentFexAdminState OBJECT-TYPE
    SYNTAX       CucsEquipmentChassisAdminState
    MAX-ACCESS   read-only
    STATUS       current
    DESCRIPTION
        "Cisco UCS equipment:Fex:adminState managed object property"
    ::= { cucsEquipmentFexEntry 5 }

cucsEquipmentFexConfigState OBJECT-TYPE
    SYNTAX       CucsEquipmentChassisConfigState
    MAX-ACCESS   read-only
    STATUS       current
    DESCRIPTION
        "Cisco UCS equipment:Fex:configState managed object property"
    ::= { cucsEquipmentFexEntry 6 }

cucsEquipmentFexFltAggr OBJECT-TYPE
    SYNTAX       Unsigned64
    MAX-ACCESS   read-only
    STATUS       current
    DESCRIPTION
        "Cisco UCS equipment:Fex:fltAggr managed object property"
    ::= { cucsEquipmentFexEntry 7 }

cucsEquipmentFexFsmDescr OBJECT-TYPE
    SYNTAX       SnmpAdminString
    MAX-ACCESS   read-only
    STATUS       current
    DESCRIPTION
        "Cisco UCS equipment:Fex:fsmDescr managed object property"
    ::= { cucsEquipmentFexEntry 8 }

cucsEquipmentFexFsmPrev OBJECT-TYPE
    SYNTAX       SnmpAdminString
    MAX-ACCESS   read-only
    STATUS       current
    DESCRIPTION
        "Cisco UCS equipment:Fex:fsmPrev managed object property"
    ::= { cucsEquipmentFexEntry 9 }

cucsEquipmentFexFsmProgr OBJECT-TYPE
    SYNTAX       Gauge32
    MAX-ACCESS   read-only
    STATUS       current
    DESCRIPTION
        "Cisco UCS equipment:Fex:fsmProgr managed object property"
    ::= { cucsEquipmentFexEntry 10 }

cucsEquipmentFexFsmRmtInvErrCode OBJECT-TYPE
    SYNTAX       Gauge32
    MAX-ACCESS   read-only
    STATUS       current
    DESCRIPTION
        "Cisco UCS equipment:Fex:fsmRmtInvErrCode managed object property"
    ::= { cucsEquipmentFexEntry 11 }

cucsEquipmentFexFsmRmtInvErrDescr OBJECT-TYPE
    SYNTAX       SnmpAdminString
    MAX-ACCESS   read-only
    STATUS       current
    DESCRIPTION
        "Cisco UCS equipment:Fex:fsmRmtInvErrDescr managed
        object property"
    ::= { cucsEquipmentFexEntry 12 }

cucsEquipmentFexFsmRmtInvRslt OBJECT-TYPE
    SYNTAX       CucsConditionRemoteInvRslt
    MAX-ACCESS   read-only
    STATUS       current
    DESCRIPTION
        "Cisco UCS equipment:Fex:fsmRmtInvRslt managed object property"
    ::= { cucsEquipmentFexEntry 13 }

cucsEquipmentFexFsmStageDescr OBJECT-TYPE
    SYNTAX       SnmpAdminString
    MAX-ACCESS   read-only
    STATUS       current
    DESCRIPTION
        "Cisco UCS equipment:Fex:fsmStageDescr managed object property"
    ::= { cucsEquipmentFexEntry 14 }

cucsEquipmentFexFsmStamp OBJECT-TYPE
    SYNTAX       DateAndTime
    MAX-ACCESS   read-only
    STATUS       current
    DESCRIPTION
        "Cisco UCS equipment:Fex:fsmStamp managed object property"
    ::= { cucsEquipmentFexEntry 15 }

cucsEquipmentFexFsmStatus OBJECT-TYPE
    SYNTAX       SnmpAdminString
    MAX-ACCESS   read-only
    STATUS       current
    DESCRIPTION
        "Cisco UCS equipment:Fex:fsmStatus managed object property"
    ::= { cucsEquipmentFexEntry 16 }

cucsEquipmentFexFsmTry OBJECT-TYPE
    SYNTAX       Gauge32
    MAX-ACCESS   read-only
    STATUS       current
    DESCRIPTION
        "Cisco UCS equipment:Fex:fsmTry managed object property"
    ::= { cucsEquipmentFexEntry 17 }

cucsEquipmentFexId OBJECT-TYPE
    SYNTAX       CucsEquipmentFexId
    MAX-ACCESS   read-only
    STATUS       current
    DESCRIPTION
        "Cisco UCS equipment:Fex:id managed object property"
    ::= { cucsEquipmentFexEntry 18 }

cucsEquipmentFexModel OBJECT-TYPE
    SYNTAX       SnmpAdminString
    MAX-ACCESS   read-only
    STATUS       current
    DESCRIPTION
        "Cisco UCS equipment:Fex:model managed object property"
    ::= { cucsEquipmentFexEntry 19 }

cucsEquipmentFexOperQualifier OBJECT-TYPE
    SYNTAX       CucsEquipmentChassisIssues
    MAX-ACCESS   read-only
    STATUS       current
    DESCRIPTION
        "Cisco UCS equipment:Fex:operQualifier managed object property"
    ::= { cucsEquipmentFexEntry 20 }

cucsEquipmentFexOperState OBJECT-TYPE
    SYNTAX       CucsEquipmentOperability
    MAX-ACCESS   read-only
    STATUS       current
    DESCRIPTION
        "Cisco UCS equipment:Fex:operState managed object property"
    ::= { cucsEquipmentFexEntry 21 }

cucsEquipmentFexOperability OBJECT-TYPE
    SYNTAX       CucsEquipmentOperability
    MAX-ACCESS   read-only
    STATUS       current
    DESCRIPTION
        "Cisco UCS equipment:Fex:operability managed object property"
    ::= { cucsEquipmentFexEntry 22 }

cucsEquipmentFexPower OBJECT-TYPE
    SYNTAX       CucsEquipmentPowerState
    MAX-ACCESS   read-only
    STATUS       current
    DESCRIPTION
        "Cisco UCS equipment:Fex:power managed object property"
    ::= { cucsEquipmentFexEntry 23 }

cucsEquipmentFexPresence OBJECT-TYPE
    SYNTAX       CucsEquipmentPresence
    MAX-ACCESS   read-only
    STATUS       current
    DESCRIPTION
        "Cisco UCS equipment:Fex:presence managed object property"
    ::= { cucsEquipmentFexEntry 24 }

cucsEquipmentFexRevision OBJECT-TYPE
    SYNTAX       SnmpAdminString
    MAX-ACCESS   read-only
    STATUS       current
    DESCRIPTION
        "Cisco UCS equipment:Fex:revision managed object property"
    ::= { cucsEquipmentFexEntry 25 }

cucsEquipmentFexSerial OBJECT-TYPE
    SYNTAX       SnmpAdminString
    MAX-ACCESS   read-only
    STATUS       current
    DESCRIPTION
        "Cisco UCS equipment:Fex:serial managed object property"
    ::= { cucsEquipmentFexEntry 26 }

cucsEquipmentFexThermal OBJECT-TYPE
    SYNTAX       CucsEquipmentSensorThresholdStatus
    MAX-ACCESS   read-only
    STATUS       current
    DESCRIPTION
        "Cisco UCS equipment:Fex:thermal managed object property"
    ::= { cucsEquipmentFexEntry 27 }

cucsEquipmentFexUsrLbl OBJECT-TYPE
    SYNTAX       SnmpAdminString
    MAX-ACCESS   read-only
    STATUS       current
    DESCRIPTION
        "Cisco UCS equipment:Fex:usrLbl managed object property"
    ::= { cucsEquipmentFexEntry 28 }

cucsEquipmentFexVendor OBJECT-TYPE
    SYNTAX       SnmpAdminString
    MAX-ACCESS   read-only
    STATUS       current
    DESCRIPTION
        "Cisco UCS equipment:Fex:vendor managed object property"
    ::= { cucsEquipmentFexEntry 29 }

cucsEquipmentFexVoltage OBJECT-TYPE
    SYNTAX       CucsEquipmentSensorThresholdStatus
    MAX-ACCESS   read-only
    STATUS       current
    DESCRIPTION
        "Cisco UCS equipment:Fex:voltage managed object property"
    ::= { cucsEquipmentFexEntry 30 }

cucsEquipmentFexSwitchId OBJECT-TYPE
    SYNTAX       CucsNetworkSwitchId
    MAX-ACCESS   read-only
    STATUS       current
    DESCRIPTION
        "Cisco UCS equipment:Fex:switchId managed object property"
    ::= { cucsEquipmentFexEntry 31 }

cucsEquipmentFexLicGP OBJECT-TYPE
    SYNTAX       Unsigned64
    MAX-ACCESS   read-only
    STATUS       current
    DESCRIPTION
        "Cisco UCS equipment:Fex:licGP managed object property"
    ::= { cucsEquipmentFexEntry 32 }

cucsEquipmentFexLicState OBJECT-TYPE
    SYNTAX       CucsLicenseState
    MAX-ACCESS   read-only
    STATUS       current
    DESCRIPTION
        "Cisco UCS equipment:Fex:licState managed object property"
    ::= { cucsEquipmentFexEntry 33 }

cucsEquipmentFexOperQualifierReason OBJECT-TYPE
    SYNTAX       SnmpAdminString
    MAX-ACCESS   read-only
    STATUS       current
    DESCRIPTION
        "Cisco UCS equipment:Fex:operQualifierReason managed
        object property"
    ::= { cucsEquipmentFexEntry 34 }

cucsEquipmentFexCapProviderTable OBJECT-TYPE
    SYNTAX           SEQUENCE OF CucsEquipmentFexCapProviderEntry
    MAX-ACCESS       not-accessible
    STATUS           current
    DESCRIPTION
        "Cisco UCS equipment:FexCapProvider managed object table"
    ::= { cucsEquipmentObjects 20 }

cucsEquipmentFexCapProviderEntry OBJECT-TYPE
    SYNTAX           CucsEquipmentFexCapProviderEntry
    MAX-ACCESS       not-accessible
    STATUS           current
    DESCRIPTION
        "Entry for the cucsEquipmentFexCapProviderTable table."
    INDEX { cucsEquipmentFexCapProviderInstanceId }
    ::= { cucsEquipmentFexCapProviderTable 1 }

CucsEquipmentFexCapProviderEntry ::= SEQUENCE {
    cucsEquipmentFexCapProviderInstanceId                            CucsManagedObjectId,
    cucsEquipmentFexCapProviderDn                                    CucsManagedObjectDn,
    cucsEquipmentFexCapProviderRn                                    SnmpAdminString,
    cucsEquipmentFexCapProviderDeprecated                            TruthValue,
    cucsEquipmentFexCapProviderGencount                              Gauge32,
    cucsEquipmentFexCapProviderMgmtPlaneVer                          SnmpAdminString,
    cucsEquipmentFexCapProviderModel                                 SnmpAdminString,
    cucsEquipmentFexCapProviderRevision                              SnmpAdminString,
    cucsEquipmentFexCapProviderVendor                                SnmpAdminString,
    cucsEquipmentFexCapProviderPromCardType                          Gauge32,
    cucsEquipmentFexCapProviderDeleted                               TruthValue,
    cucsEquipmentFexCapProviderRole                                  CucsEquipmentFexCapProviderRole,
    cucsEquipmentFexCapProviderElementLoadFailures                   Gauge32,
    cucsEquipmentFexCapProviderElementsLoaded                        Gauge32,
    cucsEquipmentFexCapProviderLoadErrors                            Gauge32,
    cucsEquipmentFexCapProviderLoadWarnings                          Gauge32
}

cucsEquipmentFexCapProviderInstanceId OBJECT-TYPE
    SYNTAX       CucsManagedObjectId
    MAX-ACCESS   not-accessible
    STATUS       current
    DESCRIPTION
        "Instance identifier of the managed object."
    ::= { cucsEquipmentFexCapProviderEntry 1 }

cucsEquipmentFexCapProviderDn OBJECT-TYPE
    SYNTAX       CucsManagedObjectDn
    MAX-ACCESS   read-only
    STATUS       current
    DESCRIPTION
        "Cisco UCS equipment:FexCapProvider:dn managed object property"
    ::= { cucsEquipmentFexCapProviderEntry 2 }

cucsEquipmentFexCapProviderRn OBJECT-TYPE
    SYNTAX       SnmpAdminString
    MAX-ACCESS   read-only
    STATUS       current
    DESCRIPTION
        "Cisco UCS equipment:FexCapProvider:rn managed object property"
    ::= { cucsEquipmentFexCapProviderEntry 3 }

cucsEquipmentFexCapProviderDeprecated OBJECT-TYPE
    SYNTAX       TruthValue
    MAX-ACCESS   read-only
    STATUS       current
    DESCRIPTION
        "Cisco UCS equipment:FexCapProvider:deprecated
        managed object property"
    ::= { cucsEquipmentFexCapProviderEntry 4 }

cucsEquipmentFexCapProviderGencount OBJECT-TYPE
    SYNTAX       Gauge32
    MAX-ACCESS   read-only
    STATUS       current
    DESCRIPTION
        "Cisco UCS equipment:FexCapProvider:gencount managed
        object property"
    ::= { cucsEquipmentFexCapProviderEntry 5 }

cucsEquipmentFexCapProviderMgmtPlaneVer OBJECT-TYPE
    SYNTAX       SnmpAdminString
    MAX-ACCESS   read-only
    STATUS       current
    DESCRIPTION
        "Cisco UCS equipment:FexCapProvider:mgmtPlaneVer
        managed object property"
    ::= { cucsEquipmentFexCapProviderEntry 6 }

cucsEquipmentFexCapProviderModel OBJECT-TYPE
    SYNTAX       SnmpAdminString
    MAX-ACCESS   read-only
    STATUS       current
    DESCRIPTION
        "Cisco UCS equipment:FexCapProvider:model managed object property"
    ::= { cucsEquipmentFexCapProviderEntry 7 }

cucsEquipmentFexCapProviderRevision OBJECT-TYPE
    SYNTAX       SnmpAdminString
    MAX-ACCESS   read-only
    STATUS       current
    DESCRIPTION
        "Cisco UCS equipment:FexCapProvider:revision managed
        object property"
    ::= { cucsEquipmentFexCapProviderEntry 8 }

cucsEquipmentFexCapProviderVendor OBJECT-TYPE
    SYNTAX       SnmpAdminString
    MAX-ACCESS   read-only
    STATUS       current
    DESCRIPTION
        "Cisco UCS equipment:FexCapProvider:vendor managed
        object property"
    ::= { cucsEquipmentFexCapProviderEntry 9 }

cucsEquipmentFexCapProviderPromCardType OBJECT-TYPE
    SYNTAX       Gauge32
    MAX-ACCESS   read-only
    STATUS       current
    DESCRIPTION
        "Cisco UCS equipment:FexCapProvider:promCardType
        managed object property"
    ::= { cucsEquipmentFexCapProviderEntry 10 }

cucsEquipmentFexCapProviderDeleted OBJECT-TYPE
    SYNTAX       TruthValue
    MAX-ACCESS   read-only
    STATUS       current
    DESCRIPTION
        "Cisco UCS equipment:FexCapProvider:deleted managed
        object property"
    ::= { cucsEquipmentFexCapProviderEntry 11 }

cucsEquipmentFexCapProviderRole OBJECT-TYPE
    SYNTAX       CucsEquipmentFexCapProviderRole
    MAX-ACCESS   read-only
    STATUS       current
    DESCRIPTION
        "Cisco UCS equipment:FexCapProvider:role managed object property"
    ::= { cucsEquipmentFexCapProviderEntry 12 }

cucsEquipmentFexCapProviderElementLoadFailures OBJECT-TYPE
    SYNTAX       Gauge32
    MAX-ACCESS   read-only
    STATUS       current
    DESCRIPTION
        "Cisco UCS equipment:FexCapProvider:elementLoadFailures
        managed object property"
    ::= { cucsEquipmentFexCapProviderEntry 13 }

cucsEquipmentFexCapProviderElementsLoaded OBJECT-TYPE
    SYNTAX       Gauge32
    MAX-ACCESS   read-only
    STATUS       current
    DESCRIPTION
        "Cisco UCS equipment:FexCapProvider:elementsLoaded
        managed object property"
    ::= { cucsEquipmentFexCapProviderEntry 14 }

cucsEquipmentFexCapProviderLoadErrors OBJECT-TYPE
    SYNTAX       Gauge32
    MAX-ACCESS   read-only
    STATUS       current
    DESCRIPTION
        "Cisco UCS equipment:FexCapProvider:loadErrors
        managed object property"
    ::= { cucsEquipmentFexCapProviderEntry 15 }

cucsEquipmentFexCapProviderLoadWarnings OBJECT-TYPE
    SYNTAX       Gauge32
    MAX-ACCESS   read-only
    STATUS       current
    DESCRIPTION
        "Cisco UCS equipment:FexCapProvider:loadWarnings
        managed object property"
    ::= { cucsEquipmentFexCapProviderEntry 16 }

cucsEquipmentFexEnvStatsTable OBJECT-TYPE
    SYNTAX           SEQUENCE OF CucsEquipmentFexEnvStatsEntry
    MAX-ACCESS       not-accessible
    STATUS           current
    DESCRIPTION
        "Cisco UCS equipment:FexEnvStats managed object table"
    ::= { cucsEquipmentObjects 21 }

cucsEquipmentFexEnvStatsEntry OBJECT-TYPE
    SYNTAX           CucsEquipmentFexEnvStatsEntry
    MAX-ACCESS       not-accessible
    STATUS           current
    DESCRIPTION
        "Entry for the cucsEquipmentFexEnvStatsTable table."
    INDEX { cucsEquipmentFexEnvStatsInstanceId }
    ::= { cucsEquipmentFexEnvStatsTable 1 }

CucsEquipmentFexEnvStatsEntry ::= SEQUENCE {
    cucsEquipmentFexEnvStatsInstanceId                               CucsManagedObjectId,
    cucsEquipmentFexEnvStatsDn                                       CucsManagedObjectDn,
    cucsEquipmentFexEnvStatsRn                                       SnmpAdminString,
    cucsEquipmentFexEnvStatsDie1                                     INTEGER,
    cucsEquipmentFexEnvStatsDie1Avg                                  INTEGER,
    cucsEquipmentFexEnvStatsDie1Max                                  INTEGER,
    cucsEquipmentFexEnvStatsDie1Min                                  INTEGER,
    cucsEquipmentFexEnvStatsInlet                                    INTEGER,
    cucsEquipmentFexEnvStatsInlet1                                   INTEGER,
    cucsEquipmentFexEnvStatsInlet1Avg                                INTEGER,
    cucsEquipmentFexEnvStatsInlet1Max                                INTEGER,
    cucsEquipmentFexEnvStatsInlet1Min                                INTEGER,
    cucsEquipmentFexEnvStatsInletAvg                                 INTEGER,
    cucsEquipmentFexEnvStatsInletMax                                 INTEGER,
    cucsEquipmentFexEnvStatsInletMin                                 INTEGER,
    cucsEquipmentFexEnvStatsInputStatus                              SnmpAdminString,
    cucsEquipmentFexEnvStatsIntervals                                Gauge32,
    cucsEquipmentFexEnvStatsOutlet1                                  INTEGER,
    cucsEquipmentFexEnvStatsOutlet1Avg                               INTEGER,
    cucsEquipmentFexEnvStatsOutlet1Max                               INTEGER,
    cucsEquipmentFexEnvStatsOutlet1Min                               INTEGER,
    cucsEquipmentFexEnvStatsOutlet2                                  INTEGER,
    cucsEquipmentFexEnvStatsOutlet2Avg                               INTEGER,
    cucsEquipmentFexEnvStatsOutlet2Max                               INTEGER,
    cucsEquipmentFexEnvStatsOutlet2Min                               INTEGER,
    cucsEquipmentFexEnvStatsSuspect                                  TruthValue,
    cucsEquipmentFexEnvStatsThresholded                              CucsEquipmentFexEnvStatsThresholded,
    cucsEquipmentFexEnvStatsTimeCollected                            DateAndTime,
    cucsEquipmentFexEnvStatsUpdate                                   Gauge32
}

cucsEquipmentFexEnvStatsInstanceId OBJECT-TYPE
    SYNTAX       CucsManagedObjectId
    MAX-ACCESS   not-accessible
    STATUS       current
    DESCRIPTION
        "Instance identifier of the managed object."
    ::= { cucsEquipmentFexEnvStatsEntry 1 }

cucsEquipmentFexEnvStatsDn OBJECT-TYPE
    SYNTAX       CucsManagedObjectDn
    MAX-ACCESS   read-only
    STATUS       current
    DESCRIPTION
        "Cisco UCS equipment:FexEnvStats:dn managed object property"
    ::= { cucsEquipmentFexEnvStatsEntry 2 }

cucsEquipmentFexEnvStatsRn OBJECT-TYPE
    SYNTAX       SnmpAdminString
    MAX-ACCESS   read-only
    STATUS       current
    DESCRIPTION
        "Cisco UCS equipment:FexEnvStats:rn managed object property"
    ::= { cucsEquipmentFexEnvStatsEntry 3 }

cucsEquipmentFexEnvStatsDie1 OBJECT-TYPE
    SYNTAX       INTEGER
    MAX-ACCESS   read-only
    STATUS       current
    DESCRIPTION
        "Cisco UCS equipment:FexEnvStats:die1 managed object property"
    ::= { cucsEquipmentFexEnvStatsEntry 4 }

cucsEquipmentFexEnvStatsDie1Avg OBJECT-TYPE
    SYNTAX       INTEGER
    MAX-ACCESS   read-only
    STATUS       current
    DESCRIPTION
        "Cisco UCS equipment:FexEnvStats:die1Avg managed object property"
    ::= { cucsEquipmentFexEnvStatsEntry 5 }

cucsEquipmentFexEnvStatsDie1Max OBJECT-TYPE
    SYNTAX       INTEGER
    MAX-ACCESS   read-only
    STATUS       current
    DESCRIPTION
        "Cisco UCS equipment:FexEnvStats:die1Max managed object property"
    ::= { cucsEquipmentFexEnvStatsEntry 6 }

cucsEquipmentFexEnvStatsDie1Min OBJECT-TYPE
    SYNTAX       INTEGER
    MAX-ACCESS   read-only
    STATUS       current
    DESCRIPTION
        "Cisco UCS equipment:FexEnvStats:die1Min managed object property"
    ::= { cucsEquipmentFexEnvStatsEntry 7 }

cucsEquipmentFexEnvStatsInlet OBJECT-TYPE
    SYNTAX       INTEGER
    MAX-ACCESS   read-only
    STATUS       current
    DESCRIPTION
        "Cisco UCS equipment:FexEnvStats:inlet managed object property"
    ::= { cucsEquipmentFexEnvStatsEntry 8 }

cucsEquipmentFexEnvStatsInlet1 OBJECT-TYPE
    SYNTAX       INTEGER
    MAX-ACCESS   read-only
    STATUS       current
    DESCRIPTION
        "Cisco UCS equipment:FexEnvStats:inlet1 managed object property"
    ::= { cucsEquipmentFexEnvStatsEntry 9 }

cucsEquipmentFexEnvStatsInlet1Avg OBJECT-TYPE
    SYNTAX       INTEGER
    MAX-ACCESS   read-only
    STATUS       current
    DESCRIPTION
        "Cisco UCS equipment:FexEnvStats:inlet1Avg managed
        object property"
    ::= { cucsEquipmentFexEnvStatsEntry 10 }

cucsEquipmentFexEnvStatsInlet1Max OBJECT-TYPE
    SYNTAX       INTEGER
    MAX-ACCESS   read-only
    STATUS       current
    DESCRIPTION
        "Cisco UCS equipment:FexEnvStats:inlet1Max managed
        object property"
    ::= { cucsEquipmentFexEnvStatsEntry 11 }

cucsEquipmentFexEnvStatsInlet1Min OBJECT-TYPE
    SYNTAX       INTEGER
    MAX-ACCESS   read-only
    STATUS       current
    DESCRIPTION
        "Cisco UCS equipment:FexEnvStats:inlet1Min managed
        object property"
    ::= { cucsEquipmentFexEnvStatsEntry 12 }

cucsEquipmentFexEnvStatsInletAvg OBJECT-TYPE
    SYNTAX       INTEGER
    MAX-ACCESS   read-only
    STATUS       current
    DESCRIPTION
        "Cisco UCS equipment:FexEnvStats:inletAvg managed object property"
    ::= { cucsEquipmentFexEnvStatsEntry 13 }

cucsEquipmentFexEnvStatsInletMax OBJECT-TYPE
    SYNTAX       INTEGER
    MAX-ACCESS   read-only
    STATUS       current
    DESCRIPTION
        "Cisco UCS equipment:FexEnvStats:inletMax managed object property"
    ::= { cucsEquipmentFexEnvStatsEntry 14 }

cucsEquipmentFexEnvStatsInletMin OBJECT-TYPE
    SYNTAX       INTEGER
    MAX-ACCESS   read-only
    STATUS       current
    DESCRIPTION
        "Cisco UCS equipment:FexEnvStats:inletMin managed object property"
    ::= { cucsEquipmentFexEnvStatsEntry 15 }

cucsEquipmentFexEnvStatsInputStatus OBJECT-TYPE
    SYNTAX       SnmpAdminString
    MAX-ACCESS   read-only
    STATUS       current
    DESCRIPTION
        "Cisco UCS equipment:FexEnvStats:inputStatus managed
        object property"
    ::= { cucsEquipmentFexEnvStatsEntry 16 }

cucsEquipmentFexEnvStatsIntervals OBJECT-TYPE
    SYNTAX       Gauge32
    MAX-ACCESS   read-only
    STATUS       current
    DESCRIPTION
        "Cisco UCS equipment:FexEnvStats:intervals managed
        object property"
    ::= { cucsEquipmentFexEnvStatsEntry 17 }

cucsEquipmentFexEnvStatsOutlet1 OBJECT-TYPE
    SYNTAX       INTEGER
    MAX-ACCESS   read-only
    STATUS       current
    DESCRIPTION
        "Cisco UCS equipment:FexEnvStats:outlet1 managed object property"
    ::= { cucsEquipmentFexEnvStatsEntry 18 }

cucsEquipmentFexEnvStatsOutlet1Avg OBJECT-TYPE
    SYNTAX       INTEGER
    MAX-ACCESS   read-only
    STATUS       current
    DESCRIPTION
        "Cisco UCS equipment:FexEnvStats:outlet1Avg managed
        object property"
    ::= { cucsEquipmentFexEnvStatsEntry 19 }

cucsEquipmentFexEnvStatsOutlet1Max OBJECT-TYPE
    SYNTAX       INTEGER
    MAX-ACCESS   read-only
    STATUS       current
    DESCRIPTION
        "Cisco UCS equipment:FexEnvStats:outlet1Max managed
        object property"
    ::= { cucsEquipmentFexEnvStatsEntry 20 }

cucsEquipmentFexEnvStatsOutlet1Min OBJECT-TYPE
    SYNTAX       INTEGER
    MAX-ACCESS   read-only
    STATUS       current
    DESCRIPTION
        "Cisco UCS equipment:FexEnvStats:outlet1Min managed
        object property"
    ::= { cucsEquipmentFexEnvStatsEntry 21 }

cucsEquipmentFexEnvStatsOutlet2 OBJECT-TYPE
    SYNTAX       INTEGER
    MAX-ACCESS   read-only
    STATUS       current
    DESCRIPTION
        "Cisco UCS equipment:FexEnvStats:outlet2 managed object property"
    ::= { cucsEquipmentFexEnvStatsEntry 22 }

cucsEquipmentFexEnvStatsOutlet2Avg OBJECT-TYPE
    SYNTAX       INTEGER
    MAX-ACCESS   read-only
    STATUS       current
    DESCRIPTION
        "Cisco UCS equipment:FexEnvStats:outlet2Avg managed
        object property"
    ::= { cucsEquipmentFexEnvStatsEntry 23 }

cucsEquipmentFexEnvStatsOutlet2Max OBJECT-TYPE
    SYNTAX       INTEGER
    MAX-ACCESS   read-only
    STATUS       current
    DESCRIPTION
        "Cisco UCS equipment:FexEnvStats:outlet2Max managed
        object property"
    ::= { cucsEquipmentFexEnvStatsEntry 24 }

cucsEquipmentFexEnvStatsOutlet2Min OBJECT-TYPE
    SYNTAX       INTEGER
    MAX-ACCESS   read-only
    STATUS       current
    DESCRIPTION
        "Cisco UCS equipment:FexEnvStats:outlet2Min managed
        object property"
    ::= { cucsEquipmentFexEnvStatsEntry 25 }

cucsEquipmentFexEnvStatsSuspect OBJECT-TYPE
    SYNTAX       TruthValue
    MAX-ACCESS   read-only
    STATUS       current
    DESCRIPTION
        "Cisco UCS equipment:FexEnvStats:suspect managed object property"
    ::= { cucsEquipmentFexEnvStatsEntry 26 }

cucsEquipmentFexEnvStatsThresholded OBJECT-TYPE
    SYNTAX       CucsEquipmentFexEnvStatsThresholded
    MAX-ACCESS   read-only
    STATUS       current
    DESCRIPTION
        "Cisco UCS equipment:FexEnvStats:thresholded managed
        object property"
    ::= { cucsEquipmentFexEnvStatsEntry 27 }

cucsEquipmentFexEnvStatsTimeCollected OBJECT-TYPE
    SYNTAX       DateAndTime
    MAX-ACCESS   read-only
    STATUS       current
    DESCRIPTION
        "Cisco UCS equipment:FexEnvStats:timeCollected
        managed object property"
    ::= { cucsEquipmentFexEnvStatsEntry 28 }

cucsEquipmentFexEnvStatsUpdate OBJECT-TYPE
    SYNTAX       Gauge32
    MAX-ACCESS   read-only
    STATUS       current
    DESCRIPTION
        "Cisco UCS equipment:FexEnvStats:update managed object property"
    ::= { cucsEquipmentFexEnvStatsEntry 29 }

cucsEquipmentFexEnvStatsHistTable OBJECT-TYPE
    SYNTAX           SEQUENCE OF CucsEquipmentFexEnvStatsHistEntry
    MAX-ACCESS       not-accessible
    STATUS           current
    DESCRIPTION
        "Cisco UCS equipment:FexEnvStatsHist managed object table"
    ::= { cucsEquipmentObjects 22 }

cucsEquipmentFexEnvStatsHistEntry OBJECT-TYPE
    SYNTAX           CucsEquipmentFexEnvStatsHistEntry
    MAX-ACCESS       not-accessible
    STATUS           current
    DESCRIPTION
        "Entry for the cucsEquipmentFexEnvStatsHistTable table."
    INDEX { cucsEquipmentFexEnvStatsHistInstanceId }
    ::= { cucsEquipmentFexEnvStatsHistTable 1 }

CucsEquipmentFexEnvStatsHistEntry ::= SEQUENCE {
    cucsEquipmentFexEnvStatsHistInstanceId                           CucsManagedObjectId,
    cucsEquipmentFexEnvStatsHistDn                                   CucsManagedObjectDn,
    cucsEquipmentFexEnvStatsHistRn                                   SnmpAdminString,
    cucsEquipmentFexEnvStatsHistDie1                                 INTEGER,
    cucsEquipmentFexEnvStatsHistDie1Avg                              INTEGER,
    cucsEquipmentFexEnvStatsHistDie1Max                              INTEGER,
    cucsEquipmentFexEnvStatsHistDie1Min                              INTEGER,
    cucsEquipmentFexEnvStatsHistId                                   Unsigned64,
    cucsEquipmentFexEnvStatsHistInlet                                INTEGER,
    cucsEquipmentFexEnvStatsHistInlet1                               INTEGER,
    cucsEquipmentFexEnvStatsHistInlet1Avg                            INTEGER,
    cucsEquipmentFexEnvStatsHistInlet1Max                            INTEGER,
    cucsEquipmentFexEnvStatsHistInlet1Min                            INTEGER,
    cucsEquipmentFexEnvStatsHistInletAvg                             INTEGER,
    cucsEquipmentFexEnvStatsHistInletMax                             INTEGER,
    cucsEquipmentFexEnvStatsHistInletMin                             INTEGER,
    cucsEquipmentFexEnvStatsHistMostRecent                           TruthValue,
    cucsEquipmentFexEnvStatsHistOutlet1                              INTEGER,
    cucsEquipmentFexEnvStatsHistOutlet1Avg                           INTEGER,
    cucsEquipmentFexEnvStatsHistOutlet1Max                           INTEGER,
    cucsEquipmentFexEnvStatsHistOutlet1Min                           INTEGER,
    cucsEquipmentFexEnvStatsHistOutlet2                              INTEGER,
    cucsEquipmentFexEnvStatsHistOutlet2Avg                           INTEGER,
    cucsEquipmentFexEnvStatsHistOutlet2Max                           INTEGER,
    cucsEquipmentFexEnvStatsHistOutlet2Min                           INTEGER,
    cucsEquipmentFexEnvStatsHistSuspect                              TruthValue,
    cucsEquipmentFexEnvStatsHistThresholded                          CucsEquipmentFexEnvStatsHistThresholded,
    cucsEquipmentFexEnvStatsHistTimeCollected                        DateAndTime
}

cucsEquipmentFexEnvStatsHistInstanceId OBJECT-TYPE
    SYNTAX       CucsManagedObjectId
    MAX-ACCESS   not-accessible
    STATUS       current
    DESCRIPTION
        "Instance identifier of the managed object."
    ::= { cucsEquipmentFexEnvStatsHistEntry 1 }

cucsEquipmentFexEnvStatsHistDn OBJECT-TYPE
    SYNTAX       CucsManagedObjectDn
    MAX-ACCESS   read-only
    STATUS       current
    DESCRIPTION
        "Cisco UCS equipment:FexEnvStatsHist:dn managed object property"
    ::= { cucsEquipmentFexEnvStatsHistEntry 2 }

cucsEquipmentFexEnvStatsHistRn OBJECT-TYPE
    SYNTAX       SnmpAdminString
    MAX-ACCESS   read-only
    STATUS       current
    DESCRIPTION
        "Cisco UCS equipment:FexEnvStatsHist:rn managed object property"
    ::= { cucsEquipmentFexEnvStatsHistEntry 3 }

cucsEquipmentFexEnvStatsHistDie1 OBJECT-TYPE
    SYNTAX       INTEGER
    MAX-ACCESS   read-only
    STATUS       current
    DESCRIPTION
        "Cisco UCS equipment:FexEnvStatsHist:die1 managed object property"
    ::= { cucsEquipmentFexEnvStatsHistEntry 4 }

cucsEquipmentFexEnvStatsHistDie1Avg OBJECT-TYPE
    SYNTAX       INTEGER
    MAX-ACCESS   read-only
    STATUS       current
    DESCRIPTION
        "Cisco UCS equipment:FexEnvStatsHist:die1Avg managed
        object property"
    ::= { cucsEquipmentFexEnvStatsHistEntry 5 }

cucsEquipmentFexEnvStatsHistDie1Max OBJECT-TYPE
    SYNTAX       INTEGER
    MAX-ACCESS   read-only
    STATUS       current
    DESCRIPTION
        "Cisco UCS equipment:FexEnvStatsHist:die1Max managed
        object property"
    ::= { cucsEquipmentFexEnvStatsHistEntry 6 }

cucsEquipmentFexEnvStatsHistDie1Min OBJECT-TYPE
    SYNTAX       INTEGER
    MAX-ACCESS   read-only
    STATUS       current
    DESCRIPTION
        "Cisco UCS equipment:FexEnvStatsHist:die1Min managed
        object property"
    ::= { cucsEquipmentFexEnvStatsHistEntry 7 }

cucsEquipmentFexEnvStatsHistId OBJECT-TYPE
    SYNTAX       Unsigned64
    MAX-ACCESS   read-only
    STATUS       current
    DESCRIPTION
        "Cisco UCS equipment:FexEnvStatsHist:id managed object property"
    ::= { cucsEquipmentFexEnvStatsHistEntry 8 }

cucsEquipmentFexEnvStatsHistInlet OBJECT-TYPE
    SYNTAX       INTEGER
    MAX-ACCESS   read-only
    STATUS       current
    DESCRIPTION
        "Cisco UCS equipment:FexEnvStatsHist:inlet managed
        object property"
    ::= { cucsEquipmentFexEnvStatsHistEntry 9 }

cucsEquipmentFexEnvStatsHistInlet1 OBJECT-TYPE
    SYNTAX       INTEGER
    MAX-ACCESS   read-only
    STATUS       current
    DESCRIPTION
        "Cisco UCS equipment:FexEnvStatsHist:inlet1 managed
        object property"
    ::= { cucsEquipmentFexEnvStatsHistEntry 10 }

cucsEquipmentFexEnvStatsHistInlet1Avg OBJECT-TYPE
    SYNTAX       INTEGER
    MAX-ACCESS   read-only
    STATUS       current
    DESCRIPTION
        "Cisco UCS equipment:FexEnvStatsHist:inlet1Avg
        managed object property"
    ::= { cucsEquipmentFexEnvStatsHistEntry 11 }

cucsEquipmentFexEnvStatsHistInlet1Max OBJECT-TYPE
    SYNTAX       INTEGER
    MAX-ACCESS   read-only
    STATUS       current
    DESCRIPTION
        "Cisco UCS equipment:FexEnvStatsHist:inlet1Max
        managed object property"
    ::= { cucsEquipmentFexEnvStatsHistEntry 12 }

cucsEquipmentFexEnvStatsHistInlet1Min OBJECT-TYPE
    SYNTAX       INTEGER
    MAX-ACCESS   read-only
    STATUS       current
    DESCRIPTION
        "Cisco UCS equipment:FexEnvStatsHist:inlet1Min
        managed object property"
    ::= { cucsEquipmentFexEnvStatsHistEntry 13 }

cucsEquipmentFexEnvStatsHistInletAvg OBJECT-TYPE
    SYNTAX       INTEGER
    MAX-ACCESS   read-only
    STATUS       current
    DESCRIPTION
        "Cisco UCS equipment:FexEnvStatsHist:inletAvg managed
        object property"
    ::= { cucsEquipmentFexEnvStatsHistEntry 14 }

cucsEquipmentFexEnvStatsHistInletMax OBJECT-TYPE
    SYNTAX       INTEGER
    MAX-ACCESS   read-only
    STATUS       current
    DESCRIPTION
        "Cisco UCS equipment:FexEnvStatsHist:inletMax managed
        object property"
    ::= { cucsEquipmentFexEnvStatsHistEntry 15 }

cucsEquipmentFexEnvStatsHistInletMin OBJECT-TYPE
    SYNTAX       INTEGER
    MAX-ACCESS   read-only
    STATUS       current
    DESCRIPTION
        "Cisco UCS equipment:FexEnvStatsHist:inletMin managed
        object property"
    ::= { cucsEquipmentFexEnvStatsHistEntry 16 }

cucsEquipmentFexEnvStatsHistMostRecent OBJECT-TYPE
    SYNTAX       TruthValue
    MAX-ACCESS   read-only
    STATUS       current
    DESCRIPTION
        "Cisco UCS equipment:FexEnvStatsHist:mostRecent
        managed object property"
    ::= { cucsEquipmentFexEnvStatsHistEntry 17 }

cucsEquipmentFexEnvStatsHistOutlet1 OBJECT-TYPE
    SYNTAX       INTEGER
    MAX-ACCESS   read-only
    STATUS       current
    DESCRIPTION
        "Cisco UCS equipment:FexEnvStatsHist:outlet1 managed
        object property"
    ::= { cucsEquipmentFexEnvStatsHistEntry 18 }

cucsEquipmentFexEnvStatsHistOutlet1Avg OBJECT-TYPE
    SYNTAX       INTEGER
    MAX-ACCESS   read-only
    STATUS       current
    DESCRIPTION
        "Cisco UCS equipment:FexEnvStatsHist:outlet1Avg
        managed object property"
    ::= { cucsEquipmentFexEnvStatsHistEntry 19 }

cucsEquipmentFexEnvStatsHistOutlet1Max OBJECT-TYPE
    SYNTAX       INTEGER
    MAX-ACCESS   read-only
    STATUS       current
    DESCRIPTION
        "Cisco UCS equipment:FexEnvStatsHist:outlet1Max
        managed object property"
    ::= { cucsEquipmentFexEnvStatsHistEntry 20 }

cucsEquipmentFexEnvStatsHistOutlet1Min OBJECT-TYPE
    SYNTAX       INTEGER
    MAX-ACCESS   read-only
    STATUS       current
    DESCRIPTION
        "Cisco UCS equipment:FexEnvStatsHist:outlet1Min
        managed object property"
    ::= { cucsEquipmentFexEnvStatsHistEntry 21 }

cucsEquipmentFexEnvStatsHistOutlet2 OBJECT-TYPE
    SYNTAX       INTEGER
    MAX-ACCESS   read-only
    STATUS       current
    DESCRIPTION
        "Cisco UCS equipment:FexEnvStatsHist:outlet2 managed
        object property"
    ::= { cucsEquipmentFexEnvStatsHistEntry 22 }

cucsEquipmentFexEnvStatsHistOutlet2Avg OBJECT-TYPE
    SYNTAX       INTEGER
    MAX-ACCESS   read-only
    STATUS       current
    DESCRIPTION
        "Cisco UCS equipment:FexEnvStatsHist:outlet2Avg
        managed object property"
    ::= { cucsEquipmentFexEnvStatsHistEntry 23 }

cucsEquipmentFexEnvStatsHistOutlet2Max OBJECT-TYPE
    SYNTAX       INTEGER
    MAX-ACCESS   read-only
    STATUS       current
    DESCRIPTION
        "Cisco UCS equipment:FexEnvStatsHist:outlet2Max
        managed object property"
    ::= { cucsEquipmentFexEnvStatsHistEntry 24 }

cucsEquipmentFexEnvStatsHistOutlet2Min OBJECT-TYPE
    SYNTAX       INTEGER
    MAX-ACCESS   read-only
    STATUS       current
    DESCRIPTION
        "Cisco UCS equipment:FexEnvStatsHist:outlet2Min
        managed object property"
    ::= { cucsEquipmentFexEnvStatsHistEntry 25 }

cucsEquipmentFexEnvStatsHistSuspect OBJECT-TYPE
    SYNTAX       TruthValue
    MAX-ACCESS   read-only
    STATUS       current
    DESCRIPTION
        "Cisco UCS equipment:FexEnvStatsHist:suspect managed
        object property"
    ::= { cucsEquipmentFexEnvStatsHistEntry 26 }

cucsEquipmentFexEnvStatsHistThresholded OBJECT-TYPE
    SYNTAX       CucsEquipmentFexEnvStatsHistThresholded
    MAX-ACCESS   read-only
    STATUS       current
    DESCRIPTION
        "Cisco UCS equipment:FexEnvStatsHist:thresholded
        managed object property"
    ::= { cucsEquipmentFexEnvStatsHistEntry 27 }

cucsEquipmentFexEnvStatsHistTimeCollected OBJECT-TYPE
    SYNTAX       DateAndTime
    MAX-ACCESS   read-only
    STATUS       current
    DESCRIPTION
        "Cisco UCS equipment:FexEnvStatsHist:timeCollected
        managed object property"
    ::= { cucsEquipmentFexEnvStatsHistEntry 28 }

cucsEquipmentFexFsmTable OBJECT-TYPE
    SYNTAX           SEQUENCE OF CucsEquipmentFexFsmEntry
    MAX-ACCESS       not-accessible
    STATUS           current
    DESCRIPTION
        "Cisco UCS equipment:FexFsm managed object table"
    ::= { cucsEquipmentObjects 107 }

cucsEquipmentFexFsmEntry OBJECT-TYPE
    SYNTAX           CucsEquipmentFexFsmEntry
    MAX-ACCESS       not-accessible
    STATUS           current
    DESCRIPTION
        "Entry for the cucsEquipmentFexFsmTable table."
    INDEX { cucsEquipmentFexFsmInstanceId }
    ::= { cucsEquipmentFexFsmTable 1 }

CucsEquipmentFexFsmEntry ::= SEQUENCE {
    cucsEquipmentFexFsmInstanceId                                    CucsManagedObjectId,
    cucsEquipmentFexFsmDn                                            CucsManagedObjectDn,
    cucsEquipmentFexFsmRn                                            SnmpAdminString,
    cucsEquipmentFexFsmCompletionTime                                DateAndTime,
    cucsEquipmentFexFsmCurrentFsm                                    CucsEquipmentFexFsmCurrentFsm,
    cucsEquipmentFexFsmDescr                                         SnmpAdminString,
    cucsEquipmentFexFsmFsmStatus                                     CucsFsmFsmStageStatus,
    cucsEquipmentFexFsmProgress                                      Gauge32,
    cucsEquipmentFexFsmRmtErrCode                                    Gauge32,
    cucsEquipmentFexFsmRmtErrDescr                                   SnmpAdminString,
    cucsEquipmentFexFsmRmtRslt                                       CucsConditionRemoteInvRslt
}

cucsEquipmentFexFsmInstanceId OBJECT-TYPE
    SYNTAX       CucsManagedObjectId
    MAX-ACCESS   not-accessible
    STATUS       current
    DESCRIPTION
        "Instance identifier of the managed object."
    ::= { cucsEquipmentFexFsmEntry 1 }

cucsEquipmentFexFsmDn OBJECT-TYPE
    SYNTAX       CucsManagedObjectDn
    MAX-ACCESS   read-only
    STATUS       current
    DESCRIPTION
        "Cisco UCS equipment:FexFsm:dn managed object property"
    ::= { cucsEquipmentFexFsmEntry 2 }

cucsEquipmentFexFsmRn OBJECT-TYPE
    SYNTAX       SnmpAdminString
    MAX-ACCESS   read-only
    STATUS       current
    DESCRIPTION
        "Cisco UCS equipment:FexFsm:rn managed object property"
    ::= { cucsEquipmentFexFsmEntry 3 }

cucsEquipmentFexFsmCompletionTime OBJECT-TYPE
    SYNTAX       DateAndTime
    MAX-ACCESS   read-only
    STATUS       current
    DESCRIPTION
        "Cisco UCS equipment:FexFsm:completionTime managed
        object property"
    ::= { cucsEquipmentFexFsmEntry 4 }

cucsEquipmentFexFsmCurrentFsm OBJECT-TYPE
    SYNTAX       CucsEquipmentFexFsmCurrentFsm
    MAX-ACCESS   read-only
    STATUS       current
    DESCRIPTION
        "Cisco UCS equipment:FexFsm:currentFsm managed object property"
    ::= { cucsEquipmentFexFsmEntry 5 }

cucsEquipmentFexFsmDescr OBJECT-TYPE
    SYNTAX       SnmpAdminString
    MAX-ACCESS   read-only
    STATUS       current
    DESCRIPTION
        "Cisco UCS equipment:FexFsm:descr managed object property"
    ::= { cucsEquipmentFexFsmEntry 6 }

cucsEquipmentFexFsmFsmStatus OBJECT-TYPE
    SYNTAX       CucsFsmFsmStageStatus
    MAX-ACCESS   read-only
    STATUS       current
    DESCRIPTION
        "Cisco UCS equipment:FexFsm:fsmStatus managed object property"
    ::= { cucsEquipmentFexFsmEntry 7 }

cucsEquipmentFexFsmProgress OBJECT-TYPE
    SYNTAX       Gauge32
    MAX-ACCESS   read-only
    STATUS       current
    DESCRIPTION
        "Cisco UCS equipment:FexFsm:progress managed object property"
    ::= { cucsEquipmentFexFsmEntry 8 }

cucsEquipmentFexFsmRmtErrCode OBJECT-TYPE
    SYNTAX       Gauge32
    MAX-ACCESS   read-only
    STATUS       current
    DESCRIPTION
        "Cisco UCS equipment:FexFsm:rmtErrCode managed object property"
    ::= { cucsEquipmentFexFsmEntry 9 }

cucsEquipmentFexFsmRmtErrDescr OBJECT-TYPE
    SYNTAX       SnmpAdminString
    MAX-ACCESS   read-only
    STATUS       current
    DESCRIPTION
        "Cisco UCS equipment:FexFsm:rmtErrDescr managed object property"
    ::= { cucsEquipmentFexFsmEntry 10 }

cucsEquipmentFexFsmRmtRslt OBJECT-TYPE
    SYNTAX       CucsConditionRemoteInvRslt
    MAX-ACCESS   read-only
    STATUS       current
    DESCRIPTION
        "Cisco UCS equipment:FexFsm:rmtRslt managed object property"
    ::= { cucsEquipmentFexFsmEntry 11 }

cucsEquipmentFexFsmStageTable OBJECT-TYPE
    SYNTAX           SEQUENCE OF CucsEquipmentFexFsmStageEntry
    MAX-ACCESS       not-accessible
    STATUS           current
    DESCRIPTION
        "Cisco UCS equipment:FexFsmStage managed object table"
    ::= { cucsEquipmentObjects 108 }

cucsEquipmentFexFsmStageEntry OBJECT-TYPE
    SYNTAX           CucsEquipmentFexFsmStageEntry
    MAX-ACCESS       not-accessible
    STATUS           current
    DESCRIPTION
        "Entry for the cucsEquipmentFexFsmStageTable table."
    INDEX { cucsEquipmentFexFsmStageInstanceId }
    ::= { cucsEquipmentFexFsmStageTable 1 }

CucsEquipmentFexFsmStageEntry ::= SEQUENCE {
    cucsEquipmentFexFsmStageInstanceId                               CucsManagedObjectId,
    cucsEquipmentFexFsmStageDn                                       CucsManagedObjectDn,
    cucsEquipmentFexFsmStageRn                                       SnmpAdminString,
    cucsEquipmentFexFsmStageDescr                                    SnmpAdminString,
    cucsEquipmentFexFsmStageLastUpdateTime                           DateAndTime,
    cucsEquipmentFexFsmStageName                                     CucsEquipmentFexFsmStageName,
    cucsEquipmentFexFsmStageOrder                                    Gauge32,
    cucsEquipmentFexFsmStageRetry                                    Gauge32,
    cucsEquipmentFexFsmStageStageStatus                              CucsFsmFsmStageStatus
}

cucsEquipmentFexFsmStageInstanceId OBJECT-TYPE
    SYNTAX       CucsManagedObjectId
    MAX-ACCESS   not-accessible
    STATUS       current
    DESCRIPTION
        "Instance identifier of the managed object."
    ::= { cucsEquipmentFexFsmStageEntry 1 }

cucsEquipmentFexFsmStageDn OBJECT-TYPE
    SYNTAX       CucsManagedObjectDn
    MAX-ACCESS   read-only
    STATUS       current
    DESCRIPTION
        "Cisco UCS equipment:FexFsmStage:dn managed object property"
    ::= { cucsEquipmentFexFsmStageEntry 2 }

cucsEquipmentFexFsmStageRn OBJECT-TYPE
    SYNTAX       SnmpAdminString
    MAX-ACCESS   read-only
    STATUS       current
    DESCRIPTION
        "Cisco UCS equipment:FexFsmStage:rn managed object property"
    ::= { cucsEquipmentFexFsmStageEntry 3 }

cucsEquipmentFexFsmStageDescr OBJECT-TYPE
    SYNTAX       SnmpAdminString
    MAX-ACCESS   read-only
    STATUS       current
    DESCRIPTION
        "Cisco UCS equipment:FexFsmStage:descr managed object property"
    ::= { cucsEquipmentFexFsmStageEntry 4 }

cucsEquipmentFexFsmStageLastUpdateTime OBJECT-TYPE
    SYNTAX       DateAndTime
    MAX-ACCESS   read-only
    STATUS       current
    DESCRIPTION
        "Cisco UCS equipment:FexFsmStage:lastUpdateTime
        managed object property"
    ::= { cucsEquipmentFexFsmStageEntry 5 }

cucsEquipmentFexFsmStageName OBJECT-TYPE
    SYNTAX       CucsEquipmentFexFsmStageName
    MAX-ACCESS   read-only
    STATUS       current
    DESCRIPTION
        "Cisco UCS equipment:FexFsmStage:name managed object property"
    ::= { cucsEquipmentFexFsmStageEntry 6 }

cucsEquipmentFexFsmStageOrder OBJECT-TYPE
    SYNTAX       Gauge32
    MAX-ACCESS   read-only
    STATUS       current
    DESCRIPTION
        "Cisco UCS equipment:FexFsmStage:order managed object property"
    ::= { cucsEquipmentFexFsmStageEntry 7 }

cucsEquipmentFexFsmStageRetry OBJECT-TYPE
    SYNTAX       Gauge32
    MAX-ACCESS   read-only
    STATUS       current
    DESCRIPTION
        "Cisco UCS equipment:FexFsmStage:retry managed object property"
    ::= { cucsEquipmentFexFsmStageEntry 8 }

cucsEquipmentFexFsmStageStageStatus OBJECT-TYPE
    SYNTAX       CucsFsmFsmStageStatus
    MAX-ACCESS   read-only
    STATUS       current
    DESCRIPTION
        "Cisco UCS equipment:FexFsmStage:stageStatus managed
        object property"
    ::= { cucsEquipmentFexFsmStageEntry 9 }

cucsEquipmentFexFsmTaskTable OBJECT-TYPE
    SYNTAX           SEQUENCE OF CucsEquipmentFexFsmTaskEntry
    MAX-ACCESS       not-accessible
    STATUS           current
    DESCRIPTION
        "Cisco UCS equipment:FexFsmTask managed object table"
    ::= { cucsEquipmentObjects 23 }

cucsEquipmentFexFsmTaskEntry OBJECT-TYPE
    SYNTAX           CucsEquipmentFexFsmTaskEntry
    MAX-ACCESS       not-accessible
    STATUS           current
    DESCRIPTION
        "Entry for the cucsEquipmentFexFsmTaskTable table."
    INDEX { cucsEquipmentFexFsmTaskInstanceId }
    ::= { cucsEquipmentFexFsmTaskTable 1 }

CucsEquipmentFexFsmTaskEntry ::= SEQUENCE {
    cucsEquipmentFexFsmTaskInstanceId                                CucsManagedObjectId,
    cucsEquipmentFexFsmTaskDn                                        CucsManagedObjectDn,
    cucsEquipmentFexFsmTaskRn                                        SnmpAdminString,
    cucsEquipmentFexFsmTaskCompletion                                CucsFsmCompletion,
    cucsEquipmentFexFsmTaskFlags                                     CucsFsmFlags,
    cucsEquipmentFexFsmTaskItem                                      CucsEquipmentFexFsmTaskItem,
    cucsEquipmentFexFsmTaskSeqId                                     Gauge32
}

cucsEquipmentFexFsmTaskInstanceId OBJECT-TYPE
    SYNTAX       CucsManagedObjectId
    MAX-ACCESS   not-accessible
    STATUS       current
    DESCRIPTION
        "Instance identifier of the managed object."
    ::= { cucsEquipmentFexFsmTaskEntry 1 }

cucsEquipmentFexFsmTaskDn OBJECT-TYPE
    SYNTAX       CucsManagedObjectDn
    MAX-ACCESS   read-only
    STATUS       current
    DESCRIPTION
        "Cisco UCS equipment:FexFsmTask:dn managed object property"
    ::= { cucsEquipmentFexFsmTaskEntry 2 }

cucsEquipmentFexFsmTaskRn OBJECT-TYPE
    SYNTAX       SnmpAdminString
    MAX-ACCESS   read-only
    STATUS       current
    DESCRIPTION
        "Cisco UCS equipment:FexFsmTask:rn managed object property"
    ::= { cucsEquipmentFexFsmTaskEntry 3 }

cucsEquipmentFexFsmTaskCompletion OBJECT-TYPE
    SYNTAX       CucsFsmCompletion
    MAX-ACCESS   read-only
    STATUS       current
    DESCRIPTION
        "Cisco UCS equipment:FexFsmTask:completion managed
        object property"
    ::= { cucsEquipmentFexFsmTaskEntry 4 }

cucsEquipmentFexFsmTaskFlags OBJECT-TYPE
    SYNTAX       CucsFsmFlags
    MAX-ACCESS   read-only
    STATUS       current
    DESCRIPTION
        "Cisco UCS equipment:FexFsmTask:flags managed object property"
    ::= { cucsEquipmentFexFsmTaskEntry 5 }

cucsEquipmentFexFsmTaskItem OBJECT-TYPE
    SYNTAX       CucsEquipmentFexFsmTaskItem
    MAX-ACCESS   read-only
    STATUS       current
    DESCRIPTION
        "Cisco UCS equipment:FexFsmTask:item managed object property"
    ::= { cucsEquipmentFexFsmTaskEntry 6 }

cucsEquipmentFexFsmTaskSeqId OBJECT-TYPE
    SYNTAX       Gauge32
    MAX-ACCESS   read-only
    STATUS       current
    DESCRIPTION
        "Cisco UCS equipment:FexFsmTask:seqId managed object property"
    ::= { cucsEquipmentFexFsmTaskEntry 7 }

cucsEquipmentFexPowerSummaryTable OBJECT-TYPE
    SYNTAX           SEQUENCE OF CucsEquipmentFexPowerSummaryEntry
    MAX-ACCESS       not-accessible
    STATUS           current
    DESCRIPTION
        "Cisco UCS equipment:FexPowerSummary managed object table"
    ::= { cucsEquipmentObjects 24 }

cucsEquipmentFexPowerSummaryEntry OBJECT-TYPE
    SYNTAX           CucsEquipmentFexPowerSummaryEntry
    MAX-ACCESS       not-accessible
    STATUS           current
    DESCRIPTION
        "Entry for the cucsEquipmentFexPowerSummaryTable table."
    INDEX { cucsEquipmentFexPowerSummaryInstanceId }
    ::= { cucsEquipmentFexPowerSummaryTable 1 }

CucsEquipmentFexPowerSummaryEntry ::= SEQUENCE {
    cucsEquipmentFexPowerSummaryInstanceId                           CucsManagedObjectId,
    cucsEquipmentFexPowerSummaryDn                                   CucsManagedObjectDn,
    cucsEquipmentFexPowerSummaryRn                                   SnmpAdminString,
    cucsEquipmentFexPowerSummaryModulePower                          INTEGER,
    cucsEquipmentFexPowerSummaryModulePowerAvg                       INTEGER,
    cucsEquipmentFexPowerSummaryModulePowerMax                       INTEGER,
    cucsEquipmentFexPowerSummaryModulePowerMin                       INTEGER,
    cucsEquipmentFexPowerSummaryAvailablePower                       INTEGER,
    cucsEquipmentFexPowerSummaryAvailablePowerAvg                    INTEGER,
    cucsEquipmentFexPowerSummaryAvailablePowerMax                    INTEGER,
    cucsEquipmentFexPowerSummaryAvailablePowerMin                    INTEGER,
    cucsEquipmentFexPowerSummaryIntervals                            Gauge32,
    cucsEquipmentFexPowerSummaryReservedPower                        INTEGER,
    cucsEquipmentFexPowerSummaryReservedPowerAvg                     INTEGER,
    cucsEquipmentFexPowerSummaryReservedPowerMax                     INTEGER,
    cucsEquipmentFexPowerSummaryReservedPowerMin                     INTEGER,
    cucsEquipmentFexPowerSummarySuspect                              TruthValue,
    cucsEquipmentFexPowerSummaryThresholded                          CucsEquipmentFexPowerSummaryThresholded,
    cucsEquipmentFexPowerSummaryTimeCollected                        DateAndTime,
    cucsEquipmentFexPowerSummaryTotalPower                           INTEGER,
    cucsEquipmentFexPowerSummaryTotalPowerAvg                        INTEGER,
    cucsEquipmentFexPowerSummaryTotalPowerMax                        INTEGER,
    cucsEquipmentFexPowerSummaryTotalPowerMin                        INTEGER,
    cucsEquipmentFexPowerSummaryUpdate                               Gauge32
}

cucsEquipmentFexPowerSummaryInstanceId OBJECT-TYPE
    SYNTAX       CucsManagedObjectId
    MAX-ACCESS   not-accessible
    STATUS       current
    DESCRIPTION
        "Instance identifier of the managed object."
    ::= { cucsEquipmentFexPowerSummaryEntry 1 }

cucsEquipmentFexPowerSummaryDn OBJECT-TYPE
    SYNTAX       CucsManagedObjectDn
    MAX-ACCESS   read-only
    STATUS       current
    DESCRIPTION
        "Cisco UCS equipment:FexPowerSummary:dn managed object property"
    ::= { cucsEquipmentFexPowerSummaryEntry 2 }

cucsEquipmentFexPowerSummaryRn OBJECT-TYPE
    SYNTAX       SnmpAdminString
    MAX-ACCESS   read-only
    STATUS       current
    DESCRIPTION
        "Cisco UCS equipment:FexPowerSummary:rn managed object property"
    ::= { cucsEquipmentFexPowerSummaryEntry 3 }

cucsEquipmentFexPowerSummaryModulePower OBJECT-TYPE
    SYNTAX       INTEGER
    MAX-ACCESS   read-only
    STATUS       current
    DESCRIPTION
        "Cisco UCS equipment:FexPowerSummary:ModulePower
        managed object property"
    ::= { cucsEquipmentFexPowerSummaryEntry 4 }

cucsEquipmentFexPowerSummaryModulePowerAvg OBJECT-TYPE
    SYNTAX       INTEGER
    MAX-ACCESS   read-only
    STATUS       current
    DESCRIPTION
        "Cisco UCS equipment:FexPowerSummary:ModulePowerAvg
        managed object property"
    ::= { cucsEquipmentFexPowerSummaryEntry 5 }

cucsEquipmentFexPowerSummaryModulePowerMax OBJECT-TYPE
    SYNTAX       INTEGER
    MAX-ACCESS   read-only
    STATUS       current
    DESCRIPTION
        "Cisco UCS equipment:FexPowerSummary:ModulePowerMax
        managed object property"
    ::= { cucsEquipmentFexPowerSummaryEntry 6 }

cucsEquipmentFexPowerSummaryModulePowerMin OBJECT-TYPE
    SYNTAX       INTEGER
    MAX-ACCESS   read-only
    STATUS       current
    DESCRIPTION
        "Cisco UCS equipment:FexPowerSummary:ModulePowerMin
        managed object property"
    ::= { cucsEquipmentFexPowerSummaryEntry 7 }

cucsEquipmentFexPowerSummaryAvailablePower OBJECT-TYPE
    SYNTAX       INTEGER
    MAX-ACCESS   read-only
    STATUS       current
    DESCRIPTION
        "Cisco UCS equipment:FexPowerSummary:availablePower
        managed object property"
    ::= { cucsEquipmentFexPowerSummaryEntry 8 }

cucsEquipmentFexPowerSummaryAvailablePowerAvg OBJECT-TYPE
    SYNTAX       INTEGER
    MAX-ACCESS   read-only
    STATUS       current
    DESCRIPTION
        "Cisco UCS equipment:FexPowerSummary:availablePowerAvg
        managed object property"
    ::= { cucsEquipmentFexPowerSummaryEntry 9 }

cucsEquipmentFexPowerSummaryAvailablePowerMax OBJECT-TYPE
    SYNTAX       INTEGER
    MAX-ACCESS   read-only
    STATUS       current
    DESCRIPTION
        "Cisco UCS equipment:FexPowerSummary:availablePowerMax
        managed object property"
    ::= { cucsEquipmentFexPowerSummaryEntry 10 }

cucsEquipmentFexPowerSummaryAvailablePowerMin OBJECT-TYPE
    SYNTAX       INTEGER
    MAX-ACCESS   read-only
    STATUS       current
    DESCRIPTION
        "Cisco UCS equipment:FexPowerSummary:availablePowerMin
        managed object property"
    ::= { cucsEquipmentFexPowerSummaryEntry 11 }

cucsEquipmentFexPowerSummaryIntervals OBJECT-TYPE
    SYNTAX       Gauge32
    MAX-ACCESS   read-only
    STATUS       current
    DESCRIPTION
        "Cisco UCS equipment:FexPowerSummary:intervals
        managed object property"
    ::= { cucsEquipmentFexPowerSummaryEntry 12 }

cucsEquipmentFexPowerSummaryReservedPower OBJECT-TYPE
    SYNTAX       INTEGER
    MAX-ACCESS   read-only
    STATUS       current
    DESCRIPTION
        "Cisco UCS equipment:FexPowerSummary:reservedPower
        managed object property"
    ::= { cucsEquipmentFexPowerSummaryEntry 13 }

cucsEquipmentFexPowerSummaryReservedPowerAvg OBJECT-TYPE
    SYNTAX       INTEGER
    MAX-ACCESS   read-only
    STATUS       current
    DESCRIPTION
        "Cisco UCS equipment:FexPowerSummary:reservedPowerAvg
        managed object property"
    ::= { cucsEquipmentFexPowerSummaryEntry 14 }

cucsEquipmentFexPowerSummaryReservedPowerMax OBJECT-TYPE
    SYNTAX       INTEGER
    MAX-ACCESS   read-only
    STATUS       current
    DESCRIPTION
        "Cisco UCS equipment:FexPowerSummary:reservedPowerMax
        managed object property"
    ::= { cucsEquipmentFexPowerSummaryEntry 15 }

cucsEquipmentFexPowerSummaryReservedPowerMin OBJECT-TYPE
    SYNTAX       INTEGER
    MAX-ACCESS   read-only
    STATUS       current
    DESCRIPTION
        "Cisco UCS equipment:FexPowerSummary:reservedPowerMin
        managed object property"
    ::= { cucsEquipmentFexPowerSummaryEntry 16 }

cucsEquipmentFexPowerSummarySuspect OBJECT-TYPE
    SYNTAX       TruthValue
    MAX-ACCESS   read-only
    STATUS       current
    DESCRIPTION
        "Cisco UCS equipment:FexPowerSummary:suspect managed
        object property"
    ::= { cucsEquipmentFexPowerSummaryEntry 17 }

cucsEquipmentFexPowerSummaryThresholded OBJECT-TYPE
    SYNTAX       CucsEquipmentFexPowerSummaryThresholded
    MAX-ACCESS   read-only
    STATUS       current
    DESCRIPTION
        "Cisco UCS equipment:FexPowerSummary:thresholded
        managed object property"
    ::= { cucsEquipmentFexPowerSummaryEntry 18 }

cucsEquipmentFexPowerSummaryTimeCollected OBJECT-TYPE
    SYNTAX       DateAndTime
    MAX-ACCESS   read-only
    STATUS       current
    DESCRIPTION
        "Cisco UCS equipment:FexPowerSummary:timeCollected
        managed object property"
    ::= { cucsEquipmentFexPowerSummaryEntry 19 }

cucsEquipmentFexPowerSummaryTotalPower OBJECT-TYPE
    SYNTAX       INTEGER
    MAX-ACCESS   read-only
    STATUS       current
    DESCRIPTION
        "Cisco UCS equipment:FexPowerSummary:totalPower
        managed object property"
    ::= { cucsEquipmentFexPowerSummaryEntry 20 }

cucsEquipmentFexPowerSummaryTotalPowerAvg OBJECT-TYPE
    SYNTAX       INTEGER
    MAX-ACCESS   read-only
    STATUS       current
    DESCRIPTION
        "Cisco UCS equipment:FexPowerSummary:totalPowerAvg
        managed object property"
    ::= { cucsEquipmentFexPowerSummaryEntry 21 }

cucsEquipmentFexPowerSummaryTotalPowerMax OBJECT-TYPE
    SYNTAX       INTEGER
    MAX-ACCESS   read-only
    STATUS       current
    DESCRIPTION
        "Cisco UCS equipment:FexPowerSummary:totalPowerMax
        managed object property"
    ::= { cucsEquipmentFexPowerSummaryEntry 22 }

cucsEquipmentFexPowerSummaryTotalPowerMin OBJECT-TYPE
    SYNTAX       INTEGER
    MAX-ACCESS   read-only
    STATUS       current
    DESCRIPTION
        "Cisco UCS equipment:FexPowerSummary:totalPowerMin
        managed object property"
    ::= { cucsEquipmentFexPowerSummaryEntry 23 }

cucsEquipmentFexPowerSummaryUpdate OBJECT-TYPE
    SYNTAX       Gauge32
    MAX-ACCESS   read-only
    STATUS       current
    DESCRIPTION
        "Cisco UCS equipment:FexPowerSummary:update managed
        object property"
    ::= { cucsEquipmentFexPowerSummaryEntry 24 }

cucsEquipmentFexPowerSummaryHistTable OBJECT-TYPE
    SYNTAX           SEQUENCE OF CucsEquipmentFexPowerSummaryHistEntry
    MAX-ACCESS       not-accessible
    STATUS           current
    DESCRIPTION
        "Cisco UCS equipment:FexPowerSummaryHist managed object table"
    ::= { cucsEquipmentObjects 25 }

cucsEquipmentFexPowerSummaryHistEntry OBJECT-TYPE
    SYNTAX           CucsEquipmentFexPowerSummaryHistEntry
    MAX-ACCESS       not-accessible
    STATUS           current
    DESCRIPTION
        "Entry for the cucsEquipmentFexPowerSummaryHistTable table."
    INDEX { cucsEquipmentFexPowerSummaryHistInstanceId }
    ::= { cucsEquipmentFexPowerSummaryHistTable 1 }

CucsEquipmentFexPowerSummaryHistEntry ::= SEQUENCE {
    cucsEquipmentFexPowerSummaryHistInstanceId                       CucsManagedObjectId,
    cucsEquipmentFexPowerSummaryHistDn                               CucsManagedObjectDn,
    cucsEquipmentFexPowerSummaryHistRn                               SnmpAdminString,
    cucsEquipmentFexPowerSummaryHistModulePower                      INTEGER,
    cucsEquipmentFexPowerSummaryHistModulePowerAvg                   INTEGER,
    cucsEquipmentFexPowerSummaryHistModulePowerMax                   INTEGER,
    cucsEquipmentFexPowerSummaryHistModulePowerMin                   INTEGER,
    cucsEquipmentFexPowerSummaryHistAvailablePower                   INTEGER,
    cucsEquipmentFexPowerSummaryHistAvailablePowerAvg                INTEGER,
    cucsEquipmentFexPowerSummaryHistAvailablePowerMax                INTEGER,
    cucsEquipmentFexPowerSummaryHistAvailablePowerMin                INTEGER,
    cucsEquipmentFexPowerSummaryHistId                               Unsigned64,
    cucsEquipmentFexPowerSummaryHistMostRecent                       TruthValue,
    cucsEquipmentFexPowerSummaryHistReservedPower                    INTEGER,
    cucsEquipmentFexPowerSummaryHistReservedPowerAvg                 INTEGER,
    cucsEquipmentFexPowerSummaryHistReservedPowerMax                 INTEGER,
    cucsEquipmentFexPowerSummaryHistReservedPowerMin                 INTEGER,
    cucsEquipmentFexPowerSummaryHistSuspect                          TruthValue,
    cucsEquipmentFexPowerSummaryHistThresholded                      CucsEquipmentFexPowerSummaryHistThresholded,
    cucsEquipmentFexPowerSummaryHistTimeCollected                    DateAndTime,
    cucsEquipmentFexPowerSummaryHistTotalPower                       INTEGER,
    cucsEquipmentFexPowerSummaryHistTotalPowerAvg                    INTEGER,
    cucsEquipmentFexPowerSummaryHistTotalPowerMax                    INTEGER,
    cucsEquipmentFexPowerSummaryHistTotalPowerMin                    INTEGER
}

cucsEquipmentFexPowerSummaryHistInstanceId OBJECT-TYPE
    SYNTAX       CucsManagedObjectId
    MAX-ACCESS   not-accessible
    STATUS       current
    DESCRIPTION
        "Instance identifier of the managed object."
    ::= { cucsEquipmentFexPowerSummaryHistEntry 1 }

cucsEquipmentFexPowerSummaryHistDn OBJECT-TYPE
    SYNTAX       CucsManagedObjectDn
    MAX-ACCESS   read-only
    STATUS       current
    DESCRIPTION
        "Cisco UCS equipment:FexPowerSummaryHist:dn managed
        object property"
    ::= { cucsEquipmentFexPowerSummaryHistEntry 2 }

cucsEquipmentFexPowerSummaryHistRn OBJECT-TYPE
    SYNTAX       SnmpAdminString
    MAX-ACCESS   read-only
    STATUS       current
    DESCRIPTION
        "Cisco UCS equipment:FexPowerSummaryHist:rn managed
        object property"
    ::= { cucsEquipmentFexPowerSummaryHistEntry 3 }

cucsEquipmentFexPowerSummaryHistModulePower OBJECT-TYPE
    SYNTAX       INTEGER
    MAX-ACCESS   read-only
    STATUS       current
    DESCRIPTION
        "Cisco UCS equipment:FexPowerSummaryHist:ModulePower
        managed object property"
    ::= { cucsEquipmentFexPowerSummaryHistEntry 4 }

cucsEquipmentFexPowerSummaryHistModulePowerAvg OBJECT-TYPE
    SYNTAX       INTEGER
    MAX-ACCESS   read-only
    STATUS       current
    DESCRIPTION
        "Cisco UCS equipment:FexPowerSummaryHist:ModulePowerAvg
        managed object property"
    ::= { cucsEquipmentFexPowerSummaryHistEntry 5 }

cucsEquipmentFexPowerSummaryHistModulePowerMax OBJECT-TYPE
    SYNTAX       INTEGER
    MAX-ACCESS   read-only
    STATUS       current
    DESCRIPTION
        "Cisco UCS equipment:FexPowerSummaryHist:ModulePowerMax
        managed object property"
    ::= { cucsEquipmentFexPowerSummaryHistEntry 6 }

cucsEquipmentFexPowerSummaryHistModulePowerMin OBJECT-TYPE
    SYNTAX       INTEGER
    MAX-ACCESS   read-only
    STATUS       current
    DESCRIPTION
        "Cisco UCS equipment:FexPowerSummaryHist:ModulePowerMin
        managed object property"
    ::= { cucsEquipmentFexPowerSummaryHistEntry 7 }

cucsEquipmentFexPowerSummaryHistAvailablePower OBJECT-TYPE
    SYNTAX       INTEGER
    MAX-ACCESS   read-only
    STATUS       current
    DESCRIPTION
        "Cisco UCS equipment:FexPowerSummaryHist:availablePower
        managed object property"
    ::= { cucsEquipmentFexPowerSummaryHistEntry 8 }

cucsEquipmentFexPowerSummaryHistAvailablePowerAvg OBJECT-TYPE
    SYNTAX       INTEGER
    MAX-ACCESS   read-only
    STATUS       current
    DESCRIPTION
        "Cisco UCS equipment:FexPowerSummaryHist:availablePowerAvg
        managed object property"
    ::= { cucsEquipmentFexPowerSummaryHistEntry 9 }

cucsEquipmentFexPowerSummaryHistAvailablePowerMax OBJECT-TYPE
    SYNTAX       INTEGER
    MAX-ACCESS   read-only
    STATUS       current
    DESCRIPTION
        "Cisco UCS equipment:FexPowerSummaryHist:availablePowerMax
        managed object property"
    ::= { cucsEquipmentFexPowerSummaryHistEntry 10 }

cucsEquipmentFexPowerSummaryHistAvailablePowerMin OBJECT-TYPE
    SYNTAX       INTEGER
    MAX-ACCESS   read-only
    STATUS       current
    DESCRIPTION
        "Cisco UCS equipment:FexPowerSummaryHist:availablePowerMin
        managed object property"
    ::= { cucsEquipmentFexPowerSummaryHistEntry 11 }

cucsEquipmentFexPowerSummaryHistId OBJECT-TYPE
    SYNTAX       Unsigned64
    MAX-ACCESS   read-only
    STATUS       current
    DESCRIPTION
        "Cisco UCS equipment:FexPowerSummaryHist:id managed
        object property"
    ::= { cucsEquipmentFexPowerSummaryHistEntry 12 }

cucsEquipmentFexPowerSummaryHistMostRecent OBJECT-TYPE
    SYNTAX       TruthValue
    MAX-ACCESS   read-only
    STATUS       current
    DESCRIPTION
        "Cisco UCS equipment:FexPowerSummaryHist:mostRecent
        managed object property"
    ::= { cucsEquipmentFexPowerSummaryHistEntry 13 }

cucsEquipmentFexPowerSummaryHistReservedPower OBJECT-TYPE
    SYNTAX       INTEGER
    MAX-ACCESS   read-only
    STATUS       current
    DESCRIPTION
        "Cisco UCS equipment:FexPowerSummaryHist:reservedPower
        managed object property"
    ::= { cucsEquipmentFexPowerSummaryHistEntry 14 }

cucsEquipmentFexPowerSummaryHistReservedPowerAvg OBJECT-TYPE
    SYNTAX       INTEGER
    MAX-ACCESS   read-only
    STATUS       current
    DESCRIPTION
        "Cisco UCS equipment:FexPowerSummaryHist:reservedPowerAvg
        managed object property"
    ::= { cucsEquipmentFexPowerSummaryHistEntry 15 }

cucsEquipmentFexPowerSummaryHistReservedPowerMax OBJECT-TYPE
    SYNTAX       INTEGER
    MAX-ACCESS   read-only
    STATUS       current
    DESCRIPTION
        "Cisco UCS equipment:FexPowerSummaryHist:reservedPowerMax
        managed object property"
    ::= { cucsEquipmentFexPowerSummaryHistEntry 16 }

cucsEquipmentFexPowerSummaryHistReservedPowerMin OBJECT-TYPE
    SYNTAX       INTEGER
    MAX-ACCESS   read-only
    STATUS       current
    DESCRIPTION
        "Cisco UCS equipment:FexPowerSummaryHist:reservedPowerMin
        managed object property"
    ::= { cucsEquipmentFexPowerSummaryHistEntry 17 }

cucsEquipmentFexPowerSummaryHistSuspect OBJECT-TYPE
    SYNTAX       TruthValue
    MAX-ACCESS   read-only
    STATUS       current
    DESCRIPTION
        "Cisco UCS equipment:FexPowerSummaryHist:suspect
        managed object property"
    ::= { cucsEquipmentFexPowerSummaryHistEntry 18 }

cucsEquipmentFexPowerSummaryHistThresholded OBJECT-TYPE
    SYNTAX       CucsEquipmentFexPowerSummaryHistThresholded
    MAX-ACCESS   read-only
    STATUS       current
    DESCRIPTION
        "Cisco UCS equipment:FexPowerSummaryHist:thresholded
        managed object property"
    ::= { cucsEquipmentFexPowerSummaryHistEntry 19 }

cucsEquipmentFexPowerSummaryHistTimeCollected OBJECT-TYPE
    SYNTAX       DateAndTime
    MAX-ACCESS   read-only
    STATUS       current
    DESCRIPTION
        "Cisco UCS equipment:FexPowerSummaryHist:timeCollected
        managed object property"
    ::= { cucsEquipmentFexPowerSummaryHistEntry 20 }

cucsEquipmentFexPowerSummaryHistTotalPower OBJECT-TYPE
    SYNTAX       INTEGER
    MAX-ACCESS   read-only
    STATUS       current
    DESCRIPTION
        "Cisco UCS equipment:FexPowerSummaryHist:totalPower
        managed object property"
    ::= { cucsEquipmentFexPowerSummaryHistEntry 21 }

cucsEquipmentFexPowerSummaryHistTotalPowerAvg OBJECT-TYPE
    SYNTAX       INTEGER
    MAX-ACCESS   read-only
    STATUS       current
    DESCRIPTION
        "Cisco UCS equipment:FexPowerSummaryHist:totalPowerAvg
        managed object property"
    ::= { cucsEquipmentFexPowerSummaryHistEntry 22 }

cucsEquipmentFexPowerSummaryHistTotalPowerMax OBJECT-TYPE
    SYNTAX       INTEGER
    MAX-ACCESS   read-only
    STATUS       current
    DESCRIPTION
        "Cisco UCS equipment:FexPowerSummaryHist:totalPowerMax
        managed object property"
    ::= { cucsEquipmentFexPowerSummaryHistEntry 23 }

cucsEquipmentFexPowerSummaryHistTotalPowerMin OBJECT-TYPE
    SYNTAX       INTEGER
    MAX-ACCESS   read-only
    STATUS       current
    DESCRIPTION
        "Cisco UCS equipment:FexPowerSummaryHist:totalPowerMin
        managed object property"
    ::= { cucsEquipmentFexPowerSummaryHistEntry 24 }

cucsEquipmentFexPsuInputStatsTable OBJECT-TYPE
    SYNTAX           SEQUENCE OF CucsEquipmentFexPsuInputStatsEntry
    MAX-ACCESS       not-accessible
    STATUS           current
    DESCRIPTION
        "Cisco UCS equipment:FexPsuInputStats managed object table"
    ::= { cucsEquipmentObjects 26 }

cucsEquipmentFexPsuInputStatsEntry OBJECT-TYPE
    SYNTAX           CucsEquipmentFexPsuInputStatsEntry
    MAX-ACCESS       not-accessible
    STATUS           current
    DESCRIPTION
        "Entry for the cucsEquipmentFexPsuInputStatsTable table."
    INDEX { cucsEquipmentFexPsuInputStatsInstanceId }
    ::= { cucsEquipmentFexPsuInputStatsTable 1 }

CucsEquipmentFexPsuInputStatsEntry ::= SEQUENCE {
    cucsEquipmentFexPsuInputStatsInstanceId                          CucsManagedObjectId,
    cucsEquipmentFexPsuInputStatsDn                                  CucsManagedObjectDn,
    cucsEquipmentFexPsuInputStatsRn                                  SnmpAdminString,
    cucsEquipmentFexPsuInputStatsCurrent                             INTEGER,
    cucsEquipmentFexPsuInputStatsCurrentAvg                          INTEGER,
    cucsEquipmentFexPsuInputStatsCurrentMax                          INTEGER,
    cucsEquipmentFexPsuInputStatsCurrentMin                          INTEGER,
    cucsEquipmentFexPsuInputStatsInputStatus                         SnmpAdminString,
    cucsEquipmentFexPsuInputStatsIntervals                           Gauge32,
    cucsEquipmentFexPsuInputStatsPower                               INTEGER,
    cucsEquipmentFexPsuInputStatsPowerAvg                            INTEGER,
    cucsEquipmentFexPsuInputStatsPowerMax                            INTEGER,
    cucsEquipmentFexPsuInputStatsPowerMin                            INTEGER,
    cucsEquipmentFexPsuInputStatsSuspect                             TruthValue,
    cucsEquipmentFexPsuInputStatsThresholded                         CucsEquipmentFexPsuInputStatsThresholded,
    cucsEquipmentFexPsuInputStatsTimeCollected                       DateAndTime,
    cucsEquipmentFexPsuInputStatsUpdate                              Gauge32,
    cucsEquipmentFexPsuInputStatsVoltage                             INTEGER,
    cucsEquipmentFexPsuInputStatsVoltageAvg                          INTEGER,
    cucsEquipmentFexPsuInputStatsVoltageMax                          INTEGER,
    cucsEquipmentFexPsuInputStatsVoltageMin                          INTEGER
}

cucsEquipmentFexPsuInputStatsInstanceId OBJECT-TYPE
    SYNTAX       CucsManagedObjectId
    MAX-ACCESS   not-accessible
    STATUS       current
    DESCRIPTION
        "Instance identifier of the managed object."
    ::= { cucsEquipmentFexPsuInputStatsEntry 1 }

cucsEquipmentFexPsuInputStatsDn OBJECT-TYPE
    SYNTAX       CucsManagedObjectDn
    MAX-ACCESS   read-only
    STATUS       current
    DESCRIPTION
        "Cisco UCS equipment:FexPsuInputStats:dn managed object property"
    ::= { cucsEquipmentFexPsuInputStatsEntry 2 }

cucsEquipmentFexPsuInputStatsRn OBJECT-TYPE
    SYNTAX       SnmpAdminString
    MAX-ACCESS   read-only
    STATUS       current
    DESCRIPTION
        "Cisco UCS equipment:FexPsuInputStats:rn managed object property"
    ::= { cucsEquipmentFexPsuInputStatsEntry 3 }

cucsEquipmentFexPsuInputStatsCurrent OBJECT-TYPE
    SYNTAX       INTEGER
    MAX-ACCESS   read-only
    STATUS       current
    DESCRIPTION
        "Cisco UCS equipment:FexPsuInputStats:current managed
        object property"
    ::= { cucsEquipmentFexPsuInputStatsEntry 4 }

cucsEquipmentFexPsuInputStatsCurrentAvg OBJECT-TYPE
    SYNTAX       INTEGER
    MAX-ACCESS   read-only
    STATUS       current
    DESCRIPTION
        "Cisco UCS equipment:FexPsuInputStats:currentAvg
        managed object property"
    ::= { cucsEquipmentFexPsuInputStatsEntry 5 }

cucsEquipmentFexPsuInputStatsCurrentMax OBJECT-TYPE
    SYNTAX       INTEGER
    MAX-ACCESS   read-only
    STATUS       current
    DESCRIPTION
        "Cisco UCS equipment:FexPsuInputStats:currentMax
        managed object property"
    ::= { cucsEquipmentFexPsuInputStatsEntry 6 }

cucsEquipmentFexPsuInputStatsCurrentMin OBJECT-TYPE
    SYNTAX       INTEGER
    MAX-ACCESS   read-only
    STATUS       current
    DESCRIPTION
        "Cisco UCS equipment:FexPsuInputStats:currentMin
        managed object property"
    ::= { cucsEquipmentFexPsuInputStatsEntry 7 }

cucsEquipmentFexPsuInputStatsInputStatus OBJECT-TYPE
    SYNTAX       SnmpAdminString
    MAX-ACCESS   read-only
    STATUS       current
    DESCRIPTION
        "Cisco UCS equipment:FexPsuInputStats:inputStatus
        managed object property"
    ::= { cucsEquipmentFexPsuInputStatsEntry 8 }

cucsEquipmentFexPsuInputStatsIntervals OBJECT-TYPE
    SYNTAX       Gauge32
    MAX-ACCESS   read-only
    STATUS       current
    DESCRIPTION
        "Cisco UCS equipment:FexPsuInputStats:intervals
        managed object property"
    ::= { cucsEquipmentFexPsuInputStatsEntry 9 }

cucsEquipmentFexPsuInputStatsPower OBJECT-TYPE
    SYNTAX       INTEGER
    MAX-ACCESS   read-only
    STATUS       current
    DESCRIPTION
        "Cisco UCS equipment:FexPsuInputStats:power managed
        object property"
    ::= { cucsEquipmentFexPsuInputStatsEntry 10 }

cucsEquipmentFexPsuInputStatsPowerAvg OBJECT-TYPE
    SYNTAX       INTEGER
    MAX-ACCESS   read-only
    STATUS       current
    DESCRIPTION
        "Cisco UCS equipment:FexPsuInputStats:powerAvg
        managed object property"
    ::= { cucsEquipmentFexPsuInputStatsEntry 11 }

cucsEquipmentFexPsuInputStatsPowerMax OBJECT-TYPE
    SYNTAX       INTEGER
    MAX-ACCESS   read-only
    STATUS       current
    DESCRIPTION
        "Cisco UCS equipment:FexPsuInputStats:powerMax
        managed object property"
    ::= { cucsEquipmentFexPsuInputStatsEntry 12 }

cucsEquipmentFexPsuInputStatsPowerMin OBJECT-TYPE
    SYNTAX       INTEGER
    MAX-ACCESS   read-only
    STATUS       current
    DESCRIPTION
        "Cisco UCS equipment:FexPsuInputStats:powerMin
        managed object property"
    ::= { cucsEquipmentFexPsuInputStatsEntry 13 }

cucsEquipmentFexPsuInputStatsSuspect OBJECT-TYPE
    SYNTAX       TruthValue
    MAX-ACCESS   read-only
    STATUS       current
    DESCRIPTION
        "Cisco UCS equipment:FexPsuInputStats:suspect managed
        object property"
    ::= { cucsEquipmentFexPsuInputStatsEntry 14 }

cucsEquipmentFexPsuInputStatsThresholded OBJECT-TYPE
    SYNTAX       CucsEquipmentFexPsuInputStatsThresholded
    MAX-ACCESS   read-only
    STATUS       current
    DESCRIPTION
        "Cisco UCS equipment:FexPsuInputStats:thresholded
        managed object property"
    ::= { cucsEquipmentFexPsuInputStatsEntry 15 }

cucsEquipmentFexPsuInputStatsTimeCollected OBJECT-TYPE
    SYNTAX       DateAndTime
    MAX-ACCESS   read-only
    STATUS       current
    DESCRIPTION
        "Cisco UCS equipment:FexPsuInputStats:timeCollected
        managed object property"
    ::= { cucsEquipmentFexPsuInputStatsEntry 16 }

cucsEquipmentFexPsuInputStatsUpdate OBJECT-TYPE
    SYNTAX       Gauge32
    MAX-ACCESS   read-only
    STATUS       current
    DESCRIPTION
        "Cisco UCS equipment:FexPsuInputStats:update managed
        object property"
    ::= { cucsEquipmentFexPsuInputStatsEntry 17 }

cucsEquipmentFexPsuInputStatsVoltage OBJECT-TYPE
    SYNTAX       INTEGER
    MAX-ACCESS   read-only
    STATUS       current
    DESCRIPTION
        "Cisco UCS equipment:FexPsuInputStats:voltage managed
        object property"
    ::= { cucsEquipmentFexPsuInputStatsEntry 18 }

cucsEquipmentFexPsuInputStatsVoltageAvg OBJECT-TYPE
    SYNTAX       INTEGER
    MAX-ACCESS   read-only
    STATUS       current
    DESCRIPTION
        "Cisco UCS equipment:FexPsuInputStats:voltageAvg
        managed object property"
    ::= { cucsEquipmentFexPsuInputStatsEntry 19 }

cucsEquipmentFexPsuInputStatsVoltageMax OBJECT-TYPE
    SYNTAX       INTEGER
    MAX-ACCESS   read-only
    STATUS       current
    DESCRIPTION
        "Cisco UCS equipment:FexPsuInputStats:voltageMax
        managed object property"
    ::= { cucsEquipmentFexPsuInputStatsEntry 20 }

cucsEquipmentFexPsuInputStatsVoltageMin OBJECT-TYPE
    SYNTAX       INTEGER
    MAX-ACCESS   read-only
    STATUS       current
    DESCRIPTION
        "Cisco UCS equipment:FexPsuInputStats:voltageMin
        managed object property"
    ::= { cucsEquipmentFexPsuInputStatsEntry 21 }

cucsEquipmentFexPsuInputStatsHistTable OBJECT-TYPE
    SYNTAX           SEQUENCE OF CucsEquipmentFexPsuInputStatsHistEntry
    MAX-ACCESS       not-accessible
    STATUS           current
    DESCRIPTION
        "Cisco UCS equipment:FexPsuInputStatsHist managed object table"
    ::= { cucsEquipmentObjects 27 }

cucsEquipmentFexPsuInputStatsHistEntry OBJECT-TYPE
    SYNTAX           CucsEquipmentFexPsuInputStatsHistEntry
    MAX-ACCESS       not-accessible
    STATUS           current
    DESCRIPTION
        "Entry for the cucsEquipmentFexPsuInputStatsHistTable table."
    INDEX { cucsEquipmentFexPsuInputStatsHistInstanceId }
    ::= { cucsEquipmentFexPsuInputStatsHistTable 1 }

CucsEquipmentFexPsuInputStatsHistEntry ::= SEQUENCE {
    cucsEquipmentFexPsuInputStatsHistInstanceId                      CucsManagedObjectId,
    cucsEquipmentFexPsuInputStatsHistDn                              CucsManagedObjectDn,
    cucsEquipmentFexPsuInputStatsHistRn                              SnmpAdminString,
    cucsEquipmentFexPsuInputStatsHistCurrent                         INTEGER,
    cucsEquipmentFexPsuInputStatsHistCurrentAvg                      INTEGER,
    cucsEquipmentFexPsuInputStatsHistCurrentMax                      INTEGER,
    cucsEquipmentFexPsuInputStatsHistCurrentMin                      INTEGER,
    cucsEquipmentFexPsuInputStatsHistId                              Unsigned64,
    cucsEquipmentFexPsuInputStatsHistMostRecent                      TruthValue,
    cucsEquipmentFexPsuInputStatsHistPower                           INTEGER,
    cucsEquipmentFexPsuInputStatsHistPowerAvg                        INTEGER,
    cucsEquipmentFexPsuInputStatsHistPowerMax                        INTEGER,
    cucsEquipmentFexPsuInputStatsHistPowerMin                        INTEGER,
    cucsEquipmentFexPsuInputStatsHistSuspect                         TruthValue,
    cucsEquipmentFexPsuInputStatsHistThresholded                     CucsEquipmentFexPsuInputStatsHistThresholded,
    cucsEquipmentFexPsuInputStatsHistTimeCollected                   DateAndTime,
    cucsEquipmentFexPsuInputStatsHistVoltage                         INTEGER,
    cucsEquipmentFexPsuInputStatsHistVoltageAvg                      INTEGER,
    cucsEquipmentFexPsuInputStatsHistVoltageMax                      INTEGER,
    cucsEquipmentFexPsuInputStatsHistVoltageMin                      INTEGER
}

cucsEquipmentFexPsuInputStatsHistInstanceId OBJECT-TYPE
    SYNTAX       CucsManagedObjectId
    MAX-ACCESS   not-accessible
    STATUS       current
    DESCRIPTION
        "Instance identifier of the managed object."
    ::= { cucsEquipmentFexPsuInputStatsHistEntry 1 }

cucsEquipmentFexPsuInputStatsHistDn OBJECT-TYPE
    SYNTAX       CucsManagedObjectDn
    MAX-ACCESS   read-only
    STATUS       current
    DESCRIPTION
        "Cisco UCS equipment:FexPsuInputStatsHist:dn managed
        object property"
    ::= { cucsEquipmentFexPsuInputStatsHistEntry 2 }

cucsEquipmentFexPsuInputStatsHistRn OBJECT-TYPE
    SYNTAX       SnmpAdminString
    MAX-ACCESS   read-only
    STATUS       current
    DESCRIPTION
        "Cisco UCS equipment:FexPsuInputStatsHist:rn managed
        object property"
    ::= { cucsEquipmentFexPsuInputStatsHistEntry 3 }

cucsEquipmentFexPsuInputStatsHistCurrent OBJECT-TYPE
    SYNTAX       INTEGER
    MAX-ACCESS   read-only
    STATUS       current
    DESCRIPTION
        "Cisco UCS equipment:FexPsuInputStatsHist:current
        managed object property"
    ::= { cucsEquipmentFexPsuInputStatsHistEntry 4 }

cucsEquipmentFexPsuInputStatsHistCurrentAvg OBJECT-TYPE
    SYNTAX       INTEGER
    MAX-ACCESS   read-only
    STATUS       current
    DESCRIPTION
        "Cisco UCS equipment:FexPsuInputStatsHist:currentAvg
        managed object property"
    ::= { cucsEquipmentFexPsuInputStatsHistEntry 5 }

cucsEquipmentFexPsuInputStatsHistCurrentMax OBJECT-TYPE
    SYNTAX       INTEGER
    MAX-ACCESS   read-only
    STATUS       current
    DESCRIPTION
        "Cisco UCS equipment:FexPsuInputStatsHist:currentMax
        managed object property"
    ::= { cucsEquipmentFexPsuInputStatsHistEntry 6 }

cucsEquipmentFexPsuInputStatsHistCurrentMin OBJECT-TYPE
    SYNTAX       INTEGER
    MAX-ACCESS   read-only
    STATUS       current
    DESCRIPTION
        "Cisco UCS equipment:FexPsuInputStatsHist:currentMin
        managed object property"
    ::= { cucsEquipmentFexPsuInputStatsHistEntry 7 }

cucsEquipmentFexPsuInputStatsHistId OBJECT-TYPE
    SYNTAX       Unsigned64
    MAX-ACCESS   read-only
    STATUS       current
    DESCRIPTION
        "Cisco UCS equipment:FexPsuInputStatsHist:id managed
        object property"
    ::= { cucsEquipmentFexPsuInputStatsHistEntry 8 }

cucsEquipmentFexPsuInputStatsHistMostRecent OBJECT-TYPE
    SYNTAX       TruthValue
    MAX-ACCESS   read-only
    STATUS       current
    DESCRIPTION
        "Cisco UCS equipment:FexPsuInputStatsHist:mostRecent
        managed object property"
    ::= { cucsEquipmentFexPsuInputStatsHistEntry 9 }

cucsEquipmentFexPsuInputStatsHistPower OBJECT-TYPE
    SYNTAX       INTEGER
    MAX-ACCESS   read-only
    STATUS       current
    DESCRIPTION
        "Cisco UCS equipment:FexPsuInputStatsHist:power
        managed object property"
    ::= { cucsEquipmentFexPsuInputStatsHistEntry 10 }

cucsEquipmentFexPsuInputStatsHistPowerAvg OBJECT-TYPE
    SYNTAX       INTEGER
    MAX-ACCESS   read-only
    STATUS       current
    DESCRIPTION
        "Cisco UCS equipment:FexPsuInputStatsHist:powerAvg
        managed object property"
    ::= { cucsEquipmentFexPsuInputStatsHistEntry 11 }

cucsEquipmentFexPsuInputStatsHistPowerMax OBJECT-TYPE
    SYNTAX       INTEGER
    MAX-ACCESS   read-only
    STATUS       current
    DESCRIPTION
        "Cisco UCS equipment:FexPsuInputStatsHist:powerMax
        managed object property"
    ::= { cucsEquipmentFexPsuInputStatsHistEntry 12 }

cucsEquipmentFexPsuInputStatsHistPowerMin OBJECT-TYPE
    SYNTAX       INTEGER
    MAX-ACCESS   read-only
    STATUS       current
    DESCRIPTION
        "Cisco UCS equipment:FexPsuInputStatsHist:powerMin
        managed object property"
    ::= { cucsEquipmentFexPsuInputStatsHistEntry 13 }

cucsEquipmentFexPsuInputStatsHistSuspect OBJECT-TYPE
    SYNTAX       TruthValue
    MAX-ACCESS   read-only
    STATUS       current
    DESCRIPTION
        "Cisco UCS equipment:FexPsuInputStatsHist:suspect
        managed object property"
    ::= { cucsEquipmentFexPsuInputStatsHistEntry 14 }

cucsEquipmentFexPsuInputStatsHistThresholded OBJECT-TYPE
    SYNTAX       CucsEquipmentFexPsuInputStatsHistThresholded
    MAX-ACCESS   read-only
    STATUS       current
    DESCRIPTION
        "Cisco UCS equipment:FexPsuInputStatsHist:thresholded
        managed object property"
    ::= { cucsEquipmentFexPsuInputStatsHistEntry 15 }

cucsEquipmentFexPsuInputStatsHistTimeCollected OBJECT-TYPE
    SYNTAX       DateAndTime
    MAX-ACCESS   read-only
    STATUS       current
    DESCRIPTION
        "Cisco UCS equipment:FexPsuInputStatsHist:timeCollected
        managed object property"
    ::= { cucsEquipmentFexPsuInputStatsHistEntry 16 }

cucsEquipmentFexPsuInputStatsHistVoltage OBJECT-TYPE
    SYNTAX       INTEGER
    MAX-ACCESS   read-only
    STATUS       current
    DESCRIPTION
        "Cisco UCS equipment:FexPsuInputStatsHist:voltage
        managed object property"
    ::= { cucsEquipmentFexPsuInputStatsHistEntry 17 }

cucsEquipmentFexPsuInputStatsHistVoltageAvg OBJECT-TYPE
    SYNTAX       INTEGER
    MAX-ACCESS   read-only
    STATUS       current
    DESCRIPTION
        "Cisco UCS equipment:FexPsuInputStatsHist:voltageAvg
        managed object property"
    ::= { cucsEquipmentFexPsuInputStatsHistEntry 18 }

cucsEquipmentFexPsuInputStatsHistVoltageMax OBJECT-TYPE
    SYNTAX       INTEGER
    MAX-ACCESS   read-only
    STATUS       current
    DESCRIPTION
        "Cisco UCS equipment:FexPsuInputStatsHist:voltageMax
        managed object property"
    ::= { cucsEquipmentFexPsuInputStatsHistEntry 19 }

cucsEquipmentFexPsuInputStatsHistVoltageMin OBJECT-TYPE
    SYNTAX       INTEGER
    MAX-ACCESS   read-only
    STATUS       current
    DESCRIPTION
        "Cisco UCS equipment:FexPsuInputStatsHist:voltageMin
        managed object property"
    ::= { cucsEquipmentFexPsuInputStatsHistEntry 20 }

cucsEquipmentFirmwareConstraintTable OBJECT-TYPE
    SYNTAX           SEQUENCE OF CucsEquipmentFirmwareConstraintEntry
    MAX-ACCESS       not-accessible
    STATUS           current
    DESCRIPTION
        "Cisco UCS equipment:FirmwareConstraint managed object table"
    ::= { cucsEquipmentObjects 113 }

cucsEquipmentFirmwareConstraintEntry OBJECT-TYPE
    SYNTAX           CucsEquipmentFirmwareConstraintEntry
    MAX-ACCESS       not-accessible
    STATUS           current
    DESCRIPTION
        "Entry for the cucsEquipmentFirmwareConstraintTable table."
    INDEX { cucsEquipmentFirmwareConstraintInstanceId }
    ::= { cucsEquipmentFirmwareConstraintTable 1 }

CucsEquipmentFirmwareConstraintEntry ::= SEQUENCE {
    cucsEquipmentFirmwareConstraintInstanceId                        CucsManagedObjectId,
    cucsEquipmentFirmwareConstraintDn                                CucsManagedObjectDn,
    cucsEquipmentFirmwareConstraintRn                                SnmpAdminString,
    cucsEquipmentFirmwareConstraintMinVer1                           SnmpAdminString,
    cucsEquipmentFirmwareConstraintMinVer2                           SnmpAdminString
}

cucsEquipmentFirmwareConstraintInstanceId OBJECT-TYPE
    SYNTAX       CucsManagedObjectId
    MAX-ACCESS   not-accessible
    STATUS       current
    DESCRIPTION
        "Instance identifier of the managed object."
    ::= { cucsEquipmentFirmwareConstraintEntry 1 }

cucsEquipmentFirmwareConstraintDn OBJECT-TYPE
    SYNTAX       CucsManagedObjectDn
    MAX-ACCESS   read-only
    STATUS       current
    DESCRIPTION
        "Cisco UCS equipment:FirmwareConstraint:dn managed
        object property"
    ::= { cucsEquipmentFirmwareConstraintEntry 2 }

cucsEquipmentFirmwareConstraintRn OBJECT-TYPE
    SYNTAX       SnmpAdminString
    MAX-ACCESS   read-only
    STATUS       current
    DESCRIPTION
        "Cisco UCS equipment:FirmwareConstraint:rn managed
        object property"
    ::= { cucsEquipmentFirmwareConstraintEntry 3 }

cucsEquipmentFirmwareConstraintMinVer1 OBJECT-TYPE
    SYNTAX       SnmpAdminString
    MAX-ACCESS   read-only
    STATUS       current
    DESCRIPTION
        "Cisco UCS equipment:FirmwareConstraint:minVer1
        managed object property"
    ::= { cucsEquipmentFirmwareConstraintEntry 4 }

cucsEquipmentFirmwareConstraintMinVer2 OBJECT-TYPE
    SYNTAX       SnmpAdminString
    MAX-ACCESS   read-only
    STATUS       current
    DESCRIPTION
        "Cisco UCS equipment:FirmwareConstraint:minVer2
        managed object property"
    ::= { cucsEquipmentFirmwareConstraintEntry 5 }

cucsEquipmentGemCapProviderTable OBJECT-TYPE
    SYNTAX           SEQUENCE OF CucsEquipmentGemCapProviderEntry
    MAX-ACCESS       not-accessible
    STATUS           current
    DESCRIPTION
        "Cisco UCS equipment:GemCapProvider managed object table"
    ::= { cucsEquipmentObjects 28 }

cucsEquipmentGemCapProviderEntry OBJECT-TYPE
    SYNTAX           CucsEquipmentGemCapProviderEntry
    MAX-ACCESS       not-accessible
    STATUS           current
    DESCRIPTION
        "Entry for the cucsEquipmentGemCapProviderTable table."
    INDEX { cucsEquipmentGemCapProviderInstanceId }
    ::= { cucsEquipmentGemCapProviderTable 1 }

CucsEquipmentGemCapProviderEntry ::= SEQUENCE {
    cucsEquipmentGemCapProviderInstanceId                            CucsManagedObjectId,
    cucsEquipmentGemCapProviderDn                                    CucsManagedObjectDn,
    cucsEquipmentGemCapProviderRn                                    SnmpAdminString,
    cucsEquipmentGemCapProviderDeprecated                            TruthValue,
    cucsEquipmentGemCapProviderGencount                              Gauge32,
    cucsEquipmentGemCapProviderMgmtPlaneVer                          SnmpAdminString,
    cucsEquipmentGemCapProviderModel                                 SnmpAdminString,
    cucsEquipmentGemCapProviderRevision                              SnmpAdminString,
    cucsEquipmentGemCapProviderVendor                                SnmpAdminString,
    cucsEquipmentGemCapProviderPromCardType                          Gauge32,
    cucsEquipmentGemCapProviderDeleted                               TruthValue,
    cucsEquipmentGemCapProviderElementLoadFailures                   Gauge32,
    cucsEquipmentGemCapProviderElementsLoaded                        Gauge32,
    cucsEquipmentGemCapProviderLoadErrors                            Gauge32,
    cucsEquipmentGemCapProviderLoadWarnings                          Gauge32
}

cucsEquipmentGemCapProviderInstanceId OBJECT-TYPE
    SYNTAX       CucsManagedObjectId
    MAX-ACCESS   not-accessible
    STATUS       current
    DESCRIPTION
        "Instance identifier of the managed object."
    ::= { cucsEquipmentGemCapProviderEntry 1 }

cucsEquipmentGemCapProviderDn OBJECT-TYPE
    SYNTAX       CucsManagedObjectDn
    MAX-ACCESS   read-only
    STATUS       current
    DESCRIPTION
        "Cisco UCS equipment:GemCapProvider:dn managed object property"
    ::= { cucsEquipmentGemCapProviderEntry 2 }

cucsEquipmentGemCapProviderRn OBJECT-TYPE
    SYNTAX       SnmpAdminString
    MAX-ACCESS   read-only
    STATUS       current
    DESCRIPTION
        "Cisco UCS equipment:GemCapProvider:rn managed object property"
    ::= { cucsEquipmentGemCapProviderEntry 3 }

cucsEquipmentGemCapProviderDeprecated OBJECT-TYPE
    SYNTAX       TruthValue
    MAX-ACCESS   read-only
    STATUS       current
    DESCRIPTION
        "Cisco UCS equipment:GemCapProvider:deprecated
        managed object property"
    ::= { cucsEquipmentGemCapProviderEntry 4 }

cucsEquipmentGemCapProviderGencount OBJECT-TYPE
    SYNTAX       Gauge32
    MAX-ACCESS   read-only
    STATUS       current
    DESCRIPTION
        "Cisco UCS equipment:GemCapProvider:gencount managed
        object property"
    ::= { cucsEquipmentGemCapProviderEntry 5 }

cucsEquipmentGemCapProviderMgmtPlaneVer OBJECT-TYPE
    SYNTAX       SnmpAdminString
    MAX-ACCESS   read-only
    STATUS       current
    DESCRIPTION
        "Cisco UCS equipment:GemCapProvider:mgmtPlaneVer
        managed object property"
    ::= { cucsEquipmentGemCapProviderEntry 6 }

cucsEquipmentGemCapProviderModel OBJECT-TYPE
    SYNTAX       SnmpAdminString
    MAX-ACCESS   read-only
    STATUS       current
    DESCRIPTION
        "Cisco UCS equipment:GemCapProvider:model managed object property"
    ::= { cucsEquipmentGemCapProviderEntry 7 }

cucsEquipmentGemCapProviderRevision OBJECT-TYPE
    SYNTAX       SnmpAdminString
    MAX-ACCESS   read-only
    STATUS       current
    DESCRIPTION
        "Cisco UCS equipment:GemCapProvider:revision managed
        object property"
    ::= { cucsEquipmentGemCapProviderEntry 8 }

cucsEquipmentGemCapProviderVendor OBJECT-TYPE
    SYNTAX       SnmpAdminString
    MAX-ACCESS   read-only
    STATUS       current
    DESCRIPTION
        "Cisco UCS equipment:GemCapProvider:vendor managed
        object property"
    ::= { cucsEquipmentGemCapProviderEntry 9 }

cucsEquipmentGemCapProviderPromCardType OBJECT-TYPE
    SYNTAX       Gauge32
    MAX-ACCESS   read-only
    STATUS       current
    DESCRIPTION
        "Cisco UCS equipment:GemCapProvider:promCardType
        managed object property"
    ::= { cucsEquipmentGemCapProviderEntry 10 }

cucsEquipmentGemCapProviderDeleted OBJECT-TYPE
    SYNTAX       TruthValue
    MAX-ACCESS   read-only
    STATUS       current
    DESCRIPTION
        "Cisco UCS equipment:GemCapProvider:deleted managed
        object property"
    ::= { cucsEquipmentGemCapProviderEntry 11 }

cucsEquipmentGemCapProviderElementLoadFailures OBJECT-TYPE
    SYNTAX       Gauge32
    MAX-ACCESS   read-only
    STATUS       current
    DESCRIPTION
        "Cisco UCS equipment:GemCapProvider:elementLoadFailures
        managed object property"
    ::= { cucsEquipmentGemCapProviderEntry 12 }

cucsEquipmentGemCapProviderElementsLoaded OBJECT-TYPE
    SYNTAX       Gauge32
    MAX-ACCESS   read-only
    STATUS       current
    DESCRIPTION
        "Cisco UCS equipment:GemCapProvider:elementsLoaded
        managed object property"
    ::= { cucsEquipmentGemCapProviderEntry 13 }

cucsEquipmentGemCapProviderLoadErrors OBJECT-TYPE
    SYNTAX       Gauge32
    MAX-ACCESS   read-only
    STATUS       current
    DESCRIPTION
        "Cisco UCS equipment:GemCapProvider:loadErrors
        managed object property"
    ::= { cucsEquipmentGemCapProviderEntry 14 }

cucsEquipmentGemCapProviderLoadWarnings OBJECT-TYPE
    SYNTAX       Gauge32
    MAX-ACCESS   read-only
    STATUS       current
    DESCRIPTION
        "Cisco UCS equipment:GemCapProvider:loadWarnings
        managed object property"
    ::= { cucsEquipmentGemCapProviderEntry 15 }

cucsEquipmentGemPortCapTable OBJECT-TYPE
    SYNTAX           SEQUENCE OF CucsEquipmentGemPortCapEntry
    MAX-ACCESS       not-accessible
    STATUS           current
    DESCRIPTION
        "Cisco UCS equipment:GemPortCap managed object table"
    ::= { cucsEquipmentObjects 78 }

cucsEquipmentGemPortCapEntry OBJECT-TYPE
    SYNTAX           CucsEquipmentGemPortCapEntry
    MAX-ACCESS       not-accessible
    STATUS           current
    DESCRIPTION
        "Entry for the cucsEquipmentGemPortCapTable table."
    INDEX { cucsEquipmentGemPortCapInstanceId }
    ::= { cucsEquipmentGemPortCapTable 1 }

CucsEquipmentGemPortCapEntry ::= SEQUENCE {
    cucsEquipmentGemPortCapInstanceId                                CucsManagedObjectId,
    cucsEquipmentGemPortCapDn                                        CucsManagedObjectDn,
    cucsEquipmentGemPortCapRn                                        SnmpAdminString,
    cucsEquipmentGemPortCapDescr                                     SnmpAdminString,
    cucsEquipmentGemPortCapIntId                                     SnmpAdminString,
    cucsEquipmentGemPortCapMaxFcSpeed                                CucsPortSpeed,
    cucsEquipmentGemPortCapName                                      SnmpAdminString,
    cucsEquipmentGemPortCapPortNumber                                Gauge32,
    cucsEquipmentGemPortCapPolicyLevel                               Gauge32,
    cucsEquipmentGemPortCapPolicyOwner                               CucsPolicyPolicyOwner
}

cucsEquipmentGemPortCapInstanceId OBJECT-TYPE
    SYNTAX       CucsManagedObjectId
    MAX-ACCESS   not-accessible
    STATUS       current
    DESCRIPTION
        "Instance identifier of the managed object."
    ::= { cucsEquipmentGemPortCapEntry 1 }

cucsEquipmentGemPortCapDn OBJECT-TYPE
    SYNTAX       CucsManagedObjectDn
    MAX-ACCESS   read-only
    STATUS       current
    DESCRIPTION
        "Cisco UCS equipment:GemPortCap:dn managed object property"
    ::= { cucsEquipmentGemPortCapEntry 2 }

cucsEquipmentGemPortCapRn OBJECT-TYPE
    SYNTAX       SnmpAdminString
    MAX-ACCESS   read-only
    STATUS       current
    DESCRIPTION
        "Cisco UCS equipment:GemPortCap:rn managed object property"
    ::= { cucsEquipmentGemPortCapEntry 3 }

cucsEquipmentGemPortCapDescr OBJECT-TYPE
    SYNTAX       SnmpAdminString
    MAX-ACCESS   read-only
    STATUS       current
    DESCRIPTION
        "Cisco UCS equipment:GemPortCap:descr managed object property"
    ::= { cucsEquipmentGemPortCapEntry 4 }

cucsEquipmentGemPortCapIntId OBJECT-TYPE
    SYNTAX       SnmpAdminString
    MAX-ACCESS   read-only
    STATUS       current
    DESCRIPTION
        "Cisco UCS equipment:GemPortCap:intId managed object property"
    ::= { cucsEquipmentGemPortCapEntry 5 }

cucsEquipmentGemPortCapMaxFcSpeed OBJECT-TYPE
    SYNTAX       CucsPortSpeed
    MAX-ACCESS   read-only
    STATUS       current
    DESCRIPTION
        "Cisco UCS equipment:GemPortCap:maxFcSpeed managed
        object property"
    ::= { cucsEquipmentGemPortCapEntry 6 }

cucsEquipmentGemPortCapName OBJECT-TYPE
    SYNTAX       SnmpAdminString
    MAX-ACCESS   read-only
    STATUS       current
    DESCRIPTION
        "Cisco UCS equipment:GemPortCap:name managed object property"
    ::= { cucsEquipmentGemPortCapEntry 7 }

cucsEquipmentGemPortCapPortNumber OBJECT-TYPE
    SYNTAX       Gauge32
    MAX-ACCESS   read-only
    STATUS       current
    DESCRIPTION
        "Cisco UCS equipment:GemPortCap:portNumber managed
        object property"
    ::= { cucsEquipmentGemPortCapEntry 8 }

cucsEquipmentGemPortCapPolicyLevel OBJECT-TYPE
    SYNTAX       Gauge32
    MAX-ACCESS   read-only
    STATUS       current
    DESCRIPTION
        "Cisco UCS equipment:GemPortCap:policyLevel managed
        object property"
    ::= { cucsEquipmentGemPortCapEntry 9 }

cucsEquipmentGemPortCapPolicyOwner OBJECT-TYPE
    SYNTAX       CucsPolicyPolicyOwner
    MAX-ACCESS   read-only
    STATUS       current
    DESCRIPTION
        "Cisco UCS equipment:GemPortCap:policyOwner managed
        object property"
    ::= { cucsEquipmentGemPortCapEntry 10 }

cucsEquipmentHDDFaultMonDefTable OBJECT-TYPE
    SYNTAX           SEQUENCE OF CucsEquipmentHDDFaultMonDefEntry
    MAX-ACCESS       not-accessible
    STATUS           current
    DESCRIPTION
        "Cisco UCS equipment:HDDFaultMonDef managed object table"
    ::= { cucsEquipmentObjects 85 }

cucsEquipmentHDDFaultMonDefEntry OBJECT-TYPE
    SYNTAX           CucsEquipmentHDDFaultMonDefEntry
    MAX-ACCESS       not-accessible
    STATUS           current
    DESCRIPTION
        "Entry for the cucsEquipmentHDDFaultMonDefTable table."
    INDEX { cucsEquipmentHDDFaultMonDefInstanceId }
    ::= { cucsEquipmentHDDFaultMonDefTable 1 }

CucsEquipmentHDDFaultMonDefEntry ::= SEQUENCE {
    cucsEquipmentHDDFaultMonDefInstanceId                            CucsManagedObjectId,
    cucsEquipmentHDDFaultMonDefDn                                    CucsManagedObjectDn,
    cucsEquipmentHDDFaultMonDefRn                                    SnmpAdminString,
    cucsEquipmentHDDFaultMonDefControllerFwVersion                   SnmpAdminString,
    cucsEquipmentHDDFaultMonDefControllerModel                       SnmpAdminString,
    cucsEquipmentHDDFaultMonDefHDDMonSupport                         SnmpAdminString,
    cucsEquipmentHDDFaultMonDefDescr                                 SnmpAdminString,
    cucsEquipmentHDDFaultMonDefIntId                                 SnmpAdminString,
    cucsEquipmentHDDFaultMonDefName                                  SnmpAdminString,
    cucsEquipmentHDDFaultMonDefPolicyLevel                           Gauge32,
    cucsEquipmentHDDFaultMonDefPolicyOwner                           CucsPolicyPolicyOwner
}

cucsEquipmentHDDFaultMonDefInstanceId OBJECT-TYPE
    SYNTAX       CucsManagedObjectId
    MAX-ACCESS   not-accessible
    STATUS       current
    DESCRIPTION
        "Instance identifier of the managed object."
    ::= { cucsEquipmentHDDFaultMonDefEntry 1 }

cucsEquipmentHDDFaultMonDefDn OBJECT-TYPE
    SYNTAX       CucsManagedObjectDn
    MAX-ACCESS   read-only
    STATUS       current
    DESCRIPTION
        "Cisco UCS equipment:HDDFaultMonDef:dn managed object property"
    ::= { cucsEquipmentHDDFaultMonDefEntry 2 }

cucsEquipmentHDDFaultMonDefRn OBJECT-TYPE
    SYNTAX       SnmpAdminString
    MAX-ACCESS   read-only
    STATUS       current
    DESCRIPTION
        "Cisco UCS equipment:HDDFaultMonDef:rn managed object property"
    ::= { cucsEquipmentHDDFaultMonDefEntry 3 }

cucsEquipmentHDDFaultMonDefControllerFwVersion OBJECT-TYPE
    SYNTAX       SnmpAdminString
    MAX-ACCESS   read-only
    STATUS       current
    DESCRIPTION
        "Cisco UCS equipment:HDDFaultMonDef:ControllerFwVersion
        managed object property"
    ::= { cucsEquipmentHDDFaultMonDefEntry 4 }

cucsEquipmentHDDFaultMonDefControllerModel OBJECT-TYPE
    SYNTAX       SnmpAdminString
    MAX-ACCESS   read-only
    STATUS       current
    DESCRIPTION
        "Cisco UCS equipment:HDDFaultMonDef:ControllerModel
        managed object property"
    ::= { cucsEquipmentHDDFaultMonDefEntry 5 }

cucsEquipmentHDDFaultMonDefHDDMonSupport OBJECT-TYPE
    SYNTAX       SnmpAdminString
    MAX-ACCESS   read-only
    STATUS       current
    DESCRIPTION
        "Cisco UCS equipment:HDDFaultMonDef:HDDMonSupport
        managed object property"
    ::= { cucsEquipmentHDDFaultMonDefEntry 6 }

cucsEquipmentHDDFaultMonDefDescr OBJECT-TYPE
    SYNTAX       SnmpAdminString
    MAX-ACCESS   read-only
    STATUS       current
    DESCRIPTION
        "Cisco UCS equipment:HDDFaultMonDef:descr managed object property"
    ::= { cucsEquipmentHDDFaultMonDefEntry 7 }

cucsEquipmentHDDFaultMonDefIntId OBJECT-TYPE
    SYNTAX       SnmpAdminString
    MAX-ACCESS   read-only
    STATUS       current
    DESCRIPTION
        "Cisco UCS equipment:HDDFaultMonDef:intId managed object property"
    ::= { cucsEquipmentHDDFaultMonDefEntry 8 }

cucsEquipmentHDDFaultMonDefName OBJECT-TYPE
    SYNTAX       SnmpAdminString
    MAX-ACCESS   read-only
    STATUS       current
    DESCRIPTION
        "Cisco UCS equipment:HDDFaultMonDef:name managed object property"
    ::= { cucsEquipmentHDDFaultMonDefEntry 9 }

cucsEquipmentHDDFaultMonDefPolicyLevel OBJECT-TYPE
    SYNTAX       Gauge32
    MAX-ACCESS   read-only
    STATUS       current
    DESCRIPTION
        "Cisco UCS equipment:HDDFaultMonDef:policyLevel
        managed object property"
    ::= { cucsEquipmentHDDFaultMonDefEntry 10 }

cucsEquipmentHDDFaultMonDefPolicyOwner OBJECT-TYPE
    SYNTAX       CucsPolicyPolicyOwner
    MAX-ACCESS   read-only
    STATUS       current
    DESCRIPTION
        "Cisco UCS equipment:HDDFaultMonDef:policyOwner
        managed object property"
    ::= { cucsEquipmentHDDFaultMonDefEntry 11 }

cucsEquipmentHealthLedTable OBJECT-TYPE
    SYNTAX           SEQUENCE OF CucsEquipmentHealthLedEntry
    MAX-ACCESS       not-accessible
    STATUS           current
    DESCRIPTION
        "Cisco UCS equipment:HealthLed managed object table"
    ::= { cucsEquipmentObjects 114 }

cucsEquipmentHealthLedEntry OBJECT-TYPE
    SYNTAX           CucsEquipmentHealthLedEntry
    MAX-ACCESS       not-accessible
    STATUS           current
    DESCRIPTION
        "Entry for the cucsEquipmentHealthLedTable table."
    INDEX { cucsEquipmentHealthLedInstanceId }
    ::= { cucsEquipmentHealthLedTable 1 }

CucsEquipmentHealthLedEntry ::= SEQUENCE {
    cucsEquipmentHealthLedInstanceId                                 CucsManagedObjectId,
    cucsEquipmentHealthLedDn                                         CucsManagedObjectDn,
    cucsEquipmentHealthLedRn                                         SnmpAdminString,
    cucsEquipmentHealthLedColor                                      CucsEquipmentLedColor,
    cucsEquipmentHealthLedHealthLedState                             CucsEquipmentHealthLedState,
    cucsEquipmentHealthLedHealthLedStateQualifier                    SnmpAdminString,
    cucsEquipmentHealthLedId                                         Gauge32,
    cucsEquipmentHealthLedName                                       SnmpAdminString,
    cucsEquipmentHealthLedOperState                                  CucsEquipmentLedOperState
}

cucsEquipmentHealthLedInstanceId OBJECT-TYPE
    SYNTAX       CucsManagedObjectId
    MAX-ACCESS   not-accessible
    STATUS       current
    DESCRIPTION
        "Instance identifier of the managed object."
    ::= { cucsEquipmentHealthLedEntry 1 }

cucsEquipmentHealthLedDn OBJECT-TYPE
    SYNTAX       CucsManagedObjectDn
    MAX-ACCESS   read-only
    STATUS       current
    DESCRIPTION
        "Cisco UCS equipment:HealthLed:dn managed object property"
    ::= { cucsEquipmentHealthLedEntry 2 }

cucsEquipmentHealthLedRn OBJECT-TYPE
    SYNTAX       SnmpAdminString
    MAX-ACCESS   read-only
    STATUS       current
    DESCRIPTION
        "Cisco UCS equipment:HealthLed:rn managed object property"
    ::= { cucsEquipmentHealthLedEntry 3 }

cucsEquipmentHealthLedColor OBJECT-TYPE
    SYNTAX       CucsEquipmentLedColor
    MAX-ACCESS   read-only
    STATUS       current
    DESCRIPTION
        "Cisco UCS equipment:HealthLed:color managed object property"
    ::= { cucsEquipmentHealthLedEntry 4 }

cucsEquipmentHealthLedHealthLedState OBJECT-TYPE
    SYNTAX       CucsEquipmentHealthLedState
    MAX-ACCESS   read-only
    STATUS       current
    DESCRIPTION
        "Cisco UCS equipment:HealthLed:healthLedState managed
        object property"
    ::= { cucsEquipmentHealthLedEntry 5 }

cucsEquipmentHealthLedHealthLedStateQualifier OBJECT-TYPE
    SYNTAX       SnmpAdminString
    MAX-ACCESS   read-only
    STATUS       current
    DESCRIPTION
        "Cisco UCS equipment:HealthLed:healthLedStateQualifier
        managed object property"
    ::= { cucsEquipmentHealthLedEntry 6 }

cucsEquipmentHealthLedId OBJECT-TYPE
    SYNTAX       Gauge32
    MAX-ACCESS   read-only
    STATUS       current
    DESCRIPTION
        "Cisco UCS equipment:HealthLed:id managed object property"
    ::= { cucsEquipmentHealthLedEntry 7 }

cucsEquipmentHealthLedName OBJECT-TYPE
    SYNTAX       SnmpAdminString
    MAX-ACCESS   read-only
    STATUS       current
    DESCRIPTION
        "Cisco UCS equipment:HealthLed:name managed object property"
    ::= { cucsEquipmentHealthLedEntry 8 }

cucsEquipmentHealthLedOperState OBJECT-TYPE
    SYNTAX       CucsEquipmentLedOperState
    MAX-ACCESS   read-only
    STATUS       current
    DESCRIPTION
        "Cisco UCS equipment:HealthLed:operState managed object property"
    ::= { cucsEquipmentHealthLedEntry 9 }

cucsEquipmentHostIfCapProviderTable OBJECT-TYPE
    SYNTAX           SEQUENCE OF CucsEquipmentHostIfCapProviderEntry
    MAX-ACCESS       not-accessible
    STATUS           current
    DESCRIPTION
        "Cisco UCS equipment:HostIfCapProvider managed object table"
    ::= { cucsEquipmentObjects 29 }

cucsEquipmentHostIfCapProviderEntry OBJECT-TYPE
    SYNTAX           CucsEquipmentHostIfCapProviderEntry
    MAX-ACCESS       not-accessible
    STATUS           current
    DESCRIPTION
        "Entry for the cucsEquipmentHostIfCapProviderTable table."
    INDEX { cucsEquipmentHostIfCapProviderInstanceId }
    ::= { cucsEquipmentHostIfCapProviderTable 1 }

CucsEquipmentHostIfCapProviderEntry ::= SEQUENCE {
    cucsEquipmentHostIfCapProviderInstanceId                         CucsManagedObjectId,
    cucsEquipmentHostIfCapProviderDn                                 CucsManagedObjectDn,
    cucsEquipmentHostIfCapProviderRn                                 SnmpAdminString,
    cucsEquipmentHostIfCapProviderDeprecated                         TruthValue,
    cucsEquipmentHostIfCapProviderGencount                           Gauge32,
    cucsEquipmentHostIfCapProviderMgmtPlaneVer                       SnmpAdminString,
    cucsEquipmentHostIfCapProviderModel                              SnmpAdminString,
    cucsEquipmentHostIfCapProviderRevision                           SnmpAdminString,
    cucsEquipmentHostIfCapProviderVendor                             SnmpAdminString,
    cucsEquipmentHostIfCapProviderPromCardType                       Gauge32,
    cucsEquipmentHostIfCapProviderDeleted                            TruthValue,
    cucsEquipmentHostIfCapProviderElementLoadFailures                Gauge32,
    cucsEquipmentHostIfCapProviderElementsLoaded                     Gauge32,
    cucsEquipmentHostIfCapProviderLoadErrors                         Gauge32,
    cucsEquipmentHostIfCapProviderLoadWarnings                       Gauge32
}

cucsEquipmentHostIfCapProviderInstanceId OBJECT-TYPE
    SYNTAX       CucsManagedObjectId
    MAX-ACCESS   not-accessible
    STATUS       current
    DESCRIPTION
        "Instance identifier of the managed object."
    ::= { cucsEquipmentHostIfCapProviderEntry 1 }

cucsEquipmentHostIfCapProviderDn OBJECT-TYPE
    SYNTAX       CucsManagedObjectDn
    MAX-ACCESS   read-only
    STATUS       current
    DESCRIPTION
        "Cisco UCS equipment:HostIfCapProvider:dn managed object property"
    ::= { cucsEquipmentHostIfCapProviderEntry 2 }

cucsEquipmentHostIfCapProviderRn OBJECT-TYPE
    SYNTAX       SnmpAdminString
    MAX-ACCESS   read-only
    STATUS       current
    DESCRIPTION
        "Cisco UCS equipment:HostIfCapProvider:rn managed object property"
    ::= { cucsEquipmentHostIfCapProviderEntry 3 }

cucsEquipmentHostIfCapProviderDeprecated OBJECT-TYPE
    SYNTAX       TruthValue
    MAX-ACCESS   read-only
    STATUS       current
    DESCRIPTION
        "Cisco UCS equipment:HostIfCapProvider:deprecated
        managed object property"
    ::= { cucsEquipmentHostIfCapProviderEntry 4 }

cucsEquipmentHostIfCapProviderGencount OBJECT-TYPE
    SYNTAX       Gauge32
    MAX-ACCESS   read-only
    STATUS       current
    DESCRIPTION
        "Cisco UCS equipment:HostIfCapProvider:gencount
        managed object property"
    ::= { cucsEquipmentHostIfCapProviderEntry 5 }

cucsEquipmentHostIfCapProviderMgmtPlaneVer OBJECT-TYPE
    SYNTAX       SnmpAdminString
    MAX-ACCESS   read-only
    STATUS       current
    DESCRIPTION
        "Cisco UCS equipment:HostIfCapProvider:mgmtPlaneVer
        managed object property"
    ::= { cucsEquipmentHostIfCapProviderEntry 6 }

cucsEquipmentHostIfCapProviderModel OBJECT-TYPE
    SYNTAX       SnmpAdminString
    MAX-ACCESS   read-only
    STATUS       current
    DESCRIPTION
        "Cisco UCS equipment:HostIfCapProvider:model managed
        object property"
    ::= { cucsEquipmentHostIfCapProviderEntry 7 }

cucsEquipmentHostIfCapProviderRevision OBJECT-TYPE
    SYNTAX       SnmpAdminString
    MAX-ACCESS   read-only
    STATUS       current
    DESCRIPTION
        "Cisco UCS equipment:HostIfCapProvider:revision
        managed object property"
    ::= { cucsEquipmentHostIfCapProviderEntry 8 }

cucsEquipmentHostIfCapProviderVendor OBJECT-TYPE
    SYNTAX       SnmpAdminString
    MAX-ACCESS   read-only
    STATUS       current
    DESCRIPTION
        "Cisco UCS equipment:HostIfCapProvider:vendor managed
        object property"
    ::= { cucsEquipmentHostIfCapProviderEntry 9 }

cucsEquipmentHostIfCapProviderPromCardType OBJECT-TYPE
    SYNTAX       Gauge32
    MAX-ACCESS   read-only
    STATUS       current
    DESCRIPTION
        "Cisco UCS equipment:HostIfCapProvider:promCardType
        managed object property"
    ::= { cucsEquipmentHostIfCapProviderEntry 10 }

cucsEquipmentHostIfCapProviderDeleted OBJECT-TYPE
    SYNTAX       TruthValue
    MAX-ACCESS   read-only
    STATUS       current
    DESCRIPTION
        "Cisco UCS equipment:HostIfCapProvider:deleted
        managed object property"
    ::= { cucsEquipmentHostIfCapProviderEntry 11 }

cucsEquipmentHostIfCapProviderElementLoadFailures OBJECT-TYPE
    SYNTAX       Gauge32
    MAX-ACCESS   read-only
    STATUS       current
    DESCRIPTION
        "Cisco UCS equipment:HostIfCapProvider:elementLoadFailures
        managed object property"
    ::= { cucsEquipmentHostIfCapProviderEntry 12 }

cucsEquipmentHostIfCapProviderElementsLoaded OBJECT-TYPE
    SYNTAX       Gauge32
    MAX-ACCESS   read-only
    STATUS       current
    DESCRIPTION
        "Cisco UCS equipment:HostIfCapProvider:elementsLoaded
        managed object property"
    ::= { cucsEquipmentHostIfCapProviderEntry 13 }

cucsEquipmentHostIfCapProviderLoadErrors OBJECT-TYPE
    SYNTAX       Gauge32
    MAX-ACCESS   read-only
    STATUS       current
    DESCRIPTION
        "Cisco UCS equipment:HostIfCapProvider:loadErrors
        managed object property"
    ::= { cucsEquipmentHostIfCapProviderEntry 14 }

cucsEquipmentHostIfCapProviderLoadWarnings OBJECT-TYPE
    SYNTAX       Gauge32
    MAX-ACCESS   read-only
    STATUS       current
    DESCRIPTION
        "Cisco UCS equipment:HostIfCapProvider:loadWarnings
        managed object property"
    ::= { cucsEquipmentHostIfCapProviderEntry 15 }

cucsEquipmentIOCardTable OBJECT-TYPE
    SYNTAX           SEQUENCE OF CucsEquipmentIOCardEntry
    MAX-ACCESS       not-accessible
    STATUS           current
    DESCRIPTION
        "Cisco UCS equipment:IOCard managed object table"
    ::= { cucsEquipmentObjects 30 }

cucsEquipmentIOCardEntry OBJECT-TYPE
    SYNTAX           CucsEquipmentIOCardEntry
    MAX-ACCESS       not-accessible
    STATUS           current
    DESCRIPTION
        "Entry for the cucsEquipmentIOCardTable table."
    INDEX { cucsEquipmentIOCardInstanceId }
    ::= { cucsEquipmentIOCardTable 1 }

CucsEquipmentIOCardEntry ::= SEQUENCE {
    cucsEquipmentIOCardInstanceId                                    CucsManagedObjectId,
    cucsEquipmentIOCardDn                                            CucsManagedObjectDn,
    cucsEquipmentIOCardRn                                            SnmpAdminString,
    cucsEquipmentIOCardAdminPowerState                               CucsEquipmentAdminPowerState,
    cucsEquipmentIOCardBaseAddr                                      InetAddressIPv4,
    cucsEquipmentIOCardChassisId                                     Gauge32,
    cucsEquipmentIOCardConfigState                                   CucsEquipmentChassisConfigState,
    cucsEquipmentIOCardDiscovery                                     CucsEquipmentDiscoveryState,
    cucsEquipmentIOCardFltAggr                                       Unsigned64,
    cucsEquipmentIOCardFsmDescr                                      SnmpAdminString,
    cucsEquipmentIOCardFsmPrev                                       SnmpAdminString,
    cucsEquipmentIOCardFsmProgr                                      Gauge32,
    cucsEquipmentIOCardFsmRmtInvErrCode                              Gauge32,
    cucsEquipmentIOCardFsmRmtInvErrDescr                             SnmpAdminString,
    cucsEquipmentIOCardFsmRmtInvRslt                                 CucsConditionRemoteInvRslt,
    cucsEquipmentIOCardFsmStageDescr                                 SnmpAdminString,
    cucsEquipmentIOCardFsmStamp                                      DateAndTime,
    cucsEquipmentIOCardFsmStatus                                     SnmpAdminString,
    cucsEquipmentIOCardFsmTry                                        Gauge32,
    cucsEquipmentIOCardId                                            CucsEquipmentIOCardId,
    cucsEquipmentIOCardLcName                                        SnmpAdminString,
    cucsEquipmentIOCardLcTs                                          DateAndTime,
    cucsEquipmentIOCardModel                                         SnmpAdminString,
    cucsEquipmentIOCardOperQualifier                                 CucsEquipmentIOCardIssues,
    cucsEquipmentIOCardOperState                                     CucsEquipmentOperability,
    cucsEquipmentIOCardOperability                                   CucsEquipmentOperability,
    cucsEquipmentIOCardPeerCommStatus                                CucsEquipmentCommStatus,
    cucsEquipmentIOCardPeerDn                                        SnmpAdminString,
    cucsEquipmentIOCardPerf                                          CucsEquipmentSensorThresholdStatus,
    cucsEquipmentIOCardPower                                         CucsEquipmentPowerState,
    cucsEquipmentIOCardPresence                                      CucsEquipmentPresence,
    cucsEquipmentIOCardRevision                                      SnmpAdminString,
    cucsEquipmentIOCardSerial                                        SnmpAdminString,
    cucsEquipmentIOCardSide                                          CucsNetworkSide,
    cucsEquipmentIOCardSwitchId                                      CucsNetworkSwitchId,
    cucsEquipmentIOCardThermal                                       CucsEquipmentSensorThresholdStatus,
    cucsEquipmentIOCardUpgradeStatus                                 CucsMgmtUpgradeStatus,
    cucsEquipmentIOCardUsrLbl                                        SnmpAdminString,
    cucsEquipmentIOCardVendor                                        SnmpAdminString,
    cucsEquipmentIOCardVoltage                                       CucsEquipmentSensorThresholdStatus,
    cucsEquipmentIOCardFeOfflineTs                                   Unsigned64,
    cucsEquipmentIOCardFeReadyTs                                     Unsigned64,
    cucsEquipmentIOCardMfgTime                                       DateAndTime,
    cucsEquipmentIOCardOperQualifierReason                           SnmpAdminString
}

cucsEquipmentIOCardInstanceId OBJECT-TYPE
    SYNTAX       CucsManagedObjectId
    MAX-ACCESS   not-accessible
    STATUS       current
    DESCRIPTION
        "Instance identifier of the managed object."
    ::= { cucsEquipmentIOCardEntry 1 }

cucsEquipmentIOCardDn OBJECT-TYPE
    SYNTAX       CucsManagedObjectDn
    MAX-ACCESS   read-only
    STATUS       current
    DESCRIPTION
        "Cisco UCS equipment:IOCard:dn managed object property"
    ::= { cucsEquipmentIOCardEntry 2 }

cucsEquipmentIOCardRn OBJECT-TYPE
    SYNTAX       SnmpAdminString
    MAX-ACCESS   read-only
    STATUS       current
    DESCRIPTION
        "Cisco UCS equipment:IOCard:rn managed object property"
    ::= { cucsEquipmentIOCardEntry 3 }

cucsEquipmentIOCardAdminPowerState OBJECT-TYPE
    SYNTAX       CucsEquipmentAdminPowerState
    MAX-ACCESS   read-only
    STATUS       current
    DESCRIPTION
        "Cisco UCS equipment:IOCard:adminPowerState managed
        object property"
    ::= { cucsEquipmentIOCardEntry 4 }

cucsEquipmentIOCardBaseAddr OBJECT-TYPE
    SYNTAX       InetAddressIPv4
    MAX-ACCESS   read-only
    STATUS       current
    DESCRIPTION
        "Cisco UCS equipment:IOCard:baseAddr managed object property"
    ::= { cucsEquipmentIOCardEntry 5 }

cucsEquipmentIOCardChassisId OBJECT-TYPE
    SYNTAX       Gauge32
    MAX-ACCESS   read-only
    STATUS       current
    DESCRIPTION
        "Cisco UCS equipment:IOCard:chassisId managed object property"
    ::= { cucsEquipmentIOCardEntry 6 }

cucsEquipmentIOCardConfigState OBJECT-TYPE
    SYNTAX       CucsEquipmentChassisConfigState
    MAX-ACCESS   read-only
    STATUS       current
    DESCRIPTION
        "Cisco UCS equipment:IOCard:configState managed object property"
    ::= { cucsEquipmentIOCardEntry 7 }

cucsEquipmentIOCardDiscovery OBJECT-TYPE
    SYNTAX       CucsEquipmentDiscoveryState
    MAX-ACCESS   read-only
    STATUS       current
    DESCRIPTION
        "Cisco UCS equipment:IOCard:discovery managed object property"
    ::= { cucsEquipmentIOCardEntry 8 }

cucsEquipmentIOCardFltAggr OBJECT-TYPE
    SYNTAX       Unsigned64
    MAX-ACCESS   read-only
    STATUS       current
    DESCRIPTION
        "Cisco UCS equipment:IOCard:fltAggr managed object property"
    ::= { cucsEquipmentIOCardEntry 9 }

cucsEquipmentIOCardFsmDescr OBJECT-TYPE
    SYNTAX       SnmpAdminString
    MAX-ACCESS   read-only
    STATUS       current
    DESCRIPTION
        "Cisco UCS equipment:IOCard:fsmDescr managed object property"
    ::= { cucsEquipmentIOCardEntry 10 }

cucsEquipmentIOCardFsmPrev OBJECT-TYPE
    SYNTAX       SnmpAdminString
    MAX-ACCESS   read-only
    STATUS       current
    DESCRIPTION
        "Cisco UCS equipment:IOCard:fsmPrev managed object property"
    ::= { cucsEquipmentIOCardEntry 11 }

cucsEquipmentIOCardFsmProgr OBJECT-TYPE
    SYNTAX       Gauge32
    MAX-ACCESS   read-only
    STATUS       current
    DESCRIPTION
        "Cisco UCS equipment:IOCard:fsmProgr managed object property"
    ::= { cucsEquipmentIOCardEntry 12 }

cucsEquipmentIOCardFsmRmtInvErrCode OBJECT-TYPE
    SYNTAX       Gauge32
    MAX-ACCESS   read-only
    STATUS       current
    DESCRIPTION
        "Cisco UCS equipment:IOCard:fsmRmtInvErrCode managed
        object property"
    ::= { cucsEquipmentIOCardEntry 13 }

cucsEquipmentIOCardFsmRmtInvErrDescr OBJECT-TYPE
    SYNTAX       SnmpAdminString
    MAX-ACCESS   read-only
    STATUS       current
    DESCRIPTION
        "Cisco UCS equipment:IOCard:fsmRmtInvErrDescr managed
        object property"
    ::= { cucsEquipmentIOCardEntry 14 }

cucsEquipmentIOCardFsmRmtInvRslt OBJECT-TYPE
    SYNTAX       CucsConditionRemoteInvRslt
    MAX-ACCESS   read-only
    STATUS       current
    DESCRIPTION
        "Cisco UCS equipment:IOCard:fsmRmtInvRslt managed object property"
    ::= { cucsEquipmentIOCardEntry 15 }

cucsEquipmentIOCardFsmStageDescr OBJECT-TYPE
    SYNTAX       SnmpAdminString
    MAX-ACCESS   read-only
    STATUS       current
    DESCRIPTION
        "Cisco UCS equipment:IOCard:fsmStageDescr managed object property"
    ::= { cucsEquipmentIOCardEntry 16 }

cucsEquipmentIOCardFsmStamp OBJECT-TYPE
    SYNTAX       DateAndTime
    MAX-ACCESS   read-only
    STATUS       current
    DESCRIPTION
        "Cisco UCS equipment:IOCard:fsmStamp managed object property"
    ::= { cucsEquipmentIOCardEntry 17 }

cucsEquipmentIOCardFsmStatus OBJECT-TYPE
    SYNTAX       SnmpAdminString
    MAX-ACCESS   read-only
    STATUS       current
    DESCRIPTION
        "Cisco UCS equipment:IOCard:fsmStatus managed object property"
    ::= { cucsEquipmentIOCardEntry 18 }

cucsEquipmentIOCardFsmTry OBJECT-TYPE
    SYNTAX       Gauge32
    MAX-ACCESS   read-only
    STATUS       current
    DESCRIPTION
        "Cisco UCS equipment:IOCard:fsmTry managed object property"
    ::= { cucsEquipmentIOCardEntry 19 }

cucsEquipmentIOCardId OBJECT-TYPE
    SYNTAX       CucsEquipmentIOCardId
    MAX-ACCESS   read-only
    STATUS       current
    DESCRIPTION
        "Cisco UCS equipment:IOCard:id managed object property"
    ::= { cucsEquipmentIOCardEntry 20 }

cucsEquipmentIOCardLcName OBJECT-TYPE
    SYNTAX       SnmpAdminString
    MAX-ACCESS   read-only
    STATUS       current
    DESCRIPTION
        "Cisco UCS equipment:IOCard:lcName managed object property"
    ::= { cucsEquipmentIOCardEntry 21 }

cucsEquipmentIOCardLcTs OBJECT-TYPE
    SYNTAX       DateAndTime
    MAX-ACCESS   read-only
    STATUS       current
    DESCRIPTION
        "Cisco UCS equipment:IOCard:lcTs managed object property"
    ::= { cucsEquipmentIOCardEntry 22 }

cucsEquipmentIOCardModel OBJECT-TYPE
    SYNTAX       SnmpAdminString
    MAX-ACCESS   read-only
    STATUS       current
    DESCRIPTION
        "Cisco UCS equipment:IOCard:model managed object property"
    ::= { cucsEquipmentIOCardEntry 23 }

cucsEquipmentIOCardOperQualifier OBJECT-TYPE
    SYNTAX       CucsEquipmentIOCardIssues
    MAX-ACCESS   read-only
    STATUS       current
    DESCRIPTION
        "Cisco UCS equipment:IOCard:operQualifier managed object property"
    ::= { cucsEquipmentIOCardEntry 24 }

cucsEquipmentIOCardOperState OBJECT-TYPE
    SYNTAX       CucsEquipmentOperability
    MAX-ACCESS   read-only
    STATUS       current
    DESCRIPTION
        "Cisco UCS equipment:IOCard:operState managed object property"
    ::= { cucsEquipmentIOCardEntry 25 }

cucsEquipmentIOCardOperability OBJECT-TYPE
    SYNTAX       CucsEquipmentOperability
    MAX-ACCESS   read-only
    STATUS       current
    DESCRIPTION
        "Cisco UCS equipment:IOCard:operability managed object property"
    ::= { cucsEquipmentIOCardEntry 26 }

cucsEquipmentIOCardPeerCommStatus OBJECT-TYPE
    SYNTAX       CucsEquipmentCommStatus
    MAX-ACCESS   read-only
    STATUS       current
    DESCRIPTION
        "Cisco UCS equipment:IOCard:peerCommStatus managed
        object property"
    ::= { cucsEquipmentIOCardEntry 27 }

cucsEquipmentIOCardPeerDn OBJECT-TYPE
    SYNTAX       SnmpAdminString
    MAX-ACCESS   read-only
    STATUS       current
    DESCRIPTION
        "Cisco UCS equipment:IOCard:peerDn managed object property"
    ::= { cucsEquipmentIOCardEntry 28 }

cucsEquipmentIOCardPerf OBJECT-TYPE
    SYNTAX       CucsEquipmentSensorThresholdStatus
    MAX-ACCESS   read-only
    STATUS       current
    DESCRIPTION
        "Cisco UCS equipment:IOCard:perf managed object property"
    ::= { cucsEquipmentIOCardEntry 29 }

cucsEquipmentIOCardPower OBJECT-TYPE
    SYNTAX       CucsEquipmentPowerState
    MAX-ACCESS   read-only
    STATUS       current
    DESCRIPTION
        "Cisco UCS equipment:IOCard:power managed object property"
    ::= { cucsEquipmentIOCardEntry 30 }

cucsEquipmentIOCardPresence OBJECT-TYPE
    SYNTAX       CucsEquipmentPresence
    MAX-ACCESS   read-only
    STATUS       current
    DESCRIPTION
        "Cisco UCS equipment:IOCard:presence managed object property"
    ::= { cucsEquipmentIOCardEntry 31 }

cucsEquipmentIOCardRevision OBJECT-TYPE
    SYNTAX       SnmpAdminString
    MAX-ACCESS   read-only
    STATUS       current
    DESCRIPTION
        "Cisco UCS equipment:IOCard:revision managed object property"
    ::= { cucsEquipmentIOCardEntry 32 }

cucsEquipmentIOCardSerial OBJECT-TYPE
    SYNTAX       SnmpAdminString
    MAX-ACCESS   read-only
    STATUS       current
    DESCRIPTION
        "Cisco UCS equipment:IOCard:serial managed object property"
    ::= { cucsEquipmentIOCardEntry 33 }

cucsEquipmentIOCardSide OBJECT-TYPE
    SYNTAX       CucsNetworkSide
    MAX-ACCESS   read-only
    STATUS       current
    DESCRIPTION
        "Cisco UCS equipment:IOCard:side managed object property"
    ::= { cucsEquipmentIOCardEntry 34 }

cucsEquipmentIOCardSwitchId OBJECT-TYPE
    SYNTAX       CucsNetworkSwitchId
    MAX-ACCESS   read-only
    STATUS       current
    DESCRIPTION
        "Cisco UCS equipment:IOCard:switchId managed object property"
    ::= { cucsEquipmentIOCardEntry 35 }

cucsEquipmentIOCardThermal OBJECT-TYPE
    SYNTAX       CucsEquipmentSensorThresholdStatus
    MAX-ACCESS   read-only
    STATUS       current
    DESCRIPTION
        "Cisco UCS equipment:IOCard:thermal managed object property"
    ::= { cucsEquipmentIOCardEntry 36 }

cucsEquipmentIOCardUpgradeStatus OBJECT-TYPE
    SYNTAX       CucsMgmtUpgradeStatus
    MAX-ACCESS   read-only
    STATUS       current
    DESCRIPTION
        "Cisco UCS equipment:IOCard:upgradeStatus managed object property"
    ::= { cucsEquipmentIOCardEntry 37 }

cucsEquipmentIOCardUsrLbl OBJECT-TYPE
    SYNTAX       SnmpAdminString
    MAX-ACCESS   read-only
    STATUS       current
    DESCRIPTION
        "Cisco UCS equipment:IOCard:usrLbl managed object property"
    ::= { cucsEquipmentIOCardEntry 38 }

cucsEquipmentIOCardVendor OBJECT-TYPE
    SYNTAX       SnmpAdminString
    MAX-ACCESS   read-only
    STATUS       current
    DESCRIPTION
        "Cisco UCS equipment:IOCard:vendor managed object property"
    ::= { cucsEquipmentIOCardEntry 39 }

cucsEquipmentIOCardVoltage OBJECT-TYPE
    SYNTAX       CucsEquipmentSensorThresholdStatus
    MAX-ACCESS   read-only
    STATUS       current
    DESCRIPTION
        "Cisco UCS equipment:IOCard:voltage managed object property"
    ::= { cucsEquipmentIOCardEntry 40 }

cucsEquipmentIOCardFeOfflineTs OBJECT-TYPE
    SYNTAX       Unsigned64
    MAX-ACCESS   read-only
    STATUS       current
    DESCRIPTION
        "Cisco UCS equipment:IOCard:feOfflineTs managed object property"
    ::= { cucsEquipmentIOCardEntry 41 }

cucsEquipmentIOCardFeReadyTs OBJECT-TYPE
    SYNTAX       Unsigned64
    MAX-ACCESS   read-only
    STATUS       current
    DESCRIPTION
        "Cisco UCS equipment:IOCard:feReadyTs managed object property"
    ::= { cucsEquipmentIOCardEntry 42 }

cucsEquipmentIOCardMfgTime OBJECT-TYPE
    SYNTAX       DateAndTime
    MAX-ACCESS   read-only
    STATUS       current
    DESCRIPTION
        "Cisco UCS equipment:IOCard:mfgTime managed object property"
    ::= { cucsEquipmentIOCardEntry 43 }

cucsEquipmentIOCardOperQualifierReason OBJECT-TYPE
    SYNTAX       SnmpAdminString
    MAX-ACCESS   read-only
    STATUS       current
    DESCRIPTION
        "Cisco UCS equipment:IOCard:operQualifierReason
        managed object property"
    ::= { cucsEquipmentIOCardEntry 44 }

cucsEquipmentIOCardCapProviderTable OBJECT-TYPE
    SYNTAX           SEQUENCE OF CucsEquipmentIOCardCapProviderEntry
    MAX-ACCESS       not-accessible
    STATUS           current
    DESCRIPTION
        "Cisco UCS equipment:IOCardCapProvider managed object table"
    ::= { cucsEquipmentObjects 31 }

cucsEquipmentIOCardCapProviderEntry OBJECT-TYPE
    SYNTAX           CucsEquipmentIOCardCapProviderEntry
    MAX-ACCESS       not-accessible
    STATUS           current
    DESCRIPTION
        "Entry for the cucsEquipmentIOCardCapProviderTable table."
    INDEX { cucsEquipmentIOCardCapProviderInstanceId }
    ::= { cucsEquipmentIOCardCapProviderTable 1 }

CucsEquipmentIOCardCapProviderEntry ::= SEQUENCE {
    cucsEquipmentIOCardCapProviderInstanceId                         CucsManagedObjectId,
    cucsEquipmentIOCardCapProviderDn                                 CucsManagedObjectDn,
    cucsEquipmentIOCardCapProviderRn                                 SnmpAdminString,
    cucsEquipmentIOCardCapProviderDeprecated                         TruthValue,
    cucsEquipmentIOCardCapProviderGencount                           Gauge32,
    cucsEquipmentIOCardCapProviderMgmtPlaneVer                       SnmpAdminString,
    cucsEquipmentIOCardCapProviderModel                              SnmpAdminString,
    cucsEquipmentIOCardCapProviderRevision                           SnmpAdminString,
    cucsEquipmentIOCardCapProviderVendor                             SnmpAdminString,
    cucsEquipmentIOCardCapProviderPromCardType                       Gauge32,
    cucsEquipmentIOCardCapProviderDeleted                            TruthValue,
    cucsEquipmentIOCardCapProviderElementLoadFailures                Gauge32,
    cucsEquipmentIOCardCapProviderElementsLoaded                     Gauge32,
    cucsEquipmentIOCardCapProviderLoadErrors                         Gauge32,
    cucsEquipmentIOCardCapProviderLoadWarnings                       Gauge32
}

cucsEquipmentIOCardCapProviderInstanceId OBJECT-TYPE
    SYNTAX       CucsManagedObjectId
    MAX-ACCESS   not-accessible
    STATUS       current
    DESCRIPTION
        "Instance identifier of the managed object."
    ::= { cucsEquipmentIOCardCapProviderEntry 1 }

cucsEquipmentIOCardCapProviderDn OBJECT-TYPE
    SYNTAX       CucsManagedObjectDn
    MAX-ACCESS   read-only
    STATUS       current
    DESCRIPTION
        "Cisco UCS equipment:IOCardCapProvider:dn managed object property"
    ::= { cucsEquipmentIOCardCapProviderEntry 2 }

cucsEquipmentIOCardCapProviderRn OBJECT-TYPE
    SYNTAX       SnmpAdminString
    MAX-ACCESS   read-only
    STATUS       current
    DESCRIPTION
        "Cisco UCS equipment:IOCardCapProvider:rn managed object property"
    ::= { cucsEquipmentIOCardCapProviderEntry 3 }

cucsEquipmentIOCardCapProviderDeprecated OBJECT-TYPE
    SYNTAX       TruthValue
    MAX-ACCESS   read-only
    STATUS       current
    DESCRIPTION
        "Cisco UCS equipment:IOCardCapProvider:deprecated
        managed object property"
    ::= { cucsEquipmentIOCardCapProviderEntry 4 }

cucsEquipmentIOCardCapProviderGencount OBJECT-TYPE
    SYNTAX       Gauge32
    MAX-ACCESS   read-only
    STATUS       current
    DESCRIPTION
        "Cisco UCS equipment:IOCardCapProvider:gencount
        managed object property"
    ::= { cucsEquipmentIOCardCapProviderEntry 5 }

cucsEquipmentIOCardCapProviderMgmtPlaneVer OBJECT-TYPE
    SYNTAX       SnmpAdminString
    MAX-ACCESS   read-only
    STATUS       current
    DESCRIPTION
        "Cisco UCS equipment:IOCardCapProvider:mgmtPlaneVer
        managed object property"
    ::= { cucsEquipmentIOCardCapProviderEntry 6 }

cucsEquipmentIOCardCapProviderModel OBJECT-TYPE
    SYNTAX       SnmpAdminString
    MAX-ACCESS   read-only
    STATUS       current
    DESCRIPTION
        "Cisco UCS equipment:IOCardCapProvider:model managed
        object property"
    ::= { cucsEquipmentIOCardCapProviderEntry 7 }

cucsEquipmentIOCardCapProviderRevision OBJECT-TYPE
    SYNTAX       SnmpAdminString
    MAX-ACCESS   read-only
    STATUS       current
    DESCRIPTION
        "Cisco UCS equipment:IOCardCapProvider:revision
        managed object property"
    ::= { cucsEquipmentIOCardCapProviderEntry 8 }

cucsEquipmentIOCardCapProviderVendor OBJECT-TYPE
    SYNTAX       SnmpAdminString
    MAX-ACCESS   read-only
    STATUS       current
    DESCRIPTION
        "Cisco UCS equipment:IOCardCapProvider:vendor managed
        object property"
    ::= { cucsEquipmentIOCardCapProviderEntry 9 }

cucsEquipmentIOCardCapProviderPromCardType OBJECT-TYPE
    SYNTAX       Gauge32
    MAX-ACCESS   read-only
    STATUS       current
    DESCRIPTION
        "Cisco UCS equipment:IOCardCapProvider:promCardType
        managed object property"
    ::= { cucsEquipmentIOCardCapProviderEntry 10 }

cucsEquipmentIOCardCapProviderDeleted OBJECT-TYPE
    SYNTAX       TruthValue
    MAX-ACCESS   read-only
    STATUS       current
    DESCRIPTION
        "Cisco UCS equipment:IOCardCapProvider:deleted
        managed object property"
    ::= { cucsEquipmentIOCardCapProviderEntry 11 }

cucsEquipmentIOCardCapProviderElementLoadFailures OBJECT-TYPE
    SYNTAX       Gauge32
    MAX-ACCESS   read-only
    STATUS       current
    DESCRIPTION
        "Cisco UCS equipment:IOCardCapProvider:elementLoadFailures
        managed object property"
    ::= { cucsEquipmentIOCardCapProviderEntry 12 }

cucsEquipmentIOCardCapProviderElementsLoaded OBJECT-TYPE
    SYNTAX       Gauge32
    MAX-ACCESS   read-only
    STATUS       current
    DESCRIPTION
        "Cisco UCS equipment:IOCardCapProvider:elementsLoaded
        managed object property"
    ::= { cucsEquipmentIOCardCapProviderEntry 13 }

cucsEquipmentIOCardCapProviderLoadErrors OBJECT-TYPE
    SYNTAX       Gauge32
    MAX-ACCESS   read-only
    STATUS       current
    DESCRIPTION
        "Cisco UCS equipment:IOCardCapProvider:loadErrors
        managed object property"
    ::= { cucsEquipmentIOCardCapProviderEntry 14 }

cucsEquipmentIOCardCapProviderLoadWarnings OBJECT-TYPE
    SYNTAX       Gauge32
    MAX-ACCESS   read-only
    STATUS       current
    DESCRIPTION
        "Cisco UCS equipment:IOCardCapProvider:loadWarnings
        managed object property"
    ::= { cucsEquipmentIOCardCapProviderEntry 15 }

cucsEquipmentIOCardFsmTable OBJECT-TYPE
    SYNTAX           SEQUENCE OF CucsEquipmentIOCardFsmEntry
    MAX-ACCESS       not-accessible
    STATUS           current
    DESCRIPTION
        "Cisco UCS equipment:IOCardFsm managed object table"
    ::= { cucsEquipmentObjects 109 }

cucsEquipmentIOCardFsmEntry OBJECT-TYPE
    SYNTAX           CucsEquipmentIOCardFsmEntry
    MAX-ACCESS       not-accessible
    STATUS           current
    DESCRIPTION
        "Entry for the cucsEquipmentIOCardFsmTable table."
    INDEX { cucsEquipmentIOCardFsmInstanceId }
    ::= { cucsEquipmentIOCardFsmTable 1 }

CucsEquipmentIOCardFsmEntry ::= SEQUENCE {
    cucsEquipmentIOCardFsmInstanceId                                 CucsManagedObjectId,
    cucsEquipmentIOCardFsmDn                                         CucsManagedObjectDn,
    cucsEquipmentIOCardFsmRn                                         SnmpAdminString,
    cucsEquipmentIOCardFsmCompletionTime                             DateAndTime,
    cucsEquipmentIOCardFsmCurrentFsm                                 CucsEquipmentIOCardFsmCurrentFsm,
    cucsEquipmentIOCardFsmDescr                                      SnmpAdminString,
    cucsEquipmentIOCardFsmFsmStatus                                  CucsFsmFsmStageStatus,
    cucsEquipmentIOCardFsmProgress                                   Gauge32,
    cucsEquipmentIOCardFsmRmtErrCode                                 Gauge32,
    cucsEquipmentIOCardFsmRmtErrDescr                                SnmpAdminString,
    cucsEquipmentIOCardFsmRmtRslt                                    CucsConditionRemoteInvRslt
}

cucsEquipmentIOCardFsmInstanceId OBJECT-TYPE
    SYNTAX       CucsManagedObjectId
    MAX-ACCESS   not-accessible
    STATUS       current
    DESCRIPTION
        "Instance identifier of the managed object."
    ::= { cucsEquipmentIOCardFsmEntry 1 }

cucsEquipmentIOCardFsmDn OBJECT-TYPE
    SYNTAX       CucsManagedObjectDn
    MAX-ACCESS   read-only
    STATUS       current
    DESCRIPTION
        "Cisco UCS equipment:IOCardFsm:dn managed object property"
    ::= { cucsEquipmentIOCardFsmEntry 2 }

cucsEquipmentIOCardFsmRn OBJECT-TYPE
    SYNTAX       SnmpAdminString
    MAX-ACCESS   read-only
    STATUS       current
    DESCRIPTION
        "Cisco UCS equipment:IOCardFsm:rn managed object property"
    ::= { cucsEquipmentIOCardFsmEntry 3 }

cucsEquipmentIOCardFsmCompletionTime OBJECT-TYPE
    SYNTAX       DateAndTime
    MAX-ACCESS   read-only
    STATUS       current
    DESCRIPTION
        "Cisco UCS equipment:IOCardFsm:completionTime managed
        object property"
    ::= { cucsEquipmentIOCardFsmEntry 4 }

cucsEquipmentIOCardFsmCurrentFsm OBJECT-TYPE
    SYNTAX       CucsEquipmentIOCardFsmCurrentFsm
    MAX-ACCESS   read-only
    STATUS       current
    DESCRIPTION
        "Cisco UCS equipment:IOCardFsm:currentFsm managed object property"
    ::= { cucsEquipmentIOCardFsmEntry 5 }

cucsEquipmentIOCardFsmDescr OBJECT-TYPE
    SYNTAX       SnmpAdminString
    MAX-ACCESS   read-only
    STATUS       current
    DESCRIPTION
        "Cisco UCS equipment:IOCardFsm:descr managed object property"
    ::= { cucsEquipmentIOCardFsmEntry 6 }

cucsEquipmentIOCardFsmFsmStatus OBJECT-TYPE
    SYNTAX       CucsFsmFsmStageStatus
    MAX-ACCESS   read-only
    STATUS       current
    DESCRIPTION
        "Cisco UCS equipment:IOCardFsm:fsmStatus managed object property"
    ::= { cucsEquipmentIOCardFsmEntry 7 }

cucsEquipmentIOCardFsmProgress OBJECT-TYPE
    SYNTAX       Gauge32
    MAX-ACCESS   read-only
    STATUS       current
    DESCRIPTION
        "Cisco UCS equipment:IOCardFsm:progress managed object property"
    ::= { cucsEquipmentIOCardFsmEntry 8 }

cucsEquipmentIOCardFsmRmtErrCode OBJECT-TYPE
    SYNTAX       Gauge32
    MAX-ACCESS   read-only
    STATUS       current
    DESCRIPTION
        "Cisco UCS equipment:IOCardFsm:rmtErrCode managed object property"
    ::= { cucsEquipmentIOCardFsmEntry 9 }

cucsEquipmentIOCardFsmRmtErrDescr OBJECT-TYPE
    SYNTAX       SnmpAdminString
    MAX-ACCESS   read-only
    STATUS       current
    DESCRIPTION
        "Cisco UCS equipment:IOCardFsm:rmtErrDescr managed
        object property"
    ::= { cucsEquipmentIOCardFsmEntry 10 }

cucsEquipmentIOCardFsmRmtRslt OBJECT-TYPE
    SYNTAX       CucsConditionRemoteInvRslt
    MAX-ACCESS   read-only
    STATUS       current
    DESCRIPTION
        "Cisco UCS equipment:IOCardFsm:rmtRslt managed object property"
    ::= { cucsEquipmentIOCardFsmEntry 11 }

cucsEquipmentIOCardFsmStageTable OBJECT-TYPE
    SYNTAX           SEQUENCE OF CucsEquipmentIOCardFsmStageEntry
    MAX-ACCESS       not-accessible
    STATUS           current
    DESCRIPTION
        "Cisco UCS equipment:IOCardFsmStage managed object table"
    ::= { cucsEquipmentObjects 110 }

cucsEquipmentIOCardFsmStageEntry OBJECT-TYPE
    SYNTAX           CucsEquipmentIOCardFsmStageEntry
    MAX-ACCESS       not-accessible
    STATUS           current
    DESCRIPTION
        "Entry for the cucsEquipmentIOCardFsmStageTable table."
    INDEX { cucsEquipmentIOCardFsmStageInstanceId }
    ::= { cucsEquipmentIOCardFsmStageTable 1 }

CucsEquipmentIOCardFsmStageEntry ::= SEQUENCE {
    cucsEquipmentIOCardFsmStageInstanceId                            CucsManagedObjectId,
    cucsEquipmentIOCardFsmStageDn                                    CucsManagedObjectDn,
    cucsEquipmentIOCardFsmStageRn                                    SnmpAdminString,
    cucsEquipmentIOCardFsmStageDescr                                 SnmpAdminString,
    cucsEquipmentIOCardFsmStageLastUpdateTime                        DateAndTime,
    cucsEquipmentIOCardFsmStageName                                  CucsEquipmentIOCardFsmStageName,
    cucsEquipmentIOCardFsmStageOrder                                 Gauge32,
    cucsEquipmentIOCardFsmStageRetry                                 Gauge32,
    cucsEquipmentIOCardFsmStageStageStatus                           CucsFsmFsmStageStatus
}

cucsEquipmentIOCardFsmStageInstanceId OBJECT-TYPE
    SYNTAX       CucsManagedObjectId
    MAX-ACCESS   not-accessible
    STATUS       current
    DESCRIPTION
        "Instance identifier of the managed object."
    ::= { cucsEquipmentIOCardFsmStageEntry 1 }

cucsEquipmentIOCardFsmStageDn OBJECT-TYPE
    SYNTAX       CucsManagedObjectDn
    MAX-ACCESS   read-only
    STATUS       current
    DESCRIPTION
        "Cisco UCS equipment:IOCardFsmStage:dn managed object property"
    ::= { cucsEquipmentIOCardFsmStageEntry 2 }

cucsEquipmentIOCardFsmStageRn OBJECT-TYPE
    SYNTAX       SnmpAdminString
    MAX-ACCESS   read-only
    STATUS       current
    DESCRIPTION
        "Cisco UCS equipment:IOCardFsmStage:rn managed object property"
    ::= { cucsEquipmentIOCardFsmStageEntry 3 }

cucsEquipmentIOCardFsmStageDescr OBJECT-TYPE
    SYNTAX       SnmpAdminString
    MAX-ACCESS   read-only
    STATUS       current
    DESCRIPTION
        "Cisco UCS equipment:IOCardFsmStage:descr managed object property"
    ::= { cucsEquipmentIOCardFsmStageEntry 4 }

cucsEquipmentIOCardFsmStageLastUpdateTime OBJECT-TYPE
    SYNTAX       DateAndTime
    MAX-ACCESS   read-only
    STATUS       current
    DESCRIPTION
        "Cisco UCS equipment:IOCardFsmStage:lastUpdateTime
        managed object property"
    ::= { cucsEquipmentIOCardFsmStageEntry 5 }

cucsEquipmentIOCardFsmStageName OBJECT-TYPE
    SYNTAX       CucsEquipmentIOCardFsmStageName
    MAX-ACCESS   read-only
    STATUS       current
    DESCRIPTION
        "Cisco UCS equipment:IOCardFsmStage:name managed object property"
    ::= { cucsEquipmentIOCardFsmStageEntry 6 }

cucsEquipmentIOCardFsmStageOrder OBJECT-TYPE
    SYNTAX       Gauge32
    MAX-ACCESS   read-only
    STATUS       current
    DESCRIPTION
        "Cisco UCS equipment:IOCardFsmStage:order managed object property"
    ::= { cucsEquipmentIOCardFsmStageEntry 7 }

cucsEquipmentIOCardFsmStageRetry OBJECT-TYPE
    SYNTAX       Gauge32
    MAX-ACCESS   read-only
    STATUS       current
    DESCRIPTION
        "Cisco UCS equipment:IOCardFsmStage:retry managed object property"
    ::= { cucsEquipmentIOCardFsmStageEntry 8 }

cucsEquipmentIOCardFsmStageStageStatus OBJECT-TYPE
    SYNTAX       CucsFsmFsmStageStatus
    MAX-ACCESS   read-only
    STATUS       current
    DESCRIPTION
        "Cisco UCS equipment:IOCardFsmStage:stageStatus
        managed object property"
    ::= { cucsEquipmentIOCardFsmStageEntry 9 }

cucsEquipmentIOCardFsmTaskTable OBJECT-TYPE
    SYNTAX           SEQUENCE OF CucsEquipmentIOCardFsmTaskEntry
    MAX-ACCESS       not-accessible
    STATUS           current
    DESCRIPTION
        "Cisco UCS equipment:IOCardFsmTask managed object table"
    ::= { cucsEquipmentObjects 32 }

cucsEquipmentIOCardFsmTaskEntry OBJECT-TYPE
    SYNTAX           CucsEquipmentIOCardFsmTaskEntry
    MAX-ACCESS       not-accessible
    STATUS           current
    DESCRIPTION
        "Entry for the cucsEquipmentIOCardFsmTaskTable table."
    INDEX { cucsEquipmentIOCardFsmTaskInstanceId }
    ::= { cucsEquipmentIOCardFsmTaskTable 1 }

CucsEquipmentIOCardFsmTaskEntry ::= SEQUENCE {
    cucsEquipmentIOCardFsmTaskInstanceId                             CucsManagedObjectId,
    cucsEquipmentIOCardFsmTaskDn                                     CucsManagedObjectDn,
    cucsEquipmentIOCardFsmTaskRn                                     SnmpAdminString,
    cucsEquipmentIOCardFsmTaskCompletion                             CucsFsmCompletion,
    cucsEquipmentIOCardFsmTaskFlags                                  CucsFsmFlags,
    cucsEquipmentIOCardFsmTaskItem                                   CucsEquipmentIOCardFsmTaskItem,
    cucsEquipmentIOCardFsmTaskSeqId                                  Gauge32
}

cucsEquipmentIOCardFsmTaskInstanceId OBJECT-TYPE
    SYNTAX       CucsManagedObjectId
    MAX-ACCESS   not-accessible
    STATUS       current
    DESCRIPTION
        "Instance identifier of the managed object."
    ::= { cucsEquipmentIOCardFsmTaskEntry 1 }

cucsEquipmentIOCardFsmTaskDn OBJECT-TYPE
    SYNTAX       CucsManagedObjectDn
    MAX-ACCESS   read-only
    STATUS       current
    DESCRIPTION
        "Cisco UCS equipment:IOCardFsmTask:dn managed object property"
    ::= { cucsEquipmentIOCardFsmTaskEntry 2 }

cucsEquipmentIOCardFsmTaskRn OBJECT-TYPE
    SYNTAX       SnmpAdminString
    MAX-ACCESS   read-only
    STATUS       current
    DESCRIPTION
        "Cisco UCS equipment:IOCardFsmTask:rn managed object property"
    ::= { cucsEquipmentIOCardFsmTaskEntry 3 }

cucsEquipmentIOCardFsmTaskCompletion OBJECT-TYPE
    SYNTAX       CucsFsmCompletion
    MAX-ACCESS   read-only
    STATUS       current
    DESCRIPTION
        "Cisco UCS equipment:IOCardFsmTask:completion managed
        object property"
    ::= { cucsEquipmentIOCardFsmTaskEntry 4 }

cucsEquipmentIOCardFsmTaskFlags OBJECT-TYPE
    SYNTAX       CucsFsmFlags
    MAX-ACCESS   read-only
    STATUS       current
    DESCRIPTION
        "Cisco UCS equipment:IOCardFsmTask:flags managed object property"
    ::= { cucsEquipmentIOCardFsmTaskEntry 5 }

cucsEquipmentIOCardFsmTaskItem OBJECT-TYPE
    SYNTAX       CucsEquipmentIOCardFsmTaskItem
    MAX-ACCESS   read-only
    STATUS       current
    DESCRIPTION
        "Cisco UCS equipment:IOCardFsmTask:item managed object property"
    ::= { cucsEquipmentIOCardFsmTaskEntry 6 }

cucsEquipmentIOCardFsmTaskSeqId OBJECT-TYPE
    SYNTAX       Gauge32
    MAX-ACCESS   read-only
    STATUS       current
    DESCRIPTION
        "Cisco UCS equipment:IOCardFsmTask:seqId managed object property"
    ::= { cucsEquipmentIOCardFsmTaskEntry 7 }

cucsEquipmentIOCardStatsTable OBJECT-TYPE
    SYNTAX           SEQUENCE OF CucsEquipmentIOCardStatsEntry
    MAX-ACCESS       not-accessible
    STATUS           current
    DESCRIPTION
        "Cisco UCS equipment:IOCardStats managed object table"
    ::= { cucsEquipmentObjects 33 }

cucsEquipmentIOCardStatsEntry OBJECT-TYPE
    SYNTAX           CucsEquipmentIOCardStatsEntry
    MAX-ACCESS       not-accessible
    STATUS           current
    DESCRIPTION
        "Entry for the cucsEquipmentIOCardStatsTable table."
    INDEX { cucsEquipmentIOCardStatsInstanceId }
    ::= { cucsEquipmentIOCardStatsTable 1 }

CucsEquipmentIOCardStatsEntry ::= SEQUENCE {
    cucsEquipmentIOCardStatsInstanceId                               CucsManagedObjectId,
    cucsEquipmentIOCardStatsDn                                       CucsManagedObjectDn,
    cucsEquipmentIOCardStatsRn                                       SnmpAdminString,
    cucsEquipmentIOCardStatsAmbientTemp                              INTEGER,
    cucsEquipmentIOCardStatsAmbientTempAvg                           INTEGER,
    cucsEquipmentIOCardStatsAmbientTempMax                           INTEGER,
    cucsEquipmentIOCardStatsAmbientTempMin                           INTEGER,
    cucsEquipmentIOCardStatsIntervals                                Gauge32,
    cucsEquipmentIOCardStatsSuspect                                  TruthValue,
    cucsEquipmentIOCardStatsTemp                                     INTEGER,
    cucsEquipmentIOCardStatsTempAvg                                  INTEGER,
    cucsEquipmentIOCardStatsTempMax                                  INTEGER,
    cucsEquipmentIOCardStatsTempMin                                  INTEGER,
    cucsEquipmentIOCardStatsThresholded                              CucsEquipmentIOCardStatsThresholded,
    cucsEquipmentIOCardStatsTimeCollected                            DateAndTime,
    cucsEquipmentIOCardStatsUpdate                                   Gauge32
}

cucsEquipmentIOCardStatsInstanceId OBJECT-TYPE
    SYNTAX       CucsManagedObjectId
    MAX-ACCESS   not-accessible
    STATUS       current
    DESCRIPTION
        "Instance identifier of the managed object."
    ::= { cucsEquipmentIOCardStatsEntry 1 }

cucsEquipmentIOCardStatsDn OBJECT-TYPE
    SYNTAX       CucsManagedObjectDn
    MAX-ACCESS   read-only
    STATUS       current
    DESCRIPTION
        "Cisco UCS equipment:IOCardStats:dn managed object property"
    ::= { cucsEquipmentIOCardStatsEntry 2 }

cucsEquipmentIOCardStatsRn OBJECT-TYPE
    SYNTAX       SnmpAdminString
    MAX-ACCESS   read-only
    STATUS       current
    DESCRIPTION
        "Cisco UCS equipment:IOCardStats:rn managed object property"
    ::= { cucsEquipmentIOCardStatsEntry 3 }

cucsEquipmentIOCardStatsAmbientTemp OBJECT-TYPE
    SYNTAX       INTEGER
    MAX-ACCESS   read-only
    STATUS       current
    DESCRIPTION
        "Cisco UCS equipment:IOCardStats:ambientTemp managed
        object property"
    ::= { cucsEquipmentIOCardStatsEntry 4 }

cucsEquipmentIOCardStatsAmbientTempAvg OBJECT-TYPE
    SYNTAX       INTEGER
    MAX-ACCESS   read-only
    STATUS       current
    DESCRIPTION
        "Cisco UCS equipment:IOCardStats:ambientTempAvg
        managed object property"
    ::= { cucsEquipmentIOCardStatsEntry 5 }

cucsEquipmentIOCardStatsAmbientTempMax OBJECT-TYPE
    SYNTAX       INTEGER
    MAX-ACCESS   read-only
    STATUS       current
    DESCRIPTION
        "Cisco UCS equipment:IOCardStats:ambientTempMax
        managed object property"
    ::= { cucsEquipmentIOCardStatsEntry 6 }

cucsEquipmentIOCardStatsAmbientTempMin OBJECT-TYPE
    SYNTAX       INTEGER
    MAX-ACCESS   read-only
    STATUS       current
    DESCRIPTION
        "Cisco UCS equipment:IOCardStats:ambientTempMin
        managed object property"
    ::= { cucsEquipmentIOCardStatsEntry 7 }

cucsEquipmentIOCardStatsIntervals OBJECT-TYPE
    SYNTAX       Gauge32
    MAX-ACCESS   read-only
    STATUS       current
    DESCRIPTION
        "Cisco UCS equipment:IOCardStats:intervals managed
        object property"
    ::= { cucsEquipmentIOCardStatsEntry 8 }

cucsEquipmentIOCardStatsSuspect OBJECT-TYPE
    SYNTAX       TruthValue
    MAX-ACCESS   read-only
    STATUS       current
    DESCRIPTION
        "Cisco UCS equipment:IOCardStats:suspect managed object property"
    ::= { cucsEquipmentIOCardStatsEntry 9 }

cucsEquipmentIOCardStatsTemp OBJECT-TYPE
    SYNTAX       INTEGER
    MAX-ACCESS   read-only
    STATUS       current
    DESCRIPTION
        "Cisco UCS equipment:IOCardStats:temp managed object property"
    ::= { cucsEquipmentIOCardStatsEntry 10 }

cucsEquipmentIOCardStatsTempAvg OBJECT-TYPE
    SYNTAX       INTEGER
    MAX-ACCESS   read-only
    STATUS       current
    DESCRIPTION
        "Cisco UCS equipment:IOCardStats:tempAvg managed object property"
    ::= { cucsEquipmentIOCardStatsEntry 11 }

cucsEquipmentIOCardStatsTempMax OBJECT-TYPE
    SYNTAX       INTEGER
    MAX-ACCESS   read-only
    STATUS       current
    DESCRIPTION
        "Cisco UCS equipment:IOCardStats:tempMax managed object property"
    ::= { cucsEquipmentIOCardStatsEntry 12 }

cucsEquipmentIOCardStatsTempMin OBJECT-TYPE
    SYNTAX       INTEGER
    MAX-ACCESS   read-only
    STATUS       current
    DESCRIPTION
        "Cisco UCS equipment:IOCardStats:tempMin managed object property"
    ::= { cucsEquipmentIOCardStatsEntry 13 }

cucsEquipmentIOCardStatsThresholded OBJECT-TYPE
    SYNTAX       CucsEquipmentIOCardStatsThresholded
    MAX-ACCESS   read-only
    STATUS       current
    DESCRIPTION
        "Cisco UCS equipment:IOCardStats:thresholded managed
        object property"
    ::= { cucsEquipmentIOCardStatsEntry 14 }

cucsEquipmentIOCardStatsTimeCollected OBJECT-TYPE
    SYNTAX       DateAndTime
    MAX-ACCESS   read-only
    STATUS       current
    DESCRIPTION
        "Cisco UCS equipment:IOCardStats:timeCollected
        managed object property"
    ::= { cucsEquipmentIOCardStatsEntry 15 }

cucsEquipmentIOCardStatsUpdate OBJECT-TYPE
    SYNTAX       Gauge32
    MAX-ACCESS   read-only
    STATUS       current
    DESCRIPTION
        "Cisco UCS equipment:IOCardStats:update managed object property"
    ::= { cucsEquipmentIOCardStatsEntry 16 }

cucsEquipmentIOCardStatsHistTable OBJECT-TYPE
    SYNTAX           SEQUENCE OF CucsEquipmentIOCardStatsHistEntry
    MAX-ACCESS       not-accessible
    STATUS           current
    DESCRIPTION
        "Cisco UCS equipment:IOCardStatsHist managed object table"
    ::= { cucsEquipmentObjects 34 }

cucsEquipmentIOCardStatsHistEntry OBJECT-TYPE
    SYNTAX           CucsEquipmentIOCardStatsHistEntry
    MAX-ACCESS       not-accessible
    STATUS           current
    DESCRIPTION
        "Entry for the cucsEquipmentIOCardStatsHistTable table."
    INDEX { cucsEquipmentIOCardStatsHistInstanceId }
    ::= { cucsEquipmentIOCardStatsHistTable 1 }

CucsEquipmentIOCardStatsHistEntry ::= SEQUENCE {
    cucsEquipmentIOCardStatsHistInstanceId                           CucsManagedObjectId,
    cucsEquipmentIOCardStatsHistDn                                   CucsManagedObjectDn,
    cucsEquipmentIOCardStatsHistRn                                   SnmpAdminString,
    cucsEquipmentIOCardStatsHistAmbientTemp                          INTEGER,
    cucsEquipmentIOCardStatsHistAmbientTempAvg                       INTEGER,
    cucsEquipmentIOCardStatsHistAmbientTempMax                       INTEGER,
    cucsEquipmentIOCardStatsHistAmbientTempMin                       INTEGER,
    cucsEquipmentIOCardStatsHistId                                   Unsigned64,
    cucsEquipmentIOCardStatsHistMostRecent                           TruthValue,
    cucsEquipmentIOCardStatsHistSuspect                              TruthValue,
    cucsEquipmentIOCardStatsHistTemp                                 INTEGER,
    cucsEquipmentIOCardStatsHistTempAvg                              INTEGER,
    cucsEquipmentIOCardStatsHistTempMax                              INTEGER,
    cucsEquipmentIOCardStatsHistTempMin                              INTEGER,
    cucsEquipmentIOCardStatsHistThresholded                          CucsEquipmentIOCardStatsHistThresholded,
    cucsEquipmentIOCardStatsHistTimeCollected                        DateAndTime
}

cucsEquipmentIOCardStatsHistInstanceId OBJECT-TYPE
    SYNTAX       CucsManagedObjectId
    MAX-ACCESS   not-accessible
    STATUS       current
    DESCRIPTION
        "Instance identifier of the managed object."
    ::= { cucsEquipmentIOCardStatsHistEntry 1 }

cucsEquipmentIOCardStatsHistDn OBJECT-TYPE
    SYNTAX       CucsManagedObjectDn
    MAX-ACCESS   read-only
    STATUS       current
    DESCRIPTION
        "Cisco UCS equipment:IOCardStatsHist:dn managed object property"
    ::= { cucsEquipmentIOCardStatsHistEntry 2 }

cucsEquipmentIOCardStatsHistRn OBJECT-TYPE
    SYNTAX       SnmpAdminString
    MAX-ACCESS   read-only
    STATUS       current
    DESCRIPTION
        "Cisco UCS equipment:IOCardStatsHist:rn managed object property"
    ::= { cucsEquipmentIOCardStatsHistEntry 3 }

cucsEquipmentIOCardStatsHistAmbientTemp OBJECT-TYPE
    SYNTAX       INTEGER
    MAX-ACCESS   read-only
    STATUS       current
    DESCRIPTION
        "Cisco UCS equipment:IOCardStatsHist:ambientTemp
        managed object property"
    ::= { cucsEquipmentIOCardStatsHistEntry 4 }

cucsEquipmentIOCardStatsHistAmbientTempAvg OBJECT-TYPE
    SYNTAX       INTEGER
    MAX-ACCESS   read-only
    STATUS       current
    DESCRIPTION
        "Cisco UCS equipment:IOCardStatsHist:ambientTempAvg
        managed object property"
    ::= { cucsEquipmentIOCardStatsHistEntry 5 }

cucsEquipmentIOCardStatsHistAmbientTempMax OBJECT-TYPE
    SYNTAX       INTEGER
    MAX-ACCESS   read-only
    STATUS       current
    DESCRIPTION
        "Cisco UCS equipment:IOCardStatsHist:ambientTempMax
        managed object property"
    ::= { cucsEquipmentIOCardStatsHistEntry 6 }

cucsEquipmentIOCardStatsHistAmbientTempMin OBJECT-TYPE
    SYNTAX       INTEGER
    MAX-ACCESS   read-only
    STATUS       current
    DESCRIPTION
        "Cisco UCS equipment:IOCardStatsHist:ambientTempMin
        managed object property"
    ::= { cucsEquipmentIOCardStatsHistEntry 7 }

cucsEquipmentIOCardStatsHistId OBJECT-TYPE
    SYNTAX       Unsigned64
    MAX-ACCESS   read-only
    STATUS       current
    DESCRIPTION
        "Cisco UCS equipment:IOCardStatsHist:id managed object property"
    ::= { cucsEquipmentIOCardStatsHistEntry 8 }

cucsEquipmentIOCardStatsHistMostRecent OBJECT-TYPE
    SYNTAX       TruthValue
    MAX-ACCESS   read-only
    STATUS       current
    DESCRIPTION
        "Cisco UCS equipment:IOCardStatsHist:mostRecent
        managed object property"
    ::= { cucsEquipmentIOCardStatsHistEntry 9 }

cucsEquipmentIOCardStatsHistSuspect OBJECT-TYPE
    SYNTAX       TruthValue
    MAX-ACCESS   read-only
    STATUS       current
    DESCRIPTION
        "Cisco UCS equipment:IOCardStatsHist:suspect managed
        object property"
    ::= { cucsEquipmentIOCardStatsHistEntry 10 }

cucsEquipmentIOCardStatsHistTemp OBJECT-TYPE
    SYNTAX       INTEGER
    MAX-ACCESS   read-only
    STATUS       current
    DESCRIPTION
        "Cisco UCS equipment:IOCardStatsHist:temp managed object property"
    ::= { cucsEquipmentIOCardStatsHistEntry 11 }

cucsEquipmentIOCardStatsHistTempAvg OBJECT-TYPE
    SYNTAX       INTEGER
    MAX-ACCESS   read-only
    STATUS       current
    DESCRIPTION
        "Cisco UCS equipment:IOCardStatsHist:tempAvg managed
        object property"
    ::= { cucsEquipmentIOCardStatsHistEntry 12 }

cucsEquipmentIOCardStatsHistTempMax OBJECT-TYPE
    SYNTAX       INTEGER
    MAX-ACCESS   read-only
    STATUS       current
    DESCRIPTION
        "Cisco UCS equipment:IOCardStatsHist:tempMax managed
        object property"
    ::= { cucsEquipmentIOCardStatsHistEntry 13 }

cucsEquipmentIOCardStatsHistTempMin OBJECT-TYPE
    SYNTAX       INTEGER
    MAX-ACCESS   read-only
    STATUS       current
    DESCRIPTION
        "Cisco UCS equipment:IOCardStatsHist:tempMin managed
        object property"
    ::= { cucsEquipmentIOCardStatsHistEntry 14 }

cucsEquipmentIOCardStatsHistThresholded OBJECT-TYPE
    SYNTAX       CucsEquipmentIOCardStatsHistThresholded
    MAX-ACCESS   read-only
    STATUS       current
    DESCRIPTION
        "Cisco UCS equipment:IOCardStatsHist:thresholded
        managed object property"
    ::= { cucsEquipmentIOCardStatsHistEntry 15 }

cucsEquipmentIOCardStatsHistTimeCollected OBJECT-TYPE
    SYNTAX       DateAndTime
    MAX-ACCESS   read-only
    STATUS       current
    DESCRIPTION
        "Cisco UCS equipment:IOCardStatsHist:timeCollected
        managed object property"
    ::= { cucsEquipmentIOCardStatsHistEntry 16 }

cucsEquipmentIOCardTypeDefTable OBJECT-TYPE
    SYNTAX           SEQUENCE OF CucsEquipmentIOCardTypeDefEntry
    MAX-ACCESS       not-accessible
    STATUS           current
    DESCRIPTION
        "Cisco UCS equipment:IOCardTypeDef managed object table"
    ::= { cucsEquipmentObjects 101 }

cucsEquipmentIOCardTypeDefEntry OBJECT-TYPE
    SYNTAX           CucsEquipmentIOCardTypeDefEntry
    MAX-ACCESS       not-accessible
    STATUS           current
    DESCRIPTION
        "Entry for the cucsEquipmentIOCardTypeDefTable table."
    INDEX { cucsEquipmentIOCardTypeDefInstanceId }
    ::= { cucsEquipmentIOCardTypeDefTable 1 }

CucsEquipmentIOCardTypeDefEntry ::= SEQUENCE {
    cucsEquipmentIOCardTypeDefInstanceId                             CucsManagedObjectId,
    cucsEquipmentIOCardTypeDefDn                                     CucsManagedObjectDn,
    cucsEquipmentIOCardTypeDefRn                                     SnmpAdminString,
    cucsEquipmentIOCardTypeDefDescr                                  SnmpAdminString,
    cucsEquipmentIOCardTypeDefIntId                                  SnmpAdminString,
    cucsEquipmentIOCardTypeDefName                                   SnmpAdminString,
    cucsEquipmentIOCardTypeDefType                                   SnmpAdminString,
    cucsEquipmentIOCardTypeDefPolicyLevel                            Gauge32,
    cucsEquipmentIOCardTypeDefPolicyOwner                            CucsPolicyPolicyOwner
}

cucsEquipmentIOCardTypeDefInstanceId OBJECT-TYPE
    SYNTAX       CucsManagedObjectId
    MAX-ACCESS   not-accessible
    STATUS       current
    DESCRIPTION
        "Instance identifier of the managed object."
    ::= { cucsEquipmentIOCardTypeDefEntry 1 }

cucsEquipmentIOCardTypeDefDn OBJECT-TYPE
    SYNTAX       CucsManagedObjectDn
    MAX-ACCESS   read-only
    STATUS       current
    DESCRIPTION
        "Cisco UCS equipment:IOCardTypeDef:dn managed object property"
    ::= { cucsEquipmentIOCardTypeDefEntry 2 }

cucsEquipmentIOCardTypeDefRn OBJECT-TYPE
    SYNTAX       SnmpAdminString
    MAX-ACCESS   read-only
    STATUS       current
    DESCRIPTION
        "Cisco UCS equipment:IOCardTypeDef:rn managed object property"
    ::= { cucsEquipmentIOCardTypeDefEntry 3 }

cucsEquipmentIOCardTypeDefDescr OBJECT-TYPE
    SYNTAX       SnmpAdminString
    MAX-ACCESS   read-only
    STATUS       current
    DESCRIPTION
        "Cisco UCS equipment:IOCardTypeDef:descr managed object property"
    ::= { cucsEquipmentIOCardTypeDefEntry 4 }

cucsEquipmentIOCardTypeDefIntId OBJECT-TYPE
    SYNTAX       SnmpAdminString
    MAX-ACCESS   read-only
    STATUS       current
    DESCRIPTION
        "Cisco UCS equipment:IOCardTypeDef:intId managed object property"
    ::= { cucsEquipmentIOCardTypeDefEntry 5 }

cucsEquipmentIOCardTypeDefName OBJECT-TYPE
    SYNTAX       SnmpAdminString
    MAX-ACCESS   read-only
    STATUS       current
    DESCRIPTION
        "Cisco UCS equipment:IOCardTypeDef:name managed object property"
    ::= { cucsEquipmentIOCardTypeDefEntry 6 }

cucsEquipmentIOCardTypeDefType OBJECT-TYPE
    SYNTAX       SnmpAdminString
    MAX-ACCESS   read-only
    STATUS       current
    DESCRIPTION
        "Cisco UCS equipment:IOCardTypeDef:type managed object property"
    ::= { cucsEquipmentIOCardTypeDefEntry 7 }

cucsEquipmentIOCardTypeDefPolicyLevel OBJECT-TYPE
    SYNTAX       Gauge32
    MAX-ACCESS   read-only
    STATUS       current
    DESCRIPTION
        "Cisco UCS equipment:IOCardTypeDef:policyLevel
        managed object property"
    ::= { cucsEquipmentIOCardTypeDefEntry 8 }

cucsEquipmentIOCardTypeDefPolicyOwner OBJECT-TYPE
    SYNTAX       CucsPolicyPolicyOwner
    MAX-ACCESS   read-only
    STATUS       current
    DESCRIPTION
        "Cisco UCS equipment:IOCardTypeDef:policyOwner
        managed object property"
    ::= { cucsEquipmentIOCardTypeDefEntry 9 }

cucsEquipmentIndicatorLedTable OBJECT-TYPE
    SYNTAX           SEQUENCE OF CucsEquipmentIndicatorLedEntry
    MAX-ACCESS       not-accessible
    STATUS           current
    DESCRIPTION
        "Cisco UCS equipment:IndicatorLed managed object table"
    ::= { cucsEquipmentObjects 35 }

cucsEquipmentIndicatorLedEntry OBJECT-TYPE
    SYNTAX           CucsEquipmentIndicatorLedEntry
    MAX-ACCESS       not-accessible
    STATUS           current
    DESCRIPTION
        "Entry for the cucsEquipmentIndicatorLedTable table."
    INDEX { cucsEquipmentIndicatorLedInstanceId }
    ::= { cucsEquipmentIndicatorLedTable 1 }

CucsEquipmentIndicatorLedEntry ::= SEQUENCE {
    cucsEquipmentIndicatorLedInstanceId                              CucsManagedObjectId,
    cucsEquipmentIndicatorLedDn                                      CucsManagedObjectDn,
    cucsEquipmentIndicatorLedRn                                      SnmpAdminString,
    cucsEquipmentIndicatorLedColor                                   CucsEquipmentLedColor,
    cucsEquipmentIndicatorLedId                                      Gauge32,
    cucsEquipmentIndicatorLedName                                    SnmpAdminString,
    cucsEquipmentIndicatorLedOperState                               CucsEquipmentLedOperState
}

cucsEquipmentIndicatorLedInstanceId OBJECT-TYPE
    SYNTAX       CucsManagedObjectId
    MAX-ACCESS   not-accessible
    STATUS       current
    DESCRIPTION
        "Instance identifier of the managed object."
    ::= { cucsEquipmentIndicatorLedEntry 1 }

cucsEquipmentIndicatorLedDn OBJECT-TYPE
    SYNTAX       CucsManagedObjectDn
    MAX-ACCESS   read-only
    STATUS       current
    DESCRIPTION
        "Cisco UCS equipment:IndicatorLed:dn managed object property"
    ::= { cucsEquipmentIndicatorLedEntry 2 }

cucsEquipmentIndicatorLedRn OBJECT-TYPE
    SYNTAX       SnmpAdminString
    MAX-ACCESS   read-only
    STATUS       current
    DESCRIPTION
        "Cisco UCS equipment:IndicatorLed:rn managed object property"
    ::= { cucsEquipmentIndicatorLedEntry 3 }

cucsEquipmentIndicatorLedColor OBJECT-TYPE
    SYNTAX       CucsEquipmentLedColor
    MAX-ACCESS   read-only
    STATUS       current
    DESCRIPTION
        "Cisco UCS equipment:IndicatorLed:color managed object property"
    ::= { cucsEquipmentIndicatorLedEntry 4 }

cucsEquipmentIndicatorLedId OBJECT-TYPE
    SYNTAX       Gauge32
    MAX-ACCESS   read-only
    STATUS       current
    DESCRIPTION
        "Cisco UCS equipment:IndicatorLed:id managed object property"
    ::= { cucsEquipmentIndicatorLedEntry 5 }

cucsEquipmentIndicatorLedName OBJECT-TYPE
    SYNTAX       SnmpAdminString
    MAX-ACCESS   read-only
    STATUS       current
    DESCRIPTION
        "Cisco UCS equipment:IndicatorLed:name managed object property"
    ::= { cucsEquipmentIndicatorLedEntry 6 }

cucsEquipmentIndicatorLedOperState OBJECT-TYPE
    SYNTAX       CucsEquipmentLedOperState
    MAX-ACCESS   read-only
    STATUS       current
    DESCRIPTION
        "Cisco UCS equipment:IndicatorLed:operState managed
        object property"
    ::= { cucsEquipmentIndicatorLedEntry 7 }

cucsEquipmentLocalDiskCapProviderTable OBJECT-TYPE
    SYNTAX           SEQUENCE OF CucsEquipmentLocalDiskCapProviderEntry
    MAX-ACCESS       not-accessible
    STATUS           current
    DESCRIPTION
        "Cisco UCS equipment:LocalDiskCapProvider managed object table"
    ::= { cucsEquipmentObjects 36 }

cucsEquipmentLocalDiskCapProviderEntry OBJECT-TYPE
    SYNTAX           CucsEquipmentLocalDiskCapProviderEntry
    MAX-ACCESS       not-accessible
    STATUS           current
    DESCRIPTION
        "Entry for the cucsEquipmentLocalDiskCapProviderTable table."
    INDEX { cucsEquipmentLocalDiskCapProviderInstanceId }
    ::= { cucsEquipmentLocalDiskCapProviderTable 1 }

CucsEquipmentLocalDiskCapProviderEntry ::= SEQUENCE {
    cucsEquipmentLocalDiskCapProviderInstanceId                      CucsManagedObjectId,
    cucsEquipmentLocalDiskCapProviderDn                              CucsManagedObjectDn,
    cucsEquipmentLocalDiskCapProviderRn                              SnmpAdminString,
    cucsEquipmentLocalDiskCapProviderDeprecated                      TruthValue,
    cucsEquipmentLocalDiskCapProviderGencount                        Gauge32,
    cucsEquipmentLocalDiskCapProviderMgmtPlaneVer                    SnmpAdminString,
    cucsEquipmentLocalDiskCapProviderModel                           SnmpAdminString,
    cucsEquipmentLocalDiskCapProviderRevision                        SnmpAdminString,
    cucsEquipmentLocalDiskCapProviderVendor                          SnmpAdminString,
    cucsEquipmentLocalDiskCapProviderPromCardType                    Gauge32,
    cucsEquipmentLocalDiskCapProviderDeleted                         TruthValue,
    cucsEquipmentLocalDiskCapProviderElementLoadFailures             Gauge32,
    cucsEquipmentLocalDiskCapProviderElementsLoaded                  Gauge32,
    cucsEquipmentLocalDiskCapProviderLoadErrors                      Gauge32,
    cucsEquipmentLocalDiskCapProviderLoadWarnings                    Gauge32
}

cucsEquipmentLocalDiskCapProviderInstanceId OBJECT-TYPE
    SYNTAX       CucsManagedObjectId
    MAX-ACCESS   not-accessible
    STATUS       current
    DESCRIPTION
        "Instance identifier of the managed object."
    ::= { cucsEquipmentLocalDiskCapProviderEntry 1 }

cucsEquipmentLocalDiskCapProviderDn OBJECT-TYPE
    SYNTAX       CucsManagedObjectDn
    MAX-ACCESS   read-only
    STATUS       current
    DESCRIPTION
        "Cisco UCS equipment:LocalDiskCapProvider:dn managed
        object property"
    ::= { cucsEquipmentLocalDiskCapProviderEntry 2 }

cucsEquipmentLocalDiskCapProviderRn OBJECT-TYPE
    SYNTAX       SnmpAdminString
    MAX-ACCESS   read-only
    STATUS       current
    DESCRIPTION
        "Cisco UCS equipment:LocalDiskCapProvider:rn managed
        object property"
    ::= { cucsEquipmentLocalDiskCapProviderEntry 3 }

cucsEquipmentLocalDiskCapProviderDeprecated OBJECT-TYPE
    SYNTAX       TruthValue
    MAX-ACCESS   read-only
    STATUS       current
    DESCRIPTION
        "Cisco UCS equipment:LocalDiskCapProvider:deprecated
        managed object property"
    ::= { cucsEquipmentLocalDiskCapProviderEntry 4 }

cucsEquipmentLocalDiskCapProviderGencount OBJECT-TYPE
    SYNTAX       Gauge32
    MAX-ACCESS   read-only
    STATUS       current
    DESCRIPTION
        "Cisco UCS equipment:LocalDiskCapProvider:gencount
        managed object property"
    ::= { cucsEquipmentLocalDiskCapProviderEntry 5 }

cucsEquipmentLocalDiskCapProviderMgmtPlaneVer OBJECT-TYPE
    SYNTAX       SnmpAdminString
    MAX-ACCESS   read-only
    STATUS       current
    DESCRIPTION
        "Cisco UCS equipment:LocalDiskCapProvider:mgmtPlaneVer
        managed object property"
    ::= { cucsEquipmentLocalDiskCapProviderEntry 6 }

cucsEquipmentLocalDiskCapProviderModel OBJECT-TYPE
    SYNTAX       SnmpAdminString
    MAX-ACCESS   read-only
    STATUS       current
    DESCRIPTION
        "Cisco UCS equipment:LocalDiskCapProvider:model
        managed object property"
    ::= { cucsEquipmentLocalDiskCapProviderEntry 7 }

cucsEquipmentLocalDiskCapProviderRevision OBJECT-TYPE
    SYNTAX       SnmpAdminString
    MAX-ACCESS   read-only
    STATUS       current
    DESCRIPTION
        "Cisco UCS equipment:LocalDiskCapProvider:revision
        managed object property"
    ::= { cucsEquipmentLocalDiskCapProviderEntry 8 }

cucsEquipmentLocalDiskCapProviderVendor OBJECT-TYPE
    SYNTAX       SnmpAdminString
    MAX-ACCESS   read-only
    STATUS       current
    DESCRIPTION
        "Cisco UCS equipment:LocalDiskCapProvider:vendor
        managed object property"
    ::= { cucsEquipmentLocalDiskCapProviderEntry 9 }

cucsEquipmentLocalDiskCapProviderPromCardType OBJECT-TYPE
    SYNTAX       Gauge32
    MAX-ACCESS   read-only
    STATUS       current
    DESCRIPTION
        "Cisco UCS equipment:LocalDiskCapProvider:promCardType
        managed object property"
    ::= { cucsEquipmentLocalDiskCapProviderEntry 10 }

cucsEquipmentLocalDiskCapProviderDeleted OBJECT-TYPE
    SYNTAX       TruthValue
    MAX-ACCESS   read-only
    STATUS       current
    DESCRIPTION
        "Cisco UCS equipment:LocalDiskCapProvider:deleted
        managed object property"
    ::= { cucsEquipmentLocalDiskCapProviderEntry 11 }

cucsEquipmentLocalDiskCapProviderElementLoadFailures OBJECT-TYPE
    SYNTAX       Gauge32
    MAX-ACCESS   read-only
    STATUS       current
    DESCRIPTION
        "Cisco UCS equipment:LocalDiskCapProvider:elementLoadFailures
        managed object property"
    ::= { cucsEquipmentLocalDiskCapProviderEntry 12 }

cucsEquipmentLocalDiskCapProviderElementsLoaded OBJECT-TYPE
    SYNTAX       Gauge32
    MAX-ACCESS   read-only
    STATUS       current
    DESCRIPTION
        "Cisco UCS equipment:LocalDiskCapProvider:elementsLoaded
        managed object property"
    ::= { cucsEquipmentLocalDiskCapProviderEntry 13 }

cucsEquipmentLocalDiskCapProviderLoadErrors OBJECT-TYPE
    SYNTAX       Gauge32
    MAX-ACCESS   read-only
    STATUS       current
    DESCRIPTION
        "Cisco UCS equipment:LocalDiskCapProvider:loadErrors
        managed object property"
    ::= { cucsEquipmentLocalDiskCapProviderEntry 14 }

cucsEquipmentLocalDiskCapProviderLoadWarnings OBJECT-TYPE
    SYNTAX       Gauge32
    MAX-ACCESS   read-only
    STATUS       current
    DESCRIPTION
        "Cisco UCS equipment:LocalDiskCapProvider:loadWarnings
        managed object property"
    ::= { cucsEquipmentLocalDiskCapProviderEntry 15 }

cucsEquipmentLocalDiskControllerCapProviderTable OBJECT-TYPE
    SYNTAX           SEQUENCE OF CucsEquipmentLocalDiskControllerCapProviderEntry
    MAX-ACCESS       not-accessible
    STATUS           current
    DESCRIPTION
        "Cisco UCS equipment:LocalDiskControllerCapProvider
        managed object table"
    ::= { cucsEquipmentObjects 37 }

cucsEquipmentLocalDiskControllerCapProviderEntry OBJECT-TYPE
    SYNTAX           CucsEquipmentLocalDiskControllerCapProviderEntry
    MAX-ACCESS       not-accessible
    STATUS           current
    DESCRIPTION
        "Entry for the cucsEquipmentLocalDiskControllerCapProviderTable table."
    INDEX { cucsEquipmentLocalDiskControllerCapProviderInstanceId }
    ::= { cucsEquipmentLocalDiskControllerCapProviderTable 1 }

CucsEquipmentLocalDiskControllerCapProviderEntry ::= SEQUENCE {
    cucsEquipmentLocalDiskControllerCapProviderInstanceId            CucsManagedObjectId,
    cucsEquipmentLocalDiskControllerCapProviderDn                    CucsManagedObjectDn,
    cucsEquipmentLocalDiskControllerCapProviderRn                    SnmpAdminString,
    cucsEquipmentLocalDiskControllerCapProviderDeprecated            TruthValue,
    cucsEquipmentLocalDiskControllerCapProviderGencount              Gauge32,
    cucsEquipmentLocalDiskControllerCapProviderMgmtPlaneVer          SnmpAdminString,
    cucsEquipmentLocalDiskControllerCapProviderModel                 SnmpAdminString,
    cucsEquipmentLocalDiskControllerCapProviderRevision              SnmpAdminString,
    cucsEquipmentLocalDiskControllerCapProviderVendor                SnmpAdminString,
    cucsEquipmentLocalDiskControllerCapProviderPromCardType          Gauge32,
    cucsEquipmentLocalDiskControllerCapProviderDeleted               TruthValue,
    cucsEquipmentLocalDiskControllerCapProviderForm                  CucsStorageControllerForm,
    cucsEquipmentLocalDiskControllerCapProviderElementLoadFailures   Gauge32,
    cucsEquipmentLocalDiskControllerCapProviderElementsLoaded        Gauge32,
    cucsEquipmentLocalDiskControllerCapProviderInternalports         Gauge32,
    cucsEquipmentLocalDiskControllerCapProviderLoadErrors            Gauge32,
    cucsEquipmentLocalDiskControllerCapProviderLoadWarnings          Gauge32
}

cucsEquipmentLocalDiskControllerCapProviderInstanceId OBJECT-TYPE
    SYNTAX       CucsManagedObjectId
    MAX-ACCESS   not-accessible
    STATUS       current
    DESCRIPTION
        "Instance identifier of the managed object."
    ::= { cucsEquipmentLocalDiskControllerCapProviderEntry 1 }

cucsEquipmentLocalDiskControllerCapProviderDn OBJECT-TYPE
    SYNTAX       CucsManagedObjectDn
    MAX-ACCESS   read-only
    STATUS       current
    DESCRIPTION
        "Cisco UCS equipment:LocalDiskControllerCapProvider:dn
        managed object property"
    ::= { cucsEquipmentLocalDiskControllerCapProviderEntry 2 }

cucsEquipmentLocalDiskControllerCapProviderRn OBJECT-TYPE
    SYNTAX       SnmpAdminString
    MAX-ACCESS   read-only
    STATUS       current
    DESCRIPTION
        "Cisco UCS equipment:LocalDiskControllerCapProvider:rn
        managed object property"
    ::= { cucsEquipmentLocalDiskControllerCapProviderEntry 3 }

cucsEquipmentLocalDiskControllerCapProviderDeprecated OBJECT-TYPE
    SYNTAX       TruthValue
    MAX-ACCESS   read-only
    STATUS       current
    DESCRIPTION
        "Cisco UCS equipment:LocalDiskControllerCapProvider:deprecated
        managed object property"
    ::= { cucsEquipmentLocalDiskControllerCapProviderEntry 4 }

cucsEquipmentLocalDiskControllerCapProviderGencount OBJECT-TYPE
    SYNTAX       Gauge32
    MAX-ACCESS   read-only
    STATUS       current
    DESCRIPTION
        "Cisco UCS equipment:LocalDiskControllerCapProvider:gencount
        managed object property"
    ::= { cucsEquipmentLocalDiskControllerCapProviderEntry 5 }

cucsEquipmentLocalDiskControllerCapProviderMgmtPlaneVer OBJECT-TYPE
    SYNTAX       SnmpAdminString
    MAX-ACCESS   read-only
    STATUS       current
    DESCRIPTION
        "Cisco UCS equipment:LocalDiskControllerCapProvider:mgmtPlaneVer
        managed object property"
    ::= { cucsEquipmentLocalDiskControllerCapProviderEntry 6 }

cucsEquipmentLocalDiskControllerCapProviderModel OBJECT-TYPE
    SYNTAX       SnmpAdminString
    MAX-ACCESS   read-only
    STATUS       current
    DESCRIPTION
        "Cisco UCS equipment:LocalDiskControllerCapProvider:model
        managed object property"
    ::= { cucsEquipmentLocalDiskControllerCapProviderEntry 7 }

cucsEquipmentLocalDiskControllerCapProviderRevision OBJECT-TYPE
    SYNTAX       SnmpAdminString
    MAX-ACCESS   read-only
    STATUS       current
    DESCRIPTION
        "Cisco UCS equipment:LocalDiskControllerCapProvider:revision
        managed object property"
    ::= { cucsEquipmentLocalDiskControllerCapProviderEntry 8 }

cucsEquipmentLocalDiskControllerCapProviderVendor OBJECT-TYPE
    SYNTAX       SnmpAdminString
    MAX-ACCESS   read-only
    STATUS       current
    DESCRIPTION
        "Cisco UCS equipment:LocalDiskControllerCapProvider:vendor
        managed object property"
    ::= { cucsEquipmentLocalDiskControllerCapProviderEntry 9 }

cucsEquipmentLocalDiskControllerCapProviderPromCardType OBJECT-TYPE
    SYNTAX       Gauge32
    MAX-ACCESS   read-only
    STATUS       current
    DESCRIPTION
        "Cisco UCS equipment:LocalDiskControllerCapProvider:promCardType
        managed object property"
    ::= { cucsEquipmentLocalDiskControllerCapProviderEntry 10 }

cucsEquipmentLocalDiskControllerCapProviderDeleted OBJECT-TYPE
    SYNTAX       TruthValue
    MAX-ACCESS   read-only
    STATUS       current
    DESCRIPTION
        "Cisco UCS equipment:LocalDiskControllerCapProvider:deleted
        managed object property"
    ::= { cucsEquipmentLocalDiskControllerCapProviderEntry 11 }

cucsEquipmentLocalDiskControllerCapProviderForm OBJECT-TYPE
    SYNTAX       CucsStorageControllerForm
    MAX-ACCESS   read-only
    STATUS       current
    DESCRIPTION
        "Cisco UCS equipment:LocalDiskControllerCapProvider:form
        managed object property"
    ::= { cucsEquipmentLocalDiskControllerCapProviderEntry 12 }

cucsEquipmentLocalDiskControllerCapProviderElementLoadFailures OBJECT-TYPE
    SYNTAX       Gauge32
    MAX-ACCESS   read-only
    STATUS       current
    DESCRIPTION
        "Cisco UCS equipment:LocalDiskControllerCapProvider:elementLoadFai
        lures managed object property"
    ::= { cucsEquipmentLocalDiskControllerCapProviderEntry 13 }

cucsEquipmentLocalDiskControllerCapProviderElementsLoaded OBJECT-TYPE
    SYNTAX       Gauge32
    MAX-ACCESS   read-only
    STATUS       current
    DESCRIPTION
        "Cisco UCS equipment:LocalDiskControllerCapProvider:elementsLoaded
         managed object property"
    ::= { cucsEquipmentLocalDiskControllerCapProviderEntry 14 }

cucsEquipmentLocalDiskControllerCapProviderInternalports OBJECT-TYPE
    SYNTAX       Gauge32
    MAX-ACCESS   read-only
    STATUS       current
    DESCRIPTION
        "Cisco UCS equipment:LocalDiskControllerCapProvider:internalports
        managed object property"
    ::= { cucsEquipmentLocalDiskControllerCapProviderEntry 15 }

cucsEquipmentLocalDiskControllerCapProviderLoadErrors OBJECT-TYPE
    SYNTAX       Gauge32
    MAX-ACCESS   read-only
    STATUS       current
    DESCRIPTION
        "Cisco UCS equipment:LocalDiskControllerCapProvider:loadErrors
        managed object property"
    ::= { cucsEquipmentLocalDiskControllerCapProviderEntry 16 }

cucsEquipmentLocalDiskControllerCapProviderLoadWarnings OBJECT-TYPE
    SYNTAX       Gauge32
    MAX-ACCESS   read-only
    STATUS       current
    DESCRIPTION
        "Cisco UCS equipment:LocalDiskControllerCapProvider:loadWarnings
        managed object property"
    ::= { cucsEquipmentLocalDiskControllerCapProviderEntry 17 }

cucsEquipmentLocalDiskControllerCapRefTable OBJECT-TYPE
    SYNTAX           SEQUENCE OF CucsEquipmentLocalDiskControllerCapRefEntry
    MAX-ACCESS       not-accessible
    STATUS           current
    DESCRIPTION
        "Cisco UCS equipment:LocalDiskControllerCapRef
        managed object table"
    ::= { cucsEquipmentObjects 80 }

cucsEquipmentLocalDiskControllerCapRefEntry OBJECT-TYPE
    SYNTAX           CucsEquipmentLocalDiskControllerCapRefEntry
    MAX-ACCESS       not-accessible
    STATUS           current
    DESCRIPTION
        "Entry for the cucsEquipmentLocalDiskControllerCapRefTable table."
    INDEX { cucsEquipmentLocalDiskControllerCapRefInstanceId }
    ::= { cucsEquipmentLocalDiskControllerCapRefTable 1 }

CucsEquipmentLocalDiskControllerCapRefEntry ::= SEQUENCE {
    cucsEquipmentLocalDiskControllerCapRefInstanceId                 CucsManagedObjectId,
    cucsEquipmentLocalDiskControllerCapRefDn                         CucsManagedObjectDn,
    cucsEquipmentLocalDiskControllerCapRefRn                         SnmpAdminString,
    cucsEquipmentLocalDiskControllerCapRefIsSupported                CucsEquipmentIsSupported,
    cucsEquipmentLocalDiskControllerCapRefModel                      SnmpAdminString,
    cucsEquipmentLocalDiskControllerCapRefRevision                   SnmpAdminString,
    cucsEquipmentLocalDiskControllerCapRefVendor                     SnmpAdminString
}

cucsEquipmentLocalDiskControllerCapRefInstanceId OBJECT-TYPE
    SYNTAX       CucsManagedObjectId
    MAX-ACCESS   not-accessible
    STATUS       current
    DESCRIPTION
        "Instance identifier of the managed object."
    ::= { cucsEquipmentLocalDiskControllerCapRefEntry 1 }

cucsEquipmentLocalDiskControllerCapRefDn OBJECT-TYPE
    SYNTAX       CucsManagedObjectDn
    MAX-ACCESS   read-only
    STATUS       current
    DESCRIPTION
        "Cisco UCS equipment:LocalDiskControllerCapRef:dn
        managed object property"
    ::= { cucsEquipmentLocalDiskControllerCapRefEntry 2 }

cucsEquipmentLocalDiskControllerCapRefRn OBJECT-TYPE
    SYNTAX       SnmpAdminString
    MAX-ACCESS   read-only
    STATUS       current
    DESCRIPTION
        "Cisco UCS equipment:LocalDiskControllerCapRef:rn
        managed object property"
    ::= { cucsEquipmentLocalDiskControllerCapRefEntry 3 }

cucsEquipmentLocalDiskControllerCapRefIsSupported OBJECT-TYPE
    SYNTAX       CucsEquipmentIsSupported
    MAX-ACCESS   read-only
    STATUS       current
    DESCRIPTION
        "Cisco UCS equipment:LocalDiskControllerCapRef:isSupported
        managed object property"
    ::= { cucsEquipmentLocalDiskControllerCapRefEntry 4 }

cucsEquipmentLocalDiskControllerCapRefModel OBJECT-TYPE
    SYNTAX       SnmpAdminString
    MAX-ACCESS   read-only
    STATUS       current
    DESCRIPTION
        "Cisco UCS equipment:LocalDiskControllerCapRef:model
        managed object property"
    ::= { cucsEquipmentLocalDiskControllerCapRefEntry 5 }

cucsEquipmentLocalDiskControllerCapRefRevision OBJECT-TYPE
    SYNTAX       SnmpAdminString
    MAX-ACCESS   read-only
    STATUS       current
    DESCRIPTION
        "Cisco UCS equipment:LocalDiskControllerCapRef:revision
        managed object property"
    ::= { cucsEquipmentLocalDiskControllerCapRefEntry 6 }

cucsEquipmentLocalDiskControllerCapRefVendor OBJECT-TYPE
    SYNTAX       SnmpAdminString
    MAX-ACCESS   read-only
    STATUS       current
    DESCRIPTION
        "Cisco UCS equipment:LocalDiskControllerCapRef:vendor
        managed object property"
    ::= { cucsEquipmentLocalDiskControllerCapRefEntry 7 }

cucsEquipmentLocalDiskControllerDefTable OBJECT-TYPE
    SYNTAX           SEQUENCE OF CucsEquipmentLocalDiskControllerDefEntry
    MAX-ACCESS       not-accessible
    STATUS           current
    DESCRIPTION
        "Cisco UCS equipment:LocalDiskControllerDef managed object table"
    ::= { cucsEquipmentObjects 38 }

cucsEquipmentLocalDiskControllerDefEntry OBJECT-TYPE
    SYNTAX           CucsEquipmentLocalDiskControllerDefEntry
    MAX-ACCESS       not-accessible
    STATUS           current
    DESCRIPTION
        "Entry for the cucsEquipmentLocalDiskControllerDefTable table."
    INDEX { cucsEquipmentLocalDiskControllerDefInstanceId }
    ::= { cucsEquipmentLocalDiskControllerDefTable 1 }

CucsEquipmentLocalDiskControllerDefEntry ::= SEQUENCE {
    cucsEquipmentLocalDiskControllerDefInstanceId                    CucsManagedObjectId,
    cucsEquipmentLocalDiskControllerDefDn                            CucsManagedObjectDn,
    cucsEquipmentLocalDiskControllerDefRn                            SnmpAdminString,
    cucsEquipmentLocalDiskControllerDefDescr                         SnmpAdminString,
    cucsEquipmentLocalDiskControllerDefForceUpdateVersion            TruthValue,
    cucsEquipmentLocalDiskControllerDefIntId                         SnmpAdminString,
    cucsEquipmentLocalDiskControllerDefName                          SnmpAdminString,
    cucsEquipmentLocalDiskControllerDefPolicyLevel                   Gauge32,
    cucsEquipmentLocalDiskControllerDefPolicyOwner                   CucsPolicyPolicyOwner
}

cucsEquipmentLocalDiskControllerDefInstanceId OBJECT-TYPE
    SYNTAX       CucsManagedObjectId
    MAX-ACCESS   not-accessible
    STATUS       current
    DESCRIPTION
        "Instance identifier of the managed object."
    ::= { cucsEquipmentLocalDiskControllerDefEntry 1 }

cucsEquipmentLocalDiskControllerDefDn OBJECT-TYPE
    SYNTAX       CucsManagedObjectDn
    MAX-ACCESS   read-only
    STATUS       current
    DESCRIPTION
        "Cisco UCS equipment:LocalDiskControllerDef:dn
        managed object property"
    ::= { cucsEquipmentLocalDiskControllerDefEntry 2 }

cucsEquipmentLocalDiskControllerDefRn OBJECT-TYPE
    SYNTAX       SnmpAdminString
    MAX-ACCESS   read-only
    STATUS       current
    DESCRIPTION
        "Cisco UCS equipment:LocalDiskControllerDef:rn
        managed object property"
    ::= { cucsEquipmentLocalDiskControllerDefEntry 3 }

cucsEquipmentLocalDiskControllerDefDescr OBJECT-TYPE
    SYNTAX       SnmpAdminString
    MAX-ACCESS   read-only
    STATUS       current
    DESCRIPTION
        "Cisco UCS equipment:LocalDiskControllerDef:descr
        managed object property"
    ::= { cucsEquipmentLocalDiskControllerDefEntry 4 }

cucsEquipmentLocalDiskControllerDefForceUpdateVersion OBJECT-TYPE
    SYNTAX       TruthValue
    MAX-ACCESS   read-only
    STATUS       current
    DESCRIPTION
        "Cisco UCS equipment:LocalDiskControllerDef:forceUpdateVersion
        managed object property"
    ::= { cucsEquipmentLocalDiskControllerDefEntry 5 }

cucsEquipmentLocalDiskControllerDefIntId OBJECT-TYPE
    SYNTAX       SnmpAdminString
    MAX-ACCESS   read-only
    STATUS       current
    DESCRIPTION
        "Cisco UCS equipment:LocalDiskControllerDef:intId
        managed object property"
    ::= { cucsEquipmentLocalDiskControllerDefEntry 6 }

cucsEquipmentLocalDiskControllerDefName OBJECT-TYPE
    SYNTAX       SnmpAdminString
    MAX-ACCESS   read-only
    STATUS       current
    DESCRIPTION
        "Cisco UCS equipment:LocalDiskControllerDef:name
        managed object property"
    ::= { cucsEquipmentLocalDiskControllerDefEntry 7 }

cucsEquipmentLocalDiskControllerDefPolicyLevel OBJECT-TYPE
    SYNTAX       Gauge32
    MAX-ACCESS   read-only
    STATUS       current
    DESCRIPTION
        "Cisco UCS equipment:LocalDiskControllerDef:policyLevel
        managed object property"
    ::= { cucsEquipmentLocalDiskControllerDefEntry 8 }

cucsEquipmentLocalDiskControllerDefPolicyOwner OBJECT-TYPE
    SYNTAX       CucsPolicyPolicyOwner
    MAX-ACCESS   read-only
    STATUS       current
    DESCRIPTION
        "Cisco UCS equipment:LocalDiskControllerDef:policyOwner
        managed object property"
    ::= { cucsEquipmentLocalDiskControllerDefEntry 9 }

cucsEquipmentLocalDiskDefTable OBJECT-TYPE
    SYNTAX           SEQUENCE OF CucsEquipmentLocalDiskDefEntry
    MAX-ACCESS       not-accessible
    STATUS           current
    DESCRIPTION
        "Cisco UCS equipment:LocalDiskDef managed object table"
    ::= { cucsEquipmentObjects 39 }

cucsEquipmentLocalDiskDefEntry OBJECT-TYPE
    SYNTAX           CucsEquipmentLocalDiskDefEntry
    MAX-ACCESS       not-accessible
    STATUS           current
    DESCRIPTION
        "Entry for the cucsEquipmentLocalDiskDefTable table."
    INDEX { cucsEquipmentLocalDiskDefInstanceId }
    ::= { cucsEquipmentLocalDiskDefTable 1 }

CucsEquipmentLocalDiskDefEntry ::= SEQUENCE {
    cucsEquipmentLocalDiskDefInstanceId                              CucsManagedObjectId,
    cucsEquipmentLocalDiskDefDn                                      CucsManagedObjectDn,
    cucsEquipmentLocalDiskDefRn                                      SnmpAdminString,
    cucsEquipmentLocalDiskDefBlockSize                               Gauge32,
    cucsEquipmentLocalDiskDefDescr                                   SnmpAdminString,
    cucsEquipmentLocalDiskDefIntId                                   SnmpAdminString,
    cucsEquipmentLocalDiskDefName                                    SnmpAdminString,
    cucsEquipmentLocalDiskDefNumberOfBlocks                          Unsigned64,
    cucsEquipmentLocalDiskDefRotationalSpeed                         INTEGER,
    cucsEquipmentLocalDiskDefCacheSize                               SnmpAdminString,
    cucsEquipmentLocalDiskDefSeekAverageReadWrite                    SnmpAdminString,
    cucsEquipmentLocalDiskDefSeekTrackToTrackReadWrite               SnmpAdminString,
    cucsEquipmentLocalDiskDefTechnology                              CucsStorageTechnology,
    cucsEquipmentLocalDiskDefPolicyLevel                             Gauge32,
    cucsEquipmentLocalDiskDefPolicyOwner                             CucsPolicyPolicyOwner
}

cucsEquipmentLocalDiskDefInstanceId OBJECT-TYPE
    SYNTAX       CucsManagedObjectId
    MAX-ACCESS   not-accessible
    STATUS       current
    DESCRIPTION
        "Instance identifier of the managed object."
    ::= { cucsEquipmentLocalDiskDefEntry 1 }

cucsEquipmentLocalDiskDefDn OBJECT-TYPE
    SYNTAX       CucsManagedObjectDn
    MAX-ACCESS   read-only
    STATUS       current
    DESCRIPTION
        "Cisco UCS equipment:LocalDiskDef:dn managed object property"
    ::= { cucsEquipmentLocalDiskDefEntry 2 }

cucsEquipmentLocalDiskDefRn OBJECT-TYPE
    SYNTAX       SnmpAdminString
    MAX-ACCESS   read-only
    STATUS       current
    DESCRIPTION
        "Cisco UCS equipment:LocalDiskDef:rn managed object property"
    ::= { cucsEquipmentLocalDiskDefEntry 3 }

cucsEquipmentLocalDiskDefBlockSize OBJECT-TYPE
    SYNTAX       Gauge32
    MAX-ACCESS   read-only
    STATUS       current
    DESCRIPTION
        "Cisco UCS equipment:LocalDiskDef:blockSize managed
        object property"
    ::= { cucsEquipmentLocalDiskDefEntry 4 }

cucsEquipmentLocalDiskDefDescr OBJECT-TYPE
    SYNTAX       SnmpAdminString
    MAX-ACCESS   read-only
    STATUS       current
    DESCRIPTION
        "Cisco UCS equipment:LocalDiskDef:descr managed object property"
    ::= { cucsEquipmentLocalDiskDefEntry 5 }

cucsEquipmentLocalDiskDefIntId OBJECT-TYPE
    SYNTAX       SnmpAdminString
    MAX-ACCESS   read-only
    STATUS       current
    DESCRIPTION
        "Cisco UCS equipment:LocalDiskDef:intId managed object property"
    ::= { cucsEquipmentLocalDiskDefEntry 6 }

cucsEquipmentLocalDiskDefName OBJECT-TYPE
    SYNTAX       SnmpAdminString
    MAX-ACCESS   read-only
    STATUS       current
    DESCRIPTION
        "Cisco UCS equipment:LocalDiskDef:name managed object property"
    ::= { cucsEquipmentLocalDiskDefEntry 7 }

cucsEquipmentLocalDiskDefNumberOfBlocks OBJECT-TYPE
    SYNTAX       Unsigned64
    MAX-ACCESS   read-only
    STATUS       current
    DESCRIPTION
        "Cisco UCS equipment:LocalDiskDef:numberOfBlocks
        managed object property"
    ::= { cucsEquipmentLocalDiskDefEntry 8 }

cucsEquipmentLocalDiskDefRotationalSpeed OBJECT-TYPE
    SYNTAX       INTEGER
    MAX-ACCESS   read-only
    STATUS       current
    DESCRIPTION
        "Cisco UCS equipment:LocalDiskDef:rotationalSpeed
        managed object property"
    ::= { cucsEquipmentLocalDiskDefEntry 9 }

cucsEquipmentLocalDiskDefCacheSize OBJECT-TYPE
    SYNTAX       SnmpAdminString
    MAX-ACCESS   read-only
    STATUS       current
    DESCRIPTION
        "Cisco UCS equipment:LocalDiskDef:cacheSize managed
        object property"
    ::= { cucsEquipmentLocalDiskDefEntry 10 }

cucsEquipmentLocalDiskDefSeekAverageReadWrite OBJECT-TYPE
    SYNTAX       SnmpAdminString
    MAX-ACCESS   read-only
    STATUS       current
    DESCRIPTION
        "Cisco UCS equipment:LocalDiskDef:seekAverageReadWrite
        managed object property"
    ::= { cucsEquipmentLocalDiskDefEntry 11 }

cucsEquipmentLocalDiskDefSeekTrackToTrackReadWrite OBJECT-TYPE
    SYNTAX       SnmpAdminString
    MAX-ACCESS   read-only
    STATUS       current
    DESCRIPTION
        "Cisco UCS equipment:LocalDiskDef:seekTrackToTrackReadWrite
        managed object property"
    ::= { cucsEquipmentLocalDiskDefEntry 12 }

cucsEquipmentLocalDiskDefTechnology OBJECT-TYPE
    SYNTAX       CucsStorageTechnology
    MAX-ACCESS   read-only
    STATUS       current
    DESCRIPTION
        "Cisco UCS equipment:LocalDiskDef:technology managed
        object property"
    ::= { cucsEquipmentLocalDiskDefEntry 13 }

cucsEquipmentLocalDiskDefPolicyLevel OBJECT-TYPE
    SYNTAX       Gauge32
    MAX-ACCESS   read-only
    STATUS       current
    DESCRIPTION
        "Cisco UCS equipment:LocalDiskDef:policyLevel managed
        object property"
    ::= { cucsEquipmentLocalDiskDefEntry 14 }

cucsEquipmentLocalDiskDefPolicyOwner OBJECT-TYPE
    SYNTAX       CucsPolicyPolicyOwner
    MAX-ACCESS   read-only
    STATUS       current
    DESCRIPTION
        "Cisco UCS equipment:LocalDiskDef:policyOwner managed
        object property"
    ::= { cucsEquipmentLocalDiskDefEntry 15 }

cucsEquipmentLocatorLedTable OBJECT-TYPE
    SYNTAX           SEQUENCE OF CucsEquipmentLocatorLedEntry
    MAX-ACCESS       not-accessible
    STATUS           current
    DESCRIPTION
        "Cisco UCS equipment:LocatorLed managed object table"
    ::= { cucsEquipmentObjects 40 }

cucsEquipmentLocatorLedEntry OBJECT-TYPE
    SYNTAX           CucsEquipmentLocatorLedEntry
    MAX-ACCESS       not-accessible
    STATUS           current
    DESCRIPTION
        "Entry for the cucsEquipmentLocatorLedTable table."
    INDEX { cucsEquipmentLocatorLedInstanceId }
    ::= { cucsEquipmentLocatorLedTable 1 }

CucsEquipmentLocatorLedEntry ::= SEQUENCE {
    cucsEquipmentLocatorLedInstanceId                                CucsManagedObjectId,
    cucsEquipmentLocatorLedDn                                        CucsManagedObjectDn,
    cucsEquipmentLocatorLedRn                                        SnmpAdminString,
    cucsEquipmentLocatorLedAdminState                                CucsEquipmentLedLocatorState,
    cucsEquipmentLocatorLedColor                                     CucsEquipmentLedColor,
    cucsEquipmentLocatorLedFsmDescr                                  SnmpAdminString,
    cucsEquipmentLocatorLedFsmPrev                                   SnmpAdminString,
    cucsEquipmentLocatorLedFsmProgr                                  Gauge32,
    cucsEquipmentLocatorLedFsmRmtInvErrCode                          Gauge32,
    cucsEquipmentLocatorLedFsmRmtInvErrDescr                         SnmpAdminString,
    cucsEquipmentLocatorLedFsmRmtInvRslt                             CucsConditionRemoteInvRslt,
    cucsEquipmentLocatorLedFsmStageDescr                             SnmpAdminString,
    cucsEquipmentLocatorLedFsmStamp                                  DateAndTime,
    cucsEquipmentLocatorLedFsmStatus                                 SnmpAdminString,
    cucsEquipmentLocatorLedFsmTry                                    Gauge32,
    cucsEquipmentLocatorLedId                                        Gauge32,
    cucsEquipmentLocatorLedName                                      SnmpAdminString,
    cucsEquipmentLocatorLedOperState                                 CucsEquipmentLedOperState
}

cucsEquipmentLocatorLedInstanceId OBJECT-TYPE
    SYNTAX       CucsManagedObjectId
    MAX-ACCESS   not-accessible
    STATUS       current
    DESCRIPTION
        "Instance identifier of the managed object."
    ::= { cucsEquipmentLocatorLedEntry 1 }

cucsEquipmentLocatorLedDn OBJECT-TYPE
    SYNTAX       CucsManagedObjectDn
    MAX-ACCESS   read-only
    STATUS       current
    DESCRIPTION
        "Cisco UCS equipment:LocatorLed:dn managed object property"
    ::= { cucsEquipmentLocatorLedEntry 2 }

cucsEquipmentLocatorLedRn OBJECT-TYPE
    SYNTAX       SnmpAdminString
    MAX-ACCESS   read-only
    STATUS       current
    DESCRIPTION
        "Cisco UCS equipment:LocatorLed:rn managed object property"
    ::= { cucsEquipmentLocatorLedEntry 3 }

cucsEquipmentLocatorLedAdminState OBJECT-TYPE
    SYNTAX       CucsEquipmentLedLocatorState
    MAX-ACCESS   read-only
    STATUS       current
    DESCRIPTION
        "Cisco UCS equipment:LocatorLed:adminState managed
        object property"
    ::= { cucsEquipmentLocatorLedEntry 4 }

cucsEquipmentLocatorLedColor OBJECT-TYPE
    SYNTAX       CucsEquipmentLedColor
    MAX-ACCESS   read-only
    STATUS       current
    DESCRIPTION
        "Cisco UCS equipment:LocatorLed:color managed object property"
    ::= { cucsEquipmentLocatorLedEntry 5 }

cucsEquipmentLocatorLedFsmDescr OBJECT-TYPE
    SYNTAX       SnmpAdminString
    MAX-ACCESS   read-only
    STATUS       current
    DESCRIPTION
        "Cisco UCS equipment:LocatorLed:fsmDescr managed object property"
    ::= { cucsEquipmentLocatorLedEntry 6 }

cucsEquipmentLocatorLedFsmPrev OBJECT-TYPE
    SYNTAX       SnmpAdminString
    MAX-ACCESS   read-only
    STATUS       current
    DESCRIPTION
        "Cisco UCS equipment:LocatorLed:fsmPrev managed object property"
    ::= { cucsEquipmentLocatorLedEntry 7 }

cucsEquipmentLocatorLedFsmProgr OBJECT-TYPE
    SYNTAX       Gauge32
    MAX-ACCESS   read-only
    STATUS       current
    DESCRIPTION
        "Cisco UCS equipment:LocatorLed:fsmProgr managed object property"
    ::= { cucsEquipmentLocatorLedEntry 8 }

cucsEquipmentLocatorLedFsmRmtInvErrCode OBJECT-TYPE
    SYNTAX       Gauge32
    MAX-ACCESS   read-only
    STATUS       current
    DESCRIPTION
        "Cisco UCS equipment:LocatorLed:fsmRmtInvErrCode
        managed object property"
    ::= { cucsEquipmentLocatorLedEntry 9 }

cucsEquipmentLocatorLedFsmRmtInvErrDescr OBJECT-TYPE
    SYNTAX       SnmpAdminString
    MAX-ACCESS   read-only
    STATUS       current
    DESCRIPTION
        "Cisco UCS equipment:LocatorLed:fsmRmtInvErrDescr
        managed object property"
    ::= { cucsEquipmentLocatorLedEntry 10 }

cucsEquipmentLocatorLedFsmRmtInvRslt OBJECT-TYPE
    SYNTAX       CucsConditionRemoteInvRslt
    MAX-ACCESS   read-only
    STATUS       current
    DESCRIPTION
        "Cisco UCS equipment:LocatorLed:fsmRmtInvRslt managed
        object property"
    ::= { cucsEquipmentLocatorLedEntry 11 }

cucsEquipmentLocatorLedFsmStageDescr OBJECT-TYPE
    SYNTAX       SnmpAdminString
    MAX-ACCESS   read-only
    STATUS       current
    DESCRIPTION
        "Cisco UCS equipment:LocatorLed:fsmStageDescr managed
        object property"
    ::= { cucsEquipmentLocatorLedEntry 12 }

cucsEquipmentLocatorLedFsmStamp OBJECT-TYPE
    SYNTAX       DateAndTime
    MAX-ACCESS   read-only
    STATUS       current
    DESCRIPTION
        "Cisco UCS equipment:LocatorLed:fsmStamp managed object property"
    ::= { cucsEquipmentLocatorLedEntry 13 }

cucsEquipmentLocatorLedFsmStatus OBJECT-TYPE
    SYNTAX       SnmpAdminString
    MAX-ACCESS   read-only
    STATUS       current
    DESCRIPTION
        "Cisco UCS equipment:LocatorLed:fsmStatus managed object property"
    ::= { cucsEquipmentLocatorLedEntry 14 }

cucsEquipmentLocatorLedFsmTry OBJECT-TYPE
    SYNTAX       Gauge32
    MAX-ACCESS   read-only
    STATUS       current
    DESCRIPTION
        "Cisco UCS equipment:LocatorLed:fsmTry managed object property"
    ::= { cucsEquipmentLocatorLedEntry 15 }

cucsEquipmentLocatorLedId OBJECT-TYPE
    SYNTAX       Gauge32
    MAX-ACCESS   read-only
    STATUS       current
    DESCRIPTION
        "Cisco UCS equipment:LocatorLed:id managed object property"
    ::= { cucsEquipmentLocatorLedEntry 16 }

cucsEquipmentLocatorLedName OBJECT-TYPE
    SYNTAX       SnmpAdminString
    MAX-ACCESS   read-only
    STATUS       current
    DESCRIPTION
        "Cisco UCS equipment:LocatorLed:name managed object property"
    ::= { cucsEquipmentLocatorLedEntry 17 }

cucsEquipmentLocatorLedOperState OBJECT-TYPE
    SYNTAX       CucsEquipmentLedOperState
    MAX-ACCESS   read-only
    STATUS       current
    DESCRIPTION
        "Cisco UCS equipment:LocatorLed:operState managed object property"
    ::= { cucsEquipmentLocatorLedEntry 18 }

cucsEquipmentLocatorLedFsmTable OBJECT-TYPE
    SYNTAX           SEQUENCE OF CucsEquipmentLocatorLedFsmEntry
    MAX-ACCESS       not-accessible
    STATUS           current
    DESCRIPTION
        "Cisco UCS equipment:LocatorLedFsm managed object table"
    ::= { cucsEquipmentObjects 111 }

cucsEquipmentLocatorLedFsmEntry OBJECT-TYPE
    SYNTAX           CucsEquipmentLocatorLedFsmEntry
    MAX-ACCESS       not-accessible
    STATUS           current
    DESCRIPTION
        "Entry for the cucsEquipmentLocatorLedFsmTable table."
    INDEX { cucsEquipmentLocatorLedFsmInstanceId }
    ::= { cucsEquipmentLocatorLedFsmTable 1 }

CucsEquipmentLocatorLedFsmEntry ::= SEQUENCE {
    cucsEquipmentLocatorLedFsmInstanceId                             CucsManagedObjectId,
    cucsEquipmentLocatorLedFsmDn                                     CucsManagedObjectDn,
    cucsEquipmentLocatorLedFsmRn                                     SnmpAdminString,
    cucsEquipmentLocatorLedFsmCompletionTime                         DateAndTime,
    cucsEquipmentLocatorLedFsmCurrentFsm                             CucsEquipmentLocatorLedFsmCurrentFsm,
    cucsEquipmentLocatorLedFsmDescr                                  SnmpAdminString,
    cucsEquipmentLocatorLedFsmFsmStatus                              CucsFsmFsmStageStatus,
    cucsEquipmentLocatorLedFsmProgress                               Gauge32,
    cucsEquipmentLocatorLedFsmRmtErrCode                             Gauge32,
    cucsEquipmentLocatorLedFsmRmtErrDescr                            SnmpAdminString,
    cucsEquipmentLocatorLedFsmRmtRslt                                CucsConditionRemoteInvRslt
}

cucsEquipmentLocatorLedFsmInstanceId OBJECT-TYPE
    SYNTAX       CucsManagedObjectId
    MAX-ACCESS   not-accessible
    STATUS       current
    DESCRIPTION
        "Instance identifier of the managed object."
    ::= { cucsEquipmentLocatorLedFsmEntry 1 }

cucsEquipmentLocatorLedFsmDn OBJECT-TYPE
    SYNTAX       CucsManagedObjectDn
    MAX-ACCESS   read-only
    STATUS       current
    DESCRIPTION
        "Cisco UCS equipment:LocatorLedFsm:dn managed object property"
    ::= { cucsEquipmentLocatorLedFsmEntry 2 }

cucsEquipmentLocatorLedFsmRn OBJECT-TYPE
    SYNTAX       SnmpAdminString
    MAX-ACCESS   read-only
    STATUS       current
    DESCRIPTION
        "Cisco UCS equipment:LocatorLedFsm:rn managed object property"
    ::= { cucsEquipmentLocatorLedFsmEntry 3 }

cucsEquipmentLocatorLedFsmCompletionTime OBJECT-TYPE
    SYNTAX       DateAndTime
    MAX-ACCESS   read-only
    STATUS       current
    DESCRIPTION
        "Cisco UCS equipment:LocatorLedFsm:completionTime
        managed object property"
    ::= { cucsEquipmentLocatorLedFsmEntry 4 }

cucsEquipmentLocatorLedFsmCurrentFsm OBJECT-TYPE
    SYNTAX       CucsEquipmentLocatorLedFsmCurrentFsm
    MAX-ACCESS   read-only
    STATUS       current
    DESCRIPTION
        "Cisco UCS equipment:LocatorLedFsm:currentFsm managed
        object property"
    ::= { cucsEquipmentLocatorLedFsmEntry 5 }

cucsEquipmentLocatorLedFsmDescr OBJECT-TYPE
    SYNTAX       SnmpAdminString
    MAX-ACCESS   read-only
    STATUS       current
    DESCRIPTION
        "Cisco UCS equipment:LocatorLedFsm:descr managed object property"
    ::= { cucsEquipmentLocatorLedFsmEntry 6 }

cucsEquipmentLocatorLedFsmFsmStatus OBJECT-TYPE
    SYNTAX       CucsFsmFsmStageStatus
    MAX-ACCESS   read-only
    STATUS       current
    DESCRIPTION
        "Cisco UCS equipment:LocatorLedFsm:fsmStatus managed
        object property"
    ::= { cucsEquipmentLocatorLedFsmEntry 7 }

cucsEquipmentLocatorLedFsmProgress OBJECT-TYPE
    SYNTAX       Gauge32
    MAX-ACCESS   read-only
    STATUS       current
    DESCRIPTION
        "Cisco UCS equipment:LocatorLedFsm:progress managed
        object property"
    ::= { cucsEquipmentLocatorLedFsmEntry 8 }

cucsEquipmentLocatorLedFsmRmtErrCode OBJECT-TYPE
    SYNTAX       Gauge32
    MAX-ACCESS   read-only
    STATUS       current
    DESCRIPTION
        "Cisco UCS equipment:LocatorLedFsm:rmtErrCode managed
        object property"
    ::= { cucsEquipmentLocatorLedFsmEntry 9 }

cucsEquipmentLocatorLedFsmRmtErrDescr OBJECT-TYPE
    SYNTAX       SnmpAdminString
    MAX-ACCESS   read-only
    STATUS       current
    DESCRIPTION
        "Cisco UCS equipment:LocatorLedFsm:rmtErrDescr
        managed object property"
    ::= { cucsEquipmentLocatorLedFsmEntry 10 }

cucsEquipmentLocatorLedFsmRmtRslt OBJECT-TYPE
    SYNTAX       CucsConditionRemoteInvRslt
    MAX-ACCESS   read-only
    STATUS       current
    DESCRIPTION
        "Cisco UCS equipment:LocatorLedFsm:rmtRslt managed
        object property"
    ::= { cucsEquipmentLocatorLedFsmEntry 11 }

cucsEquipmentLocatorLedFsmStageTable OBJECT-TYPE
    SYNTAX           SEQUENCE OF CucsEquipmentLocatorLedFsmStageEntry
    MAX-ACCESS       not-accessible
    STATUS           current
    DESCRIPTION
        "Cisco UCS equipment:LocatorLedFsmStage managed object table"
    ::= { cucsEquipmentObjects 112 }

cucsEquipmentLocatorLedFsmStageEntry OBJECT-TYPE
    SYNTAX           CucsEquipmentLocatorLedFsmStageEntry
    MAX-ACCESS       not-accessible
    STATUS           current
    DESCRIPTION
        "Entry for the cucsEquipmentLocatorLedFsmStageTable table."
    INDEX { cucsEquipmentLocatorLedFsmStageInstanceId }
    ::= { cucsEquipmentLocatorLedFsmStageTable 1 }

CucsEquipmentLocatorLedFsmStageEntry ::= SEQUENCE {
    cucsEquipmentLocatorLedFsmStageInstanceId                        CucsManagedObjectId,
    cucsEquipmentLocatorLedFsmStageDn                                CucsManagedObjectDn,
    cucsEquipmentLocatorLedFsmStageRn                                SnmpAdminString,
    cucsEquipmentLocatorLedFsmStageDescr                             SnmpAdminString,
    cucsEquipmentLocatorLedFsmStageLastUpdateTime                    DateAndTime,
    cucsEquipmentLocatorLedFsmStageName                              CucsEquipmentLocatorLedFsmStageName,
    cucsEquipmentLocatorLedFsmStageOrder                             Gauge32,
    cucsEquipmentLocatorLedFsmStageRetry                             Gauge32,
    cucsEquipmentLocatorLedFsmStageStageStatus                       CucsFsmFsmStageStatus
}

cucsEquipmentLocatorLedFsmStageInstanceId OBJECT-TYPE
    SYNTAX       CucsManagedObjectId
    MAX-ACCESS   not-accessible
    STATUS       current
    DESCRIPTION
        "Instance identifier of the managed object."
    ::= { cucsEquipmentLocatorLedFsmStageEntry 1 }

cucsEquipmentLocatorLedFsmStageDn OBJECT-TYPE
    SYNTAX       CucsManagedObjectDn
    MAX-ACCESS   read-only
    STATUS       current
    DESCRIPTION
        "Cisco UCS equipment:LocatorLedFsmStage:dn managed
        object property"
    ::= { cucsEquipmentLocatorLedFsmStageEntry 2 }

cucsEquipmentLocatorLedFsmStageRn OBJECT-TYPE
    SYNTAX       SnmpAdminString
    MAX-ACCESS   read-only
    STATUS       current
    DESCRIPTION
        "Cisco UCS equipment:LocatorLedFsmStage:rn managed
        object property"
    ::= { cucsEquipmentLocatorLedFsmStageEntry 3 }

cucsEquipmentLocatorLedFsmStageDescr OBJECT-TYPE
    SYNTAX       SnmpAdminString
    MAX-ACCESS   read-only
    STATUS       current
    DESCRIPTION
        "Cisco UCS equipment:LocatorLedFsmStage:descr managed
        object property"
    ::= { cucsEquipmentLocatorLedFsmStageEntry 4 }

cucsEquipmentLocatorLedFsmStageLastUpdateTime OBJECT-TYPE
    SYNTAX       DateAndTime
    MAX-ACCESS   read-only
    STATUS       current
    DESCRIPTION
        "Cisco UCS equipment:LocatorLedFsmStage:lastUpdateTime
        managed object property"
    ::= { cucsEquipmentLocatorLedFsmStageEntry 5 }

cucsEquipmentLocatorLedFsmStageName OBJECT-TYPE
    SYNTAX       CucsEquipmentLocatorLedFsmStageName
    MAX-ACCESS   read-only
    STATUS       current
    DESCRIPTION
        "Cisco UCS equipment:LocatorLedFsmStage:name managed
        object property"
    ::= { cucsEquipmentLocatorLedFsmStageEntry 6 }

cucsEquipmentLocatorLedFsmStageOrder OBJECT-TYPE
    SYNTAX       Gauge32
    MAX-ACCESS   read-only
    STATUS       current
    DESCRIPTION
        "Cisco UCS equipment:LocatorLedFsmStage:order managed
        object property"
    ::= { cucsEquipmentLocatorLedFsmStageEntry 7 }

cucsEquipmentLocatorLedFsmStageRetry OBJECT-TYPE
    SYNTAX       Gauge32
    MAX-ACCESS   read-only
    STATUS       current
    DESCRIPTION
        "Cisco UCS equipment:LocatorLedFsmStage:retry managed
        object property"
    ::= { cucsEquipmentLocatorLedFsmStageEntry 8 }

cucsEquipmentLocatorLedFsmStageStageStatus OBJECT-TYPE
    SYNTAX       CucsFsmFsmStageStatus
    MAX-ACCESS   read-only
    STATUS       current
    DESCRIPTION
        "Cisco UCS equipment:LocatorLedFsmStage:stageStatus
        managed object property"
    ::= { cucsEquipmentLocatorLedFsmStageEntry 9 }

cucsEquipmentLocatorLedFsmTaskTable OBJECT-TYPE
    SYNTAX           SEQUENCE OF CucsEquipmentLocatorLedFsmTaskEntry
    MAX-ACCESS       not-accessible
    STATUS           current
    DESCRIPTION
        "Cisco UCS equipment:LocatorLedFsmTask managed object table"
    ::= { cucsEquipmentObjects 41 }

cucsEquipmentLocatorLedFsmTaskEntry OBJECT-TYPE
    SYNTAX           CucsEquipmentLocatorLedFsmTaskEntry
    MAX-ACCESS       not-accessible
    STATUS           current
    DESCRIPTION
        "Entry for the cucsEquipmentLocatorLedFsmTaskTable table."
    INDEX { cucsEquipmentLocatorLedFsmTaskInstanceId }
    ::= { cucsEquipmentLocatorLedFsmTaskTable 1 }

CucsEquipmentLocatorLedFsmTaskEntry ::= SEQUENCE {
    cucsEquipmentLocatorLedFsmTaskInstanceId                         CucsManagedObjectId,
    cucsEquipmentLocatorLedFsmTaskDn                                 CucsManagedObjectDn,
    cucsEquipmentLocatorLedFsmTaskRn                                 SnmpAdminString,
    cucsEquipmentLocatorLedFsmTaskCompletion                         CucsFsmCompletion,
    cucsEquipmentLocatorLedFsmTaskFlags                              CucsFsmFlags,
    cucsEquipmentLocatorLedFsmTaskItem                               CucsEquipmentLocatorLedFsmTaskItem,
    cucsEquipmentLocatorLedFsmTaskSeqId                              Gauge32
}

cucsEquipmentLocatorLedFsmTaskInstanceId OBJECT-TYPE
    SYNTAX       CucsManagedObjectId
    MAX-ACCESS   not-accessible
    STATUS       current
    DESCRIPTION
        "Instance identifier of the managed object."
    ::= { cucsEquipmentLocatorLedFsmTaskEntry 1 }

cucsEquipmentLocatorLedFsmTaskDn OBJECT-TYPE
    SYNTAX       CucsManagedObjectDn
    MAX-ACCESS   read-only
    STATUS       current
    DESCRIPTION
        "Cisco UCS equipment:LocatorLedFsmTask:dn managed object property"
    ::= { cucsEquipmentLocatorLedFsmTaskEntry 2 }

cucsEquipmentLocatorLedFsmTaskRn OBJECT-TYPE
    SYNTAX       SnmpAdminString
    MAX-ACCESS   read-only
    STATUS       current
    DESCRIPTION
        "Cisco UCS equipment:LocatorLedFsmTask:rn managed object property"
    ::= { cucsEquipmentLocatorLedFsmTaskEntry 3 }

cucsEquipmentLocatorLedFsmTaskCompletion OBJECT-TYPE
    SYNTAX       CucsFsmCompletion
    MAX-ACCESS   read-only
    STATUS       current
    DESCRIPTION
        "Cisco UCS equipment:LocatorLedFsmTask:completion
        managed object property"
    ::= { cucsEquipmentLocatorLedFsmTaskEntry 4 }

cucsEquipmentLocatorLedFsmTaskFlags OBJECT-TYPE
    SYNTAX       CucsFsmFlags
    MAX-ACCESS   read-only
    STATUS       current
    DESCRIPTION
        "Cisco UCS equipment:LocatorLedFsmTask:flags managed
        object property"
    ::= { cucsEquipmentLocatorLedFsmTaskEntry 5 }

cucsEquipmentLocatorLedFsmTaskItem OBJECT-TYPE
    SYNTAX       CucsEquipmentLocatorLedFsmTaskItem
    MAX-ACCESS   read-only
    STATUS       current
    DESCRIPTION
        "Cisco UCS equipment:LocatorLedFsmTask:item managed
        object property"
    ::= { cucsEquipmentLocatorLedFsmTaskEntry 6 }

cucsEquipmentLocatorLedFsmTaskSeqId OBJECT-TYPE
    SYNTAX       Gauge32
    MAX-ACCESS   read-only
    STATUS       current
    DESCRIPTION
        "Cisco UCS equipment:LocatorLedFsmTask:seqId managed
        object property"
    ::= { cucsEquipmentLocatorLedFsmTaskEntry 7 }

cucsEquipmentManufacturingDefTable OBJECT-TYPE
    SYNTAX           SEQUENCE OF CucsEquipmentManufacturingDefEntry
    MAX-ACCESS       not-accessible
    STATUS           current
    DESCRIPTION
        "Cisco UCS equipment:ManufacturingDef managed object table"
    ::= { cucsEquipmentObjects 42 }

cucsEquipmentManufacturingDefEntry OBJECT-TYPE
    SYNTAX           CucsEquipmentManufacturingDefEntry
    MAX-ACCESS       not-accessible
    STATUS           current
    DESCRIPTION
        "Entry for the cucsEquipmentManufacturingDefTable table."
    INDEX { cucsEquipmentManufacturingDefInstanceId }
    ::= { cucsEquipmentManufacturingDefTable 1 }

CucsEquipmentManufacturingDefEntry ::= SEQUENCE {
    cucsEquipmentManufacturingDefInstanceId                          CucsManagedObjectId,
    cucsEquipmentManufacturingDefDn                                  CucsManagedObjectDn,
    cucsEquipmentManufacturingDefRn                                  SnmpAdminString,
    cucsEquipmentManufacturingDefCaption                             SnmpAdminString,
    cucsEquipmentManufacturingDefClei                                SnmpAdminString,
    cucsEquipmentManufacturingDefDescr                               SnmpAdminString,
    cucsEquipmentManufacturingDefDescription                         SnmpAdminString,
    cucsEquipmentManufacturingDefFruMajorType                        SnmpAdminString,
    cucsEquipmentManufacturingDefFruMinorType                        SnmpAdminString,
    cucsEquipmentManufacturingDefIntId                               SnmpAdminString,
    cucsEquipmentManufacturingDefName                                SnmpAdminString,
    cucsEquipmentManufacturingDefOemName                             SnmpAdminString,
    cucsEquipmentManufacturingDefOemPartNumber                       SnmpAdminString,
    cucsEquipmentManufacturingDefPartNumber                          SnmpAdminString,
    cucsEquipmentManufacturingDefPid                                 SnmpAdminString,
    cucsEquipmentManufacturingDefSeries                              SnmpAdminString,
    cucsEquipmentManufacturingDefSku                                 SnmpAdminString,
    cucsEquipmentManufacturingDefVendorEquipmentType                 SnmpAdminString,
    cucsEquipmentManufacturingDefVid                                 SnmpAdminString,
    cucsEquipmentManufacturingDefPolicyLevel                         Gauge32,
    cucsEquipmentManufacturingDefPolicyOwner                         CucsPolicyPolicyOwner
}

cucsEquipmentManufacturingDefInstanceId OBJECT-TYPE
    SYNTAX       CucsManagedObjectId
    MAX-ACCESS   not-accessible
    STATUS       current
    DESCRIPTION
        "Instance identifier of the managed object."
    ::= { cucsEquipmentManufacturingDefEntry 1 }

cucsEquipmentManufacturingDefDn OBJECT-TYPE
    SYNTAX       CucsManagedObjectDn
    MAX-ACCESS   read-only
    STATUS       current
    DESCRIPTION
        "Cisco UCS equipment:ManufacturingDef:dn managed object property"
    ::= { cucsEquipmentManufacturingDefEntry 2 }

cucsEquipmentManufacturingDefRn OBJECT-TYPE
    SYNTAX       SnmpAdminString
    MAX-ACCESS   read-only
    STATUS       current
    DESCRIPTION
        "Cisco UCS equipment:ManufacturingDef:rn managed object property"
    ::= { cucsEquipmentManufacturingDefEntry 3 }

cucsEquipmentManufacturingDefCaption OBJECT-TYPE
    SYNTAX       SnmpAdminString
    MAX-ACCESS   read-only
    STATUS       current
    DESCRIPTION
        "Cisco UCS equipment:ManufacturingDef:caption managed
        object property"
    ::= { cucsEquipmentManufacturingDefEntry 4 }

cucsEquipmentManufacturingDefClei OBJECT-TYPE
    SYNTAX       SnmpAdminString
    MAX-ACCESS   read-only
    STATUS       current
    DESCRIPTION
        "Cisco UCS equipment:ManufacturingDef:clei managed
        object property"
    ::= { cucsEquipmentManufacturingDefEntry 5 }

cucsEquipmentManufacturingDefDescr OBJECT-TYPE
    SYNTAX       SnmpAdminString
    MAX-ACCESS   read-only
    STATUS       current
    DESCRIPTION
        "Cisco UCS equipment:ManufacturingDef:descr managed
        object property"
    ::= { cucsEquipmentManufacturingDefEntry 6 }

cucsEquipmentManufacturingDefDescription OBJECT-TYPE
    SYNTAX       SnmpAdminString
    MAX-ACCESS   read-only
    STATUS       current
    DESCRIPTION
        "Cisco UCS equipment:ManufacturingDef:description
        managed object property"
    ::= { cucsEquipmentManufacturingDefEntry 7 }

cucsEquipmentManufacturingDefFruMajorType OBJECT-TYPE
    SYNTAX       SnmpAdminString
    MAX-ACCESS   read-only
    STATUS       current
    DESCRIPTION
        "Cisco UCS equipment:ManufacturingDef:fruMajorType
        managed object property"
    ::= { cucsEquipmentManufacturingDefEntry 8 }

cucsEquipmentManufacturingDefFruMinorType OBJECT-TYPE
    SYNTAX       SnmpAdminString
    MAX-ACCESS   read-only
    STATUS       current
    DESCRIPTION
        "Cisco UCS equipment:ManufacturingDef:fruMinorType
        managed object property"
    ::= { cucsEquipmentManufacturingDefEntry 9 }

cucsEquipmentManufacturingDefIntId OBJECT-TYPE
    SYNTAX       SnmpAdminString
    MAX-ACCESS   read-only
    STATUS       current
    DESCRIPTION
        "Cisco UCS equipment:ManufacturingDef:intId managed
        object property"
    ::= { cucsEquipmentManufacturingDefEntry 10 }

cucsEquipmentManufacturingDefName OBJECT-TYPE
    SYNTAX       SnmpAdminString
    MAX-ACCESS   read-only
    STATUS       current
    DESCRIPTION
        "Cisco UCS equipment:ManufacturingDef:name managed
        object property"
    ::= { cucsEquipmentManufacturingDefEntry 11 }

cucsEquipmentManufacturingDefOemName OBJECT-TYPE
    SYNTAX       SnmpAdminString
    MAX-ACCESS   read-only
    STATUS       current
    DESCRIPTION
        "Cisco UCS equipment:ManufacturingDef:oemName managed
        object property"
    ::= { cucsEquipmentManufacturingDefEntry 12 }

cucsEquipmentManufacturingDefOemPartNumber OBJECT-TYPE
    SYNTAX       SnmpAdminString
    MAX-ACCESS   read-only
    STATUS       current
    DESCRIPTION
        "Cisco UCS equipment:ManufacturingDef:oemPartNumber
        managed object property"
    ::= { cucsEquipmentManufacturingDefEntry 13 }

cucsEquipmentManufacturingDefPartNumber OBJECT-TYPE
    SYNTAX       SnmpAdminString
    MAX-ACCESS   read-only
    STATUS       current
    DESCRIPTION
        "Cisco UCS equipment:ManufacturingDef:partNumber
        managed object property"
    ::= { cucsEquipmentManufacturingDefEntry 14 }

cucsEquipmentManufacturingDefPid OBJECT-TYPE
    SYNTAX       SnmpAdminString
    MAX-ACCESS   read-only
    STATUS       current
    DESCRIPTION
        "Cisco UCS equipment:ManufacturingDef:pid managed object property"
    ::= { cucsEquipmentManufacturingDefEntry 15 }

cucsEquipmentManufacturingDefSeries OBJECT-TYPE
    SYNTAX       SnmpAdminString
    MAX-ACCESS   read-only
    STATUS       current
    DESCRIPTION
        "Cisco UCS equipment:ManufacturingDef:series managed
        object property"
    ::= { cucsEquipmentManufacturingDefEntry 16 }

cucsEquipmentManufacturingDefSku OBJECT-TYPE
    SYNTAX       SnmpAdminString
    MAX-ACCESS   read-only
    STATUS       current
    DESCRIPTION
        "Cisco UCS equipment:ManufacturingDef:sku managed object property"
    ::= { cucsEquipmentManufacturingDefEntry 17 }

cucsEquipmentManufacturingDefVendorEquipmentType OBJECT-TYPE
    SYNTAX       SnmpAdminString
    MAX-ACCESS   read-only
    STATUS       current
    DESCRIPTION
        "Cisco UCS equipment:ManufacturingDef:vendorEquipmentType
        managed object property"
    ::= { cucsEquipmentManufacturingDefEntry 18 }

cucsEquipmentManufacturingDefVid OBJECT-TYPE
    SYNTAX       SnmpAdminString
    MAX-ACCESS   read-only
    STATUS       current
    DESCRIPTION
        "Cisco UCS equipment:ManufacturingDef:vid managed object property"
    ::= { cucsEquipmentManufacturingDefEntry 19 }

cucsEquipmentManufacturingDefPolicyLevel OBJECT-TYPE
    SYNTAX       Gauge32
    MAX-ACCESS   read-only
    STATUS       current
    DESCRIPTION
        "Cisco UCS equipment:ManufacturingDef:policyLevel
        managed object property"
    ::= { cucsEquipmentManufacturingDefEntry 20 }

cucsEquipmentManufacturingDefPolicyOwner OBJECT-TYPE
    SYNTAX       CucsPolicyPolicyOwner
    MAX-ACCESS   read-only
    STATUS       current
    DESCRIPTION
        "Cisco UCS equipment:ManufacturingDef:policyOwner
        managed object property"
    ::= { cucsEquipmentManufacturingDefEntry 21 }

cucsEquipmentMemoryUnitCapProviderTable OBJECT-TYPE
    SYNTAX           SEQUENCE OF CucsEquipmentMemoryUnitCapProviderEntry
    MAX-ACCESS       not-accessible
    STATUS           current
    DESCRIPTION
        "Cisco UCS equipment:MemoryUnitCapProvider managed object table"
    ::= { cucsEquipmentObjects 43 }

cucsEquipmentMemoryUnitCapProviderEntry OBJECT-TYPE
    SYNTAX           CucsEquipmentMemoryUnitCapProviderEntry
    MAX-ACCESS       not-accessible
    STATUS           current
    DESCRIPTION
        "Entry for the cucsEquipmentMemoryUnitCapProviderTable table."
    INDEX { cucsEquipmentMemoryUnitCapProviderInstanceId }
    ::= { cucsEquipmentMemoryUnitCapProviderTable 1 }

CucsEquipmentMemoryUnitCapProviderEntry ::= SEQUENCE {
    cucsEquipmentMemoryUnitCapProviderInstanceId                     CucsManagedObjectId,
    cucsEquipmentMemoryUnitCapProviderDn                             CucsManagedObjectDn,
    cucsEquipmentMemoryUnitCapProviderRn                             SnmpAdminString,
    cucsEquipmentMemoryUnitCapProviderDeprecated                     TruthValue,
    cucsEquipmentMemoryUnitCapProviderGencount                       Gauge32,
    cucsEquipmentMemoryUnitCapProviderMgmtPlaneVer                   SnmpAdminString,
    cucsEquipmentMemoryUnitCapProviderModel                          SnmpAdminString,
    cucsEquipmentMemoryUnitCapProviderRevision                       SnmpAdminString,
    cucsEquipmentMemoryUnitCapProviderVendor                         SnmpAdminString,
    cucsEquipmentMemoryUnitCapProviderPromCardType                   Gauge32,
    cucsEquipmentMemoryUnitCapProviderDeleted                        TruthValue,
    cucsEquipmentMemoryUnitCapProviderElementLoadFailures            Gauge32,
    cucsEquipmentMemoryUnitCapProviderElementsLoaded                 Gauge32,
    cucsEquipmentMemoryUnitCapProviderLoadErrors                     Gauge32,
    cucsEquipmentMemoryUnitCapProviderLoadWarnings                   Gauge32
}

cucsEquipmentMemoryUnitCapProviderInstanceId OBJECT-TYPE
    SYNTAX       CucsManagedObjectId
    MAX-ACCESS   not-accessible
    STATUS       current
    DESCRIPTION
        "Instance identifier of the managed object."
    ::= { cucsEquipmentMemoryUnitCapProviderEntry 1 }

cucsEquipmentMemoryUnitCapProviderDn OBJECT-TYPE
    SYNTAX       CucsManagedObjectDn
    MAX-ACCESS   read-only
    STATUS       current
    DESCRIPTION
        "Cisco UCS equipment:MemoryUnitCapProvider:dn managed
        object property"
    ::= { cucsEquipmentMemoryUnitCapProviderEntry 2 }

cucsEquipmentMemoryUnitCapProviderRn OBJECT-TYPE
    SYNTAX       SnmpAdminString
    MAX-ACCESS   read-only
    STATUS       current
    DESCRIPTION
        "Cisco UCS equipment:MemoryUnitCapProvider:rn managed
        object property"
    ::= { cucsEquipmentMemoryUnitCapProviderEntry 3 }

cucsEquipmentMemoryUnitCapProviderDeprecated OBJECT-TYPE
    SYNTAX       TruthValue
    MAX-ACCESS   read-only
    STATUS       current
    DESCRIPTION
        "Cisco UCS equipment:MemoryUnitCapProvider:deprecated
        managed object property"
    ::= { cucsEquipmentMemoryUnitCapProviderEntry 4 }

cucsEquipmentMemoryUnitCapProviderGencount OBJECT-TYPE
    SYNTAX       Gauge32
    MAX-ACCESS   read-only
    STATUS       current
    DESCRIPTION
        "Cisco UCS equipment:MemoryUnitCapProvider:gencount
        managed object property"
    ::= { cucsEquipmentMemoryUnitCapProviderEntry 5 }

cucsEquipmentMemoryUnitCapProviderMgmtPlaneVer OBJECT-TYPE
    SYNTAX       SnmpAdminString
    MAX-ACCESS   read-only
    STATUS       current
    DESCRIPTION
        "Cisco UCS equipment:MemoryUnitCapProvider:mgmtPlaneVer
        managed object property"
    ::= { cucsEquipmentMemoryUnitCapProviderEntry 6 }

cucsEquipmentMemoryUnitCapProviderModel OBJECT-TYPE
    SYNTAX       SnmpAdminString
    MAX-ACCESS   read-only
    STATUS       current
    DESCRIPTION
        "Cisco UCS equipment:MemoryUnitCapProvider:model
        managed object property"
    ::= { cucsEquipmentMemoryUnitCapProviderEntry 7 }

cucsEquipmentMemoryUnitCapProviderRevision OBJECT-TYPE
    SYNTAX       SnmpAdminString
    MAX-ACCESS   read-only
    STATUS       current
    DESCRIPTION
        "Cisco UCS equipment:MemoryUnitCapProvider:revision
        managed object property"
    ::= { cucsEquipmentMemoryUnitCapProviderEntry 8 }

cucsEquipmentMemoryUnitCapProviderVendor OBJECT-TYPE
    SYNTAX       SnmpAdminString
    MAX-ACCESS   read-only
    STATUS       current
    DESCRIPTION
        "Cisco UCS equipment:MemoryUnitCapProvider:vendor
        managed object property"
    ::= { cucsEquipmentMemoryUnitCapProviderEntry 9 }

cucsEquipmentMemoryUnitCapProviderPromCardType OBJECT-TYPE
    SYNTAX       Gauge32
    MAX-ACCESS   read-only
    STATUS       current
    DESCRIPTION
        "Cisco UCS equipment:MemoryUnitCapProvider:promCardType
        managed object property"
    ::= { cucsEquipmentMemoryUnitCapProviderEntry 10 }

cucsEquipmentMemoryUnitCapProviderDeleted OBJECT-TYPE
    SYNTAX       TruthValue
    MAX-ACCESS   read-only
    STATUS       current
    DESCRIPTION
        "Cisco UCS equipment:MemoryUnitCapProvider:deleted
        managed object property"
    ::= { cucsEquipmentMemoryUnitCapProviderEntry 11 }

cucsEquipmentMemoryUnitCapProviderElementLoadFailures OBJECT-TYPE
    SYNTAX       Gauge32
    MAX-ACCESS   read-only
    STATUS       current
    DESCRIPTION
        "Cisco UCS equipment:MemoryUnitCapProvider:elementLoadFailures
        managed object property"
    ::= { cucsEquipmentMemoryUnitCapProviderEntry 12 }

cucsEquipmentMemoryUnitCapProviderElementsLoaded OBJECT-TYPE
    SYNTAX       Gauge32
    MAX-ACCESS   read-only
    STATUS       current
    DESCRIPTION
        "Cisco UCS equipment:MemoryUnitCapProvider:elementsLoaded
        managed object property"
    ::= { cucsEquipmentMemoryUnitCapProviderEntry 13 }

cucsEquipmentMemoryUnitCapProviderLoadErrors OBJECT-TYPE
    SYNTAX       Gauge32
    MAX-ACCESS   read-only
    STATUS       current
    DESCRIPTION
        "Cisco UCS equipment:MemoryUnitCapProvider:loadErrors
        managed object property"
    ::= { cucsEquipmentMemoryUnitCapProviderEntry 14 }

cucsEquipmentMemoryUnitCapProviderLoadWarnings OBJECT-TYPE
    SYNTAX       Gauge32
    MAX-ACCESS   read-only
    STATUS       current
    DESCRIPTION
        "Cisco UCS equipment:MemoryUnitCapProvider:loadWarnings
        managed object property"
    ::= { cucsEquipmentMemoryUnitCapProviderEntry 15 }

cucsEquipmentMemoryUnitDiscoveryModifierDefTable OBJECT-TYPE
    SYNTAX           SEQUENCE OF CucsEquipmentMemoryUnitDiscoveryModifierDefEntry
    MAX-ACCESS       not-accessible
    STATUS           current
    DESCRIPTION
        "Cisco UCS equipment:MemoryUnitDiscoveryModifierDef
        managed object table"
    ::= { cucsEquipmentObjects 44 }

cucsEquipmentMemoryUnitDiscoveryModifierDefEntry OBJECT-TYPE
    SYNTAX           CucsEquipmentMemoryUnitDiscoveryModifierDefEntry
    MAX-ACCESS       not-accessible
    STATUS           current
    DESCRIPTION
        "Entry for the cucsEquipmentMemoryUnitDiscoveryModifierDefTable table."
    INDEX { cucsEquipmentMemoryUnitDiscoveryModifierDefInstanceId }
    ::= { cucsEquipmentMemoryUnitDiscoveryModifierDefTable 1 }

CucsEquipmentMemoryUnitDiscoveryModifierDefEntry ::= SEQUENCE {
    cucsEquipmentMemoryUnitDiscoveryModifierDefInstanceId            CucsManagedObjectId,
    cucsEquipmentMemoryUnitDiscoveryModifierDefDn                    CucsManagedObjectDn,
    cucsEquipmentMemoryUnitDiscoveryModifierDefRn                    SnmpAdminString,
    cucsEquipmentMemoryUnitDiscoveryModifierDefAction                CucsEquipmentMemoryUnitDiscoveryModifierAction,
    cucsEquipmentMemoryUnitDiscoveryModifierDefConstraintType        CucsComputeMemoryUnitConstraintType,
    cucsEquipmentMemoryUnitDiscoveryModifierDefDescr                 SnmpAdminString,
    cucsEquipmentMemoryUnitDiscoveryModifierDefIntId                 SnmpAdminString,
    cucsEquipmentMemoryUnitDiscoveryModifierDefName                  SnmpAdminString,
    cucsEquipmentMemoryUnitDiscoveryModifierDefPolicyLevel           Gauge32,
    cucsEquipmentMemoryUnitDiscoveryModifierDefPolicyOwner           CucsPolicyPolicyOwner
}

cucsEquipmentMemoryUnitDiscoveryModifierDefInstanceId OBJECT-TYPE
    SYNTAX       CucsManagedObjectId
    MAX-ACCESS   not-accessible
    STATUS       current
    DESCRIPTION
        "Instance identifier of the managed object."
    ::= { cucsEquipmentMemoryUnitDiscoveryModifierDefEntry 1 }

cucsEquipmentMemoryUnitDiscoveryModifierDefDn OBJECT-TYPE
    SYNTAX       CucsManagedObjectDn
    MAX-ACCESS   read-only
    STATUS       current
    DESCRIPTION
        "Cisco UCS equipment:MemoryUnitDiscoveryModifierDef:dn
        managed object property"
    ::= { cucsEquipmentMemoryUnitDiscoveryModifierDefEntry 2 }

cucsEquipmentMemoryUnitDiscoveryModifierDefRn OBJECT-TYPE
    SYNTAX       SnmpAdminString
    MAX-ACCESS   read-only
    STATUS       current
    DESCRIPTION
        "Cisco UCS equipment:MemoryUnitDiscoveryModifierDef:rn
        managed object property"
    ::= { cucsEquipmentMemoryUnitDiscoveryModifierDefEntry 3 }

cucsEquipmentMemoryUnitDiscoveryModifierDefAction OBJECT-TYPE
    SYNTAX       CucsEquipmentMemoryUnitDiscoveryModifierAction
    MAX-ACCESS   read-only
    STATUS       current
    DESCRIPTION
        "Cisco UCS equipment:MemoryUnitDiscoveryModifierDef:action
        managed object property"
    ::= { cucsEquipmentMemoryUnitDiscoveryModifierDefEntry 4 }

cucsEquipmentMemoryUnitDiscoveryModifierDefConstraintType OBJECT-TYPE
    SYNTAX       CucsComputeMemoryUnitConstraintType
    MAX-ACCESS   read-only
    STATUS       current
    DESCRIPTION
        "Cisco UCS equipment:MemoryUnitDiscoveryModifierDef:constraintType
         managed object property"
    ::= { cucsEquipmentMemoryUnitDiscoveryModifierDefEntry 5 }

cucsEquipmentMemoryUnitDiscoveryModifierDefDescr OBJECT-TYPE
    SYNTAX       SnmpAdminString
    MAX-ACCESS   read-only
    STATUS       current
    DESCRIPTION
        "Cisco UCS equipment:MemoryUnitDiscoveryModifierDef:descr
        managed object property"
    ::= { cucsEquipmentMemoryUnitDiscoveryModifierDefEntry 6 }

cucsEquipmentMemoryUnitDiscoveryModifierDefIntId OBJECT-TYPE
    SYNTAX       SnmpAdminString
    MAX-ACCESS   read-only
    STATUS       current
    DESCRIPTION
        "Cisco UCS equipment:MemoryUnitDiscoveryModifierDef:intId
        managed object property"
    ::= { cucsEquipmentMemoryUnitDiscoveryModifierDefEntry 7 }

cucsEquipmentMemoryUnitDiscoveryModifierDefName OBJECT-TYPE
    SYNTAX       SnmpAdminString
    MAX-ACCESS   read-only
    STATUS       current
    DESCRIPTION
        "Cisco UCS equipment:MemoryUnitDiscoveryModifierDef:name
        managed object property"
    ::= { cucsEquipmentMemoryUnitDiscoveryModifierDefEntry 8 }

cucsEquipmentMemoryUnitDiscoveryModifierDefPolicyLevel OBJECT-TYPE
    SYNTAX       Gauge32
    MAX-ACCESS   read-only
    STATUS       current
    DESCRIPTION
        "Cisco UCS equipment:MemoryUnitDiscoveryModifierDef:policyLevel
        managed object property"
    ::= { cucsEquipmentMemoryUnitDiscoveryModifierDefEntry 9 }

cucsEquipmentMemoryUnitDiscoveryModifierDefPolicyOwner OBJECT-TYPE
    SYNTAX       CucsPolicyPolicyOwner
    MAX-ACCESS   read-only
    STATUS       current
    DESCRIPTION
        "Cisco UCS equipment:MemoryUnitDiscoveryModifierDef:policyOwner
        managed object property"
    ::= { cucsEquipmentMemoryUnitDiscoveryModifierDefEntry 10 }

cucsEquipmentMgmtCapProviderTable OBJECT-TYPE
    SYNTAX           SEQUENCE OF CucsEquipmentMgmtCapProviderEntry
    MAX-ACCESS       not-accessible
    STATUS           current
    DESCRIPTION
        "Cisco UCS equipment:MgmtCapProvider managed object table"
    ::= { cucsEquipmentObjects 45 }

cucsEquipmentMgmtCapProviderEntry OBJECT-TYPE
    SYNTAX           CucsEquipmentMgmtCapProviderEntry
    MAX-ACCESS       not-accessible
    STATUS           current
    DESCRIPTION
        "Entry for the cucsEquipmentMgmtCapProviderTable table."
    INDEX { cucsEquipmentMgmtCapProviderInstanceId }
    ::= { cucsEquipmentMgmtCapProviderTable 1 }

CucsEquipmentMgmtCapProviderEntry ::= SEQUENCE {
    cucsEquipmentMgmtCapProviderInstanceId                           CucsManagedObjectId,
    cucsEquipmentMgmtCapProviderDn                                   CucsManagedObjectDn,
    cucsEquipmentMgmtCapProviderRn                                   SnmpAdminString,
    cucsEquipmentMgmtCapProviderDeprecated                           TruthValue,
    cucsEquipmentMgmtCapProviderGencount                             Gauge32,
    cucsEquipmentMgmtCapProviderMgmtPlaneVer                         SnmpAdminString,
    cucsEquipmentMgmtCapProviderModel                                SnmpAdminString,
    cucsEquipmentMgmtCapProviderRevision                             SnmpAdminString,
    cucsEquipmentMgmtCapProviderVendor                               SnmpAdminString,
    cucsEquipmentMgmtCapProviderPromCardType                         Gauge32,
    cucsEquipmentMgmtCapProviderDeleted                              TruthValue,
    cucsEquipmentMgmtCapProviderElementLoadFailures                  Gauge32,
    cucsEquipmentMgmtCapProviderElementsLoaded                       Gauge32,
    cucsEquipmentMgmtCapProviderLoadErrors                           Gauge32,
    cucsEquipmentMgmtCapProviderLoadWarnings                         Gauge32
}

cucsEquipmentMgmtCapProviderInstanceId OBJECT-TYPE
    SYNTAX       CucsManagedObjectId
    MAX-ACCESS   not-accessible
    STATUS       current
    DESCRIPTION
        "Instance identifier of the managed object."
    ::= { cucsEquipmentMgmtCapProviderEntry 1 }

cucsEquipmentMgmtCapProviderDn OBJECT-TYPE
    SYNTAX       CucsManagedObjectDn
    MAX-ACCESS   read-only
    STATUS       current
    DESCRIPTION
        "Cisco UCS equipment:MgmtCapProvider:dn managed object property"
    ::= { cucsEquipmentMgmtCapProviderEntry 2 }

cucsEquipmentMgmtCapProviderRn OBJECT-TYPE
    SYNTAX       SnmpAdminString
    MAX-ACCESS   read-only
    STATUS       current
    DESCRIPTION
        "Cisco UCS equipment:MgmtCapProvider:rn managed object property"
    ::= { cucsEquipmentMgmtCapProviderEntry 3 }

cucsEquipmentMgmtCapProviderDeprecated OBJECT-TYPE
    SYNTAX       TruthValue
    MAX-ACCESS   read-only
    STATUS       current
    DESCRIPTION
        "Cisco UCS equipment:MgmtCapProvider:deprecated
        managed object property"
    ::= { cucsEquipmentMgmtCapProviderEntry 4 }

cucsEquipmentMgmtCapProviderGencount OBJECT-TYPE
    SYNTAX       Gauge32
    MAX-ACCESS   read-only
    STATUS       current
    DESCRIPTION
        "Cisco UCS equipment:MgmtCapProvider:gencount managed
        object property"
    ::= { cucsEquipmentMgmtCapProviderEntry 5 }

cucsEquipmentMgmtCapProviderMgmtPlaneVer OBJECT-TYPE
    SYNTAX       SnmpAdminString
    MAX-ACCESS   read-only
    STATUS       current
    DESCRIPTION
        "Cisco UCS equipment:MgmtCapProvider:mgmtPlaneVer
        managed object property"
    ::= { cucsEquipmentMgmtCapProviderEntry 6 }

cucsEquipmentMgmtCapProviderModel OBJECT-TYPE
    SYNTAX       SnmpAdminString
    MAX-ACCESS   read-only
    STATUS       current
    DESCRIPTION
        "Cisco UCS equipment:MgmtCapProvider:model managed
        object property"
    ::= { cucsEquipmentMgmtCapProviderEntry 7 }

cucsEquipmentMgmtCapProviderRevision OBJECT-TYPE
    SYNTAX       SnmpAdminString
    MAX-ACCESS   read-only
    STATUS       current
    DESCRIPTION
        "Cisco UCS equipment:MgmtCapProvider:revision managed
        object property"
    ::= { cucsEquipmentMgmtCapProviderEntry 8 }

cucsEquipmentMgmtCapProviderVendor OBJECT-TYPE
    SYNTAX       SnmpAdminString
    MAX-ACCESS   read-only
    STATUS       current
    DESCRIPTION
        "Cisco UCS equipment:MgmtCapProvider:vendor managed
        object property"
    ::= { cucsEquipmentMgmtCapProviderEntry 9 }

cucsEquipmentMgmtCapProviderPromCardType OBJECT-TYPE
    SYNTAX       Gauge32
    MAX-ACCESS   read-only
    STATUS       current
    DESCRIPTION
        "Cisco UCS equipment:MgmtCapProvider:promCardType
        managed object property"
    ::= { cucsEquipmentMgmtCapProviderEntry 10 }

cucsEquipmentMgmtCapProviderDeleted OBJECT-TYPE
    SYNTAX       TruthValue
    MAX-ACCESS   read-only
    STATUS       current
    DESCRIPTION
        "Cisco UCS equipment:MgmtCapProvider:deleted managed
        object property"
    ::= { cucsEquipmentMgmtCapProviderEntry 11 }

cucsEquipmentMgmtCapProviderElementLoadFailures OBJECT-TYPE
    SYNTAX       Gauge32
    MAX-ACCESS   read-only
    STATUS       current
    DESCRIPTION
        "Cisco UCS equipment:MgmtCapProvider:elementLoadFailures
        managed object property"
    ::= { cucsEquipmentMgmtCapProviderEntry 12 }

cucsEquipmentMgmtCapProviderElementsLoaded OBJECT-TYPE
    SYNTAX       Gauge32
    MAX-ACCESS   read-only
    STATUS       current
    DESCRIPTION
        "Cisco UCS equipment:MgmtCapProvider:elementsLoaded
        managed object property"
    ::= { cucsEquipmentMgmtCapProviderEntry 13 }

cucsEquipmentMgmtCapProviderLoadErrors OBJECT-TYPE
    SYNTAX       Gauge32
    MAX-ACCESS   read-only
    STATUS       current
    DESCRIPTION
        "Cisco UCS equipment:MgmtCapProvider:loadErrors
        managed object property"
    ::= { cucsEquipmentMgmtCapProviderEntry 14 }

cucsEquipmentMgmtCapProviderLoadWarnings OBJECT-TYPE
    SYNTAX       Gauge32
    MAX-ACCESS   read-only
    STATUS       current
    DESCRIPTION
        "Cisco UCS equipment:MgmtCapProvider:loadWarnings
        managed object property"
    ::= { cucsEquipmentMgmtCapProviderEntry 15 }

cucsEquipmentMgmtExtCapProviderTable OBJECT-TYPE
    SYNTAX           SEQUENCE OF CucsEquipmentMgmtExtCapProviderEntry
    MAX-ACCESS       not-accessible
    STATUS           current
    DESCRIPTION
        "Cisco UCS equipment:MgmtExtCapProvider managed object table"
    ::= { cucsEquipmentObjects 46 }

cucsEquipmentMgmtExtCapProviderEntry OBJECT-TYPE
    SYNTAX           CucsEquipmentMgmtExtCapProviderEntry
    MAX-ACCESS       not-accessible
    STATUS           current
    DESCRIPTION
        "Entry for the cucsEquipmentMgmtExtCapProviderTable table."
    INDEX { cucsEquipmentMgmtExtCapProviderInstanceId }
    ::= { cucsEquipmentMgmtExtCapProviderTable 1 }

CucsEquipmentMgmtExtCapProviderEntry ::= SEQUENCE {
    cucsEquipmentMgmtExtCapProviderInstanceId                        CucsManagedObjectId,
    cucsEquipmentMgmtExtCapProviderDn                                CucsManagedObjectDn,
    cucsEquipmentMgmtExtCapProviderRn                                SnmpAdminString,
    cucsEquipmentMgmtExtCapProviderDeprecated                        TruthValue,
    cucsEquipmentMgmtExtCapProviderGencount                          Gauge32,
    cucsEquipmentMgmtExtCapProviderMgmtPlaneVer                      SnmpAdminString,
    cucsEquipmentMgmtExtCapProviderModel                             SnmpAdminString,
    cucsEquipmentMgmtExtCapProviderRevision                          SnmpAdminString,
    cucsEquipmentMgmtExtCapProviderVendor                            SnmpAdminString,
    cucsEquipmentMgmtExtCapProviderPromCardType                      Gauge32,
    cucsEquipmentMgmtExtCapProviderDeleted                           TruthValue,
    cucsEquipmentMgmtExtCapProviderElementLoadFailures               Gauge32,
    cucsEquipmentMgmtExtCapProviderElementsLoaded                    Gauge32,
    cucsEquipmentMgmtExtCapProviderLoadErrors                        Gauge32,
    cucsEquipmentMgmtExtCapProviderLoadWarnings                      Gauge32
}

cucsEquipmentMgmtExtCapProviderInstanceId OBJECT-TYPE
    SYNTAX       CucsManagedObjectId
    MAX-ACCESS   not-accessible
    STATUS       current
    DESCRIPTION
        "Instance identifier of the managed object."
    ::= { cucsEquipmentMgmtExtCapProviderEntry 1 }

cucsEquipmentMgmtExtCapProviderDn OBJECT-TYPE
    SYNTAX       CucsManagedObjectDn
    MAX-ACCESS   read-only
    STATUS       current
    DESCRIPTION
        "Cisco UCS equipment:MgmtExtCapProvider:dn managed
        object property"
    ::= { cucsEquipmentMgmtExtCapProviderEntry 2 }

cucsEquipmentMgmtExtCapProviderRn OBJECT-TYPE
    SYNTAX       SnmpAdminString
    MAX-ACCESS   read-only
    STATUS       current
    DESCRIPTION
        "Cisco UCS equipment:MgmtExtCapProvider:rn managed
        object property"
    ::= { cucsEquipmentMgmtExtCapProviderEntry 3 }

cucsEquipmentMgmtExtCapProviderDeprecated OBJECT-TYPE
    SYNTAX       TruthValue
    MAX-ACCESS   read-only
    STATUS       current
    DESCRIPTION
        "Cisco UCS equipment:MgmtExtCapProvider:deprecated
        managed object property"
    ::= { cucsEquipmentMgmtExtCapProviderEntry 4 }

cucsEquipmentMgmtExtCapProviderGencount OBJECT-TYPE
    SYNTAX       Gauge32
    MAX-ACCESS   read-only
    STATUS       current
    DESCRIPTION
        "Cisco UCS equipment:MgmtExtCapProvider:gencount
        managed object property"
    ::= { cucsEquipmentMgmtExtCapProviderEntry 5 }

cucsEquipmentMgmtExtCapProviderMgmtPlaneVer OBJECT-TYPE
    SYNTAX       SnmpAdminString
    MAX-ACCESS   read-only
    STATUS       current
    DESCRIPTION
        "Cisco UCS equipment:MgmtExtCapProvider:mgmtPlaneVer
        managed object property"
    ::= { cucsEquipmentMgmtExtCapProviderEntry 6 }

cucsEquipmentMgmtExtCapProviderModel OBJECT-TYPE
    SYNTAX       SnmpAdminString
    MAX-ACCESS   read-only
    STATUS       current
    DESCRIPTION
        "Cisco UCS equipment:MgmtExtCapProvider:model managed
        object property"
    ::= { cucsEquipmentMgmtExtCapProviderEntry 7 }

cucsEquipmentMgmtExtCapProviderRevision OBJECT-TYPE
    SYNTAX       SnmpAdminString
    MAX-ACCESS   read-only
    STATUS       current
    DESCRIPTION
        "Cisco UCS equipment:MgmtExtCapProvider:revision
        managed object property"
    ::= { cucsEquipmentMgmtExtCapProviderEntry 8 }

cucsEquipmentMgmtExtCapProviderVendor OBJECT-TYPE
    SYNTAX       SnmpAdminString
    MAX-ACCESS   read-only
    STATUS       current
    DESCRIPTION
        "Cisco UCS equipment:MgmtExtCapProvider:vendor
        managed object property"
    ::= { cucsEquipmentMgmtExtCapProviderEntry 9 }

cucsEquipmentMgmtExtCapProviderPromCardType OBJECT-TYPE
    SYNTAX       Gauge32
    MAX-ACCESS   read-only
    STATUS       current
    DESCRIPTION
        "Cisco UCS equipment:MgmtExtCapProvider:promCardType
        managed object property"
    ::= { cucsEquipmentMgmtExtCapProviderEntry 10 }

cucsEquipmentMgmtExtCapProviderDeleted OBJECT-TYPE
    SYNTAX       TruthValue
    MAX-ACCESS   read-only
    STATUS       current
    DESCRIPTION
        "Cisco UCS equipment:MgmtExtCapProvider:deleted
        managed object property"
    ::= { cucsEquipmentMgmtExtCapProviderEntry 11 }

cucsEquipmentMgmtExtCapProviderElementLoadFailures OBJECT-TYPE
    SYNTAX       Gauge32
    MAX-ACCESS   read-only
    STATUS       current
    DESCRIPTION
        "Cisco UCS equipment:MgmtExtCapProvider:elementLoadFailures
        managed object property"
    ::= { cucsEquipmentMgmtExtCapProviderEntry 12 }

cucsEquipmentMgmtExtCapProviderElementsLoaded OBJECT-TYPE
    SYNTAX       Gauge32
    MAX-ACCESS   read-only
    STATUS       current
    DESCRIPTION
        "Cisco UCS equipment:MgmtExtCapProvider:elementsLoaded
        managed object property"
    ::= { cucsEquipmentMgmtExtCapProviderEntry 13 }

cucsEquipmentMgmtExtCapProviderLoadErrors OBJECT-TYPE
    SYNTAX       Gauge32
    MAX-ACCESS   read-only
    STATUS       current
    DESCRIPTION
        "Cisco UCS equipment:MgmtExtCapProvider:loadErrors
        managed object property"
    ::= { cucsEquipmentMgmtExtCapProviderEntry 14 }

cucsEquipmentMgmtExtCapProviderLoadWarnings OBJECT-TYPE
    SYNTAX       Gauge32
    MAX-ACCESS   read-only
    STATUS       current
    DESCRIPTION
        "Cisco UCS equipment:MgmtExtCapProvider:loadWarnings
        managed object property"
    ::= { cucsEquipmentMgmtExtCapProviderEntry 15 }

cucsEquipmentNetworkElementFanStatsTable OBJECT-TYPE
    SYNTAX           SEQUENCE OF CucsEquipmentNetworkElementFanStatsEntry
    MAX-ACCESS       not-accessible
    STATUS           current
    DESCRIPTION
        "Cisco UCS equipment:NetworkElementFanStats managed object table"
    ::= { cucsEquipmentObjects 86 }

cucsEquipmentNetworkElementFanStatsEntry OBJECT-TYPE
    SYNTAX           CucsEquipmentNetworkElementFanStatsEntry
    MAX-ACCESS       not-accessible
    STATUS           current
    DESCRIPTION
        "Entry for the cucsEquipmentNetworkElementFanStatsTable table."
    INDEX { cucsEquipmentNetworkElementFanStatsInstanceId }
    ::= { cucsEquipmentNetworkElementFanStatsTable 1 }

CucsEquipmentNetworkElementFanStatsEntry ::= SEQUENCE {
    cucsEquipmentNetworkElementFanStatsInstanceId                    CucsManagedObjectId,
    cucsEquipmentNetworkElementFanStatsDn                            CucsManagedObjectDn,
    cucsEquipmentNetworkElementFanStatsRn                            SnmpAdminString,
    cucsEquipmentNetworkElementFanStatsAirflowDirection              CucsEquipmentAirflowDirection,
    cucsEquipmentNetworkElementFanStatsDrivePercentage               Gauge32,
    cucsEquipmentNetworkElementFanStatsDrivePercentageAvg            Gauge32,
    cucsEquipmentNetworkElementFanStatsDrivePercentageMax            Gauge32,
    cucsEquipmentNetworkElementFanStatsDrivePercentageMin            Gauge32,
    cucsEquipmentNetworkElementFanStatsIntervals                     Gauge32,
    cucsEquipmentNetworkElementFanStatsSpeed                         Gauge32,
    cucsEquipmentNetworkElementFanStatsSpeedAvg                      Gauge32,
    cucsEquipmentNetworkElementFanStatsSpeedMax                      Gauge32,
    cucsEquipmentNetworkElementFanStatsSpeedMin                      Gauge32,
    cucsEquipmentNetworkElementFanStatsSuspect                       TruthValue,
    cucsEquipmentNetworkElementFanStatsThresholded                   CucsEquipmentNetworkElementFanStatsThresholded,
    cucsEquipmentNetworkElementFanStatsTimeCollected                 DateAndTime,
    cucsEquipmentNetworkElementFanStatsUpdate                        Gauge32
}

cucsEquipmentNetworkElementFanStatsInstanceId OBJECT-TYPE
    SYNTAX       CucsManagedObjectId
    MAX-ACCESS   not-accessible
    STATUS       current
    DESCRIPTION
        "Instance identifier of the managed object."
    ::= { cucsEquipmentNetworkElementFanStatsEntry 1 }

cucsEquipmentNetworkElementFanStatsDn OBJECT-TYPE
    SYNTAX       CucsManagedObjectDn
    MAX-ACCESS   read-only
    STATUS       current
    DESCRIPTION
        "Cisco UCS equipment:NetworkElementFanStats:dn
        managed object property"
    ::= { cucsEquipmentNetworkElementFanStatsEntry 2 }

cucsEquipmentNetworkElementFanStatsRn OBJECT-TYPE
    SYNTAX       SnmpAdminString
    MAX-ACCESS   read-only
    STATUS       current
    DESCRIPTION
        "Cisco UCS equipment:NetworkElementFanStats:rn
        managed object property"
    ::= { cucsEquipmentNetworkElementFanStatsEntry 3 }

cucsEquipmentNetworkElementFanStatsAirflowDirection OBJECT-TYPE
    SYNTAX       CucsEquipmentAirflowDirection
    MAX-ACCESS   read-only
    STATUS       current
    DESCRIPTION
        "Cisco UCS equipment:NetworkElementFanStats:airflowDirection
        managed object property"
    ::= { cucsEquipmentNetworkElementFanStatsEntry 4 }

cucsEquipmentNetworkElementFanStatsDrivePercentage OBJECT-TYPE
    SYNTAX       Gauge32
    MAX-ACCESS   read-only
    STATUS       current
    DESCRIPTION
        "Cisco UCS equipment:NetworkElementFanStats:drivePercentage
        managed object property"
    ::= { cucsEquipmentNetworkElementFanStatsEntry 5 }

cucsEquipmentNetworkElementFanStatsDrivePercentageAvg OBJECT-TYPE
    SYNTAX       Gauge32
    MAX-ACCESS   read-only
    STATUS       current
    DESCRIPTION
        "Cisco UCS equipment:NetworkElementFanStats:drivePercentageAvg
        managed object property"
    ::= { cucsEquipmentNetworkElementFanStatsEntry 6 }

cucsEquipmentNetworkElementFanStatsDrivePercentageMax OBJECT-TYPE
    SYNTAX       Gauge32
    MAX-ACCESS   read-only
    STATUS       current
    DESCRIPTION
        "Cisco UCS equipment:NetworkElementFanStats:drivePercentageMax
        managed object property"
    ::= { cucsEquipmentNetworkElementFanStatsEntry 7 }

cucsEquipmentNetworkElementFanStatsDrivePercentageMin OBJECT-TYPE
    SYNTAX       Gauge32
    MAX-ACCESS   read-only
    STATUS       current
    DESCRIPTION
        "Cisco UCS equipment:NetworkElementFanStats:drivePercentageMin
        managed object property"
    ::= { cucsEquipmentNetworkElementFanStatsEntry 8 }

cucsEquipmentNetworkElementFanStatsIntervals OBJECT-TYPE
    SYNTAX       Gauge32
    MAX-ACCESS   read-only
    STATUS       current
    DESCRIPTION
        "Cisco UCS equipment:NetworkElementFanStats:intervals
        managed object property"
    ::= { cucsEquipmentNetworkElementFanStatsEntry 9 }

cucsEquipmentNetworkElementFanStatsSpeed OBJECT-TYPE
    SYNTAX       Gauge32
    MAX-ACCESS   read-only
    STATUS       current
    DESCRIPTION
        "Cisco UCS equipment:NetworkElementFanStats:speed
        managed object property"
    ::= { cucsEquipmentNetworkElementFanStatsEntry 10 }

cucsEquipmentNetworkElementFanStatsSpeedAvg OBJECT-TYPE
    SYNTAX       Gauge32
    MAX-ACCESS   read-only
    STATUS       current
    DESCRIPTION
        "Cisco UCS equipment:NetworkElementFanStats:speedAvg
        managed object property"
    ::= { cucsEquipmentNetworkElementFanStatsEntry 11 }

cucsEquipmentNetworkElementFanStatsSpeedMax OBJECT-TYPE
    SYNTAX       Gauge32
    MAX-ACCESS   read-only
    STATUS       current
    DESCRIPTION
        "Cisco UCS equipment:NetworkElementFanStats:speedMax
        managed object property"
    ::= { cucsEquipmentNetworkElementFanStatsEntry 12 }

cucsEquipmentNetworkElementFanStatsSpeedMin OBJECT-TYPE
    SYNTAX       Gauge32
    MAX-ACCESS   read-only
    STATUS       current
    DESCRIPTION
        "Cisco UCS equipment:NetworkElementFanStats:speedMin
        managed object property"
    ::= { cucsEquipmentNetworkElementFanStatsEntry 13 }

cucsEquipmentNetworkElementFanStatsSuspect OBJECT-TYPE
    SYNTAX       TruthValue
    MAX-ACCESS   read-only
    STATUS       current
    DESCRIPTION
        "Cisco UCS equipment:NetworkElementFanStats:suspect
        managed object property"
    ::= { cucsEquipmentNetworkElementFanStatsEntry 14 }

cucsEquipmentNetworkElementFanStatsThresholded OBJECT-TYPE
    SYNTAX       CucsEquipmentNetworkElementFanStatsThresholded
    MAX-ACCESS   read-only
    STATUS       current
    DESCRIPTION
        "Cisco UCS equipment:NetworkElementFanStats:thresholded
        managed object property"
    ::= { cucsEquipmentNetworkElementFanStatsEntry 15 }

cucsEquipmentNetworkElementFanStatsTimeCollected OBJECT-TYPE
    SYNTAX       DateAndTime
    MAX-ACCESS   read-only
    STATUS       current
    DESCRIPTION
        "Cisco UCS equipment:NetworkElementFanStats:timeCollected
        managed object property"
    ::= { cucsEquipmentNetworkElementFanStatsEntry 16 }

cucsEquipmentNetworkElementFanStatsUpdate OBJECT-TYPE
    SYNTAX       Gauge32
    MAX-ACCESS   read-only
    STATUS       current
    DESCRIPTION
        "Cisco UCS equipment:NetworkElementFanStats:update
        managed object property"
    ::= { cucsEquipmentNetworkElementFanStatsEntry 17 }

cucsEquipmentNetworkElementFanStatsHistTable OBJECT-TYPE
    SYNTAX           SEQUENCE OF CucsEquipmentNetworkElementFanStatsHistEntry
    MAX-ACCESS       not-accessible
    STATUS           current
    DESCRIPTION
        "Cisco UCS equipment:NetworkElementFanStatsHist
        managed object table"
    ::= { cucsEquipmentObjects 87 }

cucsEquipmentNetworkElementFanStatsHistEntry OBJECT-TYPE
    SYNTAX           CucsEquipmentNetworkElementFanStatsHistEntry
    MAX-ACCESS       not-accessible
    STATUS           current
    DESCRIPTION
        "Entry for the cucsEquipmentNetworkElementFanStatsHistTable table."
    INDEX { cucsEquipmentNetworkElementFanStatsHistInstanceId }
    ::= { cucsEquipmentNetworkElementFanStatsHistTable 1 }

CucsEquipmentNetworkElementFanStatsHistEntry ::= SEQUENCE {
    cucsEquipmentNetworkElementFanStatsHistInstanceId                CucsManagedObjectId,
    cucsEquipmentNetworkElementFanStatsHistDn                        CucsManagedObjectDn,
    cucsEquipmentNetworkElementFanStatsHistRn                        SnmpAdminString,
    cucsEquipmentNetworkElementFanStatsHistDrivePercentage           Gauge32,
    cucsEquipmentNetworkElementFanStatsHistDrivePercentageAvg        Gauge32,
    cucsEquipmentNetworkElementFanStatsHistDrivePercentageMax        Gauge32,
    cucsEquipmentNetworkElementFanStatsHistDrivePercentageMin        Gauge32,
    cucsEquipmentNetworkElementFanStatsHistId                        Unsigned64,
    cucsEquipmentNetworkElementFanStatsHistMostRecent                TruthValue,
    cucsEquipmentNetworkElementFanStatsHistSpeed                     Gauge32,
    cucsEquipmentNetworkElementFanStatsHistSpeedAvg                  Gauge32,
    cucsEquipmentNetworkElementFanStatsHistSpeedMax                  Gauge32,
    cucsEquipmentNetworkElementFanStatsHistSpeedMin                  Gauge32,
    cucsEquipmentNetworkElementFanStatsHistSuspect                   TruthValue,
    cucsEquipmentNetworkElementFanStatsHistThresholded               CucsEquipmentNetworkElementFanStatsHistThresholded,
    cucsEquipmentNetworkElementFanStatsHistTimeCollected             DateAndTime
}

cucsEquipmentNetworkElementFanStatsHistInstanceId OBJECT-TYPE
    SYNTAX       CucsManagedObjectId
    MAX-ACCESS   not-accessible
    STATUS       current
    DESCRIPTION
        "Instance identifier of the managed object."
    ::= { cucsEquipmentNetworkElementFanStatsHistEntry 1 }

cucsEquipmentNetworkElementFanStatsHistDn OBJECT-TYPE
    SYNTAX       CucsManagedObjectDn
    MAX-ACCESS   read-only
    STATUS       current
    DESCRIPTION
        "Cisco UCS equipment:NetworkElementFanStatsHist:dn
        managed object property"
    ::= { cucsEquipmentNetworkElementFanStatsHistEntry 2 }

cucsEquipmentNetworkElementFanStatsHistRn OBJECT-TYPE
    SYNTAX       SnmpAdminString
    MAX-ACCESS   read-only
    STATUS       current
    DESCRIPTION
        "Cisco UCS equipment:NetworkElementFanStatsHist:rn
        managed object property"
    ::= { cucsEquipmentNetworkElementFanStatsHistEntry 3 }

cucsEquipmentNetworkElementFanStatsHistDrivePercentage OBJECT-TYPE
    SYNTAX       Gauge32
    MAX-ACCESS   read-only
    STATUS       current
    DESCRIPTION
        "Cisco UCS equipment:NetworkElementFanStatsHist:drivePercentage
        managed object property"
    ::= { cucsEquipmentNetworkElementFanStatsHistEntry 4 }

cucsEquipmentNetworkElementFanStatsHistDrivePercentageAvg OBJECT-TYPE
    SYNTAX       Gauge32
    MAX-ACCESS   read-only
    STATUS       current
    DESCRIPTION
        "Cisco UCS equipment:NetworkElementFanStatsHist:drivePercentageAvg
         managed object property"
    ::= { cucsEquipmentNetworkElementFanStatsHistEntry 5 }

cucsEquipmentNetworkElementFanStatsHistDrivePercentageMax OBJECT-TYPE
    SYNTAX       Gauge32
    MAX-ACCESS   read-only
    STATUS       current
    DESCRIPTION
        "Cisco UCS equipment:NetworkElementFanStatsHist:drivePercentageMax
         managed object property"
    ::= { cucsEquipmentNetworkElementFanStatsHistEntry 6 }

cucsEquipmentNetworkElementFanStatsHistDrivePercentageMin OBJECT-TYPE
    SYNTAX       Gauge32
    MAX-ACCESS   read-only
    STATUS       current
    DESCRIPTION
        "Cisco UCS equipment:NetworkElementFanStatsHist:drivePercentageMin
         managed object property"
    ::= { cucsEquipmentNetworkElementFanStatsHistEntry 7 }

cucsEquipmentNetworkElementFanStatsHistId OBJECT-TYPE
    SYNTAX       Unsigned64
    MAX-ACCESS   read-only
    STATUS       current
    DESCRIPTION
        "Cisco UCS equipment:NetworkElementFanStatsHist:id
        managed object property"
    ::= { cucsEquipmentNetworkElementFanStatsHistEntry 8 }

cucsEquipmentNetworkElementFanStatsHistMostRecent OBJECT-TYPE
    SYNTAX       TruthValue
    MAX-ACCESS   read-only
    STATUS       current
    DESCRIPTION
        "Cisco UCS equipment:NetworkElementFanStatsHist:mostRecent
        managed object property"
    ::= { cucsEquipmentNetworkElementFanStatsHistEntry 9 }

cucsEquipmentNetworkElementFanStatsHistSpeed OBJECT-TYPE
    SYNTAX       Gauge32
    MAX-ACCESS   read-only
    STATUS       current
    DESCRIPTION
        "Cisco UCS equipment:NetworkElementFanStatsHist:speed
        managed object property"
    ::= { cucsEquipmentNetworkElementFanStatsHistEntry 10 }

cucsEquipmentNetworkElementFanStatsHistSpeedAvg OBJECT-TYPE
    SYNTAX       Gauge32
    MAX-ACCESS   read-only
    STATUS       current
    DESCRIPTION
        "Cisco UCS equipment:NetworkElementFanStatsHist:speedAvg
        managed object property"
    ::= { cucsEquipmentNetworkElementFanStatsHistEntry 11 }

cucsEquipmentNetworkElementFanStatsHistSpeedMax OBJECT-TYPE
    SYNTAX       Gauge32
    MAX-ACCESS   read-only
    STATUS       current
    DESCRIPTION
        "Cisco UCS equipment:NetworkElementFanStatsHist:speedMax
        managed object property"
    ::= { cucsEquipmentNetworkElementFanStatsHistEntry 12 }

cucsEquipmentNetworkElementFanStatsHistSpeedMin OBJECT-TYPE
    SYNTAX       Gauge32
    MAX-ACCESS   read-only
    STATUS       current
    DESCRIPTION
        "Cisco UCS equipment:NetworkElementFanStatsHist:speedMin
        managed object property"
    ::= { cucsEquipmentNetworkElementFanStatsHistEntry 13 }

cucsEquipmentNetworkElementFanStatsHistSuspect OBJECT-TYPE
    SYNTAX       TruthValue
    MAX-ACCESS   read-only
    STATUS       current
    DESCRIPTION
        "Cisco UCS equipment:NetworkElementFanStatsHist:suspect
        managed object property"
    ::= { cucsEquipmentNetworkElementFanStatsHistEntry 14 }

cucsEquipmentNetworkElementFanStatsHistThresholded OBJECT-TYPE
    SYNTAX       CucsEquipmentNetworkElementFanStatsHistThresholded
    MAX-ACCESS   read-only
    STATUS       current
    DESCRIPTION
        "Cisco UCS equipment:NetworkElementFanStatsHist:thresholded
        managed object property"
    ::= { cucsEquipmentNetworkElementFanStatsHistEntry 15 }

cucsEquipmentNetworkElementFanStatsHistTimeCollected OBJECT-TYPE
    SYNTAX       DateAndTime
    MAX-ACCESS   read-only
    STATUS       current
    DESCRIPTION
        "Cisco UCS equipment:NetworkElementFanStatsHist:timeCollected
        managed object property"
    ::= { cucsEquipmentNetworkElementFanStatsHistEntry 16 }

cucsEquipmentPOSTTable OBJECT-TYPE
    SYNTAX           SEQUENCE OF CucsEquipmentPOSTEntry
    MAX-ACCESS       not-accessible
    STATUS           current
    DESCRIPTION
        "Cisco UCS equipment:POST managed object table"
    ::= { cucsEquipmentObjects 47 }

cucsEquipmentPOSTEntry OBJECT-TYPE
    SYNTAX           CucsEquipmentPOSTEntry
    MAX-ACCESS       not-accessible
    STATUS           current
    DESCRIPTION
        "Entry for the cucsEquipmentPOSTTable table."
    INDEX { cucsEquipmentPOSTInstanceId }
    ::= { cucsEquipmentPOSTTable 1 }

CucsEquipmentPOSTEntry ::= SEQUENCE {
    cucsEquipmentPOSTInstanceId                                      CucsManagedObjectId,
    cucsEquipmentPOSTDn                                              CucsManagedObjectDn,
    cucsEquipmentPOSTRn                                              SnmpAdminString,
    cucsEquipmentPOSTCode                                            SnmpAdminString,
    cucsEquipmentPOSTCreated                                         DateAndTime,
    cucsEquipmentPOSTDescr                                           SnmpAdminString,
    cucsEquipmentPOSTGlobalId                                        SnmpAdminString,
    cucsEquipmentPOSTLocalId                                         SnmpAdminString,
    cucsEquipmentPOSTMethod                                          CucsEquipmentMethod,
    cucsEquipmentPOSTName                                            SnmpAdminString,
    cucsEquipmentPOSTRecoverable                                     CucsEquipmentPOSTRecoverability,
    cucsEquipmentPOSTRecoveryAction                                  SnmpAdminString,
    cucsEquipmentPOSTSeverity                                        CucsConditionSeverity,
    cucsEquipmentPOSTType                                            SnmpAdminString,
    cucsEquipmentPOSTValue                                           Gauge32
}

cucsEquipmentPOSTInstanceId OBJECT-TYPE
    SYNTAX       CucsManagedObjectId
    MAX-ACCESS   not-accessible
    STATUS       current
    DESCRIPTION
        "Instance identifier of the managed object."
    ::= { cucsEquipmentPOSTEntry 1 }

cucsEquipmentPOSTDn OBJECT-TYPE
    SYNTAX       CucsManagedObjectDn
    MAX-ACCESS   read-only
    STATUS       current
    DESCRIPTION
        "Cisco UCS equipment:POST:dn managed object property"
    ::= { cucsEquipmentPOSTEntry 2 }

cucsEquipmentPOSTRn OBJECT-TYPE
    SYNTAX       SnmpAdminString
    MAX-ACCESS   read-only
    STATUS       current
    DESCRIPTION
        "Cisco UCS equipment:POST:rn managed object property"
    ::= { cucsEquipmentPOSTEntry 3 }

cucsEquipmentPOSTCode OBJECT-TYPE
    SYNTAX       SnmpAdminString
    MAX-ACCESS   read-only
    STATUS       current
    DESCRIPTION
        "Cisco UCS equipment:POST:code managed object property"
    ::= { cucsEquipmentPOSTEntry 4 }

cucsEquipmentPOSTCreated OBJECT-TYPE
    SYNTAX       DateAndTime
    MAX-ACCESS   read-only
    STATUS       current
    DESCRIPTION
        "Cisco UCS equipment:POST:created managed object property"
    ::= { cucsEquipmentPOSTEntry 5 }

cucsEquipmentPOSTDescr OBJECT-TYPE
    SYNTAX       SnmpAdminString
    MAX-ACCESS   read-only
    STATUS       current
    DESCRIPTION
        "Cisco UCS equipment:POST:descr managed object property"
    ::= { cucsEquipmentPOSTEntry 6 }

cucsEquipmentPOSTGlobalId OBJECT-TYPE
    SYNTAX       SnmpAdminString
    MAX-ACCESS   read-only
    STATUS       current
    DESCRIPTION
        "Cisco UCS equipment:POST:globalId managed object property"
    ::= { cucsEquipmentPOSTEntry 7 }

cucsEquipmentPOSTLocalId OBJECT-TYPE
    SYNTAX       SnmpAdminString
    MAX-ACCESS   read-only
    STATUS       current
    DESCRIPTION
        "Cisco UCS equipment:POST:localId managed object property"
    ::= { cucsEquipmentPOSTEntry 8 }

cucsEquipmentPOSTMethod OBJECT-TYPE
    SYNTAX       CucsEquipmentMethod
    MAX-ACCESS   read-only
    STATUS       current
    DESCRIPTION
        "Cisco UCS equipment:POST:method managed object property"
    ::= { cucsEquipmentPOSTEntry 9 }

cucsEquipmentPOSTName OBJECT-TYPE
    SYNTAX       SnmpAdminString
    MAX-ACCESS   read-only
    STATUS       current
    DESCRIPTION
        "Cisco UCS equipment:POST:name managed object property"
    ::= { cucsEquipmentPOSTEntry 10 }

cucsEquipmentPOSTRecoverable OBJECT-TYPE
    SYNTAX       CucsEquipmentPOSTRecoverability
    MAX-ACCESS   read-only
    STATUS       current
    DESCRIPTION
        "Cisco UCS equipment:POST:recoverable managed object property"
    ::= { cucsEquipmentPOSTEntry 11 }

cucsEquipmentPOSTRecoveryAction OBJECT-TYPE
    SYNTAX       SnmpAdminString
    MAX-ACCESS   read-only
    STATUS       current
    DESCRIPTION
        "Cisco UCS equipment:POST:recoveryAction managed object property"
    ::= { cucsEquipmentPOSTEntry 12 }

cucsEquipmentPOSTSeverity OBJECT-TYPE
    SYNTAX       CucsConditionSeverity
    MAX-ACCESS   read-only
    STATUS       current
    DESCRIPTION
        "Cisco UCS equipment:POST:severity managed object property"
    ::= { cucsEquipmentPOSTEntry 13 }

cucsEquipmentPOSTType OBJECT-TYPE
    SYNTAX       SnmpAdminString
    MAX-ACCESS   read-only
    STATUS       current
    DESCRIPTION
        "Cisco UCS equipment:POST:type managed object property"
    ::= { cucsEquipmentPOSTEntry 14 }

cucsEquipmentPOSTValue OBJECT-TYPE
    SYNTAX       Gauge32
    MAX-ACCESS   read-only
    STATUS       current
    DESCRIPTION
        "Cisco UCS equipment:POST:value managed object property"
    ::= { cucsEquipmentPOSTEntry 15 }

cucsEquipmentPOSTCodeTable OBJECT-TYPE
    SYNTAX           SEQUENCE OF CucsEquipmentPOSTCodeEntry
    MAX-ACCESS       not-accessible
    STATUS           current
    DESCRIPTION
        "Cisco UCS equipment:POSTCode managed object table"
    ::= { cucsEquipmentObjects 48 }

cucsEquipmentPOSTCodeEntry OBJECT-TYPE
    SYNTAX           CucsEquipmentPOSTCodeEntry
    MAX-ACCESS       not-accessible
    STATUS           current
    DESCRIPTION
        "Entry for the cucsEquipmentPOSTCodeTable table."
    INDEX { cucsEquipmentPOSTCodeInstanceId }
    ::= { cucsEquipmentPOSTCodeTable 1 }

CucsEquipmentPOSTCodeEntry ::= SEQUENCE {
    cucsEquipmentPOSTCodeInstanceId                                  CucsManagedObjectId,
    cucsEquipmentPOSTCodeDn                                          CucsManagedObjectDn,
    cucsEquipmentPOSTCodeRn                                          SnmpAdminString,
    cucsEquipmentPOSTCodeCode                                        SnmpAdminString,
    cucsEquipmentPOSTCodeDescr                                       SnmpAdminString,
    cucsEquipmentPOSTCodeGlobalId                                    SnmpAdminString,
    cucsEquipmentPOSTCodeLocalId                                     SnmpAdminString,
    cucsEquipmentPOSTCodeMethod                                      CucsEquipmentMethod,
    cucsEquipmentPOSTCodeName                                        SnmpAdminString,
    cucsEquipmentPOSTCodeRecoverable                                 CucsEquipmentPOSTRecoverability,
    cucsEquipmentPOSTCodeRecoveryAction                              SnmpAdminString,
    cucsEquipmentPOSTCodeSeverity                                    CucsConditionSeverity
}

cucsEquipmentPOSTCodeInstanceId OBJECT-TYPE
    SYNTAX       CucsManagedObjectId
    MAX-ACCESS   not-accessible
    STATUS       current
    DESCRIPTION
        "Instance identifier of the managed object."
    ::= { cucsEquipmentPOSTCodeEntry 1 }

cucsEquipmentPOSTCodeDn OBJECT-TYPE
    SYNTAX       CucsManagedObjectDn
    MAX-ACCESS   read-only
    STATUS       current
    DESCRIPTION
        "Cisco UCS equipment:POSTCode:dn managed object property"
    ::= { cucsEquipmentPOSTCodeEntry 2 }

cucsEquipmentPOSTCodeRn OBJECT-TYPE
    SYNTAX       SnmpAdminString
    MAX-ACCESS   read-only
    STATUS       current
    DESCRIPTION
        "Cisco UCS equipment:POSTCode:rn managed object property"
    ::= { cucsEquipmentPOSTCodeEntry 3 }

cucsEquipmentPOSTCodeCode OBJECT-TYPE
    SYNTAX       SnmpAdminString
    MAX-ACCESS   read-only
    STATUS       current
    DESCRIPTION
        "Cisco UCS equipment:POSTCode:code managed object property"
    ::= { cucsEquipmentPOSTCodeEntry 4 }

cucsEquipmentPOSTCodeDescr OBJECT-TYPE
    SYNTAX       SnmpAdminString
    MAX-ACCESS   read-only
    STATUS       current
    DESCRIPTION
        "Cisco UCS equipment:POSTCode:descr managed object property"
    ::= { cucsEquipmentPOSTCodeEntry 5 }

cucsEquipmentPOSTCodeGlobalId OBJECT-TYPE
    SYNTAX       SnmpAdminString
    MAX-ACCESS   read-only
    STATUS       current
    DESCRIPTION
        "Cisco UCS equipment:POSTCode:globalId managed object property"
    ::= { cucsEquipmentPOSTCodeEntry 6 }

cucsEquipmentPOSTCodeLocalId OBJECT-TYPE
    SYNTAX       SnmpAdminString
    MAX-ACCESS   read-only
    STATUS       current
    DESCRIPTION
        "Cisco UCS equipment:POSTCode:localId managed object property"
    ::= { cucsEquipmentPOSTCodeEntry 7 }

cucsEquipmentPOSTCodeMethod OBJECT-TYPE
    SYNTAX       CucsEquipmentMethod
    MAX-ACCESS   read-only
    STATUS       current
    DESCRIPTION
        "Cisco UCS equipment:POSTCode:method managed object property"
    ::= { cucsEquipmentPOSTCodeEntry 8 }

cucsEquipmentPOSTCodeName OBJECT-TYPE
    SYNTAX       SnmpAdminString
    MAX-ACCESS   read-only
    STATUS       current
    DESCRIPTION
        "Cisco UCS equipment:POSTCode:name managed object property"
    ::= { cucsEquipmentPOSTCodeEntry 9 }

cucsEquipmentPOSTCodeRecoverable OBJECT-TYPE
    SYNTAX       CucsEquipmentPOSTRecoverability
    MAX-ACCESS   read-only
    STATUS       current
    DESCRIPTION
        "Cisco UCS equipment:POSTCode:recoverable managed object property"
    ::= { cucsEquipmentPOSTCodeEntry 10 }

cucsEquipmentPOSTCodeRecoveryAction OBJECT-TYPE
    SYNTAX       SnmpAdminString
    MAX-ACCESS   read-only
    STATUS       current
    DESCRIPTION
        "Cisco UCS equipment:POSTCode:recoveryAction managed
        object property"
    ::= { cucsEquipmentPOSTCodeEntry 11 }

cucsEquipmentPOSTCodeSeverity OBJECT-TYPE
    SYNTAX       CucsConditionSeverity
    MAX-ACCESS   read-only
    STATUS       current
    DESCRIPTION
        "Cisco UCS equipment:POSTCode:severity managed object property"
    ::= { cucsEquipmentPOSTCodeEntry 12 }

cucsEquipmentPOSTCodeReporterTable OBJECT-TYPE
    SYNTAX           SEQUENCE OF CucsEquipmentPOSTCodeReporterEntry
    MAX-ACCESS       not-accessible
    STATUS           current
    DESCRIPTION
        "Cisco UCS equipment:POSTCodeReporter managed object table"
    ::= { cucsEquipmentObjects 49 }

cucsEquipmentPOSTCodeReporterEntry OBJECT-TYPE
    SYNTAX           CucsEquipmentPOSTCodeReporterEntry
    MAX-ACCESS       not-accessible
    STATUS           current
    DESCRIPTION
        "Entry for the cucsEquipmentPOSTCodeReporterTable table."
    INDEX { cucsEquipmentPOSTCodeReporterInstanceId }
    ::= { cucsEquipmentPOSTCodeReporterTable 1 }

CucsEquipmentPOSTCodeReporterEntry ::= SEQUENCE {
    cucsEquipmentPOSTCodeReporterInstanceId                          CucsManagedObjectId,
    cucsEquipmentPOSTCodeReporterDn                                  CucsManagedObjectDn,
    cucsEquipmentPOSTCodeReporterRn                                  SnmpAdminString,
    cucsEquipmentPOSTCodeReporterModel                               SnmpAdminString,
    cucsEquipmentPOSTCodeReporterRevision                            SnmpAdminString,
    cucsEquipmentPOSTCodeReporterSerial                              SnmpAdminString,
    cucsEquipmentPOSTCodeReporterType                                SnmpAdminString,
    cucsEquipmentPOSTCodeReporterVendor                              SnmpAdminString,
    cucsEquipmentPOSTCodeReporterBaseContainer                       SnmpAdminString,
    cucsEquipmentPOSTCodeReporterName                                SnmpAdminString
}

cucsEquipmentPOSTCodeReporterInstanceId OBJECT-TYPE
    SYNTAX       CucsManagedObjectId
    MAX-ACCESS   not-accessible
    STATUS       current
    DESCRIPTION
        "Instance identifier of the managed object."
    ::= { cucsEquipmentPOSTCodeReporterEntry 1 }

cucsEquipmentPOSTCodeReporterDn OBJECT-TYPE
    SYNTAX       CucsManagedObjectDn
    MAX-ACCESS   read-only
    STATUS       current
    DESCRIPTION
        "Cisco UCS equipment:POSTCodeReporter:dn managed object property"
    ::= { cucsEquipmentPOSTCodeReporterEntry 2 }

cucsEquipmentPOSTCodeReporterRn OBJECT-TYPE
    SYNTAX       SnmpAdminString
    MAX-ACCESS   read-only
    STATUS       current
    DESCRIPTION
        "Cisco UCS equipment:POSTCodeReporter:rn managed object property"
    ::= { cucsEquipmentPOSTCodeReporterEntry 3 }

cucsEquipmentPOSTCodeReporterModel OBJECT-TYPE
    SYNTAX       SnmpAdminString
    MAX-ACCESS   read-only
    STATUS       current
    DESCRIPTION
        "Cisco UCS equipment:POSTCodeReporter:model managed
        object property"
    ::= { cucsEquipmentPOSTCodeReporterEntry 4 }

cucsEquipmentPOSTCodeReporterRevision OBJECT-TYPE
    SYNTAX       SnmpAdminString
    MAX-ACCESS   read-only
    STATUS       current
    DESCRIPTION
        "Cisco UCS equipment:POSTCodeReporter:revision
        managed object property"
    ::= { cucsEquipmentPOSTCodeReporterEntry 5 }

cucsEquipmentPOSTCodeReporterSerial OBJECT-TYPE
    SYNTAX       SnmpAdminString
    MAX-ACCESS   read-only
    STATUS       current
    DESCRIPTION
        "Cisco UCS equipment:POSTCodeReporter:serial managed
        object property"
    ::= { cucsEquipmentPOSTCodeReporterEntry 6 }

cucsEquipmentPOSTCodeReporterType OBJECT-TYPE
    SYNTAX       SnmpAdminString
    MAX-ACCESS   read-only
    STATUS       current
    DESCRIPTION
        "Cisco UCS equipment:POSTCodeReporter:type managed
        object property"
    ::= { cucsEquipmentPOSTCodeReporterEntry 7 }

cucsEquipmentPOSTCodeReporterVendor OBJECT-TYPE
    SYNTAX       SnmpAdminString
    MAX-ACCESS   read-only
    STATUS       current
    DESCRIPTION
        "Cisco UCS equipment:POSTCodeReporter:vendor managed
        object property"
    ::= { cucsEquipmentPOSTCodeReporterEntry 8 }

cucsEquipmentPOSTCodeReporterBaseContainer OBJECT-TYPE
    SYNTAX       SnmpAdminString
    MAX-ACCESS   read-only
    STATUS       current
    DESCRIPTION
        "Cisco UCS equipment:POSTCodeReporter:baseContainer
        managed object property"
    ::= { cucsEquipmentPOSTCodeReporterEntry 9 }

cucsEquipmentPOSTCodeReporterName OBJECT-TYPE
    SYNTAX       SnmpAdminString
    MAX-ACCESS   read-only
    STATUS       current
    DESCRIPTION
        "Cisco UCS equipment:POSTCodeReporter:name managed
        object property"
    ::= { cucsEquipmentPOSTCodeReporterEntry 10 }

cucsEquipmentPOSTCodeTemplateTable OBJECT-TYPE
    SYNTAX           SEQUENCE OF CucsEquipmentPOSTCodeTemplateEntry
    MAX-ACCESS       not-accessible
    STATUS           current
    DESCRIPTION
        "Cisco UCS equipment:POSTCodeTemplate managed object table"
    ::= { cucsEquipmentObjects 74 }

cucsEquipmentPOSTCodeTemplateEntry OBJECT-TYPE
    SYNTAX           CucsEquipmentPOSTCodeTemplateEntry
    MAX-ACCESS       not-accessible
    STATUS           current
    DESCRIPTION
        "Entry for the cucsEquipmentPOSTCodeTemplateTable table."
    INDEX { cucsEquipmentPOSTCodeTemplateInstanceId }
    ::= { cucsEquipmentPOSTCodeTemplateTable 1 }

CucsEquipmentPOSTCodeTemplateEntry ::= SEQUENCE {
    cucsEquipmentPOSTCodeTemplateInstanceId                          CucsManagedObjectId,
    cucsEquipmentPOSTCodeTemplateDn                                  CucsManagedObjectDn,
    cucsEquipmentPOSTCodeTemplateRn                                  SnmpAdminString,
    cucsEquipmentPOSTCodeTemplateBaseContainer                       SnmpAdminString,
    cucsEquipmentPOSTCodeTemplateName                                SnmpAdminString
}

cucsEquipmentPOSTCodeTemplateInstanceId OBJECT-TYPE
    SYNTAX       CucsManagedObjectId
    MAX-ACCESS   not-accessible
    STATUS       current
    DESCRIPTION
        "Instance identifier of the managed object."
    ::= { cucsEquipmentPOSTCodeTemplateEntry 1 }

cucsEquipmentPOSTCodeTemplateDn OBJECT-TYPE
    SYNTAX       CucsManagedObjectDn
    MAX-ACCESS   read-only
    STATUS       current
    DESCRIPTION
        "Cisco UCS equipment:POSTCodeTemplate:dn managed object property"
    ::= { cucsEquipmentPOSTCodeTemplateEntry 2 }

cucsEquipmentPOSTCodeTemplateRn OBJECT-TYPE
    SYNTAX       SnmpAdminString
    MAX-ACCESS   read-only
    STATUS       current
    DESCRIPTION
        "Cisco UCS equipment:POSTCodeTemplate:rn managed object property"
    ::= { cucsEquipmentPOSTCodeTemplateEntry 3 }

cucsEquipmentPOSTCodeTemplateBaseContainer OBJECT-TYPE
    SYNTAX       SnmpAdminString
    MAX-ACCESS   read-only
    STATUS       current
    DESCRIPTION
        "Cisco UCS equipment:POSTCodeTemplate:baseContainer
        managed object property"
    ::= { cucsEquipmentPOSTCodeTemplateEntry 4 }

cucsEquipmentPOSTCodeTemplateName OBJECT-TYPE
    SYNTAX       SnmpAdminString
    MAX-ACCESS   read-only
    STATUS       current
    DESCRIPTION
        "Cisco UCS equipment:POSTCodeTemplate:name managed
        object property"
    ::= { cucsEquipmentPOSTCodeTemplateEntry 5 }

cucsEquipmentPciDefTable OBJECT-TYPE
    SYNTAX           SEQUENCE OF CucsEquipmentPciDefEntry
    MAX-ACCESS       not-accessible
    STATUS           current
    DESCRIPTION
        "Cisco UCS equipment:PciDef managed object table"
    ::= { cucsEquipmentObjects 50 }

cucsEquipmentPciDefEntry OBJECT-TYPE
    SYNTAX           CucsEquipmentPciDefEntry
    MAX-ACCESS       not-accessible
    STATUS           current
    DESCRIPTION
        "Entry for the cucsEquipmentPciDefTable table."
    INDEX { cucsEquipmentPciDefInstanceId }
    ::= { cucsEquipmentPciDefTable 1 }

CucsEquipmentPciDefEntry ::= SEQUENCE {
    cucsEquipmentPciDefInstanceId                                    CucsManagedObjectId,
    cucsEquipmentPciDefDn                                            CucsManagedObjectDn,
    cucsEquipmentPciDefRn                                            SnmpAdminString,
    cucsEquipmentPciDefDescr                                         SnmpAdminString,
    cucsEquipmentPciDefDevice                                        Gauge32,
    cucsEquipmentPciDefIntId                                         SnmpAdminString,
    cucsEquipmentPciDefName                                          SnmpAdminString,
    cucsEquipmentPciDefSubdevice                                     Gauge32,
    cucsEquipmentPciDefSubvendor                                     Gauge32,
    cucsEquipmentPciDefVendor                                        Gauge32,
    cucsEquipmentPciDefPolicyLevel                                   Gauge32,
    cucsEquipmentPciDefPolicyOwner                                   CucsPolicyPolicyOwner
}

cucsEquipmentPciDefInstanceId OBJECT-TYPE
    SYNTAX       CucsManagedObjectId
    MAX-ACCESS   not-accessible
    STATUS       current
    DESCRIPTION
        "Instance identifier of the managed object."
    ::= { cucsEquipmentPciDefEntry 1 }

cucsEquipmentPciDefDn OBJECT-TYPE
    SYNTAX       CucsManagedObjectDn
    MAX-ACCESS   read-only
    STATUS       current
    DESCRIPTION
        "Cisco UCS equipment:PciDef:dn managed object property"
    ::= { cucsEquipmentPciDefEntry 2 }

cucsEquipmentPciDefRn OBJECT-TYPE
    SYNTAX       SnmpAdminString
    MAX-ACCESS   read-only
    STATUS       current
    DESCRIPTION
        "Cisco UCS equipment:PciDef:rn managed object property"
    ::= { cucsEquipmentPciDefEntry 3 }

cucsEquipmentPciDefDescr OBJECT-TYPE
    SYNTAX       SnmpAdminString
    MAX-ACCESS   read-only
    STATUS       current
    DESCRIPTION
        "Cisco UCS equipment:PciDef:descr managed object property"
    ::= { cucsEquipmentPciDefEntry 4 }

cucsEquipmentPciDefDevice OBJECT-TYPE
    SYNTAX       Gauge32
    MAX-ACCESS   read-only
    STATUS       current
    DESCRIPTION
        "Cisco UCS equipment:PciDef:device managed object property"
    ::= { cucsEquipmentPciDefEntry 5 }

cucsEquipmentPciDefIntId OBJECT-TYPE
    SYNTAX       SnmpAdminString
    MAX-ACCESS   read-only
    STATUS       current
    DESCRIPTION
        "Cisco UCS equipment:PciDef:intId managed object property"
    ::= { cucsEquipmentPciDefEntry 6 }

cucsEquipmentPciDefName OBJECT-TYPE
    SYNTAX       SnmpAdminString
    MAX-ACCESS   read-only
    STATUS       current
    DESCRIPTION
        "Cisco UCS equipment:PciDef:name managed object property"
    ::= { cucsEquipmentPciDefEntry 7 }

cucsEquipmentPciDefSubdevice OBJECT-TYPE
    SYNTAX       Gauge32
    MAX-ACCESS   read-only
    STATUS       current
    DESCRIPTION
        "Cisco UCS equipment:PciDef:subdevice managed object property"
    ::= { cucsEquipmentPciDefEntry 8 }

cucsEquipmentPciDefSubvendor OBJECT-TYPE
    SYNTAX       Gauge32
    MAX-ACCESS   read-only
    STATUS       current
    DESCRIPTION
        "Cisco UCS equipment:PciDef:subvendor managed object property"
    ::= { cucsEquipmentPciDefEntry 9 }

cucsEquipmentPciDefVendor OBJECT-TYPE
    SYNTAX       Gauge32
    MAX-ACCESS   read-only
    STATUS       current
    DESCRIPTION
        "Cisco UCS equipment:PciDef:vendor managed object property"
    ::= { cucsEquipmentPciDefEntry 10 }

cucsEquipmentPciDefPolicyLevel OBJECT-TYPE
    SYNTAX       Gauge32
    MAX-ACCESS   read-only
    STATUS       current
    DESCRIPTION
        "Cisco UCS equipment:PciDef:policyLevel managed object property"
    ::= { cucsEquipmentPciDefEntry 11 }

cucsEquipmentPciDefPolicyOwner OBJECT-TYPE
    SYNTAX       CucsPolicyPolicyOwner
    MAX-ACCESS   read-only
    STATUS       current
    DESCRIPTION
        "Cisco UCS equipment:PciDef:policyOwner managed object property"
    ::= { cucsEquipmentPciDefEntry 12 }

cucsEquipmentPhysicalDefTable OBJECT-TYPE
    SYNTAX           SEQUENCE OF CucsEquipmentPhysicalDefEntry
    MAX-ACCESS       not-accessible
    STATUS           current
    DESCRIPTION
        "Cisco UCS equipment:PhysicalDef managed object table"
    ::= { cucsEquipmentObjects 51 }

cucsEquipmentPhysicalDefEntry OBJECT-TYPE
    SYNTAX           CucsEquipmentPhysicalDefEntry
    MAX-ACCESS       not-accessible
    STATUS           current
    DESCRIPTION
        "Entry for the cucsEquipmentPhysicalDefTable table."
    INDEX { cucsEquipmentPhysicalDefInstanceId }
    ::= { cucsEquipmentPhysicalDefTable 1 }

CucsEquipmentPhysicalDefEntry ::= SEQUENCE {
    cucsEquipmentPhysicalDefInstanceId                               CucsManagedObjectId,
    cucsEquipmentPhysicalDefDn                                       CucsManagedObjectDn,
    cucsEquipmentPhysicalDefRn                                       SnmpAdminString,
    cucsEquipmentPhysicalDefDepth                                    INTEGER,
    cucsEquipmentPhysicalDefDescr                                    SnmpAdminString,
    cucsEquipmentPhysicalDefHeight                                   INTEGER,
    cucsEquipmentPhysicalDefIntId                                    SnmpAdminString,
    cucsEquipmentPhysicalDefMaximumPower                             INTEGER,
    cucsEquipmentPhysicalDefMaximumTemperature                       INTEGER,
    cucsEquipmentPhysicalDefMinimumPower                             INTEGER,
    cucsEquipmentPhysicalDefMinimumTemperature                       INTEGER,
    cucsEquipmentPhysicalDefName                                     SnmpAdminString,
    cucsEquipmentPhysicalDefNominalPower                             INTEGER,
    cucsEquipmentPhysicalDefNominalTemperature                       INTEGER,
    cucsEquipmentPhysicalDefOperatingVoltages                        SnmpAdminString,
    cucsEquipmentPhysicalDefWeight                                   INTEGER,
    cucsEquipmentPhysicalDefWidth                                    INTEGER,
    cucsEquipmentPhysicalDefPolicyLevel                              Gauge32,
    cucsEquipmentPhysicalDefPolicyOwner                              CucsPolicyPolicyOwner
}

cucsEquipmentPhysicalDefInstanceId OBJECT-TYPE
    SYNTAX       CucsManagedObjectId
    MAX-ACCESS   not-accessible
    STATUS       current
    DESCRIPTION
        "Instance identifier of the managed object."
    ::= { cucsEquipmentPhysicalDefEntry 1 }

cucsEquipmentPhysicalDefDn OBJECT-TYPE
    SYNTAX       CucsManagedObjectDn
    MAX-ACCESS   read-only
    STATUS       current
    DESCRIPTION
        "Cisco UCS equipment:PhysicalDef:dn managed object property"
    ::= { cucsEquipmentPhysicalDefEntry 2 }

cucsEquipmentPhysicalDefRn OBJECT-TYPE
    SYNTAX       SnmpAdminString
    MAX-ACCESS   read-only
    STATUS       current
    DESCRIPTION
        "Cisco UCS equipment:PhysicalDef:rn managed object property"
    ::= { cucsEquipmentPhysicalDefEntry 3 }

cucsEquipmentPhysicalDefDepth OBJECT-TYPE
    SYNTAX       INTEGER
    MAX-ACCESS   read-only
    STATUS       current
    DESCRIPTION
        "Cisco UCS equipment:PhysicalDef:depth managed object property"
    ::= { cucsEquipmentPhysicalDefEntry 4 }

cucsEquipmentPhysicalDefDescr OBJECT-TYPE
    SYNTAX       SnmpAdminString
    MAX-ACCESS   read-only
    STATUS       current
    DESCRIPTION
        "Cisco UCS equipment:PhysicalDef:descr managed object property"
    ::= { cucsEquipmentPhysicalDefEntry 5 }

cucsEquipmentPhysicalDefHeight OBJECT-TYPE
    SYNTAX       INTEGER
    MAX-ACCESS   read-only
    STATUS       current
    DESCRIPTION
        "Cisco UCS equipment:PhysicalDef:height managed object property"
    ::= { cucsEquipmentPhysicalDefEntry 6 }

cucsEquipmentPhysicalDefIntId OBJECT-TYPE
    SYNTAX       SnmpAdminString
    MAX-ACCESS   read-only
    STATUS       current
    DESCRIPTION
        "Cisco UCS equipment:PhysicalDef:intId managed object property"
    ::= { cucsEquipmentPhysicalDefEntry 7 }

cucsEquipmentPhysicalDefMaximumPower OBJECT-TYPE
    SYNTAX       INTEGER
    MAX-ACCESS   read-only
    STATUS       current
    DESCRIPTION
        "Cisco UCS equipment:PhysicalDef:maximumPower managed
        object property"
    ::= { cucsEquipmentPhysicalDefEntry 8 }

cucsEquipmentPhysicalDefMaximumTemperature OBJECT-TYPE
    SYNTAX       INTEGER
    MAX-ACCESS   read-only
    STATUS       current
    DESCRIPTION
        "Cisco UCS equipment:PhysicalDef:maximumTemperature
        managed object property"
    ::= { cucsEquipmentPhysicalDefEntry 9 }

cucsEquipmentPhysicalDefMinimumPower OBJECT-TYPE
    SYNTAX       INTEGER
    MAX-ACCESS   read-only
    STATUS       current
    DESCRIPTION
        "Cisco UCS equipment:PhysicalDef:minimumPower managed
        object property"
    ::= { cucsEquipmentPhysicalDefEntry 10 }

cucsEquipmentPhysicalDefMinimumTemperature OBJECT-TYPE
    SYNTAX       INTEGER
    MAX-ACCESS   read-only
    STATUS       current
    DESCRIPTION
        "Cisco UCS equipment:PhysicalDef:minimumTemperature
        managed object property"
    ::= { cucsEquipmentPhysicalDefEntry 11 }

cucsEquipmentPhysicalDefName OBJECT-TYPE
    SYNTAX       SnmpAdminString
    MAX-ACCESS   read-only
    STATUS       current
    DESCRIPTION
        "Cisco UCS equipment:PhysicalDef:name managed object property"
    ::= { cucsEquipmentPhysicalDefEntry 12 }

cucsEquipmentPhysicalDefNominalPower OBJECT-TYPE
    SYNTAX       INTEGER
    MAX-ACCESS   read-only
    STATUS       current
    DESCRIPTION
        "Cisco UCS equipment:PhysicalDef:nominalPower managed
        object property"
    ::= { cucsEquipmentPhysicalDefEntry 13 }

cucsEquipmentPhysicalDefNominalTemperature OBJECT-TYPE
    SYNTAX       INTEGER
    MAX-ACCESS   read-only
    STATUS       current
    DESCRIPTION
        "Cisco UCS equipment:PhysicalDef:nominalTemperature
        managed object property"
    ::= { cucsEquipmentPhysicalDefEntry 14 }

cucsEquipmentPhysicalDefOperatingVoltages OBJECT-TYPE
    SYNTAX       SnmpAdminString
    MAX-ACCESS   read-only
    STATUS       current
    DESCRIPTION
        "Cisco UCS equipment:PhysicalDef:operatingVoltages
        managed object property"
    ::= { cucsEquipmentPhysicalDefEntry 15 }

cucsEquipmentPhysicalDefWeight OBJECT-TYPE
    SYNTAX       INTEGER
    MAX-ACCESS   read-only
    STATUS       current
    DESCRIPTION
        "Cisco UCS equipment:PhysicalDef:weight managed object property"
    ::= { cucsEquipmentPhysicalDefEntry 16 }

cucsEquipmentPhysicalDefWidth OBJECT-TYPE
    SYNTAX       INTEGER
    MAX-ACCESS   read-only
    STATUS       current
    DESCRIPTION
        "Cisco UCS equipment:PhysicalDef:width managed object property"
    ::= { cucsEquipmentPhysicalDefEntry 17 }

cucsEquipmentPhysicalDefPolicyLevel OBJECT-TYPE
    SYNTAX       Gauge32
    MAX-ACCESS   read-only
    STATUS       current
    DESCRIPTION
        "Cisco UCS equipment:PhysicalDef:policyLevel managed
        object property"
    ::= { cucsEquipmentPhysicalDefEntry 18 }

cucsEquipmentPhysicalDefPolicyOwner OBJECT-TYPE
    SYNTAX       CucsPolicyPolicyOwner
    MAX-ACCESS   read-only
    STATUS       current
    DESCRIPTION
        "Cisco UCS equipment:PhysicalDef:policyOwner managed
        object property"
    ::= { cucsEquipmentPhysicalDefEntry 19 }

cucsEquipmentPictureTable OBJECT-TYPE
    SYNTAX           SEQUENCE OF CucsEquipmentPictureEntry
    MAX-ACCESS       not-accessible
    STATUS           current
    DESCRIPTION
        "Cisco UCS equipment:Picture managed object table"
    ::= { cucsEquipmentObjects 52 }

cucsEquipmentPictureEntry OBJECT-TYPE
    SYNTAX           CucsEquipmentPictureEntry
    MAX-ACCESS       not-accessible
    STATUS           current
    DESCRIPTION
        "Entry for the cucsEquipmentPictureTable table."
    INDEX { cucsEquipmentPictureInstanceId }
    ::= { cucsEquipmentPictureTable 1 }

CucsEquipmentPictureEntry ::= SEQUENCE {
    cucsEquipmentPictureInstanceId                                   CucsManagedObjectId,
    cucsEquipmentPictureDn                                           CucsManagedObjectDn,
    cucsEquipmentPictureRn                                           SnmpAdminString,
    cucsEquipmentPictureFileName                                     SnmpAdminString,
    cucsEquipmentPictureType                                         CucsEquipmentPictureType
}

cucsEquipmentPictureInstanceId OBJECT-TYPE
    SYNTAX       CucsManagedObjectId
    MAX-ACCESS   not-accessible
    STATUS       current
    DESCRIPTION
        "Instance identifier of the managed object."
    ::= { cucsEquipmentPictureEntry 1 }

cucsEquipmentPictureDn OBJECT-TYPE
    SYNTAX       CucsManagedObjectDn
    MAX-ACCESS   read-only
    STATUS       current
    DESCRIPTION
        "Cisco UCS equipment:Picture:dn managed object property"
    ::= { cucsEquipmentPictureEntry 2 }

cucsEquipmentPictureRn OBJECT-TYPE
    SYNTAX       SnmpAdminString
    MAX-ACCESS   read-only
    STATUS       current
    DESCRIPTION
        "Cisco UCS equipment:Picture:rn managed object property"
    ::= { cucsEquipmentPictureEntry 3 }

cucsEquipmentPictureFileName OBJECT-TYPE
    SYNTAX       SnmpAdminString
    MAX-ACCESS   read-only
    STATUS       current
    DESCRIPTION
        "Cisco UCS equipment:Picture:fileName managed object property"
    ::= { cucsEquipmentPictureEntry 4 }

cucsEquipmentPictureType OBJECT-TYPE
    SYNTAX       CucsEquipmentPictureType
    MAX-ACCESS   read-only
    STATUS       current
    DESCRIPTION
        "Cisco UCS equipment:Picture:type managed object property"
    ::= { cucsEquipmentPictureEntry 5 }

cucsEquipmentPortGroupAggregationDefTable OBJECT-TYPE
    SYNTAX           SEQUENCE OF CucsEquipmentPortGroupAggregationDefEntry
    MAX-ACCESS       not-accessible
    STATUS           current
    DESCRIPTION
        "Cisco UCS equipment:PortGroupAggregationDef managed object table"
    ::= { cucsEquipmentObjects 88 }

cucsEquipmentPortGroupAggregationDefEntry OBJECT-TYPE
    SYNTAX           CucsEquipmentPortGroupAggregationDefEntry
    MAX-ACCESS       not-accessible
    STATUS           current
    DESCRIPTION
        "Entry for the cucsEquipmentPortGroupAggregationDefTable table."
    INDEX { cucsEquipmentPortGroupAggregationDefInstanceId }
    ::= { cucsEquipmentPortGroupAggregationDefTable 1 }

CucsEquipmentPortGroupAggregationDefEntry ::= SEQUENCE {
    cucsEquipmentPortGroupAggregationDefInstanceId                   CucsManagedObjectId,
    cucsEquipmentPortGroupAggregationDefDn                           CucsManagedObjectDn,
    cucsEquipmentPortGroupAggregationDefRn                           SnmpAdminString,
    cucsEquipmentPortGroupAggregationDefAggregationCap               CucsComputeLinkAggregationCap,
    cucsEquipmentPortGroupAggregationDefDescr                        SnmpAdminString,
    cucsEquipmentPortGroupAggregationDefIntId                        SnmpAdminString,
    cucsEquipmentPortGroupAggregationDefName                         SnmpAdminString,
    cucsEquipmentPortGroupAggregationDefType                         CucsPortGroupType,
    cucsEquipmentPortGroupAggregationDefPolicyLevel                  Gauge32,
    cucsEquipmentPortGroupAggregationDefPolicyOwner                  CucsPolicyPolicyOwner
}

cucsEquipmentPortGroupAggregationDefInstanceId OBJECT-TYPE
    SYNTAX       CucsManagedObjectId
    MAX-ACCESS   not-accessible
    STATUS       current
    DESCRIPTION
        "Instance identifier of the managed object."
    ::= { cucsEquipmentPortGroupAggregationDefEntry 1 }

cucsEquipmentPortGroupAggregationDefDn OBJECT-TYPE
    SYNTAX       CucsManagedObjectDn
    MAX-ACCESS   read-only
    STATUS       current
    DESCRIPTION
        "Cisco UCS equipment:PortGroupAggregationDef:dn
        managed object property"
    ::= { cucsEquipmentPortGroupAggregationDefEntry 2 }

cucsEquipmentPortGroupAggregationDefRn OBJECT-TYPE
    SYNTAX       SnmpAdminString
    MAX-ACCESS   read-only
    STATUS       current
    DESCRIPTION
        "Cisco UCS equipment:PortGroupAggregationDef:rn
        managed object property"
    ::= { cucsEquipmentPortGroupAggregationDefEntry 3 }

cucsEquipmentPortGroupAggregationDefAggregationCap OBJECT-TYPE
    SYNTAX       CucsComputeLinkAggregationCap
    MAX-ACCESS   read-only
    STATUS       current
    DESCRIPTION
        "Cisco UCS equipment:PortGroupAggregationDef:aggregationCap
        managed object property"
    ::= { cucsEquipmentPortGroupAggregationDefEntry 4 }

cucsEquipmentPortGroupAggregationDefDescr OBJECT-TYPE
    SYNTAX       SnmpAdminString
    MAX-ACCESS   read-only
    STATUS       current
    DESCRIPTION
        "Cisco UCS equipment:PortGroupAggregationDef:descr
        managed object property"
    ::= { cucsEquipmentPortGroupAggregationDefEntry 5 }

cucsEquipmentPortGroupAggregationDefIntId OBJECT-TYPE
    SYNTAX       SnmpAdminString
    MAX-ACCESS   read-only
    STATUS       current
    DESCRIPTION
        "Cisco UCS equipment:PortGroupAggregationDef:intId
        managed object property"
    ::= { cucsEquipmentPortGroupAggregationDefEntry 6 }

cucsEquipmentPortGroupAggregationDefName OBJECT-TYPE
    SYNTAX       SnmpAdminString
    MAX-ACCESS   read-only
    STATUS       current
    DESCRIPTION
        "Cisco UCS equipment:PortGroupAggregationDef:name
        managed object property"
    ::= { cucsEquipmentPortGroupAggregationDefEntry 7 }

cucsEquipmentPortGroupAggregationDefType OBJECT-TYPE
    SYNTAX       CucsPortGroupType
    MAX-ACCESS   read-only
    STATUS       current
    DESCRIPTION
        "Cisco UCS equipment:PortGroupAggregationDef:type
        managed object property"
    ::= { cucsEquipmentPortGroupAggregationDefEntry 8 }

cucsEquipmentPortGroupAggregationDefPolicyLevel OBJECT-TYPE
    SYNTAX       Gauge32
    MAX-ACCESS   read-only
    STATUS       current
    DESCRIPTION
        "Cisco UCS equipment:PortGroupAggregationDef:policyLevel
        managed object property"
    ::= { cucsEquipmentPortGroupAggregationDefEntry 9 }

cucsEquipmentPortGroupAggregationDefPolicyOwner OBJECT-TYPE
    SYNTAX       CucsPolicyPolicyOwner
    MAX-ACCESS   read-only
    STATUS       current
    DESCRIPTION
        "Cisco UCS equipment:PortGroupAggregationDef:policyOwner
        managed object property"
    ::= { cucsEquipmentPortGroupAggregationDefEntry 10 }

cucsEquipmentPortGroupDefTable OBJECT-TYPE
    SYNTAX           SEQUENCE OF CucsEquipmentPortGroupDefEntry
    MAX-ACCESS       not-accessible
    STATUS           current
    DESCRIPTION
        "Cisco UCS equipment:PortGroupDef managed object table"
    ::= { cucsEquipmentObjects 53 }

cucsEquipmentPortGroupDefEntry OBJECT-TYPE
    SYNTAX           CucsEquipmentPortGroupDefEntry
    MAX-ACCESS       not-accessible
    STATUS           current
    DESCRIPTION
        "Entry for the cucsEquipmentPortGroupDefTable table."
    INDEX { cucsEquipmentPortGroupDefInstanceId }
    ::= { cucsEquipmentPortGroupDefTable 1 }

CucsEquipmentPortGroupDefEntry ::= SEQUENCE {
    cucsEquipmentPortGroupDefInstanceId                              CucsManagedObjectId,
    cucsEquipmentPortGroupDefDn                                      CucsManagedObjectDn,
    cucsEquipmentPortGroupDefRn                                      SnmpAdminString,
    cucsEquipmentPortGroupDefDescr                                   SnmpAdminString,
    cucsEquipmentPortGroupDefIntId                                   SnmpAdminString,
    cucsEquipmentPortGroupDefName                                    SnmpAdminString,
    cucsEquipmentPortGroupDefNumberOfPorts                           Gauge32,
    cucsEquipmentPortGroupDefType                                    CucsPortGroupType,
    cucsEquipmentPortGroupDefPolicyLevel                             Gauge32,
    cucsEquipmentPortGroupDefPolicyOwner                             CucsPolicyPolicyOwner
}

cucsEquipmentPortGroupDefInstanceId OBJECT-TYPE
    SYNTAX       CucsManagedObjectId
    MAX-ACCESS   not-accessible
    STATUS       current
    DESCRIPTION
        "Instance identifier of the managed object."
    ::= { cucsEquipmentPortGroupDefEntry 1 }

cucsEquipmentPortGroupDefDn OBJECT-TYPE
    SYNTAX       CucsManagedObjectDn
    MAX-ACCESS   read-only
    STATUS       current
    DESCRIPTION
        "Cisco UCS equipment:PortGroupDef:dn managed object property"
    ::= { cucsEquipmentPortGroupDefEntry 2 }

cucsEquipmentPortGroupDefRn OBJECT-TYPE
    SYNTAX       SnmpAdminString
    MAX-ACCESS   read-only
    STATUS       current
    DESCRIPTION
        "Cisco UCS equipment:PortGroupDef:rn managed object property"
    ::= { cucsEquipmentPortGroupDefEntry 3 }

cucsEquipmentPortGroupDefDescr OBJECT-TYPE
    SYNTAX       SnmpAdminString
    MAX-ACCESS   read-only
    STATUS       current
    DESCRIPTION
        "Cisco UCS equipment:PortGroupDef:descr managed object property"
    ::= { cucsEquipmentPortGroupDefEntry 4 }

cucsEquipmentPortGroupDefIntId OBJECT-TYPE
    SYNTAX       SnmpAdminString
    MAX-ACCESS   read-only
    STATUS       current
    DESCRIPTION
        "Cisco UCS equipment:PortGroupDef:intId managed object property"
    ::= { cucsEquipmentPortGroupDefEntry 5 }

cucsEquipmentPortGroupDefName OBJECT-TYPE
    SYNTAX       SnmpAdminString
    MAX-ACCESS   read-only
    STATUS       current
    DESCRIPTION
        "Cisco UCS equipment:PortGroupDef:name managed object property"
    ::= { cucsEquipmentPortGroupDefEntry 6 }

cucsEquipmentPortGroupDefNumberOfPorts OBJECT-TYPE
    SYNTAX       Gauge32
    MAX-ACCESS   read-only
    STATUS       current
    DESCRIPTION
        "Cisco UCS equipment:PortGroupDef:numberOfPorts
        managed object property"
    ::= { cucsEquipmentPortGroupDefEntry 7 }

cucsEquipmentPortGroupDefType OBJECT-TYPE
    SYNTAX       CucsPortGroupType
    MAX-ACCESS   read-only
    STATUS       current
    DESCRIPTION
        "Cisco UCS equipment:PortGroupDef:type managed object property"
    ::= { cucsEquipmentPortGroupDefEntry 8 }

cucsEquipmentPortGroupDefPolicyLevel OBJECT-TYPE
    SYNTAX       Gauge32
    MAX-ACCESS   read-only
    STATUS       current
    DESCRIPTION
        "Cisco UCS equipment:PortGroupDef:policyLevel managed
        object property"
    ::= { cucsEquipmentPortGroupDefEntry 9 }

cucsEquipmentPortGroupDefPolicyOwner OBJECT-TYPE
    SYNTAX       CucsPolicyPolicyOwner
    MAX-ACCESS   read-only
    STATUS       current
    DESCRIPTION
        "Cisco UCS equipment:PortGroupDef:policyOwner managed
        object property"
    ::= { cucsEquipmentPortGroupDefEntry 10 }

cucsEquipmentPortGroupSwComplexDefTable OBJECT-TYPE
    SYNTAX           SEQUENCE OF CucsEquipmentPortGroupSwComplexDefEntry
    MAX-ACCESS       not-accessible
    STATUS           current
    DESCRIPTION
        "Cisco UCS equipment:PortGroupSwComplexDef managed object table"
    ::= { cucsEquipmentObjects 89 }

cucsEquipmentPortGroupSwComplexDefEntry OBJECT-TYPE
    SYNTAX           CucsEquipmentPortGroupSwComplexDefEntry
    MAX-ACCESS       not-accessible
    STATUS           current
    DESCRIPTION
        "Entry for the cucsEquipmentPortGroupSwComplexDefTable table."
    INDEX { cucsEquipmentPortGroupSwComplexDefInstanceId }
    ::= { cucsEquipmentPortGroupSwComplexDefTable 1 }

CucsEquipmentPortGroupSwComplexDefEntry ::= SEQUENCE {
    cucsEquipmentPortGroupSwComplexDefInstanceId                     CucsManagedObjectId,
    cucsEquipmentPortGroupSwComplexDefDn                             CucsManagedObjectDn,
    cucsEquipmentPortGroupSwComplexDefRn                             SnmpAdminString,
    cucsEquipmentPortGroupSwComplexDefAsic                           CucsEquipmentAsicType,
    cucsEquipmentPortGroupSwComplexDefDescr                          SnmpAdminString,
    cucsEquipmentPortGroupSwComplexDefIntId                          SnmpAdminString,
    cucsEquipmentPortGroupSwComplexDefName                           SnmpAdminString,
    cucsEquipmentPortGroupSwComplexDefPortCapacity                   Gauge32,
    cucsEquipmentPortGroupSwComplexDefSwComplexCapacity              Gauge32,
    cucsEquipmentPortGroupSwComplexDefVifCapacity                    Gauge32,
    cucsEquipmentPortGroupSwComplexDefPolicyLevel                    Gauge32,
    cucsEquipmentPortGroupSwComplexDefPolicyOwner                    CucsPolicyPolicyOwner
}

cucsEquipmentPortGroupSwComplexDefInstanceId OBJECT-TYPE
    SYNTAX       CucsManagedObjectId
    MAX-ACCESS   not-accessible
    STATUS       current
    DESCRIPTION
        "Instance identifier of the managed object."
    ::= { cucsEquipmentPortGroupSwComplexDefEntry 1 }

cucsEquipmentPortGroupSwComplexDefDn OBJECT-TYPE
    SYNTAX       CucsManagedObjectDn
    MAX-ACCESS   read-only
    STATUS       current
    DESCRIPTION
        "Cisco UCS equipment:PortGroupSwComplexDef:dn managed
        object property"
    ::= { cucsEquipmentPortGroupSwComplexDefEntry 2 }

cucsEquipmentPortGroupSwComplexDefRn OBJECT-TYPE
    SYNTAX       SnmpAdminString
    MAX-ACCESS   read-only
    STATUS       current
    DESCRIPTION
        "Cisco UCS equipment:PortGroupSwComplexDef:rn managed
        object property"
    ::= { cucsEquipmentPortGroupSwComplexDefEntry 3 }

cucsEquipmentPortGroupSwComplexDefAsic OBJECT-TYPE
    SYNTAX       CucsEquipmentAsicType
    MAX-ACCESS   read-only
    STATUS       current
    DESCRIPTION
        "Cisco UCS equipment:PortGroupSwComplexDef:asic
        managed object property"
    ::= { cucsEquipmentPortGroupSwComplexDefEntry 4 }

cucsEquipmentPortGroupSwComplexDefDescr OBJECT-TYPE
    SYNTAX       SnmpAdminString
    MAX-ACCESS   read-only
    STATUS       current
    DESCRIPTION
        "Cisco UCS equipment:PortGroupSwComplexDef:descr
        managed object property"
    ::= { cucsEquipmentPortGroupSwComplexDefEntry 5 }

cucsEquipmentPortGroupSwComplexDefIntId OBJECT-TYPE
    SYNTAX       SnmpAdminString
    MAX-ACCESS   read-only
    STATUS       current
    DESCRIPTION
        "Cisco UCS equipment:PortGroupSwComplexDef:intId
        managed object property"
    ::= { cucsEquipmentPortGroupSwComplexDefEntry 6 }

cucsEquipmentPortGroupSwComplexDefName OBJECT-TYPE
    SYNTAX       SnmpAdminString
    MAX-ACCESS   read-only
    STATUS       current
    DESCRIPTION
        "Cisco UCS equipment:PortGroupSwComplexDef:name
        managed object property"
    ::= { cucsEquipmentPortGroupSwComplexDefEntry 7 }

cucsEquipmentPortGroupSwComplexDefPortCapacity OBJECT-TYPE
    SYNTAX       Gauge32
    MAX-ACCESS   read-only
    STATUS       current
    DESCRIPTION
        "Cisco UCS equipment:PortGroupSwComplexDef:portCapacity
        managed object property"
    ::= { cucsEquipmentPortGroupSwComplexDefEntry 8 }

cucsEquipmentPortGroupSwComplexDefSwComplexCapacity OBJECT-TYPE
    SYNTAX       Gauge32
    MAX-ACCESS   read-only
    STATUS       current
    DESCRIPTION
        "Cisco UCS equipment:PortGroupSwComplexDef:swComplexCapacity
        managed object property"
    ::= { cucsEquipmentPortGroupSwComplexDefEntry 9 }

cucsEquipmentPortGroupSwComplexDefVifCapacity OBJECT-TYPE
    SYNTAX       Gauge32
    MAX-ACCESS   read-only
    STATUS       current
    DESCRIPTION
        "Cisco UCS equipment:PortGroupSwComplexDef:vifCapacity
        managed object property"
    ::= { cucsEquipmentPortGroupSwComplexDefEntry 10 }

cucsEquipmentPortGroupSwComplexDefPolicyLevel OBJECT-TYPE
    SYNTAX       Gauge32
    MAX-ACCESS   read-only
    STATUS       current
    DESCRIPTION
        "Cisco UCS equipment:PortGroupSwComplexDef:policyLevel
        managed object property"
    ::= { cucsEquipmentPortGroupSwComplexDefEntry 11 }

cucsEquipmentPortGroupSwComplexDefPolicyOwner OBJECT-TYPE
    SYNTAX       CucsPolicyPolicyOwner
    MAX-ACCESS   read-only
    STATUS       current
    DESCRIPTION
        "Cisco UCS equipment:PortGroupSwComplexDef:policyOwner
        managed object property"
    ::= { cucsEquipmentPortGroupSwComplexDefEntry 12 }

cucsEquipmentPortSwComplexRefTable OBJECT-TYPE
    SYNTAX           SEQUENCE OF CucsEquipmentPortSwComplexRefEntry
    MAX-ACCESS       not-accessible
    STATUS           current
    DESCRIPTION
        "Cisco UCS equipment:PortSwComplexRef managed object table"
    ::= { cucsEquipmentObjects 90 }

cucsEquipmentPortSwComplexRefEntry OBJECT-TYPE
    SYNTAX           CucsEquipmentPortSwComplexRefEntry
    MAX-ACCESS       not-accessible
    STATUS           current
    DESCRIPTION
        "Entry for the cucsEquipmentPortSwComplexRefTable table."
    INDEX { cucsEquipmentPortSwComplexRefInstanceId }
    ::= { cucsEquipmentPortSwComplexRefTable 1 }

CucsEquipmentPortSwComplexRefEntry ::= SEQUENCE {
    cucsEquipmentPortSwComplexRefInstanceId                          CucsManagedObjectId,
    cucsEquipmentPortSwComplexRefDn                                  CucsManagedObjectDn,
    cucsEquipmentPortSwComplexRefRn                                  SnmpAdminString,
    cucsEquipmentPortSwComplexRefDescr                               SnmpAdminString,
    cucsEquipmentPortSwComplexRefIntId                               SnmpAdminString,
    cucsEquipmentPortSwComplexRefMaxPortId                           Gauge32,
    cucsEquipmentPortSwComplexRefMinPortId                           Gauge32,
    cucsEquipmentPortSwComplexRefName                                SnmpAdminString,
    cucsEquipmentPortSwComplexRefSlotId                              Gauge32,
    cucsEquipmentPortSwComplexRefSwComplexId                         Gauge32,
    cucsEquipmentPortSwComplexRefPolicyLevel                         Gauge32,
    cucsEquipmentPortSwComplexRefPolicyOwner                         CucsPolicyPolicyOwner
}

cucsEquipmentPortSwComplexRefInstanceId OBJECT-TYPE
    SYNTAX       CucsManagedObjectId
    MAX-ACCESS   not-accessible
    STATUS       current
    DESCRIPTION
        "Instance identifier of the managed object."
    ::= { cucsEquipmentPortSwComplexRefEntry 1 }

cucsEquipmentPortSwComplexRefDn OBJECT-TYPE
    SYNTAX       CucsManagedObjectDn
    MAX-ACCESS   read-only
    STATUS       current
    DESCRIPTION
        "Cisco UCS equipment:PortSwComplexRef:dn managed object property"
    ::= { cucsEquipmentPortSwComplexRefEntry 2 }

cucsEquipmentPortSwComplexRefRn OBJECT-TYPE
    SYNTAX       SnmpAdminString
    MAX-ACCESS   read-only
    STATUS       current
    DESCRIPTION
        "Cisco UCS equipment:PortSwComplexRef:rn managed object property"
    ::= { cucsEquipmentPortSwComplexRefEntry 3 }

cucsEquipmentPortSwComplexRefDescr OBJECT-TYPE
    SYNTAX       SnmpAdminString
    MAX-ACCESS   read-only
    STATUS       current
    DESCRIPTION
        "Cisco UCS equipment:PortSwComplexRef:descr managed
        object property"
    ::= { cucsEquipmentPortSwComplexRefEntry 4 }

cucsEquipmentPortSwComplexRefIntId OBJECT-TYPE
    SYNTAX       SnmpAdminString
    MAX-ACCESS   read-only
    STATUS       current
    DESCRIPTION
        "Cisco UCS equipment:PortSwComplexRef:intId managed
        object property"
    ::= { cucsEquipmentPortSwComplexRefEntry 5 }

cucsEquipmentPortSwComplexRefMaxPortId OBJECT-TYPE
    SYNTAX       Gauge32
    MAX-ACCESS   read-only
    STATUS       current
    DESCRIPTION
        "Cisco UCS equipment:PortSwComplexRef:maxPortId
        managed object property"
    ::= { cucsEquipmentPortSwComplexRefEntry 6 }

cucsEquipmentPortSwComplexRefMinPortId OBJECT-TYPE
    SYNTAX       Gauge32
    MAX-ACCESS   read-only
    STATUS       current
    DESCRIPTION
        "Cisco UCS equipment:PortSwComplexRef:minPortId
        managed object property"
    ::= { cucsEquipmentPortSwComplexRefEntry 7 }

cucsEquipmentPortSwComplexRefName OBJECT-TYPE
    SYNTAX       SnmpAdminString
    MAX-ACCESS   read-only
    STATUS       current
    DESCRIPTION
        "Cisco UCS equipment:PortSwComplexRef:name managed
        object property"
    ::= { cucsEquipmentPortSwComplexRefEntry 8 }

cucsEquipmentPortSwComplexRefSlotId OBJECT-TYPE
    SYNTAX       Gauge32
    MAX-ACCESS   read-only
    STATUS       current
    DESCRIPTION
        "Cisco UCS equipment:PortSwComplexRef:slotId managed
        object property"
    ::= { cucsEquipmentPortSwComplexRefEntry 9 }

cucsEquipmentPortSwComplexRefSwComplexId OBJECT-TYPE
    SYNTAX       Gauge32
    MAX-ACCESS   read-only
    STATUS       current
    DESCRIPTION
        "Cisco UCS equipment:PortSwComplexRef:swComplexId
        managed object property"
    ::= { cucsEquipmentPortSwComplexRefEntry 10 }

cucsEquipmentPortSwComplexRefPolicyLevel OBJECT-TYPE
    SYNTAX       Gauge32
    MAX-ACCESS   read-only
    STATUS       current
    DESCRIPTION
        "Cisco UCS equipment:PortSwComplexRef:policyLevel
        managed object property"
    ::= { cucsEquipmentPortSwComplexRefEntry 11 }

cucsEquipmentPortSwComplexRefPolicyOwner OBJECT-TYPE
    SYNTAX       CucsPolicyPolicyOwner
    MAX-ACCESS   read-only
    STATUS       current
    DESCRIPTION
        "Cisco UCS equipment:PortSwComplexRef:policyOwner
        managed object property"
    ::= { cucsEquipmentPortSwComplexRefEntry 12 }

cucsEquipmentProcessorUnitCapProviderTable OBJECT-TYPE
    SYNTAX           SEQUENCE OF CucsEquipmentProcessorUnitCapProviderEntry
    MAX-ACCESS       not-accessible
    STATUS           current
    DESCRIPTION
        "Cisco UCS equipment:ProcessorUnitCapProvider managed
        object table"
    ::= { cucsEquipmentObjects 54 }

cucsEquipmentProcessorUnitCapProviderEntry OBJECT-TYPE
    SYNTAX           CucsEquipmentProcessorUnitCapProviderEntry
    MAX-ACCESS       not-accessible
    STATUS           current
    DESCRIPTION
        "Entry for the cucsEquipmentProcessorUnitCapProviderTable table."
    INDEX { cucsEquipmentProcessorUnitCapProviderInstanceId }
    ::= { cucsEquipmentProcessorUnitCapProviderTable 1 }

CucsEquipmentProcessorUnitCapProviderEntry ::= SEQUENCE {
    cucsEquipmentProcessorUnitCapProviderInstanceId                  CucsManagedObjectId,
    cucsEquipmentProcessorUnitCapProviderDn                          CucsManagedObjectDn,
    cucsEquipmentProcessorUnitCapProviderRn                          SnmpAdminString,
    cucsEquipmentProcessorUnitCapProviderDeprecated                  TruthValue,
    cucsEquipmentProcessorUnitCapProviderGencount                    Gauge32,
    cucsEquipmentProcessorUnitCapProviderMgmtPlaneVer                SnmpAdminString,
    cucsEquipmentProcessorUnitCapProviderModel                       SnmpAdminString,
    cucsEquipmentProcessorUnitCapProviderRevision                    SnmpAdminString,
    cucsEquipmentProcessorUnitCapProviderVendor                      SnmpAdminString,
    cucsEquipmentProcessorUnitCapProviderPromCardType                Gauge32,
    cucsEquipmentProcessorUnitCapProviderDeleted                     TruthValue,
    cucsEquipmentProcessorUnitCapProviderElementLoadFailures         Gauge32,
    cucsEquipmentProcessorUnitCapProviderElementsLoaded              Gauge32,
    cucsEquipmentProcessorUnitCapProviderLoadErrors                  Gauge32,
    cucsEquipmentProcessorUnitCapProviderLoadWarnings                Gauge32
}

cucsEquipmentProcessorUnitCapProviderInstanceId OBJECT-TYPE
    SYNTAX       CucsManagedObjectId
    MAX-ACCESS   not-accessible
    STATUS       current
    DESCRIPTION
        "Instance identifier of the managed object."
    ::= { cucsEquipmentProcessorUnitCapProviderEntry 1 }

cucsEquipmentProcessorUnitCapProviderDn OBJECT-TYPE
    SYNTAX       CucsManagedObjectDn
    MAX-ACCESS   read-only
    STATUS       current
    DESCRIPTION
        "Cisco UCS equipment:ProcessorUnitCapProvider:dn
        managed object property"
    ::= { cucsEquipmentProcessorUnitCapProviderEntry 2 }

cucsEquipmentProcessorUnitCapProviderRn OBJECT-TYPE
    SYNTAX       SnmpAdminString
    MAX-ACCESS   read-only
    STATUS       current
    DESCRIPTION
        "Cisco UCS equipment:ProcessorUnitCapProvider:rn
        managed object property"
    ::= { cucsEquipmentProcessorUnitCapProviderEntry 3 }

cucsEquipmentProcessorUnitCapProviderDeprecated OBJECT-TYPE
    SYNTAX       TruthValue
    MAX-ACCESS   read-only
    STATUS       current
    DESCRIPTION
        "Cisco UCS equipment:ProcessorUnitCapProvider:deprecated
        managed object property"
    ::= { cucsEquipmentProcessorUnitCapProviderEntry 4 }

cucsEquipmentProcessorUnitCapProviderGencount OBJECT-TYPE
    SYNTAX       Gauge32
    MAX-ACCESS   read-only
    STATUS       current
    DESCRIPTION
        "Cisco UCS equipment:ProcessorUnitCapProvider:gencount
        managed object property"
    ::= { cucsEquipmentProcessorUnitCapProviderEntry 5 }

cucsEquipmentProcessorUnitCapProviderMgmtPlaneVer OBJECT-TYPE
    SYNTAX       SnmpAdminString
    MAX-ACCESS   read-only
    STATUS       current
    DESCRIPTION
        "Cisco UCS equipment:ProcessorUnitCapProvider:mgmtPlaneVer
        managed object property"
    ::= { cucsEquipmentProcessorUnitCapProviderEntry 6 }

cucsEquipmentProcessorUnitCapProviderModel OBJECT-TYPE
    SYNTAX       SnmpAdminString
    MAX-ACCESS   read-only
    STATUS       current
    DESCRIPTION
        "Cisco UCS equipment:ProcessorUnitCapProvider:model
        managed object property"
    ::= { cucsEquipmentProcessorUnitCapProviderEntry 7 }

cucsEquipmentProcessorUnitCapProviderRevision OBJECT-TYPE
    SYNTAX       SnmpAdminString
    MAX-ACCESS   read-only
    STATUS       current
    DESCRIPTION
        "Cisco UCS equipment:ProcessorUnitCapProvider:revision
        managed object property"
    ::= { cucsEquipmentProcessorUnitCapProviderEntry 8 }

cucsEquipmentProcessorUnitCapProviderVendor OBJECT-TYPE
    SYNTAX       SnmpAdminString
    MAX-ACCESS   read-only
    STATUS       current
    DESCRIPTION
        "Cisco UCS equipment:ProcessorUnitCapProvider:vendor
        managed object property"
    ::= { cucsEquipmentProcessorUnitCapProviderEntry 9 }

cucsEquipmentProcessorUnitCapProviderPromCardType OBJECT-TYPE
    SYNTAX       Gauge32
    MAX-ACCESS   read-only
    STATUS       current
    DESCRIPTION
        "Cisco UCS equipment:ProcessorUnitCapProvider:promCardType
        managed object property"
    ::= { cucsEquipmentProcessorUnitCapProviderEntry 10 }

cucsEquipmentProcessorUnitCapProviderDeleted OBJECT-TYPE
    SYNTAX       TruthValue
    MAX-ACCESS   read-only
    STATUS       current
    DESCRIPTION
        "Cisco UCS equipment:ProcessorUnitCapProvider:deleted
        managed object property"
    ::= { cucsEquipmentProcessorUnitCapProviderEntry 11 }

cucsEquipmentProcessorUnitCapProviderElementLoadFailures OBJECT-TYPE
    SYNTAX       Gauge32
    MAX-ACCESS   read-only
    STATUS       current
    DESCRIPTION
        "Cisco UCS equipment:ProcessorUnitCapProvider:elementLoadFailures
        managed object property"
    ::= { cucsEquipmentProcessorUnitCapProviderEntry 12 }

cucsEquipmentProcessorUnitCapProviderElementsLoaded OBJECT-TYPE
    SYNTAX       Gauge32
    MAX-ACCESS   read-only
    STATUS       current
    DESCRIPTION
        "Cisco UCS equipment:ProcessorUnitCapProvider:elementsLoaded
        managed object property"
    ::= { cucsEquipmentProcessorUnitCapProviderEntry 13 }

cucsEquipmentProcessorUnitCapProviderLoadErrors OBJECT-TYPE
    SYNTAX       Gauge32
    MAX-ACCESS   read-only
    STATUS       current
    DESCRIPTION
        "Cisco UCS equipment:ProcessorUnitCapProvider:loadErrors
        managed object property"
    ::= { cucsEquipmentProcessorUnitCapProviderEntry 14 }

cucsEquipmentProcessorUnitCapProviderLoadWarnings OBJECT-TYPE
    SYNTAX       Gauge32
    MAX-ACCESS   read-only
    STATUS       current
    DESCRIPTION
        "Cisco UCS equipment:ProcessorUnitCapProvider:loadWarnings
        managed object property"
    ::= { cucsEquipmentProcessorUnitCapProviderEntry 15 }

cucsEquipmentProcessorUnitDefTable OBJECT-TYPE
    SYNTAX           SEQUENCE OF CucsEquipmentProcessorUnitDefEntry
    MAX-ACCESS       not-accessible
    STATUS           current
    DESCRIPTION
        "Cisco UCS equipment:ProcessorUnitDef managed object table"
    ::= { cucsEquipmentObjects 55 }

cucsEquipmentProcessorUnitDefEntry OBJECT-TYPE
    SYNTAX           CucsEquipmentProcessorUnitDefEntry
    MAX-ACCESS       not-accessible
    STATUS           current
    DESCRIPTION
        "Entry for the cucsEquipmentProcessorUnitDefTable table."
    INDEX { cucsEquipmentProcessorUnitDefInstanceId }
    ::= { cucsEquipmentProcessorUnitDefTable 1 }

CucsEquipmentProcessorUnitDefEntry ::= SEQUENCE {
    cucsEquipmentProcessorUnitDefInstanceId                          CucsManagedObjectId,
    cucsEquipmentProcessorUnitDefDn                                  CucsManagedObjectDn,
    cucsEquipmentProcessorUnitDefRn                                  SnmpAdminString,
    cucsEquipmentProcessorUnitDefAddressWidth                        Gauge32,
    cucsEquipmentProcessorUnitDefDataWidth                           Gauge32,
    cucsEquipmentProcessorUnitDefDescr                               SnmpAdminString,
    cucsEquipmentProcessorUnitDefIntId                               SnmpAdminString,
    cucsEquipmentProcessorUnitDefMaxSpeed                            INTEGER,
    cucsEquipmentProcessorUnitDefName                                SnmpAdminString,
    cucsEquipmentProcessorUnitDefPolicyLevel                         Gauge32,
    cucsEquipmentProcessorUnitDefPolicyOwner                         CucsPolicyPolicyOwner
}

cucsEquipmentProcessorUnitDefInstanceId OBJECT-TYPE
    SYNTAX       CucsManagedObjectId
    MAX-ACCESS   not-accessible
    STATUS       current
    DESCRIPTION
        "Instance identifier of the managed object."
    ::= { cucsEquipmentProcessorUnitDefEntry 1 }

cucsEquipmentProcessorUnitDefDn OBJECT-TYPE
    SYNTAX       CucsManagedObjectDn
    MAX-ACCESS   read-only
    STATUS       current
    DESCRIPTION
        "Cisco UCS equipment:ProcessorUnitDef:dn managed object property"
    ::= { cucsEquipmentProcessorUnitDefEntry 2 }

cucsEquipmentProcessorUnitDefRn OBJECT-TYPE
    SYNTAX       SnmpAdminString
    MAX-ACCESS   read-only
    STATUS       current
    DESCRIPTION
        "Cisco UCS equipment:ProcessorUnitDef:rn managed object property"
    ::= { cucsEquipmentProcessorUnitDefEntry 3 }

cucsEquipmentProcessorUnitDefAddressWidth OBJECT-TYPE
    SYNTAX       Gauge32
    MAX-ACCESS   read-only
    STATUS       current
    DESCRIPTION
        "Cisco UCS equipment:ProcessorUnitDef:addressWidth
        managed object property"
    ::= { cucsEquipmentProcessorUnitDefEntry 4 }

cucsEquipmentProcessorUnitDefDataWidth OBJECT-TYPE
    SYNTAX       Gauge32
    MAX-ACCESS   read-only
    STATUS       current
    DESCRIPTION
        "Cisco UCS equipment:ProcessorUnitDef:dataWidth
        managed object property"
    ::= { cucsEquipmentProcessorUnitDefEntry 5 }

cucsEquipmentProcessorUnitDefDescr OBJECT-TYPE
    SYNTAX       SnmpAdminString
    MAX-ACCESS   read-only
    STATUS       current
    DESCRIPTION
        "Cisco UCS equipment:ProcessorUnitDef:descr managed
        object property"
    ::= { cucsEquipmentProcessorUnitDefEntry 6 }

cucsEquipmentProcessorUnitDefIntId OBJECT-TYPE
    SYNTAX       SnmpAdminString
    MAX-ACCESS   read-only
    STATUS       current
    DESCRIPTION
        "Cisco UCS equipment:ProcessorUnitDef:intId managed
        object property"
    ::= { cucsEquipmentProcessorUnitDefEntry 7 }

cucsEquipmentProcessorUnitDefMaxSpeed OBJECT-TYPE
    SYNTAX       INTEGER
    MAX-ACCESS   read-only
    STATUS       current
    DESCRIPTION
        "Cisco UCS equipment:ProcessorUnitDef:maxSpeed
        managed object property"
    ::= { cucsEquipmentProcessorUnitDefEntry 8 }

cucsEquipmentProcessorUnitDefName OBJECT-TYPE
    SYNTAX       SnmpAdminString
    MAX-ACCESS   read-only
    STATUS       current
    DESCRIPTION
        "Cisco UCS equipment:ProcessorUnitDef:name managed
        object property"
    ::= { cucsEquipmentProcessorUnitDefEntry 9 }

cucsEquipmentProcessorUnitDefPolicyLevel OBJECT-TYPE
    SYNTAX       Gauge32
    MAX-ACCESS   read-only
    STATUS       current
    DESCRIPTION
        "Cisco UCS equipment:ProcessorUnitDef:policyLevel
        managed object property"
    ::= { cucsEquipmentProcessorUnitDefEntry 10 }

cucsEquipmentProcessorUnitDefPolicyOwner OBJECT-TYPE
    SYNTAX       CucsPolicyPolicyOwner
    MAX-ACCESS   read-only
    STATUS       current
    DESCRIPTION
        "Cisco UCS equipment:ProcessorUnitDef:policyOwner
        managed object property"
    ::= { cucsEquipmentProcessorUnitDefEntry 11 }

cucsEquipmentPsuTable OBJECT-TYPE
    SYNTAX           SEQUENCE OF CucsEquipmentPsuEntry
    MAX-ACCESS       not-accessible
    STATUS           current
    DESCRIPTION
        "Cisco UCS equipment:Psu managed object table"
    ::= { cucsEquipmentObjects 56 }

cucsEquipmentPsuEntry OBJECT-TYPE
    SYNTAX           CucsEquipmentPsuEntry
    MAX-ACCESS       not-accessible
    STATUS           current
    DESCRIPTION
        "Entry for the cucsEquipmentPsuTable table."
    INDEX { cucsEquipmentPsuInstanceId }
    ::= { cucsEquipmentPsuTable 1 }

CucsEquipmentPsuEntry ::= SEQUENCE {
    cucsEquipmentPsuInstanceId                                       CucsManagedObjectId,
    cucsEquipmentPsuDn                                               CucsManagedObjectDn,
    cucsEquipmentPsuRn                                               SnmpAdminString,
    cucsEquipmentPsuFltAggr                                          Unsigned64,
    cucsEquipmentPsuId                                               CucsEquipmentPsuId,
    cucsEquipmentPsuModel                                            SnmpAdminString,
    cucsEquipmentPsuOperState                                        CucsEquipmentOperability,
    cucsEquipmentPsuOperability                                      CucsEquipmentOperability,
    cucsEquipmentPsuPerf                                             CucsEquipmentSensorThresholdStatus,
    cucsEquipmentPsuPower                                            CucsEquipmentPowerState,
    cucsEquipmentPsuPresence                                         CucsEquipmentPresence,
    cucsEquipmentPsuRevision                                         SnmpAdminString,
    cucsEquipmentPsuSerial                                           SnmpAdminString,
    cucsEquipmentPsuThermal                                          CucsEquipmentSensorThresholdStatus,
    cucsEquipmentPsuVendor                                           SnmpAdminString,
    cucsEquipmentPsuVoltage                                          CucsEquipmentSensorThresholdStatus,
    cucsEquipmentPsuType                                             CucsEquipmentPsuType,
    cucsEquipmentPsuPowerStateQualifier                              CucsEquipmentPsuStateQualifier,
    cucsEquipmentPsuOperQualifierReason                              SnmpAdminString,
    cucsEquipmentPsuPsuFirmwareVersion                               SnmpAdminString
}

cucsEquipmentPsuInstanceId OBJECT-TYPE
    SYNTAX       CucsManagedObjectId
    MAX-ACCESS   not-accessible
    STATUS       current
    DESCRIPTION
        "Instance identifier of the managed object."
    ::= { cucsEquipmentPsuEntry 1 }

cucsEquipmentPsuDn OBJECT-TYPE
    SYNTAX       CucsManagedObjectDn
    MAX-ACCESS   read-only
    STATUS       current
    DESCRIPTION
        "Cisco UCS equipment:Psu:dn managed object property"
    ::= { cucsEquipmentPsuEntry 2 }

cucsEquipmentPsuRn OBJECT-TYPE
    SYNTAX       SnmpAdminString
    MAX-ACCESS   read-only
    STATUS       current
    DESCRIPTION
        "Cisco UCS equipment:Psu:rn managed object property"
    ::= { cucsEquipmentPsuEntry 3 }

cucsEquipmentPsuFltAggr OBJECT-TYPE
    SYNTAX       Unsigned64
    MAX-ACCESS   read-only
    STATUS       current
    DESCRIPTION
        "Cisco UCS equipment:Psu:fltAggr managed object property"
    ::= { cucsEquipmentPsuEntry 4 }

cucsEquipmentPsuId OBJECT-TYPE
    SYNTAX       CucsEquipmentPsuId
    MAX-ACCESS   read-only
    STATUS       current
    DESCRIPTION
        "Cisco UCS equipment:Psu:id managed object property"
    ::= { cucsEquipmentPsuEntry 5 }

cucsEquipmentPsuModel OBJECT-TYPE
    SYNTAX       SnmpAdminString
    MAX-ACCESS   read-only
    STATUS       current
    DESCRIPTION
        "Cisco UCS equipment:Psu:model managed object property"
    ::= { cucsEquipmentPsuEntry 6 }

cucsEquipmentPsuOperState OBJECT-TYPE
    SYNTAX       CucsEquipmentOperability
    MAX-ACCESS   read-only
    STATUS       current
    DESCRIPTION
        "Cisco UCS equipment:Psu:operState managed object property"
    ::= { cucsEquipmentPsuEntry 7 }

cucsEquipmentPsuOperability OBJECT-TYPE
    SYNTAX       CucsEquipmentOperability
    MAX-ACCESS   read-only
    STATUS       current
    DESCRIPTION
        "Cisco UCS equipment:Psu:operability managed object property"
    ::= { cucsEquipmentPsuEntry 8 }

cucsEquipmentPsuPerf OBJECT-TYPE
    SYNTAX       CucsEquipmentSensorThresholdStatus
    MAX-ACCESS   read-only
    STATUS       current
    DESCRIPTION
        "Cisco UCS equipment:Psu:perf managed object property"
    ::= { cucsEquipmentPsuEntry 9 }

cucsEquipmentPsuPower OBJECT-TYPE
    SYNTAX       CucsEquipmentPowerState
    MAX-ACCESS   read-only
    STATUS       current
    DESCRIPTION
        "Cisco UCS equipment:Psu:power managed object property"
    ::= { cucsEquipmentPsuEntry 10 }

cucsEquipmentPsuPresence OBJECT-TYPE
    SYNTAX       CucsEquipmentPresence
    MAX-ACCESS   read-only
    STATUS       current
    DESCRIPTION
        "Cisco UCS equipment:Psu:presence managed object property"
    ::= { cucsEquipmentPsuEntry 11 }

cucsEquipmentPsuRevision OBJECT-TYPE
    SYNTAX       SnmpAdminString
    MAX-ACCESS   read-only
    STATUS       current
    DESCRIPTION
        "Cisco UCS equipment:Psu:revision managed object property"
    ::= { cucsEquipmentPsuEntry 12 }

cucsEquipmentPsuSerial OBJECT-TYPE
    SYNTAX       SnmpAdminString
    MAX-ACCESS   read-only
    STATUS       current
    DESCRIPTION
        "Cisco UCS equipment:Psu:serial managed object property"
    ::= { cucsEquipmentPsuEntry 13 }

cucsEquipmentPsuThermal OBJECT-TYPE
    SYNTAX       CucsEquipmentSensorThresholdStatus
    MAX-ACCESS   read-only
    STATUS       current
    DESCRIPTION
        "Cisco UCS equipment:Psu:thermal managed object property"
    ::= { cucsEquipmentPsuEntry 14 }

cucsEquipmentPsuVendor OBJECT-TYPE
    SYNTAX       SnmpAdminString
    MAX-ACCESS   read-only
    STATUS       current
    DESCRIPTION
        "Cisco UCS equipment:Psu:vendor managed object property"
    ::= { cucsEquipmentPsuEntry 15 }

cucsEquipmentPsuVoltage OBJECT-TYPE
    SYNTAX       CucsEquipmentSensorThresholdStatus
    MAX-ACCESS   read-only
    STATUS       current
    DESCRIPTION
        "Cisco UCS equipment:Psu:voltage managed object property"
    ::= { cucsEquipmentPsuEntry 16 }

cucsEquipmentPsuType OBJECT-TYPE
    SYNTAX       CucsEquipmentPsuType
    MAX-ACCESS   read-only
    STATUS       current
    DESCRIPTION
        "Cisco UCS equipment:Psu:Type managed object property"
    ::= { cucsEquipmentPsuEntry 17 }

cucsEquipmentPsuPowerStateQualifier OBJECT-TYPE
    SYNTAX       CucsEquipmentPsuStateQualifier
    MAX-ACCESS   read-only
    STATUS       current
    DESCRIPTION
        "Cisco UCS equipment:Psu:powerStateQualifier managed
        object property"
    ::= { cucsEquipmentPsuEntry 18 }

cucsEquipmentPsuOperQualifierReason OBJECT-TYPE
    SYNTAX       SnmpAdminString
    MAX-ACCESS   read-only
    STATUS       current
    DESCRIPTION
        "Cisco UCS equipment:Psu:operQualifierReason managed
        object property"
    ::= { cucsEquipmentPsuEntry 19 }

cucsEquipmentPsuPsuFirmwareVersion OBJECT-TYPE
    SYNTAX       SnmpAdminString
    MAX-ACCESS   read-only
    STATUS       current
    DESCRIPTION
        "Cisco UCS equipment:Psu:psuFirmwareVersion managed
        object property"
    ::= { cucsEquipmentPsuEntry 20 }

cucsEquipmentPsuCapProviderTable OBJECT-TYPE
    SYNTAX           SEQUENCE OF CucsEquipmentPsuCapProviderEntry
    MAX-ACCESS       not-accessible
    STATUS           current
    DESCRIPTION
        "Cisco UCS equipment:PsuCapProvider managed object table"
    ::= { cucsEquipmentObjects 57 }

cucsEquipmentPsuCapProviderEntry OBJECT-TYPE
    SYNTAX           CucsEquipmentPsuCapProviderEntry
    MAX-ACCESS       not-accessible
    STATUS           current
    DESCRIPTION
        "Entry for the cucsEquipmentPsuCapProviderTable table."
    INDEX { cucsEquipmentPsuCapProviderInstanceId }
    ::= { cucsEquipmentPsuCapProviderTable 1 }

CucsEquipmentPsuCapProviderEntry ::= SEQUENCE {
    cucsEquipmentPsuCapProviderInstanceId                            CucsManagedObjectId,
    cucsEquipmentPsuCapProviderDn                                    CucsManagedObjectDn,
    cucsEquipmentPsuCapProviderRn                                    SnmpAdminString,
    cucsEquipmentPsuCapProviderDeprecated                            TruthValue,
    cucsEquipmentPsuCapProviderGencount                              Gauge32,
    cucsEquipmentPsuCapProviderMgmtPlaneVer                          SnmpAdminString,
    cucsEquipmentPsuCapProviderModel                                 SnmpAdminString,
    cucsEquipmentPsuCapProviderRevision                              SnmpAdminString,
    cucsEquipmentPsuCapProviderVendor                                SnmpAdminString,
    cucsEquipmentPsuCapProviderPromCardType                          Gauge32,
    cucsEquipmentPsuCapProviderDeleted                               TruthValue,
    cucsEquipmentPsuCapProviderElementLoadFailures                   Gauge32,
    cucsEquipmentPsuCapProviderElementsLoaded                        Gauge32,
    cucsEquipmentPsuCapProviderLoadErrors                            Gauge32,
    cucsEquipmentPsuCapProviderLoadWarnings                          Gauge32
}

cucsEquipmentPsuCapProviderInstanceId OBJECT-TYPE
    SYNTAX       CucsManagedObjectId
    MAX-ACCESS   not-accessible
    STATUS       current
    DESCRIPTION
        "Instance identifier of the managed object."
    ::= { cucsEquipmentPsuCapProviderEntry 1 }

cucsEquipmentPsuCapProviderDn OBJECT-TYPE
    SYNTAX       CucsManagedObjectDn
    MAX-ACCESS   read-only
    STATUS       current
    DESCRIPTION
        "Cisco UCS equipment:PsuCapProvider:dn managed object property"
    ::= { cucsEquipmentPsuCapProviderEntry 2 }

cucsEquipmentPsuCapProviderRn OBJECT-TYPE
    SYNTAX       SnmpAdminString
    MAX-ACCESS   read-only
    STATUS       current
    DESCRIPTION
        "Cisco UCS equipment:PsuCapProvider:rn managed object property"
    ::= { cucsEquipmentPsuCapProviderEntry 3 }

cucsEquipmentPsuCapProviderDeprecated OBJECT-TYPE
    SYNTAX       TruthValue
    MAX-ACCESS   read-only
    STATUS       current
    DESCRIPTION
        "Cisco UCS equipment:PsuCapProvider:deprecated
        managed object property"
    ::= { cucsEquipmentPsuCapProviderEntry 4 }

cucsEquipmentPsuCapProviderGencount OBJECT-TYPE
    SYNTAX       Gauge32
    MAX-ACCESS   read-only
    STATUS       current
    DESCRIPTION
        "Cisco UCS equipment:PsuCapProvider:gencount managed
        object property"
    ::= { cucsEquipmentPsuCapProviderEntry 5 }

cucsEquipmentPsuCapProviderMgmtPlaneVer OBJECT-TYPE
    SYNTAX       SnmpAdminString
    MAX-ACCESS   read-only
    STATUS       current
    DESCRIPTION
        "Cisco UCS equipment:PsuCapProvider:mgmtPlaneVer
        managed object property"
    ::= { cucsEquipmentPsuCapProviderEntry 6 }

cucsEquipmentPsuCapProviderModel OBJECT-TYPE
    SYNTAX       SnmpAdminString
    MAX-ACCESS   read-only
    STATUS       current
    DESCRIPTION
        "Cisco UCS equipment:PsuCapProvider:model managed object property"
    ::= { cucsEquipmentPsuCapProviderEntry 7 }

cucsEquipmentPsuCapProviderRevision OBJECT-TYPE
    SYNTAX       SnmpAdminString
    MAX-ACCESS   read-only
    STATUS       current
    DESCRIPTION
        "Cisco UCS equipment:PsuCapProvider:revision managed
        object property"
    ::= { cucsEquipmentPsuCapProviderEntry 8 }

cucsEquipmentPsuCapProviderVendor OBJECT-TYPE
    SYNTAX       SnmpAdminString
    MAX-ACCESS   read-only
    STATUS       current
    DESCRIPTION
        "Cisco UCS equipment:PsuCapProvider:vendor managed
        object property"
    ::= { cucsEquipmentPsuCapProviderEntry 9 }

cucsEquipmentPsuCapProviderPromCardType OBJECT-TYPE
    SYNTAX       Gauge32
    MAX-ACCESS   read-only
    STATUS       current
    DESCRIPTION
        "Cisco UCS equipment:PsuCapProvider:promCardType
        managed object property"
    ::= { cucsEquipmentPsuCapProviderEntry 10 }

cucsEquipmentPsuCapProviderDeleted OBJECT-TYPE
    SYNTAX       TruthValue
    MAX-ACCESS   read-only
    STATUS       current
    DESCRIPTION
        "Cisco UCS equipment:PsuCapProvider:deleted managed
        object property"
    ::= { cucsEquipmentPsuCapProviderEntry 11 }

cucsEquipmentPsuCapProviderElementLoadFailures OBJECT-TYPE
    SYNTAX       Gauge32
    MAX-ACCESS   read-only
    STATUS       current
    DESCRIPTION
        "Cisco UCS equipment:PsuCapProvider:elementLoadFailures
        managed object property"
    ::= { cucsEquipmentPsuCapProviderEntry 12 }

cucsEquipmentPsuCapProviderElementsLoaded OBJECT-TYPE
    SYNTAX       Gauge32
    MAX-ACCESS   read-only
    STATUS       current
    DESCRIPTION
        "Cisco UCS equipment:PsuCapProvider:elementsLoaded
        managed object property"
    ::= { cucsEquipmentPsuCapProviderEntry 13 }

cucsEquipmentPsuCapProviderLoadErrors OBJECT-TYPE
    SYNTAX       Gauge32
    MAX-ACCESS   read-only
    STATUS       current
    DESCRIPTION
        "Cisco UCS equipment:PsuCapProvider:loadErrors
        managed object property"
    ::= { cucsEquipmentPsuCapProviderEntry 14 }

cucsEquipmentPsuCapProviderLoadWarnings OBJECT-TYPE
    SYNTAX       Gauge32
    MAX-ACCESS   read-only
    STATUS       current
    DESCRIPTION
        "Cisco UCS equipment:PsuCapProvider:loadWarnings
        managed object property"
    ::= { cucsEquipmentPsuCapProviderEntry 15 }

cucsEquipmentPsuDefTable OBJECT-TYPE
    SYNTAX           SEQUENCE OF CucsEquipmentPsuDefEntry
    MAX-ACCESS       not-accessible
    STATUS           current
    DESCRIPTION
        "Cisco UCS equipment:PsuDef managed object table"
    ::= { cucsEquipmentObjects 91 }

cucsEquipmentPsuDefEntry OBJECT-TYPE
    SYNTAX           CucsEquipmentPsuDefEntry
    MAX-ACCESS       not-accessible
    STATUS           current
    DESCRIPTION
        "Entry for the cucsEquipmentPsuDefTable table."
    INDEX { cucsEquipmentPsuDefInstanceId }
    ::= { cucsEquipmentPsuDefTable 1 }

CucsEquipmentPsuDefEntry ::= SEQUENCE {
    cucsEquipmentPsuDefInstanceId                                    CucsManagedObjectId,
    cucsEquipmentPsuDefDn                                            CucsManagedObjectDn,
    cucsEquipmentPsuDefRn                                            SnmpAdminString,
    cucsEquipmentPsuDefPsuType                                       SnmpAdminString,
    cucsEquipmentPsuDefDescr                                         SnmpAdminString,
    cucsEquipmentPsuDefIntId                                         SnmpAdminString,
    cucsEquipmentPsuDefName                                          SnmpAdminString,
    cucsEquipmentPsuDefPolicyLevel                                   Gauge32,
    cucsEquipmentPsuDefPolicyOwner                                   CucsPolicyPolicyOwner
}

cucsEquipmentPsuDefInstanceId OBJECT-TYPE
    SYNTAX       CucsManagedObjectId
    MAX-ACCESS   not-accessible
    STATUS       current
    DESCRIPTION
        "Instance identifier of the managed object."
    ::= { cucsEquipmentPsuDefEntry 1 }

cucsEquipmentPsuDefDn OBJECT-TYPE
    SYNTAX       CucsManagedObjectDn
    MAX-ACCESS   read-only
    STATUS       current
    DESCRIPTION
        "Cisco UCS equipment:PsuDef:dn managed object property"
    ::= { cucsEquipmentPsuDefEntry 2 }

cucsEquipmentPsuDefRn OBJECT-TYPE
    SYNTAX       SnmpAdminString
    MAX-ACCESS   read-only
    STATUS       current
    DESCRIPTION
        "Cisco UCS equipment:PsuDef:rn managed object property"
    ::= { cucsEquipmentPsuDefEntry 3 }

cucsEquipmentPsuDefPsuType OBJECT-TYPE
    SYNTAX       SnmpAdminString
    MAX-ACCESS   read-only
    STATUS       current
    DESCRIPTION
        "Cisco UCS equipment:PsuDef:PsuType managed object property"
    ::= { cucsEquipmentPsuDefEntry 4 }

cucsEquipmentPsuDefDescr OBJECT-TYPE
    SYNTAX       SnmpAdminString
    MAX-ACCESS   read-only
    STATUS       current
    DESCRIPTION
        "Cisco UCS equipment:PsuDef:descr managed object property"
    ::= { cucsEquipmentPsuDefEntry 5 }

cucsEquipmentPsuDefIntId OBJECT-TYPE
    SYNTAX       SnmpAdminString
    MAX-ACCESS   read-only
    STATUS       current
    DESCRIPTION
        "Cisco UCS equipment:PsuDef:intId managed object property"
    ::= { cucsEquipmentPsuDefEntry 6 }

cucsEquipmentPsuDefName OBJECT-TYPE
    SYNTAX       SnmpAdminString
    MAX-ACCESS   read-only
    STATUS       current
    DESCRIPTION
        "Cisco UCS equipment:PsuDef:name managed object property"
    ::= { cucsEquipmentPsuDefEntry 7 }

cucsEquipmentPsuDefPolicyLevel OBJECT-TYPE
    SYNTAX       Gauge32
    MAX-ACCESS   read-only
    STATUS       current
    DESCRIPTION
        "Cisco UCS equipment:PsuDef:policyLevel managed object property"
    ::= { cucsEquipmentPsuDefEntry 8 }

cucsEquipmentPsuDefPolicyOwner OBJECT-TYPE
    SYNTAX       CucsPolicyPolicyOwner
    MAX-ACCESS   read-only
    STATUS       current
    DESCRIPTION
        "Cisco UCS equipment:PsuDef:policyOwner managed object property"
    ::= { cucsEquipmentPsuDefEntry 9 }

cucsEquipmentPsuInputStatsTable OBJECT-TYPE
    SYNTAX           SEQUENCE OF CucsEquipmentPsuInputStatsEntry
    MAX-ACCESS       not-accessible
    STATUS           current
    DESCRIPTION
        "Cisco UCS equipment:PsuInputStats managed object table"
    ::= { cucsEquipmentObjects 58 }

cucsEquipmentPsuInputStatsEntry OBJECT-TYPE
    SYNTAX           CucsEquipmentPsuInputStatsEntry
    MAX-ACCESS       not-accessible
    STATUS           current
    DESCRIPTION
        "Entry for the cucsEquipmentPsuInputStatsTable table."
    INDEX { cucsEquipmentPsuInputStatsInstanceId }
    ::= { cucsEquipmentPsuInputStatsTable 1 }

CucsEquipmentPsuInputStatsEntry ::= SEQUENCE {
    cucsEquipmentPsuInputStatsInstanceId                             CucsManagedObjectId,
    cucsEquipmentPsuInputStatsDn                                     CucsManagedObjectDn,
    cucsEquipmentPsuInputStatsRn                                     SnmpAdminString,
    cucsEquipmentPsuInputStatsCurrent                                INTEGER,
    cucsEquipmentPsuInputStatsCurrentAvg                             INTEGER,
    cucsEquipmentPsuInputStatsCurrentMax                             INTEGER,
    cucsEquipmentPsuInputStatsCurrentMin                             INTEGER,
    cucsEquipmentPsuInputStatsInputStatus                            SnmpAdminString,
    cucsEquipmentPsuInputStatsIntervals                              Gauge32,
    cucsEquipmentPsuInputStatsPower                                  INTEGER,
    cucsEquipmentPsuInputStatsPowerAvg                               INTEGER,
    cucsEquipmentPsuInputStatsPowerMax                               INTEGER,
    cucsEquipmentPsuInputStatsPowerMin                               INTEGER,
    cucsEquipmentPsuInputStatsSuspect                                TruthValue,
    cucsEquipmentPsuInputStatsThresholded                            CucsEquipmentPsuInputStatsThresholded,
    cucsEquipmentPsuInputStatsTimeCollected                          DateAndTime,
    cucsEquipmentPsuInputStatsUpdate                                 Gauge32,
    cucsEquipmentPsuInputStatsVoltage                                INTEGER,
    cucsEquipmentPsuInputStatsVoltageAvg                             INTEGER,
    cucsEquipmentPsuInputStatsVoltageMax                             INTEGER,
    cucsEquipmentPsuInputStatsVoltageMin                             INTEGER
}

cucsEquipmentPsuInputStatsInstanceId OBJECT-TYPE
    SYNTAX       CucsManagedObjectId
    MAX-ACCESS   not-accessible
    STATUS       current
    DESCRIPTION
        "Instance identifier of the managed object."
    ::= { cucsEquipmentPsuInputStatsEntry 1 }

cucsEquipmentPsuInputStatsDn OBJECT-TYPE
    SYNTAX       CucsManagedObjectDn
    MAX-ACCESS   read-only
    STATUS       current
    DESCRIPTION
        "Cisco UCS equipment:PsuInputStats:dn managed object property"
    ::= { cucsEquipmentPsuInputStatsEntry 2 }

cucsEquipmentPsuInputStatsRn OBJECT-TYPE
    SYNTAX       SnmpAdminString
    MAX-ACCESS   read-only
    STATUS       current
    DESCRIPTION
        "Cisco UCS equipment:PsuInputStats:rn managed object property"
    ::= { cucsEquipmentPsuInputStatsEntry 3 }

cucsEquipmentPsuInputStatsCurrent OBJECT-TYPE
    SYNTAX       INTEGER
    MAX-ACCESS   read-only
    STATUS       current
    DESCRIPTION
        "Cisco UCS equipment:PsuInputStats:current managed
        object property"
    ::= { cucsEquipmentPsuInputStatsEntry 4 }

cucsEquipmentPsuInputStatsCurrentAvg OBJECT-TYPE
    SYNTAX       INTEGER
    MAX-ACCESS   read-only
    STATUS       current
    DESCRIPTION
        "Cisco UCS equipment:PsuInputStats:currentAvg managed
        object property"
    ::= { cucsEquipmentPsuInputStatsEntry 5 }

cucsEquipmentPsuInputStatsCurrentMax OBJECT-TYPE
    SYNTAX       INTEGER
    MAX-ACCESS   read-only
    STATUS       current
    DESCRIPTION
        "Cisco UCS equipment:PsuInputStats:currentMax managed
        object property"
    ::= { cucsEquipmentPsuInputStatsEntry 6 }

cucsEquipmentPsuInputStatsCurrentMin OBJECT-TYPE
    SYNTAX       INTEGER
    MAX-ACCESS   read-only
    STATUS       current
    DESCRIPTION
        "Cisco UCS equipment:PsuInputStats:currentMin managed
        object property"
    ::= { cucsEquipmentPsuInputStatsEntry 7 }

cucsEquipmentPsuInputStatsInputStatus OBJECT-TYPE
    SYNTAX       SnmpAdminString
    MAX-ACCESS   read-only
    STATUS       current
    DESCRIPTION
        "Cisco UCS equipment:PsuInputStats:inputStatus
        managed object property"
    ::= { cucsEquipmentPsuInputStatsEntry 8 }

cucsEquipmentPsuInputStatsIntervals OBJECT-TYPE
    SYNTAX       Gauge32
    MAX-ACCESS   read-only
    STATUS       current
    DESCRIPTION
        "Cisco UCS equipment:PsuInputStats:intervals managed
        object property"
    ::= { cucsEquipmentPsuInputStatsEntry 9 }

cucsEquipmentPsuInputStatsPower OBJECT-TYPE
    SYNTAX       INTEGER
    MAX-ACCESS   read-only
    STATUS       current
    DESCRIPTION
        "Cisco UCS equipment:PsuInputStats:power managed object property"
    ::= { cucsEquipmentPsuInputStatsEntry 10 }

cucsEquipmentPsuInputStatsPowerAvg OBJECT-TYPE
    SYNTAX       INTEGER
    MAX-ACCESS   read-only
    STATUS       current
    DESCRIPTION
        "Cisco UCS equipment:PsuInputStats:powerAvg managed
        object property"
    ::= { cucsEquipmentPsuInputStatsEntry 11 }

cucsEquipmentPsuInputStatsPowerMax OBJECT-TYPE
    SYNTAX       INTEGER
    MAX-ACCESS   read-only
    STATUS       current
    DESCRIPTION
        "Cisco UCS equipment:PsuInputStats:powerMax managed
        object property"
    ::= { cucsEquipmentPsuInputStatsEntry 12 }

cucsEquipmentPsuInputStatsPowerMin OBJECT-TYPE
    SYNTAX       INTEGER
    MAX-ACCESS   read-only
    STATUS       current
    DESCRIPTION
        "Cisco UCS equipment:PsuInputStats:powerMin managed
        object property"
    ::= { cucsEquipmentPsuInputStatsEntry 13 }

cucsEquipmentPsuInputStatsSuspect OBJECT-TYPE
    SYNTAX       TruthValue
    MAX-ACCESS   read-only
    STATUS       current
    DESCRIPTION
        "Cisco UCS equipment:PsuInputStats:suspect managed
        object property"
    ::= { cucsEquipmentPsuInputStatsEntry 14 }

cucsEquipmentPsuInputStatsThresholded OBJECT-TYPE
    SYNTAX       CucsEquipmentPsuInputStatsThresholded
    MAX-ACCESS   read-only
    STATUS       current
    DESCRIPTION
        "Cisco UCS equipment:PsuInputStats:thresholded
        managed object property"
    ::= { cucsEquipmentPsuInputStatsEntry 15 }

cucsEquipmentPsuInputStatsTimeCollected OBJECT-TYPE
    SYNTAX       DateAndTime
    MAX-ACCESS   read-only
    STATUS       current
    DESCRIPTION
        "Cisco UCS equipment:PsuInputStats:timeCollected
        managed object property"
    ::= { cucsEquipmentPsuInputStatsEntry 16 }

cucsEquipmentPsuInputStatsUpdate OBJECT-TYPE
    SYNTAX       Gauge32
    MAX-ACCESS   read-only
    STATUS       current
    DESCRIPTION
        "Cisco UCS equipment:PsuInputStats:update managed object property"
    ::= { cucsEquipmentPsuInputStatsEntry 17 }

cucsEquipmentPsuInputStatsVoltage OBJECT-TYPE
    SYNTAX       INTEGER
    MAX-ACCESS   read-only
    STATUS       current
    DESCRIPTION
        "Cisco UCS equipment:PsuInputStats:voltage managed
        object property"
    ::= { cucsEquipmentPsuInputStatsEntry 18 }

cucsEquipmentPsuInputStatsVoltageAvg OBJECT-TYPE
    SYNTAX       INTEGER
    MAX-ACCESS   read-only
    STATUS       current
    DESCRIPTION
        "Cisco UCS equipment:PsuInputStats:voltageAvg managed
        object property"
    ::= { cucsEquipmentPsuInputStatsEntry 19 }

cucsEquipmentPsuInputStatsVoltageMax OBJECT-TYPE
    SYNTAX       INTEGER
    MAX-ACCESS   read-only
    STATUS       current
    DESCRIPTION
        "Cisco UCS equipment:PsuInputStats:voltageMax managed
        object property"
    ::= { cucsEquipmentPsuInputStatsEntry 20 }

cucsEquipmentPsuInputStatsVoltageMin OBJECT-TYPE
    SYNTAX       INTEGER
    MAX-ACCESS   read-only
    STATUS       current
    DESCRIPTION
        "Cisco UCS equipment:PsuInputStats:voltageMin managed
        object property"
    ::= { cucsEquipmentPsuInputStatsEntry 21 }

cucsEquipmentPsuInputStatsHistTable OBJECT-TYPE
    SYNTAX           SEQUENCE OF CucsEquipmentPsuInputStatsHistEntry
    MAX-ACCESS       not-accessible
    STATUS           current
    DESCRIPTION
        "Cisco UCS equipment:PsuInputStatsHist managed object table"
    ::= { cucsEquipmentObjects 59 }

cucsEquipmentPsuInputStatsHistEntry OBJECT-TYPE
    SYNTAX           CucsEquipmentPsuInputStatsHistEntry
    MAX-ACCESS       not-accessible
    STATUS           current
    DESCRIPTION
        "Entry for the cucsEquipmentPsuInputStatsHistTable table."
    INDEX { cucsEquipmentPsuInputStatsHistInstanceId }
    ::= { cucsEquipmentPsuInputStatsHistTable 1 }

CucsEquipmentPsuInputStatsHistEntry ::= SEQUENCE {
    cucsEquipmentPsuInputStatsHistInstanceId                         CucsManagedObjectId,
    cucsEquipmentPsuInputStatsHistDn                                 CucsManagedObjectDn,
    cucsEquipmentPsuInputStatsHistRn                                 SnmpAdminString,
    cucsEquipmentPsuInputStatsHistCurrent                            INTEGER,
    cucsEquipmentPsuInputStatsHistCurrentAvg                         INTEGER,
    cucsEquipmentPsuInputStatsHistCurrentMax                         INTEGER,
    cucsEquipmentPsuInputStatsHistCurrentMin                         INTEGER,
    cucsEquipmentPsuInputStatsHistId                                 Unsigned64,
    cucsEquipmentPsuInputStatsHistMostRecent                         TruthValue,
    cucsEquipmentPsuInputStatsHistPower                              INTEGER,
    cucsEquipmentPsuInputStatsHistPowerAvg                           INTEGER,
    cucsEquipmentPsuInputStatsHistPowerMax                           INTEGER,
    cucsEquipmentPsuInputStatsHistPowerMin                           INTEGER,
    cucsEquipmentPsuInputStatsHistSuspect                            TruthValue,
    cucsEquipmentPsuInputStatsHistThresholded                        CucsEquipmentPsuInputStatsHistThresholded,
    cucsEquipmentPsuInputStatsHistTimeCollected                      DateAndTime,
    cucsEquipmentPsuInputStatsHistVoltage                            INTEGER,
    cucsEquipmentPsuInputStatsHistVoltageAvg                         INTEGER,
    cucsEquipmentPsuInputStatsHistVoltageMax                         INTEGER,
    cucsEquipmentPsuInputStatsHistVoltageMin                         INTEGER
}

cucsEquipmentPsuInputStatsHistInstanceId OBJECT-TYPE
    SYNTAX       CucsManagedObjectId
    MAX-ACCESS   not-accessible
    STATUS       current
    DESCRIPTION
        "Instance identifier of the managed object."
    ::= { cucsEquipmentPsuInputStatsHistEntry 1 }

cucsEquipmentPsuInputStatsHistDn OBJECT-TYPE
    SYNTAX       CucsManagedObjectDn
    MAX-ACCESS   read-only
    STATUS       current
    DESCRIPTION
        "Cisco UCS equipment:PsuInputStatsHist:dn managed object property"
    ::= { cucsEquipmentPsuInputStatsHistEntry 2 }

cucsEquipmentPsuInputStatsHistRn OBJECT-TYPE
    SYNTAX       SnmpAdminString
    MAX-ACCESS   read-only
    STATUS       current
    DESCRIPTION
        "Cisco UCS equipment:PsuInputStatsHist:rn managed object property"
    ::= { cucsEquipmentPsuInputStatsHistEntry 3 }

cucsEquipmentPsuInputStatsHistCurrent OBJECT-TYPE
    SYNTAX       INTEGER
    MAX-ACCESS   read-only
    STATUS       current
    DESCRIPTION
        "Cisco UCS equipment:PsuInputStatsHist:current
        managed object property"
    ::= { cucsEquipmentPsuInputStatsHistEntry 4 }

cucsEquipmentPsuInputStatsHistCurrentAvg OBJECT-TYPE
    SYNTAX       INTEGER
    MAX-ACCESS   read-only
    STATUS       current
    DESCRIPTION
        "Cisco UCS equipment:PsuInputStatsHist:currentAvg
        managed object property"
    ::= { cucsEquipmentPsuInputStatsHistEntry 5 }

cucsEquipmentPsuInputStatsHistCurrentMax OBJECT-TYPE
    SYNTAX       INTEGER
    MAX-ACCESS   read-only
    STATUS       current
    DESCRIPTION
        "Cisco UCS equipment:PsuInputStatsHist:currentMax
        managed object property"
    ::= { cucsEquipmentPsuInputStatsHistEntry 6 }

cucsEquipmentPsuInputStatsHistCurrentMin OBJECT-TYPE
    SYNTAX       INTEGER
    MAX-ACCESS   read-only
    STATUS       current
    DESCRIPTION
        "Cisco UCS equipment:PsuInputStatsHist:currentMin
        managed object property"
    ::= { cucsEquipmentPsuInputStatsHistEntry 7 }

cucsEquipmentPsuInputStatsHistId OBJECT-TYPE
    SYNTAX       Unsigned64
    MAX-ACCESS   read-only
    STATUS       current
    DESCRIPTION
        "Cisco UCS equipment:PsuInputStatsHist:id managed object property"
    ::= { cucsEquipmentPsuInputStatsHistEntry 8 }

cucsEquipmentPsuInputStatsHistMostRecent OBJECT-TYPE
    SYNTAX       TruthValue
    MAX-ACCESS   read-only
    STATUS       current
    DESCRIPTION
        "Cisco UCS equipment:PsuInputStatsHist:mostRecent
        managed object property"
    ::= { cucsEquipmentPsuInputStatsHistEntry 9 }

cucsEquipmentPsuInputStatsHistPower OBJECT-TYPE
    SYNTAX       INTEGER
    MAX-ACCESS   read-only
    STATUS       current
    DESCRIPTION
        "Cisco UCS equipment:PsuInputStatsHist:power managed
        object property"
    ::= { cucsEquipmentPsuInputStatsHistEntry 10 }

cucsEquipmentPsuInputStatsHistPowerAvg OBJECT-TYPE
    SYNTAX       INTEGER
    MAX-ACCESS   read-only
    STATUS       current
    DESCRIPTION
        "Cisco UCS equipment:PsuInputStatsHist:powerAvg
        managed object property"
    ::= { cucsEquipmentPsuInputStatsHistEntry 11 }

cucsEquipmentPsuInputStatsHistPowerMax OBJECT-TYPE
    SYNTAX       INTEGER
    MAX-ACCESS   read-only
    STATUS       current
    DESCRIPTION
        "Cisco UCS equipment:PsuInputStatsHist:powerMax
        managed object property"
    ::= { cucsEquipmentPsuInputStatsHistEntry 12 }

cucsEquipmentPsuInputStatsHistPowerMin OBJECT-TYPE
    SYNTAX       INTEGER
    MAX-ACCESS   read-only
    STATUS       current
    DESCRIPTION
        "Cisco UCS equipment:PsuInputStatsHist:powerMin
        managed object property"
    ::= { cucsEquipmentPsuInputStatsHistEntry 13 }

cucsEquipmentPsuInputStatsHistSuspect OBJECT-TYPE
    SYNTAX       TruthValue
    MAX-ACCESS   read-only
    STATUS       current
    DESCRIPTION
        "Cisco UCS equipment:PsuInputStatsHist:suspect
        managed object property"
    ::= { cucsEquipmentPsuInputStatsHistEntry 14 }

cucsEquipmentPsuInputStatsHistThresholded OBJECT-TYPE
    SYNTAX       CucsEquipmentPsuInputStatsHistThresholded
    MAX-ACCESS   read-only
    STATUS       current
    DESCRIPTION
        "Cisco UCS equipment:PsuInputStatsHist:thresholded
        managed object property"
    ::= { cucsEquipmentPsuInputStatsHistEntry 15 }

cucsEquipmentPsuInputStatsHistTimeCollected OBJECT-TYPE
    SYNTAX       DateAndTime
    MAX-ACCESS   read-only
    STATUS       current
    DESCRIPTION
        "Cisco UCS equipment:PsuInputStatsHist:timeCollected
        managed object property"
    ::= { cucsEquipmentPsuInputStatsHistEntry 16 }

cucsEquipmentPsuInputStatsHistVoltage OBJECT-TYPE
    SYNTAX       INTEGER
    MAX-ACCESS   read-only
    STATUS       current
    DESCRIPTION
        "Cisco UCS equipment:PsuInputStatsHist:voltage
        managed object property"
    ::= { cucsEquipmentPsuInputStatsHistEntry 17 }

cucsEquipmentPsuInputStatsHistVoltageAvg OBJECT-TYPE
    SYNTAX       INTEGER
    MAX-ACCESS   read-only
    STATUS       current
    DESCRIPTION
        "Cisco UCS equipment:PsuInputStatsHist:voltageAvg
        managed object property"
    ::= { cucsEquipmentPsuInputStatsHistEntry 18 }

cucsEquipmentPsuInputStatsHistVoltageMax OBJECT-TYPE
    SYNTAX       INTEGER
    MAX-ACCESS   read-only
    STATUS       current
    DESCRIPTION
        "Cisco UCS equipment:PsuInputStatsHist:voltageMax
        managed object property"
    ::= { cucsEquipmentPsuInputStatsHistEntry 19 }

cucsEquipmentPsuInputStatsHistVoltageMin OBJECT-TYPE
    SYNTAX       INTEGER
    MAX-ACCESS   read-only
    STATUS       current
    DESCRIPTION
        "Cisco UCS equipment:PsuInputStatsHist:voltageMin
        managed object property"
    ::= { cucsEquipmentPsuInputStatsHistEntry 20 }

cucsEquipmentPsuOutputStatsTable OBJECT-TYPE
    SYNTAX           SEQUENCE OF CucsEquipmentPsuOutputStatsEntry
    MAX-ACCESS       not-accessible
    STATUS           current
    DESCRIPTION
        "Cisco UCS equipment:PsuOutputStats managed object table"
    ::= { cucsEquipmentObjects 92 }

cucsEquipmentPsuOutputStatsEntry OBJECT-TYPE
    SYNTAX           CucsEquipmentPsuOutputStatsEntry
    MAX-ACCESS       not-accessible
    STATUS           current
    DESCRIPTION
        "Entry for the cucsEquipmentPsuOutputStatsTable table."
    INDEX { cucsEquipmentPsuOutputStatsInstanceId }
    ::= { cucsEquipmentPsuOutputStatsTable 1 }

CucsEquipmentPsuOutputStatsEntry ::= SEQUENCE {
    cucsEquipmentPsuOutputStatsInstanceId                            CucsManagedObjectId,
    cucsEquipmentPsuOutputStatsDn                                    CucsManagedObjectDn,
    cucsEquipmentPsuOutputStatsRn                                    SnmpAdminString,
    cucsEquipmentPsuOutputStatsCurrent                               INTEGER,
    cucsEquipmentPsuOutputStatsCurrentAvg                            INTEGER,
    cucsEquipmentPsuOutputStatsCurrentMax                            INTEGER,
    cucsEquipmentPsuOutputStatsCurrentMin                            INTEGER,
    cucsEquipmentPsuOutputStatsIntervals                             Gauge32,
    cucsEquipmentPsuOutputStatsOutputStatus                          SnmpAdminString,
    cucsEquipmentPsuOutputStatsPower                                 INTEGER,
    cucsEquipmentPsuOutputStatsPowerAvg                              INTEGER,
    cucsEquipmentPsuOutputStatsPowerMax                              INTEGER,
    cucsEquipmentPsuOutputStatsPowerMin                              INTEGER,
    cucsEquipmentPsuOutputStatsSuspect                               TruthValue,
    cucsEquipmentPsuOutputStatsThresholded                           CucsEquipmentPsuOutputStatsThresholded,
    cucsEquipmentPsuOutputStatsTimeCollected                         DateAndTime,
    cucsEquipmentPsuOutputStatsUpdate                                Gauge32,
    cucsEquipmentPsuOutputStatsVoltage                               INTEGER,
    cucsEquipmentPsuOutputStatsVoltageAvg                            INTEGER,
    cucsEquipmentPsuOutputStatsVoltageMax                            INTEGER,
    cucsEquipmentPsuOutputStatsVoltageMin                            INTEGER
}

cucsEquipmentPsuOutputStatsInstanceId OBJECT-TYPE
    SYNTAX       CucsManagedObjectId
    MAX-ACCESS   not-accessible
    STATUS       current
    DESCRIPTION
        "Instance identifier of the managed object."
    ::= { cucsEquipmentPsuOutputStatsEntry 1 }

cucsEquipmentPsuOutputStatsDn OBJECT-TYPE
    SYNTAX       CucsManagedObjectDn
    MAX-ACCESS   read-only
    STATUS       current
    DESCRIPTION
        "Cisco UCS equipment:PsuOutputStats:dn managed object property"
    ::= { cucsEquipmentPsuOutputStatsEntry 2 }

cucsEquipmentPsuOutputStatsRn OBJECT-TYPE
    SYNTAX       SnmpAdminString
    MAX-ACCESS   read-only
    STATUS       current
    DESCRIPTION
        "Cisco UCS equipment:PsuOutputStats:rn managed object property"
    ::= { cucsEquipmentPsuOutputStatsEntry 3 }

cucsEquipmentPsuOutputStatsCurrent OBJECT-TYPE
    SYNTAX       INTEGER
    MAX-ACCESS   read-only
    STATUS       current
    DESCRIPTION
        "Cisco UCS equipment:PsuOutputStats:current managed
        object property"
    ::= { cucsEquipmentPsuOutputStatsEntry 4 }

cucsEquipmentPsuOutputStatsCurrentAvg OBJECT-TYPE
    SYNTAX       INTEGER
    MAX-ACCESS   read-only
    STATUS       current
    DESCRIPTION
        "Cisco UCS equipment:PsuOutputStats:currentAvg
        managed object property"
    ::= { cucsEquipmentPsuOutputStatsEntry 5 }

cucsEquipmentPsuOutputStatsCurrentMax OBJECT-TYPE
    SYNTAX       INTEGER
    MAX-ACCESS   read-only
    STATUS       current
    DESCRIPTION
        "Cisco UCS equipment:PsuOutputStats:currentMax
        managed object property"
    ::= { cucsEquipmentPsuOutputStatsEntry 6 }

cucsEquipmentPsuOutputStatsCurrentMin OBJECT-TYPE
    SYNTAX       INTEGER
    MAX-ACCESS   read-only
    STATUS       current
    DESCRIPTION
        "Cisco UCS equipment:PsuOutputStats:currentMin
        managed object property"
    ::= { cucsEquipmentPsuOutputStatsEntry 7 }

cucsEquipmentPsuOutputStatsIntervals OBJECT-TYPE
    SYNTAX       Gauge32
    MAX-ACCESS   read-only
    STATUS       current
    DESCRIPTION
        "Cisco UCS equipment:PsuOutputStats:intervals managed
        object property"
    ::= { cucsEquipmentPsuOutputStatsEntry 8 }

cucsEquipmentPsuOutputStatsOutputStatus OBJECT-TYPE
    SYNTAX       SnmpAdminString
    MAX-ACCESS   read-only
    STATUS       current
    DESCRIPTION
        "Cisco UCS equipment:PsuOutputStats:outputStatus
        managed object property"
    ::= { cucsEquipmentPsuOutputStatsEntry 9 }

cucsEquipmentPsuOutputStatsPower OBJECT-TYPE
    SYNTAX       INTEGER
    MAX-ACCESS   read-only
    STATUS       current
    DESCRIPTION
        "Cisco UCS equipment:PsuOutputStats:power managed object property"
    ::= { cucsEquipmentPsuOutputStatsEntry 10 }

cucsEquipmentPsuOutputStatsPowerAvg OBJECT-TYPE
    SYNTAX       INTEGER
    MAX-ACCESS   read-only
    STATUS       current
    DESCRIPTION
        "Cisco UCS equipment:PsuOutputStats:powerAvg managed
        object property"
    ::= { cucsEquipmentPsuOutputStatsEntry 11 }

cucsEquipmentPsuOutputStatsPowerMax OBJECT-TYPE
    SYNTAX       INTEGER
    MAX-ACCESS   read-only
    STATUS       current
    DESCRIPTION
        "Cisco UCS equipment:PsuOutputStats:powerMax managed
        object property"
    ::= { cucsEquipmentPsuOutputStatsEntry 12 }

cucsEquipmentPsuOutputStatsPowerMin OBJECT-TYPE
    SYNTAX       INTEGER
    MAX-ACCESS   read-only
    STATUS       current
    DESCRIPTION
        "Cisco UCS equipment:PsuOutputStats:powerMin managed
        object property"
    ::= { cucsEquipmentPsuOutputStatsEntry 13 }

cucsEquipmentPsuOutputStatsSuspect OBJECT-TYPE
    SYNTAX       TruthValue
    MAX-ACCESS   read-only
    STATUS       current
    DESCRIPTION
        "Cisco UCS equipment:PsuOutputStats:suspect managed
        object property"
    ::= { cucsEquipmentPsuOutputStatsEntry 14 }

cucsEquipmentPsuOutputStatsThresholded OBJECT-TYPE
    SYNTAX       CucsEquipmentPsuOutputStatsThresholded
    MAX-ACCESS   read-only
    STATUS       current
    DESCRIPTION
        "Cisco UCS equipment:PsuOutputStats:thresholded
        managed object property"
    ::= { cucsEquipmentPsuOutputStatsEntry 15 }

cucsEquipmentPsuOutputStatsTimeCollected OBJECT-TYPE
    SYNTAX       DateAndTime
    MAX-ACCESS   read-only
    STATUS       current
    DESCRIPTION
        "Cisco UCS equipment:PsuOutputStats:timeCollected
        managed object property"
    ::= { cucsEquipmentPsuOutputStatsEntry 16 }

cucsEquipmentPsuOutputStatsUpdate OBJECT-TYPE
    SYNTAX       Gauge32
    MAX-ACCESS   read-only
    STATUS       current
    DESCRIPTION
        "Cisco UCS equipment:PsuOutputStats:update managed
        object property"
    ::= { cucsEquipmentPsuOutputStatsEntry 17 }

cucsEquipmentPsuOutputStatsVoltage OBJECT-TYPE
    SYNTAX       INTEGER
    MAX-ACCESS   read-only
    STATUS       current
    DESCRIPTION
        "Cisco UCS equipment:PsuOutputStats:voltage managed
        object property"
    ::= { cucsEquipmentPsuOutputStatsEntry 18 }

cucsEquipmentPsuOutputStatsVoltageAvg OBJECT-TYPE
    SYNTAX       INTEGER
    MAX-ACCESS   read-only
    STATUS       current
    DESCRIPTION
        "Cisco UCS equipment:PsuOutputStats:voltageAvg
        managed object property"
    ::= { cucsEquipmentPsuOutputStatsEntry 19 }

cucsEquipmentPsuOutputStatsVoltageMax OBJECT-TYPE
    SYNTAX       INTEGER
    MAX-ACCESS   read-only
    STATUS       current
    DESCRIPTION
        "Cisco UCS equipment:PsuOutputStats:voltageMax
        managed object property"
    ::= { cucsEquipmentPsuOutputStatsEntry 20 }

cucsEquipmentPsuOutputStatsVoltageMin OBJECT-TYPE
    SYNTAX       INTEGER
    MAX-ACCESS   read-only
    STATUS       current
    DESCRIPTION
        "Cisco UCS equipment:PsuOutputStats:voltageMin
        managed object property"
    ::= { cucsEquipmentPsuOutputStatsEntry 21 }

cucsEquipmentPsuOutputStatsHistTable OBJECT-TYPE
    SYNTAX           SEQUENCE OF CucsEquipmentPsuOutputStatsHistEntry
    MAX-ACCESS       not-accessible
    STATUS           current
    DESCRIPTION
        "Cisco UCS equipment:PsuOutputStatsHist managed object table"
    ::= { cucsEquipmentObjects 93 }

cucsEquipmentPsuOutputStatsHistEntry OBJECT-TYPE
    SYNTAX           CucsEquipmentPsuOutputStatsHistEntry
    MAX-ACCESS       not-accessible
    STATUS           current
    DESCRIPTION
        "Entry for the cucsEquipmentPsuOutputStatsHistTable table."
    INDEX { cucsEquipmentPsuOutputStatsHistInstanceId }
    ::= { cucsEquipmentPsuOutputStatsHistTable 1 }

CucsEquipmentPsuOutputStatsHistEntry ::= SEQUENCE {
    cucsEquipmentPsuOutputStatsHistInstanceId                        CucsManagedObjectId,
    cucsEquipmentPsuOutputStatsHistDn                                CucsManagedObjectDn,
    cucsEquipmentPsuOutputStatsHistRn                                SnmpAdminString,
    cucsEquipmentPsuOutputStatsHistCurrent                           INTEGER,
    cucsEquipmentPsuOutputStatsHistCurrentAvg                        INTEGER,
    cucsEquipmentPsuOutputStatsHistCurrentMax                        INTEGER,
    cucsEquipmentPsuOutputStatsHistCurrentMin                        INTEGER,
    cucsEquipmentPsuOutputStatsHistId                                Unsigned64,
    cucsEquipmentPsuOutputStatsHistMostRecent                        TruthValue,
    cucsEquipmentPsuOutputStatsHistPower                             INTEGER,
    cucsEquipmentPsuOutputStatsHistPowerAvg                          INTEGER,
    cucsEquipmentPsuOutputStatsHistPowerMax                          INTEGER,
    cucsEquipmentPsuOutputStatsHistPowerMin                          INTEGER,
    cucsEquipmentPsuOutputStatsHistSuspect                           TruthValue,
    cucsEquipmentPsuOutputStatsHistThresholded                       CucsEquipmentPsuOutputStatsHistThresholded,
    cucsEquipmentPsuOutputStatsHistTimeCollected                     DateAndTime,
    cucsEquipmentPsuOutputStatsHistVoltage                           INTEGER,
    cucsEquipmentPsuOutputStatsHistVoltageAvg                        INTEGER,
    cucsEquipmentPsuOutputStatsHistVoltageMax                        INTEGER,
    cucsEquipmentPsuOutputStatsHistVoltageMin                        INTEGER
}

cucsEquipmentPsuOutputStatsHistInstanceId OBJECT-TYPE
    SYNTAX       CucsManagedObjectId
    MAX-ACCESS   not-accessible
    STATUS       current
    DESCRIPTION
        "Instance identifier of the managed object."
    ::= { cucsEquipmentPsuOutputStatsHistEntry 1 }

cucsEquipmentPsuOutputStatsHistDn OBJECT-TYPE
    SYNTAX       CucsManagedObjectDn
    MAX-ACCESS   read-only
    STATUS       current
    DESCRIPTION
        "Cisco UCS equipment:PsuOutputStatsHist:dn managed
        object property"
    ::= { cucsEquipmentPsuOutputStatsHistEntry 2 }

cucsEquipmentPsuOutputStatsHistRn OBJECT-TYPE
    SYNTAX       SnmpAdminString
    MAX-ACCESS   read-only
    STATUS       current
    DESCRIPTION
        "Cisco UCS equipment:PsuOutputStatsHist:rn managed
        object property"
    ::= { cucsEquipmentPsuOutputStatsHistEntry 3 }

cucsEquipmentPsuOutputStatsHistCurrent OBJECT-TYPE
    SYNTAX       INTEGER
    MAX-ACCESS   read-only
    STATUS       current
    DESCRIPTION
        "Cisco UCS equipment:PsuOutputStatsHist:current
        managed object property"
    ::= { cucsEquipmentPsuOutputStatsHistEntry 4 }

cucsEquipmentPsuOutputStatsHistCurrentAvg OBJECT-TYPE
    SYNTAX       INTEGER
    MAX-ACCESS   read-only
    STATUS       current
    DESCRIPTION
        "Cisco UCS equipment:PsuOutputStatsHist:currentAvg
        managed object property"
    ::= { cucsEquipmentPsuOutputStatsHistEntry 5 }

cucsEquipmentPsuOutputStatsHistCurrentMax OBJECT-TYPE
    SYNTAX       INTEGER
    MAX-ACCESS   read-only
    STATUS       current
    DESCRIPTION
        "Cisco UCS equipment:PsuOutputStatsHist:currentMax
        managed object property"
    ::= { cucsEquipmentPsuOutputStatsHistEntry 6 }

cucsEquipmentPsuOutputStatsHistCurrentMin OBJECT-TYPE
    SYNTAX       INTEGER
    MAX-ACCESS   read-only
    STATUS       current
    DESCRIPTION
        "Cisco UCS equipment:PsuOutputStatsHist:currentMin
        managed object property"
    ::= { cucsEquipmentPsuOutputStatsHistEntry 7 }

cucsEquipmentPsuOutputStatsHistId OBJECT-TYPE
    SYNTAX       Unsigned64
    MAX-ACCESS   read-only
    STATUS       current
    DESCRIPTION
        "Cisco UCS equipment:PsuOutputStatsHist:id managed
        object property"
    ::= { cucsEquipmentPsuOutputStatsHistEntry 8 }

cucsEquipmentPsuOutputStatsHistMostRecent OBJECT-TYPE
    SYNTAX       TruthValue
    MAX-ACCESS   read-only
    STATUS       current
    DESCRIPTION
        "Cisco UCS equipment:PsuOutputStatsHist:mostRecent
        managed object property"
    ::= { cucsEquipmentPsuOutputStatsHistEntry 9 }

cucsEquipmentPsuOutputStatsHistPower OBJECT-TYPE
    SYNTAX       INTEGER
    MAX-ACCESS   read-only
    STATUS       current
    DESCRIPTION
        "Cisco UCS equipment:PsuOutputStatsHist:power managed
        object property"
    ::= { cucsEquipmentPsuOutputStatsHistEntry 10 }

cucsEquipmentPsuOutputStatsHistPowerAvg OBJECT-TYPE
    SYNTAX       INTEGER
    MAX-ACCESS   read-only
    STATUS       current
    DESCRIPTION
        "Cisco UCS equipment:PsuOutputStatsHist:powerAvg
        managed object property"
    ::= { cucsEquipmentPsuOutputStatsHistEntry 11 }

cucsEquipmentPsuOutputStatsHistPowerMax OBJECT-TYPE
    SYNTAX       INTEGER
    MAX-ACCESS   read-only
    STATUS       current
    DESCRIPTION
        "Cisco UCS equipment:PsuOutputStatsHist:powerMax
        managed object property"
    ::= { cucsEquipmentPsuOutputStatsHistEntry 12 }

cucsEquipmentPsuOutputStatsHistPowerMin OBJECT-TYPE
    SYNTAX       INTEGER
    MAX-ACCESS   read-only
    STATUS       current
    DESCRIPTION
        "Cisco UCS equipment:PsuOutputStatsHist:powerMin
        managed object property"
    ::= { cucsEquipmentPsuOutputStatsHistEntry 13 }

cucsEquipmentPsuOutputStatsHistSuspect OBJECT-TYPE
    SYNTAX       TruthValue
    MAX-ACCESS   read-only
    STATUS       current
    DESCRIPTION
        "Cisco UCS equipment:PsuOutputStatsHist:suspect
        managed object property"
    ::= { cucsEquipmentPsuOutputStatsHistEntry 14 }

cucsEquipmentPsuOutputStatsHistThresholded OBJECT-TYPE
    SYNTAX       CucsEquipmentPsuOutputStatsHistThresholded
    MAX-ACCESS   read-only
    STATUS       current
    DESCRIPTION
        "Cisco UCS equipment:PsuOutputStatsHist:thresholded
        managed object property"
    ::= { cucsEquipmentPsuOutputStatsHistEntry 15 }

cucsEquipmentPsuOutputStatsHistTimeCollected OBJECT-TYPE
    SYNTAX       DateAndTime
    MAX-ACCESS   read-only
    STATUS       current
    DESCRIPTION
        "Cisco UCS equipment:PsuOutputStatsHist:timeCollected
        managed object property"
    ::= { cucsEquipmentPsuOutputStatsHistEntry 16 }

cucsEquipmentPsuOutputStatsHistVoltage OBJECT-TYPE
    SYNTAX       INTEGER
    MAX-ACCESS   read-only
    STATUS       current
    DESCRIPTION
        "Cisco UCS equipment:PsuOutputStatsHist:voltage
        managed object property"
    ::= { cucsEquipmentPsuOutputStatsHistEntry 17 }

cucsEquipmentPsuOutputStatsHistVoltageAvg OBJECT-TYPE
    SYNTAX       INTEGER
    MAX-ACCESS   read-only
    STATUS       current
    DESCRIPTION
        "Cisco UCS equipment:PsuOutputStatsHist:voltageAvg
        managed object property"
    ::= { cucsEquipmentPsuOutputStatsHistEntry 18 }

cucsEquipmentPsuOutputStatsHistVoltageMax OBJECT-TYPE
    SYNTAX       INTEGER
    MAX-ACCESS   read-only
    STATUS       current
    DESCRIPTION
        "Cisco UCS equipment:PsuOutputStatsHist:voltageMax
        managed object property"
    ::= { cucsEquipmentPsuOutputStatsHistEntry 19 }

cucsEquipmentPsuOutputStatsHistVoltageMin OBJECT-TYPE
    SYNTAX       INTEGER
    MAX-ACCESS   read-only
    STATUS       current
    DESCRIPTION
        "Cisco UCS equipment:PsuOutputStatsHist:voltageMin
        managed object property"
    ::= { cucsEquipmentPsuOutputStatsHistEntry 20 }

cucsEquipmentPsuStatsTable OBJECT-TYPE
    SYNTAX           SEQUENCE OF CucsEquipmentPsuStatsEntry
    MAX-ACCESS       not-accessible
    STATUS           current
    DESCRIPTION
        "Cisco UCS equipment:PsuStats managed object table"
    ::= { cucsEquipmentObjects 60 }

cucsEquipmentPsuStatsEntry OBJECT-TYPE
    SYNTAX           CucsEquipmentPsuStatsEntry
    MAX-ACCESS       not-accessible
    STATUS           current
    DESCRIPTION
        "Entry for the cucsEquipmentPsuStatsTable table."
    INDEX { cucsEquipmentPsuStatsInstanceId }
    ::= { cucsEquipmentPsuStatsTable 1 }

CucsEquipmentPsuStatsEntry ::= SEQUENCE {
    cucsEquipmentPsuStatsInstanceId                                  CucsManagedObjectId,
    cucsEquipmentPsuStatsDn                                          CucsManagedObjectDn,
    cucsEquipmentPsuStatsRn                                          SnmpAdminString,
    cucsEquipmentPsuStatsAmbientTemp                                 INTEGER,
    cucsEquipmentPsuStatsAmbientTempAvg                              INTEGER,
    cucsEquipmentPsuStatsAmbientTempMax                              INTEGER,
    cucsEquipmentPsuStatsAmbientTempMin                              INTEGER,
    cucsEquipmentPsuStatsInput210v                                   INTEGER,
    cucsEquipmentPsuStatsInput210vAvg                                INTEGER,
    cucsEquipmentPsuStatsInput210vMax                                INTEGER,
    cucsEquipmentPsuStatsInput210vMin                                INTEGER,
    cucsEquipmentPsuStatsIntervals                                   Gauge32,
    cucsEquipmentPsuStatsOutput12v                                   INTEGER,
    cucsEquipmentPsuStatsOutput12vAvg                                INTEGER,
    cucsEquipmentPsuStatsOutput12vMax                                INTEGER,
    cucsEquipmentPsuStatsOutput12vMin                                INTEGER,
    cucsEquipmentPsuStatsOutput3v3                                   INTEGER,
    cucsEquipmentPsuStatsOutput3v3Avg                                INTEGER,
    cucsEquipmentPsuStatsOutput3v3Max                                INTEGER,
    cucsEquipmentPsuStatsOutput3v3Min                                INTEGER,
    cucsEquipmentPsuStatsOutputCurrent                               INTEGER,
    cucsEquipmentPsuStatsOutputCurrentAvg                            INTEGER,
    cucsEquipmentPsuStatsOutputCurrentMax                            INTEGER,
    cucsEquipmentPsuStatsOutputCurrentMin                            INTEGER,
    cucsEquipmentPsuStatsOutputPower                                 INTEGER,
    cucsEquipmentPsuStatsOutputPowerAvg                              INTEGER,
    cucsEquipmentPsuStatsOutputPowerMax                              INTEGER,
    cucsEquipmentPsuStatsOutputPowerMin                              INTEGER,
    cucsEquipmentPsuStatsSuspect                                     TruthValue,
    cucsEquipmentPsuStatsThresholded                                 CucsEquipmentPsuStatsThresholded,
    cucsEquipmentPsuStatsTimeCollected                               DateAndTime,
    cucsEquipmentPsuStatsUpdate                                      Gauge32,
    cucsEquipmentPsuStatsPsuTemp1                                    INTEGER,
    cucsEquipmentPsuStatsPsuTemp2                                    INTEGER
}

cucsEquipmentPsuStatsInstanceId OBJECT-TYPE
    SYNTAX       CucsManagedObjectId
    MAX-ACCESS   not-accessible
    STATUS       current
    DESCRIPTION
        "Instance identifier of the managed object."
    ::= { cucsEquipmentPsuStatsEntry 1 }

cucsEquipmentPsuStatsDn OBJECT-TYPE
    SYNTAX       CucsManagedObjectDn
    MAX-ACCESS   read-only
    STATUS       current
    DESCRIPTION
        "Cisco UCS equipment:PsuStats:dn managed object property"
    ::= { cucsEquipmentPsuStatsEntry 2 }

cucsEquipmentPsuStatsRn OBJECT-TYPE
    SYNTAX       SnmpAdminString
    MAX-ACCESS   read-only
    STATUS       current
    DESCRIPTION
        "Cisco UCS equipment:PsuStats:rn managed object property"
    ::= { cucsEquipmentPsuStatsEntry 3 }

cucsEquipmentPsuStatsAmbientTemp OBJECT-TYPE
    SYNTAX       INTEGER
    MAX-ACCESS   read-only
    STATUS       current
    DESCRIPTION
        "Cisco UCS equipment:PsuStats:ambientTemp managed object property"
    ::= { cucsEquipmentPsuStatsEntry 4 }

cucsEquipmentPsuStatsAmbientTempAvg OBJECT-TYPE
    SYNTAX       INTEGER
    MAX-ACCESS   read-only
    STATUS       current
    DESCRIPTION
        "Cisco UCS equipment:PsuStats:ambientTempAvg managed
        object property"
    ::= { cucsEquipmentPsuStatsEntry 5 }

cucsEquipmentPsuStatsAmbientTempMax OBJECT-TYPE
    SYNTAX       INTEGER
    MAX-ACCESS   read-only
    STATUS       current
    DESCRIPTION
        "Cisco UCS equipment:PsuStats:ambientTempMax managed
        object property"
    ::= { cucsEquipmentPsuStatsEntry 6 }

cucsEquipmentPsuStatsAmbientTempMin OBJECT-TYPE
    SYNTAX       INTEGER
    MAX-ACCESS   read-only
    STATUS       current
    DESCRIPTION
        "Cisco UCS equipment:PsuStats:ambientTempMin managed
        object property"
    ::= { cucsEquipmentPsuStatsEntry 7 }

cucsEquipmentPsuStatsInput210v OBJECT-TYPE
    SYNTAX       INTEGER
    MAX-ACCESS   read-only
    STATUS       current
    DESCRIPTION
        "Cisco UCS equipment:PsuStats:input210v managed object property"
    ::= { cucsEquipmentPsuStatsEntry 8 }

cucsEquipmentPsuStatsInput210vAvg OBJECT-TYPE
    SYNTAX       INTEGER
    MAX-ACCESS   read-only
    STATUS       current
    DESCRIPTION
        "Cisco UCS equipment:PsuStats:input210vAvg managed
        object property"
    ::= { cucsEquipmentPsuStatsEntry 9 }

cucsEquipmentPsuStatsInput210vMax OBJECT-TYPE
    SYNTAX       INTEGER
    MAX-ACCESS   read-only
    STATUS       current
    DESCRIPTION
        "Cisco UCS equipment:PsuStats:input210vMax managed
        object property"
    ::= { cucsEquipmentPsuStatsEntry 10 }

cucsEquipmentPsuStatsInput210vMin OBJECT-TYPE
    SYNTAX       INTEGER
    MAX-ACCESS   read-only
    STATUS       current
    DESCRIPTION
        "Cisco UCS equipment:PsuStats:input210vMin managed
        object property"
    ::= { cucsEquipmentPsuStatsEntry 11 }

cucsEquipmentPsuStatsIntervals OBJECT-TYPE
    SYNTAX       Gauge32
    MAX-ACCESS   read-only
    STATUS       current
    DESCRIPTION
        "Cisco UCS equipment:PsuStats:intervals managed object property"
    ::= { cucsEquipmentPsuStatsEntry 12 }

cucsEquipmentPsuStatsOutput12v OBJECT-TYPE
    SYNTAX       INTEGER
    MAX-ACCESS   read-only
    STATUS       current
    DESCRIPTION
        "Cisco UCS equipment:PsuStats:output12v managed object property"
    ::= { cucsEquipmentPsuStatsEntry 13 }

cucsEquipmentPsuStatsOutput12vAvg OBJECT-TYPE
    SYNTAX       INTEGER
    MAX-ACCESS   read-only
    STATUS       current
    DESCRIPTION
        "Cisco UCS equipment:PsuStats:output12vAvg managed
        object property"
    ::= { cucsEquipmentPsuStatsEntry 14 }

cucsEquipmentPsuStatsOutput12vMax OBJECT-TYPE
    SYNTAX       INTEGER
    MAX-ACCESS   read-only
    STATUS       current
    DESCRIPTION
        "Cisco UCS equipment:PsuStats:output12vMax managed
        object property"
    ::= { cucsEquipmentPsuStatsEntry 15 }

cucsEquipmentPsuStatsOutput12vMin OBJECT-TYPE
    SYNTAX       INTEGER
    MAX-ACCESS   read-only
    STATUS       current
    DESCRIPTION
        "Cisco UCS equipment:PsuStats:output12vMin managed
        object property"
    ::= { cucsEquipmentPsuStatsEntry 16 }

cucsEquipmentPsuStatsOutput3v3 OBJECT-TYPE
    SYNTAX       INTEGER
    MAX-ACCESS   read-only
    STATUS       current
    DESCRIPTION
        "Cisco UCS equipment:PsuStats:output3v3 managed object property"
    ::= { cucsEquipmentPsuStatsEntry 17 }

cucsEquipmentPsuStatsOutput3v3Avg OBJECT-TYPE
    SYNTAX       INTEGER
    MAX-ACCESS   read-only
    STATUS       current
    DESCRIPTION
        "Cisco UCS equipment:PsuStats:output3v3Avg managed
        object property"
    ::= { cucsEquipmentPsuStatsEntry 18 }

cucsEquipmentPsuStatsOutput3v3Max OBJECT-TYPE
    SYNTAX       INTEGER
    MAX-ACCESS   read-only
    STATUS       current
    DESCRIPTION
        "Cisco UCS equipment:PsuStats:output3v3Max managed
        object property"
    ::= { cucsEquipmentPsuStatsEntry 19 }

cucsEquipmentPsuStatsOutput3v3Min OBJECT-TYPE
    SYNTAX       INTEGER
    MAX-ACCESS   read-only
    STATUS       current
    DESCRIPTION
        "Cisco UCS equipment:PsuStats:output3v3Min managed
        object property"
    ::= { cucsEquipmentPsuStatsEntry 20 }

cucsEquipmentPsuStatsOutputCurrent OBJECT-TYPE
    SYNTAX       INTEGER
    MAX-ACCESS   read-only
    STATUS       current
    DESCRIPTION
        "Cisco UCS equipment:PsuStats:outputCurrent managed
        object property"
    ::= { cucsEquipmentPsuStatsEntry 21 }

cucsEquipmentPsuStatsOutputCurrentAvg OBJECT-TYPE
    SYNTAX       INTEGER
    MAX-ACCESS   read-only
    STATUS       current
    DESCRIPTION
        "Cisco UCS equipment:PsuStats:outputCurrentAvg
        managed object property"
    ::= { cucsEquipmentPsuStatsEntry 22 }

cucsEquipmentPsuStatsOutputCurrentMax OBJECT-TYPE
    SYNTAX       INTEGER
    MAX-ACCESS   read-only
    STATUS       current
    DESCRIPTION
        "Cisco UCS equipment:PsuStats:outputCurrentMax
        managed object property"
    ::= { cucsEquipmentPsuStatsEntry 23 }

cucsEquipmentPsuStatsOutputCurrentMin OBJECT-TYPE
    SYNTAX       INTEGER
    MAX-ACCESS   read-only
    STATUS       current
    DESCRIPTION
        "Cisco UCS equipment:PsuStats:outputCurrentMin
        managed object property"
    ::= { cucsEquipmentPsuStatsEntry 24 }

cucsEquipmentPsuStatsOutputPower OBJECT-TYPE
    SYNTAX       INTEGER
    MAX-ACCESS   read-only
    STATUS       current
    DESCRIPTION
        "Cisco UCS equipment:PsuStats:outputPower managed object property"
    ::= { cucsEquipmentPsuStatsEntry 25 }

cucsEquipmentPsuStatsOutputPowerAvg OBJECT-TYPE
    SYNTAX       INTEGER
    MAX-ACCESS   read-only
    STATUS       current
    DESCRIPTION
        "Cisco UCS equipment:PsuStats:outputPowerAvg managed
        object property"
    ::= { cucsEquipmentPsuStatsEntry 26 }

cucsEquipmentPsuStatsOutputPowerMax OBJECT-TYPE
    SYNTAX       INTEGER
    MAX-ACCESS   read-only
    STATUS       current
    DESCRIPTION
        "Cisco UCS equipment:PsuStats:outputPowerMax managed
        object property"
    ::= { cucsEquipmentPsuStatsEntry 27 }

cucsEquipmentPsuStatsOutputPowerMin OBJECT-TYPE
    SYNTAX       INTEGER
    MAX-ACCESS   read-only
    STATUS       current
    DESCRIPTION
        "Cisco UCS equipment:PsuStats:outputPowerMin managed
        object property"
    ::= { cucsEquipmentPsuStatsEntry 28 }

cucsEquipmentPsuStatsSuspect OBJECT-TYPE
    SYNTAX       TruthValue
    MAX-ACCESS   read-only
    STATUS       current
    DESCRIPTION
        "Cisco UCS equipment:PsuStats:suspect managed object property"
    ::= { cucsEquipmentPsuStatsEntry 29 }

cucsEquipmentPsuStatsThresholded OBJECT-TYPE
    SYNTAX       CucsEquipmentPsuStatsThresholded
    MAX-ACCESS   read-only
    STATUS       current
    DESCRIPTION
        "Cisco UCS equipment:PsuStats:thresholded managed object property"
    ::= { cucsEquipmentPsuStatsEntry 30 }

cucsEquipmentPsuStatsTimeCollected OBJECT-TYPE
    SYNTAX       DateAndTime
    MAX-ACCESS   read-only
    STATUS       current
    DESCRIPTION
        "Cisco UCS equipment:PsuStats:timeCollected managed
        object property"
    ::= { cucsEquipmentPsuStatsEntry 31 }

cucsEquipmentPsuStatsUpdate OBJECT-TYPE
    SYNTAX       Gauge32
    MAX-ACCESS   read-only
    STATUS       current
    DESCRIPTION
        "Cisco UCS equipment:PsuStats:update managed object property"
    ::= { cucsEquipmentPsuStatsEntry 32 }

cucsEquipmentPsuStatsPsuTemp1 OBJECT-TYPE
    SYNTAX       INTEGER
    MAX-ACCESS   read-only
    STATUS       current
    DESCRIPTION
        "Cisco UCS equipment:PsuStats:psuTemp1 managed object property"
    ::= { cucsEquipmentPsuStatsEntry 33 }

cucsEquipmentPsuStatsPsuTemp2 OBJECT-TYPE
    SYNTAX       INTEGER
    MAX-ACCESS   read-only
    STATUS       current
    DESCRIPTION
        "Cisco UCS equipment:PsuStats:psuTemp2 managed object property"
    ::= { cucsEquipmentPsuStatsEntry 34 }

cucsEquipmentPsuStatsHistTable OBJECT-TYPE
    SYNTAX           SEQUENCE OF CucsEquipmentPsuStatsHistEntry
    MAX-ACCESS       not-accessible
    STATUS           current
    DESCRIPTION
        "Cisco UCS equipment:PsuStatsHist managed object table"
    ::= { cucsEquipmentObjects 61 }

cucsEquipmentPsuStatsHistEntry OBJECT-TYPE
    SYNTAX           CucsEquipmentPsuStatsHistEntry
    MAX-ACCESS       not-accessible
    STATUS           current
    DESCRIPTION
        "Entry for the cucsEquipmentPsuStatsHistTable table."
    INDEX { cucsEquipmentPsuStatsHistInstanceId }
    ::= { cucsEquipmentPsuStatsHistTable 1 }

CucsEquipmentPsuStatsHistEntry ::= SEQUENCE {
    cucsEquipmentPsuStatsHistInstanceId                              CucsManagedObjectId,
    cucsEquipmentPsuStatsHistDn                                      CucsManagedObjectDn,
    cucsEquipmentPsuStatsHistRn                                      SnmpAdminString,
    cucsEquipmentPsuStatsHistAmbientTemp                             INTEGER,
    cucsEquipmentPsuStatsHistAmbientTempAvg                          INTEGER,
    cucsEquipmentPsuStatsHistAmbientTempMax                          INTEGER,
    cucsEquipmentPsuStatsHistAmbientTempMin                          INTEGER,
    cucsEquipmentPsuStatsHistId                                      Unsigned64,
    cucsEquipmentPsuStatsHistInput210v                               INTEGER,
    cucsEquipmentPsuStatsHistInput210vAvg                            INTEGER,
    cucsEquipmentPsuStatsHistInput210vMax                            INTEGER,
    cucsEquipmentPsuStatsHistInput210vMin                            INTEGER,
    cucsEquipmentPsuStatsHistMostRecent                              TruthValue,
    cucsEquipmentPsuStatsHistOutput12v                               INTEGER,
    cucsEquipmentPsuStatsHistOutput12vAvg                            INTEGER,
    cucsEquipmentPsuStatsHistOutput12vMax                            INTEGER,
    cucsEquipmentPsuStatsHistOutput12vMin                            INTEGER,
    cucsEquipmentPsuStatsHistOutput3v3                               INTEGER,
    cucsEquipmentPsuStatsHistOutput3v3Avg                            INTEGER,
    cucsEquipmentPsuStatsHistOutput3v3Max                            INTEGER,
    cucsEquipmentPsuStatsHistOutput3v3Min                            INTEGER,
    cucsEquipmentPsuStatsHistOutputCurrent                           INTEGER,
    cucsEquipmentPsuStatsHistOutputCurrentAvg                        INTEGER,
    cucsEquipmentPsuStatsHistOutputCurrentMax                        INTEGER,
    cucsEquipmentPsuStatsHistOutputCurrentMin                        INTEGER,
    cucsEquipmentPsuStatsHistOutputPower                             INTEGER,
    cucsEquipmentPsuStatsHistOutputPowerAvg                          INTEGER,
    cucsEquipmentPsuStatsHistOutputPowerMax                          INTEGER,
    cucsEquipmentPsuStatsHistOutputPowerMin                          INTEGER,
    cucsEquipmentPsuStatsHistSuspect                                 TruthValue,
    cucsEquipmentPsuStatsHistThresholded                             CucsEquipmentPsuStatsHistThresholded,
    cucsEquipmentPsuStatsHistTimeCollected                           DateAndTime
}

cucsEquipmentPsuStatsHistInstanceId OBJECT-TYPE
    SYNTAX       CucsManagedObjectId
    MAX-ACCESS   not-accessible
    STATUS       current
    DESCRIPTION
        "Instance identifier of the managed object."
    ::= { cucsEquipmentPsuStatsHistEntry 1 }

cucsEquipmentPsuStatsHistDn OBJECT-TYPE
    SYNTAX       CucsManagedObjectDn
    MAX-ACCESS   read-only
    STATUS       current
    DESCRIPTION
        "Cisco UCS equipment:PsuStatsHist:dn managed object property"
    ::= { cucsEquipmentPsuStatsHistEntry 2 }

cucsEquipmentPsuStatsHistRn OBJECT-TYPE
    SYNTAX       SnmpAdminString
    MAX-ACCESS   read-only
    STATUS       current
    DESCRIPTION
        "Cisco UCS equipment:PsuStatsHist:rn managed object property"
    ::= { cucsEquipmentPsuStatsHistEntry 3 }

cucsEquipmentPsuStatsHistAmbientTemp OBJECT-TYPE
    SYNTAX       INTEGER
    MAX-ACCESS   read-only
    STATUS       current
    DESCRIPTION
        "Cisco UCS equipment:PsuStatsHist:ambientTemp managed
        object property"
    ::= { cucsEquipmentPsuStatsHistEntry 4 }

cucsEquipmentPsuStatsHistAmbientTempAvg OBJECT-TYPE
    SYNTAX       INTEGER
    MAX-ACCESS   read-only
    STATUS       current
    DESCRIPTION
        "Cisco UCS equipment:PsuStatsHist:ambientTempAvg
        managed object property"
    ::= { cucsEquipmentPsuStatsHistEntry 5 }

cucsEquipmentPsuStatsHistAmbientTempMax OBJECT-TYPE
    SYNTAX       INTEGER
    MAX-ACCESS   read-only
    STATUS       current
    DESCRIPTION
        "Cisco UCS equipment:PsuStatsHist:ambientTempMax
        managed object property"
    ::= { cucsEquipmentPsuStatsHistEntry 6 }

cucsEquipmentPsuStatsHistAmbientTempMin OBJECT-TYPE
    SYNTAX       INTEGER
    MAX-ACCESS   read-only
    STATUS       current
    DESCRIPTION
        "Cisco UCS equipment:PsuStatsHist:ambientTempMin
        managed object property"
    ::= { cucsEquipmentPsuStatsHistEntry 7 }

cucsEquipmentPsuStatsHistId OBJECT-TYPE
    SYNTAX       Unsigned64
    MAX-ACCESS   read-only
    STATUS       current
    DESCRIPTION
        "Cisco UCS equipment:PsuStatsHist:id managed object property"
    ::= { cucsEquipmentPsuStatsHistEntry 8 }

cucsEquipmentPsuStatsHistInput210v OBJECT-TYPE
    SYNTAX       INTEGER
    MAX-ACCESS   read-only
    STATUS       current
    DESCRIPTION
        "Cisco UCS equipment:PsuStatsHist:input210v managed
        object property"
    ::= { cucsEquipmentPsuStatsHistEntry 9 }

cucsEquipmentPsuStatsHistInput210vAvg OBJECT-TYPE
    SYNTAX       INTEGER
    MAX-ACCESS   read-only
    STATUS       current
    DESCRIPTION
        "Cisco UCS equipment:PsuStatsHist:input210vAvg
        managed object property"
    ::= { cucsEquipmentPsuStatsHistEntry 10 }

cucsEquipmentPsuStatsHistInput210vMax OBJECT-TYPE
    SYNTAX       INTEGER
    MAX-ACCESS   read-only
    STATUS       current
    DESCRIPTION
        "Cisco UCS equipment:PsuStatsHist:input210vMax
        managed object property"
    ::= { cucsEquipmentPsuStatsHistEntry 11 }

cucsEquipmentPsuStatsHistInput210vMin OBJECT-TYPE
    SYNTAX       INTEGER
    MAX-ACCESS   read-only
    STATUS       current
    DESCRIPTION
        "Cisco UCS equipment:PsuStatsHist:input210vMin
        managed object property"
    ::= { cucsEquipmentPsuStatsHistEntry 12 }

cucsEquipmentPsuStatsHistMostRecent OBJECT-TYPE
    SYNTAX       TruthValue
    MAX-ACCESS   read-only
    STATUS       current
    DESCRIPTION
        "Cisco UCS equipment:PsuStatsHist:mostRecent managed
        object property"
    ::= { cucsEquipmentPsuStatsHistEntry 13 }

cucsEquipmentPsuStatsHistOutput12v OBJECT-TYPE
    SYNTAX       INTEGER
    MAX-ACCESS   read-only
    STATUS       current
    DESCRIPTION
        "Cisco UCS equipment:PsuStatsHist:output12v managed
        object property"
    ::= { cucsEquipmentPsuStatsHistEntry 14 }

cucsEquipmentPsuStatsHistOutput12vAvg OBJECT-TYPE
    SYNTAX       INTEGER
    MAX-ACCESS   read-only
    STATUS       current
    DESCRIPTION
        "Cisco UCS equipment:PsuStatsHist:output12vAvg
        managed object property"
    ::= { cucsEquipmentPsuStatsHistEntry 15 }

cucsEquipmentPsuStatsHistOutput12vMax OBJECT-TYPE
    SYNTAX       INTEGER
    MAX-ACCESS   read-only
    STATUS       current
    DESCRIPTION
        "Cisco UCS equipment:PsuStatsHist:output12vMax
        managed object property"
    ::= { cucsEquipmentPsuStatsHistEntry 16 }

cucsEquipmentPsuStatsHistOutput12vMin OBJECT-TYPE
    SYNTAX       INTEGER
    MAX-ACCESS   read-only
    STATUS       current
    DESCRIPTION
        "Cisco UCS equipment:PsuStatsHist:output12vMin
        managed object property"
    ::= { cucsEquipmentPsuStatsHistEntry 17 }

cucsEquipmentPsuStatsHistOutput3v3 OBJECT-TYPE
    SYNTAX       INTEGER
    MAX-ACCESS   read-only
    STATUS       current
    DESCRIPTION
        "Cisco UCS equipment:PsuStatsHist:output3v3 managed
        object property"
    ::= { cucsEquipmentPsuStatsHistEntry 18 }

cucsEquipmentPsuStatsHistOutput3v3Avg OBJECT-TYPE
    SYNTAX       INTEGER
    MAX-ACCESS   read-only
    STATUS       current
    DESCRIPTION
        "Cisco UCS equipment:PsuStatsHist:output3v3Avg
        managed object property"
    ::= { cucsEquipmentPsuStatsHistEntry 19 }

cucsEquipmentPsuStatsHistOutput3v3Max OBJECT-TYPE
    SYNTAX       INTEGER
    MAX-ACCESS   read-only
    STATUS       current
    DESCRIPTION
        "Cisco UCS equipment:PsuStatsHist:output3v3Max
        managed object property"
    ::= { cucsEquipmentPsuStatsHistEntry 20 }

cucsEquipmentPsuStatsHistOutput3v3Min OBJECT-TYPE
    SYNTAX       INTEGER
    MAX-ACCESS   read-only
    STATUS       current
    DESCRIPTION
        "Cisco UCS equipment:PsuStatsHist:output3v3Min
        managed object property"
    ::= { cucsEquipmentPsuStatsHistEntry 21 }

cucsEquipmentPsuStatsHistOutputCurrent OBJECT-TYPE
    SYNTAX       INTEGER
    MAX-ACCESS   read-only
    STATUS       current
    DESCRIPTION
        "Cisco UCS equipment:PsuStatsHist:outputCurrent
        managed object property"
    ::= { cucsEquipmentPsuStatsHistEntry 22 }

cucsEquipmentPsuStatsHistOutputCurrentAvg OBJECT-TYPE
    SYNTAX       INTEGER
    MAX-ACCESS   read-only
    STATUS       current
    DESCRIPTION
        "Cisco UCS equipment:PsuStatsHist:outputCurrentAvg
        managed object property"
    ::= { cucsEquipmentPsuStatsHistEntry 23 }

cucsEquipmentPsuStatsHistOutputCurrentMax OBJECT-TYPE
    SYNTAX       INTEGER
    MAX-ACCESS   read-only
    STATUS       current
    DESCRIPTION
        "Cisco UCS equipment:PsuStatsHist:outputCurrentMax
        managed object property"
    ::= { cucsEquipmentPsuStatsHistEntry 24 }

cucsEquipmentPsuStatsHistOutputCurrentMin OBJECT-TYPE
    SYNTAX       INTEGER
    MAX-ACCESS   read-only
    STATUS       current
    DESCRIPTION
        "Cisco UCS equipment:PsuStatsHist:outputCurrentMin
        managed object property"
    ::= { cucsEquipmentPsuStatsHistEntry 25 }

cucsEquipmentPsuStatsHistOutputPower OBJECT-TYPE
    SYNTAX       INTEGER
    MAX-ACCESS   read-only
    STATUS       current
    DESCRIPTION
        "Cisco UCS equipment:PsuStatsHist:outputPower managed
        object property"
    ::= { cucsEquipmentPsuStatsHistEntry 26 }

cucsEquipmentPsuStatsHistOutputPowerAvg OBJECT-TYPE
    SYNTAX       INTEGER
    MAX-ACCESS   read-only
    STATUS       current
    DESCRIPTION
        "Cisco UCS equipment:PsuStatsHist:outputPowerAvg
        managed object property"
    ::= { cucsEquipmentPsuStatsHistEntry 27 }

cucsEquipmentPsuStatsHistOutputPowerMax OBJECT-TYPE
    SYNTAX       INTEGER
    MAX-ACCESS   read-only
    STATUS       current
    DESCRIPTION
        "Cisco UCS equipment:PsuStatsHist:outputPowerMax
        managed object property"
    ::= { cucsEquipmentPsuStatsHistEntry 28 }

cucsEquipmentPsuStatsHistOutputPowerMin OBJECT-TYPE
    SYNTAX       INTEGER
    MAX-ACCESS   read-only
    STATUS       current
    DESCRIPTION
        "Cisco UCS equipment:PsuStatsHist:outputPowerMin
        managed object property"
    ::= { cucsEquipmentPsuStatsHistEntry 29 }

cucsEquipmentPsuStatsHistSuspect OBJECT-TYPE
    SYNTAX       TruthValue
    MAX-ACCESS   read-only
    STATUS       current
    DESCRIPTION
        "Cisco UCS equipment:PsuStatsHist:suspect managed object property"
    ::= { cucsEquipmentPsuStatsHistEntry 30 }

cucsEquipmentPsuStatsHistThresholded OBJECT-TYPE
    SYNTAX       CucsEquipmentPsuStatsHistThresholded
    MAX-ACCESS   read-only
    STATUS       current
    DESCRIPTION
        "Cisco UCS equipment:PsuStatsHist:thresholded managed
        object property"
    ::= { cucsEquipmentPsuStatsHistEntry 31 }

cucsEquipmentPsuStatsHistTimeCollected OBJECT-TYPE
    SYNTAX       DateAndTime
    MAX-ACCESS   read-only
    STATUS       current
    DESCRIPTION
        "Cisco UCS equipment:PsuStatsHist:timeCollected
        managed object property"
    ::= { cucsEquipmentPsuStatsHistEntry 32 }

cucsEquipmentRackFanModuleDefTable OBJECT-TYPE
    SYNTAX           SEQUENCE OF CucsEquipmentRackFanModuleDefEntry
    MAX-ACCESS       not-accessible
    STATUS           current
    DESCRIPTION
        "Cisco UCS equipment:RackFanModuleDef managed object table"
    ::= { cucsEquipmentObjects 115 }

cucsEquipmentRackFanModuleDefEntry OBJECT-TYPE
    SYNTAX           CucsEquipmentRackFanModuleDefEntry
    MAX-ACCESS       not-accessible
    STATUS           current
    DESCRIPTION
        "Entry for the cucsEquipmentRackFanModuleDefTable table."
    INDEX { cucsEquipmentRackFanModuleDefInstanceId }
    ::= { cucsEquipmentRackFanModuleDefTable 1 }

CucsEquipmentRackFanModuleDefEntry ::= SEQUENCE {
    cucsEquipmentRackFanModuleDefInstanceId                          CucsManagedObjectId,
    cucsEquipmentRackFanModuleDefDn                                  CucsManagedObjectDn,
    cucsEquipmentRackFanModuleDefRn                                  SnmpAdminString,
    cucsEquipmentRackFanModuleDefDescr                               SnmpAdminString,
    cucsEquipmentRackFanModuleDefFanCapacity                         Gauge32,
    cucsEquipmentRackFanModuleDefIntId                               SnmpAdminString,
    cucsEquipmentRackFanModuleDefName                                SnmpAdminString,
    cucsEquipmentRackFanModuleDefPolicyLevel                         Gauge32,
    cucsEquipmentRackFanModuleDefPolicyOwner                         CucsPolicyPolicyOwner
}

cucsEquipmentRackFanModuleDefInstanceId OBJECT-TYPE
    SYNTAX       CucsManagedObjectId
    MAX-ACCESS   not-accessible
    STATUS       current
    DESCRIPTION
        "Instance identifier of the managed object."
    ::= { cucsEquipmentRackFanModuleDefEntry 1 }

cucsEquipmentRackFanModuleDefDn OBJECT-TYPE
    SYNTAX       CucsManagedObjectDn
    MAX-ACCESS   read-only
    STATUS       current
    DESCRIPTION
        "Cisco UCS equipment:RackFanModuleDef:dn managed object property"
    ::= { cucsEquipmentRackFanModuleDefEntry 2 }

cucsEquipmentRackFanModuleDefRn OBJECT-TYPE
    SYNTAX       SnmpAdminString
    MAX-ACCESS   read-only
    STATUS       current
    DESCRIPTION
        "Cisco UCS equipment:RackFanModuleDef:rn managed object property"
    ::= { cucsEquipmentRackFanModuleDefEntry 3 }

cucsEquipmentRackFanModuleDefDescr OBJECT-TYPE
    SYNTAX       SnmpAdminString
    MAX-ACCESS   read-only
    STATUS       current
    DESCRIPTION
        "Cisco UCS equipment:RackFanModuleDef:descr managed
        object property"
    ::= { cucsEquipmentRackFanModuleDefEntry 4 }

cucsEquipmentRackFanModuleDefFanCapacity OBJECT-TYPE
    SYNTAX       Gauge32
    MAX-ACCESS   read-only
    STATUS       current
    DESCRIPTION
        "Cisco UCS equipment:RackFanModuleDef:fanCapacity
        managed object property"
    ::= { cucsEquipmentRackFanModuleDefEntry 5 }

cucsEquipmentRackFanModuleDefIntId OBJECT-TYPE
    SYNTAX       SnmpAdminString
    MAX-ACCESS   read-only
    STATUS       current
    DESCRIPTION
        "Cisco UCS equipment:RackFanModuleDef:intId managed
        object property"
    ::= { cucsEquipmentRackFanModuleDefEntry 6 }

cucsEquipmentRackFanModuleDefName OBJECT-TYPE
    SYNTAX       SnmpAdminString
    MAX-ACCESS   read-only
    STATUS       current
    DESCRIPTION
        "Cisco UCS equipment:RackFanModuleDef:name managed
        object property"
    ::= { cucsEquipmentRackFanModuleDefEntry 7 }

cucsEquipmentRackFanModuleDefPolicyLevel OBJECT-TYPE
    SYNTAX       Gauge32
    MAX-ACCESS   read-only
    STATUS       current
    DESCRIPTION
        "Cisco UCS equipment:RackFanModuleDef:policyLevel
        managed object property"
    ::= { cucsEquipmentRackFanModuleDefEntry 8 }

cucsEquipmentRackFanModuleDefPolicyOwner OBJECT-TYPE
    SYNTAX       CucsPolicyPolicyOwner
    MAX-ACCESS   read-only
    STATUS       current
    DESCRIPTION
        "Cisco UCS equipment:RackFanModuleDef:policyOwner
        managed object property"
    ::= { cucsEquipmentRackFanModuleDefEntry 9 }

cucsEquipmentRackUnitCapProviderTable OBJECT-TYPE
    SYNTAX           SEQUENCE OF CucsEquipmentRackUnitCapProviderEntry
    MAX-ACCESS       not-accessible
    STATUS           current
    DESCRIPTION
        "Cisco UCS equipment:RackUnitCapProvider managed object table"
    ::= { cucsEquipmentObjects 62 }

cucsEquipmentRackUnitCapProviderEntry OBJECT-TYPE
    SYNTAX           CucsEquipmentRackUnitCapProviderEntry
    MAX-ACCESS       not-accessible
    STATUS           current
    DESCRIPTION
        "Entry for the cucsEquipmentRackUnitCapProviderTable table."
    INDEX { cucsEquipmentRackUnitCapProviderInstanceId }
    ::= { cucsEquipmentRackUnitCapProviderTable 1 }

CucsEquipmentRackUnitCapProviderEntry ::= SEQUENCE {
    cucsEquipmentRackUnitCapProviderInstanceId                       CucsManagedObjectId,
    cucsEquipmentRackUnitCapProviderDn                               CucsManagedObjectDn,
    cucsEquipmentRackUnitCapProviderRn                               SnmpAdminString,
    cucsEquipmentRackUnitCapProviderDeprecated                       TruthValue,
    cucsEquipmentRackUnitCapProviderGencount                         Gauge32,
    cucsEquipmentRackUnitCapProviderMgmtPlaneVer                     SnmpAdminString,
    cucsEquipmentRackUnitCapProviderModel                            SnmpAdminString,
    cucsEquipmentRackUnitCapProviderRevision                         SnmpAdminString,
    cucsEquipmentRackUnitCapProviderVendor                           SnmpAdminString,
    cucsEquipmentRackUnitCapProviderPromCardType                     Gauge32,
    cucsEquipmentRackUnitCapProviderDeleted                          TruthValue,
    cucsEquipmentRackUnitCapProviderMaxLocalDisks                    Gauge32,
    cucsEquipmentRackUnitCapProviderElementLoadFailures              Gauge32,
    cucsEquipmentRackUnitCapProviderElementsLoaded                   Gauge32,
    cucsEquipmentRackUnitCapProviderLoadErrors                       Gauge32,
    cucsEquipmentRackUnitCapProviderLoadWarnings                     Gauge32
}

cucsEquipmentRackUnitCapProviderInstanceId OBJECT-TYPE
    SYNTAX       CucsManagedObjectId
    MAX-ACCESS   not-accessible
    STATUS       current
    DESCRIPTION
        "Instance identifier of the managed object."
    ::= { cucsEquipmentRackUnitCapProviderEntry 1 }

cucsEquipmentRackUnitCapProviderDn OBJECT-TYPE
    SYNTAX       CucsManagedObjectDn
    MAX-ACCESS   read-only
    STATUS       current
    DESCRIPTION
        "Cisco UCS equipment:RackUnitCapProvider:dn managed
        object property"
    ::= { cucsEquipmentRackUnitCapProviderEntry 2 }

cucsEquipmentRackUnitCapProviderRn OBJECT-TYPE
    SYNTAX       SnmpAdminString
    MAX-ACCESS   read-only
    STATUS       current
    DESCRIPTION
        "Cisco UCS equipment:RackUnitCapProvider:rn managed
        object property"
    ::= { cucsEquipmentRackUnitCapProviderEntry 3 }

cucsEquipmentRackUnitCapProviderDeprecated OBJECT-TYPE
    SYNTAX       TruthValue
    MAX-ACCESS   read-only
    STATUS       current
    DESCRIPTION
        "Cisco UCS equipment:RackUnitCapProvider:deprecated
        managed object property"
    ::= { cucsEquipmentRackUnitCapProviderEntry 4 }

cucsEquipmentRackUnitCapProviderGencount OBJECT-TYPE
    SYNTAX       Gauge32
    MAX-ACCESS   read-only
    STATUS       current
    DESCRIPTION
        "Cisco UCS equipment:RackUnitCapProvider:gencount
        managed object property"
    ::= { cucsEquipmentRackUnitCapProviderEntry 5 }

cucsEquipmentRackUnitCapProviderMgmtPlaneVer OBJECT-TYPE
    SYNTAX       SnmpAdminString
    MAX-ACCESS   read-only
    STATUS       current
    DESCRIPTION
        "Cisco UCS equipment:RackUnitCapProvider:mgmtPlaneVer
        managed object property"
    ::= { cucsEquipmentRackUnitCapProviderEntry 6 }

cucsEquipmentRackUnitCapProviderModel OBJECT-TYPE
    SYNTAX       SnmpAdminString
    MAX-ACCESS   read-only
    STATUS       current
    DESCRIPTION
        "Cisco UCS equipment:RackUnitCapProvider:model
        managed object property"
    ::= { cucsEquipmentRackUnitCapProviderEntry 7 }

cucsEquipmentRackUnitCapProviderRevision OBJECT-TYPE
    SYNTAX       SnmpAdminString
    MAX-ACCESS   read-only
    STATUS       current
    DESCRIPTION
        "Cisco UCS equipment:RackUnitCapProvider:revision
        managed object property"
    ::= { cucsEquipmentRackUnitCapProviderEntry 8 }

cucsEquipmentRackUnitCapProviderVendor OBJECT-TYPE
    SYNTAX       SnmpAdminString
    MAX-ACCESS   read-only
    STATUS       current
    DESCRIPTION
        "Cisco UCS equipment:RackUnitCapProvider:vendor
        managed object property"
    ::= { cucsEquipmentRackUnitCapProviderEntry 9 }

cucsEquipmentRackUnitCapProviderPromCardType OBJECT-TYPE
    SYNTAX       Gauge32
    MAX-ACCESS   read-only
    STATUS       current
    DESCRIPTION
        "Cisco UCS equipment:RackUnitCapProvider:promCardType
        managed object property"
    ::= { cucsEquipmentRackUnitCapProviderEntry 10 }

cucsEquipmentRackUnitCapProviderDeleted OBJECT-TYPE
    SYNTAX       TruthValue
    MAX-ACCESS   read-only
    STATUS       current
    DESCRIPTION
        "Cisco UCS equipment:RackUnitCapProvider:deleted
        managed object property"
    ::= { cucsEquipmentRackUnitCapProviderEntry 11 }

cucsEquipmentRackUnitCapProviderMaxLocalDisks OBJECT-TYPE
    SYNTAX       Gauge32
    MAX-ACCESS   read-only
    STATUS       current
    DESCRIPTION
        "Cisco UCS equipment:RackUnitCapProvider:maxLocalDisks
        managed object property"
    ::= { cucsEquipmentRackUnitCapProviderEntry 12 }

cucsEquipmentRackUnitCapProviderElementLoadFailures OBJECT-TYPE
    SYNTAX       Gauge32
    MAX-ACCESS   read-only
    STATUS       current
    DESCRIPTION
        "Cisco UCS equipment:RackUnitCapProvider:elementLoadFailures
        managed object property"
    ::= { cucsEquipmentRackUnitCapProviderEntry 13 }

cucsEquipmentRackUnitCapProviderElementsLoaded OBJECT-TYPE
    SYNTAX       Gauge32
    MAX-ACCESS   read-only
    STATUS       current
    DESCRIPTION
        "Cisco UCS equipment:RackUnitCapProvider:elementsLoaded
        managed object property"
    ::= { cucsEquipmentRackUnitCapProviderEntry 14 }

cucsEquipmentRackUnitCapProviderLoadErrors OBJECT-TYPE
    SYNTAX       Gauge32
    MAX-ACCESS   read-only
    STATUS       current
    DESCRIPTION
        "Cisco UCS equipment:RackUnitCapProvider:loadErrors
        managed object property"
    ::= { cucsEquipmentRackUnitCapProviderEntry 15 }

cucsEquipmentRackUnitCapProviderLoadWarnings OBJECT-TYPE
    SYNTAX       Gauge32
    MAX-ACCESS   read-only
    STATUS       current
    DESCRIPTION
        "Cisco UCS equipment:RackUnitCapProvider:loadWarnings
        managed object property"
    ::= { cucsEquipmentRackUnitCapProviderEntry 16 }

cucsEquipmentRackUnitFanStatsTable OBJECT-TYPE
    SYNTAX           SEQUENCE OF CucsEquipmentRackUnitFanStatsEntry
    MAX-ACCESS       not-accessible
    STATUS           current
    DESCRIPTION
        "Cisco UCS equipment:RackUnitFanStats managed object table"
    ::= { cucsEquipmentObjects 71 }

cucsEquipmentRackUnitFanStatsEntry OBJECT-TYPE
    SYNTAX           CucsEquipmentRackUnitFanStatsEntry
    MAX-ACCESS       not-accessible
    STATUS           current
    DESCRIPTION
        "Entry for the cucsEquipmentRackUnitFanStatsTable table."
    INDEX { cucsEquipmentRackUnitFanStatsInstanceId }
    ::= { cucsEquipmentRackUnitFanStatsTable 1 }

CucsEquipmentRackUnitFanStatsEntry ::= SEQUENCE {
    cucsEquipmentRackUnitFanStatsInstanceId                          CucsManagedObjectId,
    cucsEquipmentRackUnitFanStatsDn                                  CucsManagedObjectDn,
    cucsEquipmentRackUnitFanStatsRn                                  SnmpAdminString,
    cucsEquipmentRackUnitFanStatsIntervals                           Gauge32,
    cucsEquipmentRackUnitFanStatsSpeed                               Gauge32,
    cucsEquipmentRackUnitFanStatsSpeedAvg                            Gauge32,
    cucsEquipmentRackUnitFanStatsSpeedMax                            Gauge32,
    cucsEquipmentRackUnitFanStatsSpeedMin                            Gauge32,
    cucsEquipmentRackUnitFanStatsSuspect                             TruthValue,
    cucsEquipmentRackUnitFanStatsThresholded                         CucsEquipmentRackUnitFanStatsThresholded,
    cucsEquipmentRackUnitFanStatsTimeCollected                       DateAndTime,
    cucsEquipmentRackUnitFanStatsUpdate                              Gauge32
}

cucsEquipmentRackUnitFanStatsInstanceId OBJECT-TYPE
    SYNTAX       CucsManagedObjectId
    MAX-ACCESS   not-accessible
    STATUS       current
    DESCRIPTION
        "Instance identifier of the managed object."
    ::= { cucsEquipmentRackUnitFanStatsEntry 1 }

cucsEquipmentRackUnitFanStatsDn OBJECT-TYPE
    SYNTAX       CucsManagedObjectDn
    MAX-ACCESS   read-only
    STATUS       current
    DESCRIPTION
        "Cisco UCS equipment:RackUnitFanStats:dn managed object property"
    ::= { cucsEquipmentRackUnitFanStatsEntry 2 }

cucsEquipmentRackUnitFanStatsRn OBJECT-TYPE
    SYNTAX       SnmpAdminString
    MAX-ACCESS   read-only
    STATUS       current
    DESCRIPTION
        "Cisco UCS equipment:RackUnitFanStats:rn managed object property"
    ::= { cucsEquipmentRackUnitFanStatsEntry 3 }

cucsEquipmentRackUnitFanStatsIntervals OBJECT-TYPE
    SYNTAX       Gauge32
    MAX-ACCESS   read-only
    STATUS       current
    DESCRIPTION
        "Cisco UCS equipment:RackUnitFanStats:intervals
        managed object property"
    ::= { cucsEquipmentRackUnitFanStatsEntry 4 }

cucsEquipmentRackUnitFanStatsSpeed OBJECT-TYPE
    SYNTAX       Gauge32
    MAX-ACCESS   read-only
    STATUS       current
    DESCRIPTION
        "Cisco UCS equipment:RackUnitFanStats:speed managed
        object property"
    ::= { cucsEquipmentRackUnitFanStatsEntry 5 }

cucsEquipmentRackUnitFanStatsSpeedAvg OBJECT-TYPE
    SYNTAX       Gauge32
    MAX-ACCESS   read-only
    STATUS       current
    DESCRIPTION
        "Cisco UCS equipment:RackUnitFanStats:speedAvg
        managed object property"
    ::= { cucsEquipmentRackUnitFanStatsEntry 6 }

cucsEquipmentRackUnitFanStatsSpeedMax OBJECT-TYPE
    SYNTAX       Gauge32
    MAX-ACCESS   read-only
    STATUS       current
    DESCRIPTION
        "Cisco UCS equipment:RackUnitFanStats:speedMax
        managed object property"
    ::= { cucsEquipmentRackUnitFanStatsEntry 7 }

cucsEquipmentRackUnitFanStatsSpeedMin OBJECT-TYPE
    SYNTAX       Gauge32
    MAX-ACCESS   read-only
    STATUS       current
    DESCRIPTION
        "Cisco UCS equipment:RackUnitFanStats:speedMin
        managed object property"
    ::= { cucsEquipmentRackUnitFanStatsEntry 8 }

cucsEquipmentRackUnitFanStatsSuspect OBJECT-TYPE
    SYNTAX       TruthValue
    MAX-ACCESS   read-only
    STATUS       current
    DESCRIPTION
        "Cisco UCS equipment:RackUnitFanStats:suspect managed
        object property"
    ::= { cucsEquipmentRackUnitFanStatsEntry 9 }

cucsEquipmentRackUnitFanStatsThresholded OBJECT-TYPE
    SYNTAX       CucsEquipmentRackUnitFanStatsThresholded
    MAX-ACCESS   read-only
    STATUS       current
    DESCRIPTION
        "Cisco UCS equipment:RackUnitFanStats:thresholded
        managed object property"
    ::= { cucsEquipmentRackUnitFanStatsEntry 10 }

cucsEquipmentRackUnitFanStatsTimeCollected OBJECT-TYPE
    SYNTAX       DateAndTime
    MAX-ACCESS   read-only
    STATUS       current
    DESCRIPTION
        "Cisco UCS equipment:RackUnitFanStats:timeCollected
        managed object property"
    ::= { cucsEquipmentRackUnitFanStatsEntry 11 }

cucsEquipmentRackUnitFanStatsUpdate OBJECT-TYPE
    SYNTAX       Gauge32
    MAX-ACCESS   read-only
    STATUS       current
    DESCRIPTION
        "Cisco UCS equipment:RackUnitFanStats:update managed
        object property"
    ::= { cucsEquipmentRackUnitFanStatsEntry 12 }

cucsEquipmentRackUnitFanStatsHistTable OBJECT-TYPE
    SYNTAX           SEQUENCE OF CucsEquipmentRackUnitFanStatsHistEntry
    MAX-ACCESS       not-accessible
    STATUS           current
    DESCRIPTION
        "Cisco UCS equipment:RackUnitFanStatsHist managed object table"
    ::= { cucsEquipmentObjects 72 }

cucsEquipmentRackUnitFanStatsHistEntry OBJECT-TYPE
    SYNTAX           CucsEquipmentRackUnitFanStatsHistEntry
    MAX-ACCESS       not-accessible
    STATUS           current
    DESCRIPTION
        "Entry for the cucsEquipmentRackUnitFanStatsHistTable table."
    INDEX { cucsEquipmentRackUnitFanStatsHistInstanceId }
    ::= { cucsEquipmentRackUnitFanStatsHistTable 1 }

CucsEquipmentRackUnitFanStatsHistEntry ::= SEQUENCE {
    cucsEquipmentRackUnitFanStatsHistInstanceId                      CucsManagedObjectId,
    cucsEquipmentRackUnitFanStatsHistDn                              CucsManagedObjectDn,
    cucsEquipmentRackUnitFanStatsHistRn                              SnmpAdminString,
    cucsEquipmentRackUnitFanStatsHistId                              Unsigned64,
    cucsEquipmentRackUnitFanStatsHistMostRecent                      TruthValue,
    cucsEquipmentRackUnitFanStatsHistSpeed                           Gauge32,
    cucsEquipmentRackUnitFanStatsHistSpeedAvg                        Gauge32,
    cucsEquipmentRackUnitFanStatsHistSpeedMax                        Gauge32,
    cucsEquipmentRackUnitFanStatsHistSpeedMin                        Gauge32,
    cucsEquipmentRackUnitFanStatsHistSuspect                         TruthValue,
    cucsEquipmentRackUnitFanStatsHistThresholded                     CucsEquipmentRackUnitFanStatsHistThresholded,
    cucsEquipmentRackUnitFanStatsHistTimeCollected                   DateAndTime
}

cucsEquipmentRackUnitFanStatsHistInstanceId OBJECT-TYPE
    SYNTAX       CucsManagedObjectId
    MAX-ACCESS   not-accessible
    STATUS       current
    DESCRIPTION
        "Instance identifier of the managed object."
    ::= { cucsEquipmentRackUnitFanStatsHistEntry 1 }

cucsEquipmentRackUnitFanStatsHistDn OBJECT-TYPE
    SYNTAX       CucsManagedObjectDn
    MAX-ACCESS   read-only
    STATUS       current
    DESCRIPTION
        "Cisco UCS equipment:RackUnitFanStatsHist:dn managed
        object property"
    ::= { cucsEquipmentRackUnitFanStatsHistEntry 2 }

cucsEquipmentRackUnitFanStatsHistRn OBJECT-TYPE
    SYNTAX       SnmpAdminString
    MAX-ACCESS   read-only
    STATUS       current
    DESCRIPTION
        "Cisco UCS equipment:RackUnitFanStatsHist:rn managed
        object property"
    ::= { cucsEquipmentRackUnitFanStatsHistEntry 3 }

cucsEquipmentRackUnitFanStatsHistId OBJECT-TYPE
    SYNTAX       Unsigned64
    MAX-ACCESS   read-only
    STATUS       current
    DESCRIPTION
        "Cisco UCS equipment:RackUnitFanStatsHist:id managed
        object property"
    ::= { cucsEquipmentRackUnitFanStatsHistEntry 4 }

cucsEquipmentRackUnitFanStatsHistMostRecent OBJECT-TYPE
    SYNTAX       TruthValue
    MAX-ACCESS   read-only
    STATUS       current
    DESCRIPTION
        "Cisco UCS equipment:RackUnitFanStatsHist:mostRecent
        managed object property"
    ::= { cucsEquipmentRackUnitFanStatsHistEntry 5 }

cucsEquipmentRackUnitFanStatsHistSpeed OBJECT-TYPE
    SYNTAX       Gauge32
    MAX-ACCESS   read-only
    STATUS       current
    DESCRIPTION
        "Cisco UCS equipment:RackUnitFanStatsHist:speed
        managed object property"
    ::= { cucsEquipmentRackUnitFanStatsHistEntry 6 }

cucsEquipmentRackUnitFanStatsHistSpeedAvg OBJECT-TYPE
    SYNTAX       Gauge32
    MAX-ACCESS   read-only
    STATUS       current
    DESCRIPTION
        "Cisco UCS equipment:RackUnitFanStatsHist:speedAvg
        managed object property"
    ::= { cucsEquipmentRackUnitFanStatsHistEntry 7 }

cucsEquipmentRackUnitFanStatsHistSpeedMax OBJECT-TYPE
    SYNTAX       Gauge32
    MAX-ACCESS   read-only
    STATUS       current
    DESCRIPTION
        "Cisco UCS equipment:RackUnitFanStatsHist:speedMax
        managed object property"
    ::= { cucsEquipmentRackUnitFanStatsHistEntry 8 }

cucsEquipmentRackUnitFanStatsHistSpeedMin OBJECT-TYPE
    SYNTAX       Gauge32
    MAX-ACCESS   read-only
    STATUS       current
    DESCRIPTION
        "Cisco UCS equipment:RackUnitFanStatsHist:speedMin
        managed object property"
    ::= { cucsEquipmentRackUnitFanStatsHistEntry 9 }

cucsEquipmentRackUnitFanStatsHistSuspect OBJECT-TYPE
    SYNTAX       TruthValue
    MAX-ACCESS   read-only
    STATUS       current
    DESCRIPTION
        "Cisco UCS equipment:RackUnitFanStatsHist:suspect
        managed object property"
    ::= { cucsEquipmentRackUnitFanStatsHistEntry 10 }

cucsEquipmentRackUnitFanStatsHistThresholded OBJECT-TYPE
    SYNTAX       CucsEquipmentRackUnitFanStatsHistThresholded
    MAX-ACCESS   read-only
    STATUS       current
    DESCRIPTION
        "Cisco UCS equipment:RackUnitFanStatsHist:thresholded
        managed object property"
    ::= { cucsEquipmentRackUnitFanStatsHistEntry 11 }

cucsEquipmentRackUnitFanStatsHistTimeCollected OBJECT-TYPE
    SYNTAX       DateAndTime
    MAX-ACCESS   read-only
    STATUS       current
    DESCRIPTION
        "Cisco UCS equipment:RackUnitFanStatsHist:timeCollected
        managed object property"
    ::= { cucsEquipmentRackUnitFanStatsHistEntry 12 }

cucsEquipmentRackUnitPsuStatsTable OBJECT-TYPE
    SYNTAX           SEQUENCE OF CucsEquipmentRackUnitPsuStatsEntry
    MAX-ACCESS       not-accessible
    STATUS           current
    DESCRIPTION
        "Cisco UCS equipment:RackUnitPsuStats managed object table"
    ::= { cucsEquipmentObjects 63 }

cucsEquipmentRackUnitPsuStatsEntry OBJECT-TYPE
    SYNTAX           CucsEquipmentRackUnitPsuStatsEntry
    MAX-ACCESS       not-accessible
    STATUS           current
    DESCRIPTION
        "Entry for the cucsEquipmentRackUnitPsuStatsTable table."
    INDEX { cucsEquipmentRackUnitPsuStatsInstanceId }
    ::= { cucsEquipmentRackUnitPsuStatsTable 1 }

CucsEquipmentRackUnitPsuStatsEntry ::= SEQUENCE {
    cucsEquipmentRackUnitPsuStatsInstanceId                          CucsManagedObjectId,
    cucsEquipmentRackUnitPsuStatsDn                                  CucsManagedObjectDn,
    cucsEquipmentRackUnitPsuStatsRn                                  SnmpAdminString,
    cucsEquipmentRackUnitPsuStatsAmbientTemp                         INTEGER,
    cucsEquipmentRackUnitPsuStatsAmbientTempAvg                      INTEGER,
    cucsEquipmentRackUnitPsuStatsAmbientTempMax                      INTEGER,
    cucsEquipmentRackUnitPsuStatsAmbientTempMin                      INTEGER,
    cucsEquipmentRackUnitPsuStatsInputPower                          INTEGER,
    cucsEquipmentRackUnitPsuStatsInputPowerAvg                       INTEGER,
    cucsEquipmentRackUnitPsuStatsInputPowerMax                       INTEGER,
    cucsEquipmentRackUnitPsuStatsInputPowerMin                       INTEGER,
    cucsEquipmentRackUnitPsuStatsInputVoltage                        INTEGER,
    cucsEquipmentRackUnitPsuStatsInputVoltageAvg                     INTEGER,
    cucsEquipmentRackUnitPsuStatsInputVoltageMax                     INTEGER,
    cucsEquipmentRackUnitPsuStatsInputVoltageMin                     INTEGER,
    cucsEquipmentRackUnitPsuStatsIntervals                           Gauge32,
    cucsEquipmentRackUnitPsuStatsOutputCurrent                       INTEGER,
    cucsEquipmentRackUnitPsuStatsOutputCurrentAvg                    INTEGER,
    cucsEquipmentRackUnitPsuStatsOutputCurrentMax                    INTEGER,
    cucsEquipmentRackUnitPsuStatsOutputCurrentMin                    INTEGER,
    cucsEquipmentRackUnitPsuStatsOutputPower                         INTEGER,
    cucsEquipmentRackUnitPsuStatsOutputPowerAvg                      INTEGER,
    cucsEquipmentRackUnitPsuStatsOutputPowerMax                      INTEGER,
    cucsEquipmentRackUnitPsuStatsOutputPowerMin                      INTEGER,
    cucsEquipmentRackUnitPsuStatsOutputVoltage                       INTEGER,
    cucsEquipmentRackUnitPsuStatsOutputVoltageAvg                    INTEGER,
    cucsEquipmentRackUnitPsuStatsOutputVoltageMax                    INTEGER,
    cucsEquipmentRackUnitPsuStatsOutputVoltageMin                    INTEGER,
    cucsEquipmentRackUnitPsuStatsSuspect                             TruthValue,
    cucsEquipmentRackUnitPsuStatsThresholded                         CucsEquipmentRackUnitPsuStatsThresholded,
    cucsEquipmentRackUnitPsuStatsTimeCollected                       DateAndTime,
    cucsEquipmentRackUnitPsuStatsUpdate                              Gauge32
}

cucsEquipmentRackUnitPsuStatsInstanceId OBJECT-TYPE
    SYNTAX       CucsManagedObjectId
    MAX-ACCESS   not-accessible
    STATUS       current
    DESCRIPTION
        "Instance identifier of the managed object."
    ::= { cucsEquipmentRackUnitPsuStatsEntry 1 }

cucsEquipmentRackUnitPsuStatsDn OBJECT-TYPE
    SYNTAX       CucsManagedObjectDn
    MAX-ACCESS   read-only
    STATUS       current
    DESCRIPTION
        "Cisco UCS equipment:RackUnitPsuStats:dn managed object property"
    ::= { cucsEquipmentRackUnitPsuStatsEntry 2 }

cucsEquipmentRackUnitPsuStatsRn OBJECT-TYPE
    SYNTAX       SnmpAdminString
    MAX-ACCESS   read-only
    STATUS       current
    DESCRIPTION
        "Cisco UCS equipment:RackUnitPsuStats:rn managed object property"
    ::= { cucsEquipmentRackUnitPsuStatsEntry 3 }

cucsEquipmentRackUnitPsuStatsAmbientTemp OBJECT-TYPE
    SYNTAX       INTEGER
    MAX-ACCESS   read-only
    STATUS       current
    DESCRIPTION
        "Cisco UCS equipment:RackUnitPsuStats:ambientTemp
        managed object property"
    ::= { cucsEquipmentRackUnitPsuStatsEntry 4 }

cucsEquipmentRackUnitPsuStatsAmbientTempAvg OBJECT-TYPE
    SYNTAX       INTEGER
    MAX-ACCESS   read-only
    STATUS       current
    DESCRIPTION
        "Cisco UCS equipment:RackUnitPsuStats:ambientTempAvg
        managed object property"
    ::= { cucsEquipmentRackUnitPsuStatsEntry 5 }

cucsEquipmentRackUnitPsuStatsAmbientTempMax OBJECT-TYPE
    SYNTAX       INTEGER
    MAX-ACCESS   read-only
    STATUS       current
    DESCRIPTION
        "Cisco UCS equipment:RackUnitPsuStats:ambientTempMax
        managed object property"
    ::= { cucsEquipmentRackUnitPsuStatsEntry 6 }

cucsEquipmentRackUnitPsuStatsAmbientTempMin OBJECT-TYPE
    SYNTAX       INTEGER
    MAX-ACCESS   read-only
    STATUS       current
    DESCRIPTION
        "Cisco UCS equipment:RackUnitPsuStats:ambientTempMin
        managed object property"
    ::= { cucsEquipmentRackUnitPsuStatsEntry 7 }

cucsEquipmentRackUnitPsuStatsInputPower OBJECT-TYPE
    SYNTAX       INTEGER
    MAX-ACCESS   read-only
    STATUS       current
    DESCRIPTION
        "Cisco UCS equipment:RackUnitPsuStats:inputPower
        managed object property"
    ::= { cucsEquipmentRackUnitPsuStatsEntry 8 }

cucsEquipmentRackUnitPsuStatsInputPowerAvg OBJECT-TYPE
    SYNTAX       INTEGER
    MAX-ACCESS   read-only
    STATUS       current
    DESCRIPTION
        "Cisco UCS equipment:RackUnitPsuStats:inputPowerAvg
        managed object property"
    ::= { cucsEquipmentRackUnitPsuStatsEntry 9 }

cucsEquipmentRackUnitPsuStatsInputPowerMax OBJECT-TYPE
    SYNTAX       INTEGER
    MAX-ACCESS   read-only
    STATUS       current
    DESCRIPTION
        "Cisco UCS equipment:RackUnitPsuStats:inputPowerMax
        managed object property"
    ::= { cucsEquipmentRackUnitPsuStatsEntry 10 }

cucsEquipmentRackUnitPsuStatsInputPowerMin OBJECT-TYPE
    SYNTAX       INTEGER
    MAX-ACCESS   read-only
    STATUS       current
    DESCRIPTION
        "Cisco UCS equipment:RackUnitPsuStats:inputPowerMin
        managed object property"
    ::= { cucsEquipmentRackUnitPsuStatsEntry 11 }

cucsEquipmentRackUnitPsuStatsInputVoltage OBJECT-TYPE
    SYNTAX       INTEGER
    MAX-ACCESS   read-only
    STATUS       current
    DESCRIPTION
        "Cisco UCS equipment:RackUnitPsuStats:inputVoltage
        managed object property"
    ::= { cucsEquipmentRackUnitPsuStatsEntry 12 }

cucsEquipmentRackUnitPsuStatsInputVoltageAvg OBJECT-TYPE
    SYNTAX       INTEGER
    MAX-ACCESS   read-only
    STATUS       current
    DESCRIPTION
        "Cisco UCS equipment:RackUnitPsuStats:inputVoltageAvg
        managed object property"
    ::= { cucsEquipmentRackUnitPsuStatsEntry 13 }

cucsEquipmentRackUnitPsuStatsInputVoltageMax OBJECT-TYPE
    SYNTAX       INTEGER
    MAX-ACCESS   read-only
    STATUS       current
    DESCRIPTION
        "Cisco UCS equipment:RackUnitPsuStats:inputVoltageMax
        managed object property"
    ::= { cucsEquipmentRackUnitPsuStatsEntry 14 }

cucsEquipmentRackUnitPsuStatsInputVoltageMin OBJECT-TYPE
    SYNTAX       INTEGER
    MAX-ACCESS   read-only
    STATUS       current
    DESCRIPTION
        "Cisco UCS equipment:RackUnitPsuStats:inputVoltageMin
        managed object property"
    ::= { cucsEquipmentRackUnitPsuStatsEntry 15 }

cucsEquipmentRackUnitPsuStatsIntervals OBJECT-TYPE
    SYNTAX       Gauge32
    MAX-ACCESS   read-only
    STATUS       current
    DESCRIPTION
        "Cisco UCS equipment:RackUnitPsuStats:intervals
        managed object property"
    ::= { cucsEquipmentRackUnitPsuStatsEntry 16 }

cucsEquipmentRackUnitPsuStatsOutputCurrent OBJECT-TYPE
    SYNTAX       INTEGER
    MAX-ACCESS   read-only
    STATUS       current
    DESCRIPTION
        "Cisco UCS equipment:RackUnitPsuStats:outputCurrent
        managed object property"
    ::= { cucsEquipmentRackUnitPsuStatsEntry 17 }

cucsEquipmentRackUnitPsuStatsOutputCurrentAvg OBJECT-TYPE
    SYNTAX       INTEGER
    MAX-ACCESS   read-only
    STATUS       current
    DESCRIPTION
        "Cisco UCS equipment:RackUnitPsuStats:outputCurrentAvg
        managed object property"
    ::= { cucsEquipmentRackUnitPsuStatsEntry 18 }

cucsEquipmentRackUnitPsuStatsOutputCurrentMax OBJECT-TYPE
    SYNTAX       INTEGER
    MAX-ACCESS   read-only
    STATUS       current
    DESCRIPTION
        "Cisco UCS equipment:RackUnitPsuStats:outputCurrentMax
        managed object property"
    ::= { cucsEquipmentRackUnitPsuStatsEntry 19 }

cucsEquipmentRackUnitPsuStatsOutputCurrentMin OBJECT-TYPE
    SYNTAX       INTEGER
    MAX-ACCESS   read-only
    STATUS       current
    DESCRIPTION
        "Cisco UCS equipment:RackUnitPsuStats:outputCurrentMin
        managed object property"
    ::= { cucsEquipmentRackUnitPsuStatsEntry 20 }

cucsEquipmentRackUnitPsuStatsOutputPower OBJECT-TYPE
    SYNTAX       INTEGER
    MAX-ACCESS   read-only
    STATUS       current
    DESCRIPTION
        "Cisco UCS equipment:RackUnitPsuStats:outputPower
        managed object property"
    ::= { cucsEquipmentRackUnitPsuStatsEntry 21 }

cucsEquipmentRackUnitPsuStatsOutputPowerAvg OBJECT-TYPE
    SYNTAX       INTEGER
    MAX-ACCESS   read-only
    STATUS       current
    DESCRIPTION
        "Cisco UCS equipment:RackUnitPsuStats:outputPowerAvg
        managed object property"
    ::= { cucsEquipmentRackUnitPsuStatsEntry 22 }

cucsEquipmentRackUnitPsuStatsOutputPowerMax OBJECT-TYPE
    SYNTAX       INTEGER
    MAX-ACCESS   read-only
    STATUS       current
    DESCRIPTION
        "Cisco UCS equipment:RackUnitPsuStats:outputPowerMax
        managed object property"
    ::= { cucsEquipmentRackUnitPsuStatsEntry 23 }

cucsEquipmentRackUnitPsuStatsOutputPowerMin OBJECT-TYPE
    SYNTAX       INTEGER
    MAX-ACCESS   read-only
    STATUS       current
    DESCRIPTION
        "Cisco UCS equipment:RackUnitPsuStats:outputPowerMin
        managed object property"
    ::= { cucsEquipmentRackUnitPsuStatsEntry 24 }

cucsEquipmentRackUnitPsuStatsOutputVoltage OBJECT-TYPE
    SYNTAX       INTEGER
    MAX-ACCESS   read-only
    STATUS       current
    DESCRIPTION
        "Cisco UCS equipment:RackUnitPsuStats:outputVoltage
        managed object property"
    ::= { cucsEquipmentRackUnitPsuStatsEntry 25 }

cucsEquipmentRackUnitPsuStatsOutputVoltageAvg OBJECT-TYPE
    SYNTAX       INTEGER
    MAX-ACCESS   read-only
    STATUS       current
    DESCRIPTION
        "Cisco UCS equipment:RackUnitPsuStats:outputVoltageAvg
        managed object property"
    ::= { cucsEquipmentRackUnitPsuStatsEntry 26 }

cucsEquipmentRackUnitPsuStatsOutputVoltageMax OBJECT-TYPE
    SYNTAX       INTEGER
    MAX-ACCESS   read-only
    STATUS       current
    DESCRIPTION
        "Cisco UCS equipment:RackUnitPsuStats:outputVoltageMax
        managed object property"
    ::= { cucsEquipmentRackUnitPsuStatsEntry 27 }

cucsEquipmentRackUnitPsuStatsOutputVoltageMin OBJECT-TYPE
    SYNTAX       INTEGER
    MAX-ACCESS   read-only
    STATUS       current
    DESCRIPTION
        "Cisco UCS equipment:RackUnitPsuStats:outputVoltageMin
        managed object property"
    ::= { cucsEquipmentRackUnitPsuStatsEntry 28 }

cucsEquipmentRackUnitPsuStatsSuspect OBJECT-TYPE
    SYNTAX       TruthValue
    MAX-ACCESS   read-only
    STATUS       current
    DESCRIPTION
        "Cisco UCS equipment:RackUnitPsuStats:suspect managed
        object property"
    ::= { cucsEquipmentRackUnitPsuStatsEntry 29 }

cucsEquipmentRackUnitPsuStatsThresholded OBJECT-TYPE
    SYNTAX       CucsEquipmentRackUnitPsuStatsThresholded
    MAX-ACCESS   read-only
    STATUS       current
    DESCRIPTION
        "Cisco UCS equipment:RackUnitPsuStats:thresholded
        managed object property"
    ::= { cucsEquipmentRackUnitPsuStatsEntry 30 }

cucsEquipmentRackUnitPsuStatsTimeCollected OBJECT-TYPE
    SYNTAX       DateAndTime
    MAX-ACCESS   read-only
    STATUS       current
    DESCRIPTION
        "Cisco UCS equipment:RackUnitPsuStats:timeCollected
        managed object property"
    ::= { cucsEquipmentRackUnitPsuStatsEntry 31 }

cucsEquipmentRackUnitPsuStatsUpdate OBJECT-TYPE
    SYNTAX       Gauge32
    MAX-ACCESS   read-only
    STATUS       current
    DESCRIPTION
        "Cisco UCS equipment:RackUnitPsuStats:update managed
        object property"
    ::= { cucsEquipmentRackUnitPsuStatsEntry 32 }

cucsEquipmentRackUnitPsuStatsHistTable OBJECT-TYPE
    SYNTAX           SEQUENCE OF CucsEquipmentRackUnitPsuStatsHistEntry
    MAX-ACCESS       not-accessible
    STATUS           current
    DESCRIPTION
        "Cisco UCS equipment:RackUnitPsuStatsHist managed object table"
    ::= { cucsEquipmentObjects 64 }

cucsEquipmentRackUnitPsuStatsHistEntry OBJECT-TYPE
    SYNTAX           CucsEquipmentRackUnitPsuStatsHistEntry
    MAX-ACCESS       not-accessible
    STATUS           current
    DESCRIPTION
        "Entry for the cucsEquipmentRackUnitPsuStatsHistTable table."
    INDEX { cucsEquipmentRackUnitPsuStatsHistInstanceId }
    ::= { cucsEquipmentRackUnitPsuStatsHistTable 1 }

CucsEquipmentRackUnitPsuStatsHistEntry ::= SEQUENCE {
    cucsEquipmentRackUnitPsuStatsHistInstanceId                      CucsManagedObjectId,
    cucsEquipmentRackUnitPsuStatsHistDn                              CucsManagedObjectDn,
    cucsEquipmentRackUnitPsuStatsHistRn                              SnmpAdminString,
    cucsEquipmentRackUnitPsuStatsHistAmbientTemp                     INTEGER,
    cucsEquipmentRackUnitPsuStatsHistAmbientTempAvg                  INTEGER,
    cucsEquipmentRackUnitPsuStatsHistAmbientTempMax                  INTEGER,
    cucsEquipmentRackUnitPsuStatsHistAmbientTempMin                  INTEGER,
    cucsEquipmentRackUnitPsuStatsHistId                              Unsigned64,
    cucsEquipmentRackUnitPsuStatsHistInputPower                      INTEGER,
    cucsEquipmentRackUnitPsuStatsHistInputPowerAvg                   INTEGER,
    cucsEquipmentRackUnitPsuStatsHistInputPowerMax                   INTEGER,
    cucsEquipmentRackUnitPsuStatsHistInputPowerMin                   INTEGER,
    cucsEquipmentRackUnitPsuStatsHistInputVoltage                    INTEGER,
    cucsEquipmentRackUnitPsuStatsHistInputVoltageAvg                 INTEGER,
    cucsEquipmentRackUnitPsuStatsHistInputVoltageMax                 INTEGER,
    cucsEquipmentRackUnitPsuStatsHistInputVoltageMin                 INTEGER,
    cucsEquipmentRackUnitPsuStatsHistMostRecent                      TruthValue,
    cucsEquipmentRackUnitPsuStatsHistOutputCurrent                   INTEGER,
    cucsEquipmentRackUnitPsuStatsHistOutputCurrentAvg                INTEGER,
    cucsEquipmentRackUnitPsuStatsHistOutputCurrentMax                INTEGER,
    cucsEquipmentRackUnitPsuStatsHistOutputCurrentMin                INTEGER,
    cucsEquipmentRackUnitPsuStatsHistOutputPower                     INTEGER,
    cucsEquipmentRackUnitPsuStatsHistOutputPowerAvg                  INTEGER,
    cucsEquipmentRackUnitPsuStatsHistOutputPowerMax                  INTEGER,
    cucsEquipmentRackUnitPsuStatsHistOutputPowerMin                  INTEGER,
    cucsEquipmentRackUnitPsuStatsHistOutputVoltage                   INTEGER,
    cucsEquipmentRackUnitPsuStatsHistOutputVoltageAvg                INTEGER,
    cucsEquipmentRackUnitPsuStatsHistOutputVoltageMax                INTEGER,
    cucsEquipmentRackUnitPsuStatsHistOutputVoltageMin                INTEGER,
    cucsEquipmentRackUnitPsuStatsHistSuspect                         TruthValue,
    cucsEquipmentRackUnitPsuStatsHistThresholded                     CucsEquipmentRackUnitPsuStatsHistThresholded,
    cucsEquipmentRackUnitPsuStatsHistTimeCollected                   DateAndTime
}

cucsEquipmentRackUnitPsuStatsHistInstanceId OBJECT-TYPE
    SYNTAX       CucsManagedObjectId
    MAX-ACCESS   not-accessible
    STATUS       current
    DESCRIPTION
        "Instance identifier of the managed object."
    ::= { cucsEquipmentRackUnitPsuStatsHistEntry 1 }

cucsEquipmentRackUnitPsuStatsHistDn OBJECT-TYPE
    SYNTAX       CucsManagedObjectDn
    MAX-ACCESS   read-only
    STATUS       current
    DESCRIPTION
        "Cisco UCS equipment:RackUnitPsuStatsHist:dn managed
        object property"
    ::= { cucsEquipmentRackUnitPsuStatsHistEntry 2 }

cucsEquipmentRackUnitPsuStatsHistRn OBJECT-TYPE
    SYNTAX       SnmpAdminString
    MAX-ACCESS   read-only
    STATUS       current
    DESCRIPTION
        "Cisco UCS equipment:RackUnitPsuStatsHist:rn managed
        object property"
    ::= { cucsEquipmentRackUnitPsuStatsHistEntry 3 }

cucsEquipmentRackUnitPsuStatsHistAmbientTemp OBJECT-TYPE
    SYNTAX       INTEGER
    MAX-ACCESS   read-only
    STATUS       current
    DESCRIPTION
        "Cisco UCS equipment:RackUnitPsuStatsHist:ambientTemp
        managed object property"
    ::= { cucsEquipmentRackUnitPsuStatsHistEntry 4 }

cucsEquipmentRackUnitPsuStatsHistAmbientTempAvg OBJECT-TYPE
    SYNTAX       INTEGER
    MAX-ACCESS   read-only
    STATUS       current
    DESCRIPTION
        "Cisco UCS equipment:RackUnitPsuStatsHist:ambientTempAvg
        managed object property"
    ::= { cucsEquipmentRackUnitPsuStatsHistEntry 5 }

cucsEquipmentRackUnitPsuStatsHistAmbientTempMax OBJECT-TYPE
    SYNTAX       INTEGER
    MAX-ACCESS   read-only
    STATUS       current
    DESCRIPTION
        "Cisco UCS equipment:RackUnitPsuStatsHist:ambientTempMax
        managed object property"
    ::= { cucsEquipmentRackUnitPsuStatsHistEntry 6 }

cucsEquipmentRackUnitPsuStatsHistAmbientTempMin OBJECT-TYPE
    SYNTAX       INTEGER
    MAX-ACCESS   read-only
    STATUS       current
    DESCRIPTION
        "Cisco UCS equipment:RackUnitPsuStatsHist:ambientTempMin
        managed object property"
    ::= { cucsEquipmentRackUnitPsuStatsHistEntry 7 }

cucsEquipmentRackUnitPsuStatsHistId OBJECT-TYPE
    SYNTAX       Unsigned64
    MAX-ACCESS   read-only
    STATUS       current
    DESCRIPTION
        "Cisco UCS equipment:RackUnitPsuStatsHist:id managed
        object property"
    ::= { cucsEquipmentRackUnitPsuStatsHistEntry 8 }

cucsEquipmentRackUnitPsuStatsHistInputPower OBJECT-TYPE
    SYNTAX       INTEGER
    MAX-ACCESS   read-only
    STATUS       current
    DESCRIPTION
        "Cisco UCS equipment:RackUnitPsuStatsHist:inputPower
        managed object property"
    ::= { cucsEquipmentRackUnitPsuStatsHistEntry 9 }

cucsEquipmentRackUnitPsuStatsHistInputPowerAvg OBJECT-TYPE
    SYNTAX       INTEGER
    MAX-ACCESS   read-only
    STATUS       current
    DESCRIPTION
        "Cisco UCS equipment:RackUnitPsuStatsHist:inputPowerAvg
        managed object property"
    ::= { cucsEquipmentRackUnitPsuStatsHistEntry 10 }

cucsEquipmentRackUnitPsuStatsHistInputPowerMax OBJECT-TYPE
    SYNTAX       INTEGER
    MAX-ACCESS   read-only
    STATUS       current
    DESCRIPTION
        "Cisco UCS equipment:RackUnitPsuStatsHist:inputPowerMax
        managed object property"
    ::= { cucsEquipmentRackUnitPsuStatsHistEntry 11 }

cucsEquipmentRackUnitPsuStatsHistInputPowerMin OBJECT-TYPE
    SYNTAX       INTEGER
    MAX-ACCESS   read-only
    STATUS       current
    DESCRIPTION
        "Cisco UCS equipment:RackUnitPsuStatsHist:inputPowerMin
        managed object property"
    ::= { cucsEquipmentRackUnitPsuStatsHistEntry 12 }

cucsEquipmentRackUnitPsuStatsHistInputVoltage OBJECT-TYPE
    SYNTAX       INTEGER
    MAX-ACCESS   read-only
    STATUS       current
    DESCRIPTION
        "Cisco UCS equipment:RackUnitPsuStatsHist:inputVoltage
        managed object property"
    ::= { cucsEquipmentRackUnitPsuStatsHistEntry 13 }

cucsEquipmentRackUnitPsuStatsHistInputVoltageAvg OBJECT-TYPE
    SYNTAX       INTEGER
    MAX-ACCESS   read-only
    STATUS       current
    DESCRIPTION
        "Cisco UCS equipment:RackUnitPsuStatsHist:inputVoltageAvg
        managed object property"
    ::= { cucsEquipmentRackUnitPsuStatsHistEntry 14 }

cucsEquipmentRackUnitPsuStatsHistInputVoltageMax OBJECT-TYPE
    SYNTAX       INTEGER
    MAX-ACCESS   read-only
    STATUS       current
    DESCRIPTION
        "Cisco UCS equipment:RackUnitPsuStatsHist:inputVoltageMax
        managed object property"
    ::= { cucsEquipmentRackUnitPsuStatsHistEntry 15 }

cucsEquipmentRackUnitPsuStatsHistInputVoltageMin OBJECT-TYPE
    SYNTAX       INTEGER
    MAX-ACCESS   read-only
    STATUS       current
    DESCRIPTION
        "Cisco UCS equipment:RackUnitPsuStatsHist:inputVoltageMin
        managed object property"
    ::= { cucsEquipmentRackUnitPsuStatsHistEntry 16 }

cucsEquipmentRackUnitPsuStatsHistMostRecent OBJECT-TYPE
    SYNTAX       TruthValue
    MAX-ACCESS   read-only
    STATUS       current
    DESCRIPTION
        "Cisco UCS equipment:RackUnitPsuStatsHist:mostRecent
        managed object property"
    ::= { cucsEquipmentRackUnitPsuStatsHistEntry 17 }

cucsEquipmentRackUnitPsuStatsHistOutputCurrent OBJECT-TYPE
    SYNTAX       INTEGER
    MAX-ACCESS   read-only
    STATUS       current
    DESCRIPTION
        "Cisco UCS equipment:RackUnitPsuStatsHist:outputCurrent
        managed object property"
    ::= { cucsEquipmentRackUnitPsuStatsHistEntry 18 }

cucsEquipmentRackUnitPsuStatsHistOutputCurrentAvg OBJECT-TYPE
    SYNTAX       INTEGER
    MAX-ACCESS   read-only
    STATUS       current
    DESCRIPTION
        "Cisco UCS equipment:RackUnitPsuStatsHist:outputCurrentAvg
        managed object property"
    ::= { cucsEquipmentRackUnitPsuStatsHistEntry 19 }

cucsEquipmentRackUnitPsuStatsHistOutputCurrentMax OBJECT-TYPE
    SYNTAX       INTEGER
    MAX-ACCESS   read-only
    STATUS       current
    DESCRIPTION
        "Cisco UCS equipment:RackUnitPsuStatsHist:outputCurrentMax
        managed object property"
    ::= { cucsEquipmentRackUnitPsuStatsHistEntry 20 }

cucsEquipmentRackUnitPsuStatsHistOutputCurrentMin OBJECT-TYPE
    SYNTAX       INTEGER
    MAX-ACCESS   read-only
    STATUS       current
    DESCRIPTION
        "Cisco UCS equipment:RackUnitPsuStatsHist:outputCurrentMin
        managed object property"
    ::= { cucsEquipmentRackUnitPsuStatsHistEntry 21 }

cucsEquipmentRackUnitPsuStatsHistOutputPower OBJECT-TYPE
    SYNTAX       INTEGER
    MAX-ACCESS   read-only
    STATUS       current
    DESCRIPTION
        "Cisco UCS equipment:RackUnitPsuStatsHist:outputPower
        managed object property"
    ::= { cucsEquipmentRackUnitPsuStatsHistEntry 22 }

cucsEquipmentRackUnitPsuStatsHistOutputPowerAvg OBJECT-TYPE
    SYNTAX       INTEGER
    MAX-ACCESS   read-only
    STATUS       current
    DESCRIPTION
        "Cisco UCS equipment:RackUnitPsuStatsHist:outputPowerAvg
        managed object property"
    ::= { cucsEquipmentRackUnitPsuStatsHistEntry 23 }

cucsEquipmentRackUnitPsuStatsHistOutputPowerMax OBJECT-TYPE
    SYNTAX       INTEGER
    MAX-ACCESS   read-only
    STATUS       current
    DESCRIPTION
        "Cisco UCS equipment:RackUnitPsuStatsHist:outputPowerMax
        managed object property"
    ::= { cucsEquipmentRackUnitPsuStatsHistEntry 24 }

cucsEquipmentRackUnitPsuStatsHistOutputPowerMin OBJECT-TYPE
    SYNTAX       INTEGER
    MAX-ACCESS   read-only
    STATUS       current
    DESCRIPTION
        "Cisco UCS equipment:RackUnitPsuStatsHist:outputPowerMin
        managed object property"
    ::= { cucsEquipmentRackUnitPsuStatsHistEntry 25 }

cucsEquipmentRackUnitPsuStatsHistOutputVoltage OBJECT-TYPE
    SYNTAX       INTEGER
    MAX-ACCESS   read-only
    STATUS       current
    DESCRIPTION
        "Cisco UCS equipment:RackUnitPsuStatsHist:outputVoltage
        managed object property"
    ::= { cucsEquipmentRackUnitPsuStatsHistEntry 26 }

cucsEquipmentRackUnitPsuStatsHistOutputVoltageAvg OBJECT-TYPE
    SYNTAX       INTEGER
    MAX-ACCESS   read-only
    STATUS       current
    DESCRIPTION
        "Cisco UCS equipment:RackUnitPsuStatsHist:outputVoltageAvg
        managed object property"
    ::= { cucsEquipmentRackUnitPsuStatsHistEntry 27 }

cucsEquipmentRackUnitPsuStatsHistOutputVoltageMax OBJECT-TYPE
    SYNTAX       INTEGER
    MAX-ACCESS   read-only
    STATUS       current
    DESCRIPTION
        "Cisco UCS equipment:RackUnitPsuStatsHist:outputVoltageMax
        managed object property"
    ::= { cucsEquipmentRackUnitPsuStatsHistEntry 28 }

cucsEquipmentRackUnitPsuStatsHistOutputVoltageMin OBJECT-TYPE
    SYNTAX       INTEGER
    MAX-ACCESS   read-only
    STATUS       current
    DESCRIPTION
        "Cisco UCS equipment:RackUnitPsuStatsHist:outputVoltageMin
        managed object property"
    ::= { cucsEquipmentRackUnitPsuStatsHistEntry 29 }

cucsEquipmentRackUnitPsuStatsHistSuspect OBJECT-TYPE
    SYNTAX       TruthValue
    MAX-ACCESS   read-only
    STATUS       current
    DESCRIPTION
        "Cisco UCS equipment:RackUnitPsuStatsHist:suspect
        managed object property"
    ::= { cucsEquipmentRackUnitPsuStatsHistEntry 30 }

cucsEquipmentRackUnitPsuStatsHistThresholded OBJECT-TYPE
    SYNTAX       CucsEquipmentRackUnitPsuStatsHistThresholded
    MAX-ACCESS   read-only
    STATUS       current
    DESCRIPTION
        "Cisco UCS equipment:RackUnitPsuStatsHist:thresholded
        managed object property"
    ::= { cucsEquipmentRackUnitPsuStatsHistEntry 31 }

cucsEquipmentRackUnitPsuStatsHistTimeCollected OBJECT-TYPE
    SYNTAX       DateAndTime
    MAX-ACCESS   read-only
    STATUS       current
    DESCRIPTION
        "Cisco UCS equipment:RackUnitPsuStatsHist:timeCollected
        managed object property"
    ::= { cucsEquipmentRackUnitPsuStatsHistEntry 32 }

cucsEquipmentRaidDefTable OBJECT-TYPE
    SYNTAX           SEQUENCE OF CucsEquipmentRaidDefEntry
    MAX-ACCESS       not-accessible
    STATUS           current
    DESCRIPTION
        "Cisco UCS equipment:RaidDef managed object table"
    ::= { cucsEquipmentObjects 75 }

cucsEquipmentRaidDefEntry OBJECT-TYPE
    SYNTAX           CucsEquipmentRaidDefEntry
    MAX-ACCESS       not-accessible
    STATUS           current
    DESCRIPTION
        "Entry for the cucsEquipmentRaidDefTable table."
    INDEX { cucsEquipmentRaidDefInstanceId }
    ::= { cucsEquipmentRaidDefTable 1 }

CucsEquipmentRaidDefEntry ::= SEQUENCE {
    cucsEquipmentRaidDefInstanceId                                   CucsManagedObjectId,
    cucsEquipmentRaidDefDn                                           CucsManagedObjectDn,
    cucsEquipmentRaidDefRn                                           SnmpAdminString,
    cucsEquipmentRaidDefDescr                                        SnmpAdminString,
    cucsEquipmentRaidDefIntId                                        SnmpAdminString,
    cucsEquipmentRaidDefLevel                                        CucsStorageLocalDiskMode,
    cucsEquipmentRaidDefName                                         SnmpAdminString,
    cucsEquipmentRaidDefPolicyLevel                                  Gauge32,
    cucsEquipmentRaidDefPolicyOwner                                  CucsPolicyPolicyOwner
}

cucsEquipmentRaidDefInstanceId OBJECT-TYPE
    SYNTAX       CucsManagedObjectId
    MAX-ACCESS   not-accessible
    STATUS       current
    DESCRIPTION
        "Instance identifier of the managed object."
    ::= { cucsEquipmentRaidDefEntry 1 }

cucsEquipmentRaidDefDn OBJECT-TYPE
    SYNTAX       CucsManagedObjectDn
    MAX-ACCESS   read-only
    STATUS       current
    DESCRIPTION
        "Cisco UCS equipment:RaidDef:dn managed object property"
    ::= { cucsEquipmentRaidDefEntry 2 }

cucsEquipmentRaidDefRn OBJECT-TYPE
    SYNTAX       SnmpAdminString
    MAX-ACCESS   read-only
    STATUS       current
    DESCRIPTION
        "Cisco UCS equipment:RaidDef:rn managed object property"
    ::= { cucsEquipmentRaidDefEntry 3 }

cucsEquipmentRaidDefDescr OBJECT-TYPE
    SYNTAX       SnmpAdminString
    MAX-ACCESS   read-only
    STATUS       current
    DESCRIPTION
        "Cisco UCS equipment:RaidDef:descr managed object property"
    ::= { cucsEquipmentRaidDefEntry 4 }

cucsEquipmentRaidDefIntId OBJECT-TYPE
    SYNTAX       SnmpAdminString
    MAX-ACCESS   read-only
    STATUS       current
    DESCRIPTION
        "Cisco UCS equipment:RaidDef:intId managed object property"
    ::= { cucsEquipmentRaidDefEntry 5 }

cucsEquipmentRaidDefLevel OBJECT-TYPE
    SYNTAX       CucsStorageLocalDiskMode
    MAX-ACCESS   read-only
    STATUS       current
    DESCRIPTION
        "Cisco UCS equipment:RaidDef:level managed object property"
    ::= { cucsEquipmentRaidDefEntry 6 }

cucsEquipmentRaidDefName OBJECT-TYPE
    SYNTAX       SnmpAdminString
    MAX-ACCESS   read-only
    STATUS       current
    DESCRIPTION
        "Cisco UCS equipment:RaidDef:name managed object property"
    ::= { cucsEquipmentRaidDefEntry 7 }

cucsEquipmentRaidDefPolicyLevel OBJECT-TYPE
    SYNTAX       Gauge32
    MAX-ACCESS   read-only
    STATUS       current
    DESCRIPTION
        "Cisco UCS equipment:RaidDef:policyLevel managed object property"
    ::= { cucsEquipmentRaidDefEntry 8 }

cucsEquipmentRaidDefPolicyOwner OBJECT-TYPE
    SYNTAX       CucsPolicyPolicyOwner
    MAX-ACCESS   read-only
    STATUS       current
    DESCRIPTION
        "Cisco UCS equipment:RaidDef:policyOwner managed object property"
    ::= { cucsEquipmentRaidDefEntry 9 }

cucsEquipmentServerFeatureCapTable OBJECT-TYPE
    SYNTAX           SEQUENCE OF CucsEquipmentServerFeatureCapEntry
    MAX-ACCESS       not-accessible
    STATUS           current
    DESCRIPTION
        "Cisco UCS equipment:ServerFeatureCap managed object table"
    ::= { cucsEquipmentObjects 102 }

cucsEquipmentServerFeatureCapEntry OBJECT-TYPE
    SYNTAX           CucsEquipmentServerFeatureCapEntry
    MAX-ACCESS       not-accessible
    STATUS           current
    DESCRIPTION
        "Entry for the cucsEquipmentServerFeatureCapTable table."
    INDEX { cucsEquipmentServerFeatureCapInstanceId }
    ::= { cucsEquipmentServerFeatureCapTable 1 }

CucsEquipmentServerFeatureCapEntry ::= SEQUENCE {
    cucsEquipmentServerFeatureCapInstanceId                          CucsManagedObjectId,
    cucsEquipmentServerFeatureCapDn                                  CucsManagedObjectDn,
    cucsEquipmentServerFeatureCapRn                                  SnmpAdminString,
    cucsEquipmentServerFeatureCapCmosResetSupported                  TruthValue
}

cucsEquipmentServerFeatureCapInstanceId OBJECT-TYPE
    SYNTAX       CucsManagedObjectId
    MAX-ACCESS   not-accessible
    STATUS       current
    DESCRIPTION
        "Instance identifier of the managed object."
    ::= { cucsEquipmentServerFeatureCapEntry 1 }

cucsEquipmentServerFeatureCapDn OBJECT-TYPE
    SYNTAX       CucsManagedObjectDn
    MAX-ACCESS   read-only
    STATUS       current
    DESCRIPTION
        "Cisco UCS equipment:ServerFeatureCap:dn managed object property"
    ::= { cucsEquipmentServerFeatureCapEntry 2 }

cucsEquipmentServerFeatureCapRn OBJECT-TYPE
    SYNTAX       SnmpAdminString
    MAX-ACCESS   read-only
    STATUS       current
    DESCRIPTION
        "Cisco UCS equipment:ServerFeatureCap:rn managed object property"
    ::= { cucsEquipmentServerFeatureCapEntry 3 }

cucsEquipmentServerFeatureCapCmosResetSupported OBJECT-TYPE
    SYNTAX       TruthValue
    MAX-ACCESS   read-only
    STATUS       current
    DESCRIPTION
        "Cisco UCS equipment:ServerFeatureCap:cmosResetSupported
        managed object property"
    ::= { cucsEquipmentServerFeatureCapEntry 4 }

cucsEquipmentServiceDefTable OBJECT-TYPE
    SYNTAX           SEQUENCE OF CucsEquipmentServiceDefEntry
    MAX-ACCESS       not-accessible
    STATUS           current
    DESCRIPTION
        "Cisco UCS equipment:ServiceDef managed object table"
    ::= { cucsEquipmentObjects 65 }

cucsEquipmentServiceDefEntry OBJECT-TYPE
    SYNTAX           CucsEquipmentServiceDefEntry
    MAX-ACCESS       not-accessible
    STATUS           current
    DESCRIPTION
        "Entry for the cucsEquipmentServiceDefTable table."
    INDEX { cucsEquipmentServiceDefInstanceId }
    ::= { cucsEquipmentServiceDefTable 1 }

CucsEquipmentServiceDefEntry ::= SEQUENCE {
    cucsEquipmentServiceDefInstanceId                                CucsManagedObjectId,
    cucsEquipmentServiceDefDn                                        CucsManagedObjectDn,
    cucsEquipmentServiceDefRn                                        SnmpAdminString,
    cucsEquipmentServiceDefCanBeFRUed                                TruthValue,
    cucsEquipmentServiceDefDescr                                     SnmpAdminString,
    cucsEquipmentServiceDefIntId                                     SnmpAdminString,
    cucsEquipmentServiceDefName                                      SnmpAdminString,
    cucsEquipmentServiceDefRemovalConditions                         CucsEquipmentRemovalConditions,
    cucsEquipmentServiceDefServicePhilosophy                         SnmpAdminString,
    cucsEquipmentServiceDefPolicyLevel                               Gauge32,
    cucsEquipmentServiceDefPolicyOwner                               CucsPolicyPolicyOwner
}

cucsEquipmentServiceDefInstanceId OBJECT-TYPE
    SYNTAX       CucsManagedObjectId
    MAX-ACCESS   not-accessible
    STATUS       current
    DESCRIPTION
        "Instance identifier of the managed object."
    ::= { cucsEquipmentServiceDefEntry 1 }

cucsEquipmentServiceDefDn OBJECT-TYPE
    SYNTAX       CucsManagedObjectDn
    MAX-ACCESS   read-only
    STATUS       current
    DESCRIPTION
        "Cisco UCS equipment:ServiceDef:dn managed object property"
    ::= { cucsEquipmentServiceDefEntry 2 }

cucsEquipmentServiceDefRn OBJECT-TYPE
    SYNTAX       SnmpAdminString
    MAX-ACCESS   read-only
    STATUS       current
    DESCRIPTION
        "Cisco UCS equipment:ServiceDef:rn managed object property"
    ::= { cucsEquipmentServiceDefEntry 3 }

cucsEquipmentServiceDefCanBeFRUed OBJECT-TYPE
    SYNTAX       TruthValue
    MAX-ACCESS   read-only
    STATUS       current
    DESCRIPTION
        "Cisco UCS equipment:ServiceDef:canBeFRUed managed
        object property"
    ::= { cucsEquipmentServiceDefEntry 4 }

cucsEquipmentServiceDefDescr OBJECT-TYPE
    SYNTAX       SnmpAdminString
    MAX-ACCESS   read-only
    STATUS       current
    DESCRIPTION
        "Cisco UCS equipment:ServiceDef:descr managed object property"
    ::= { cucsEquipmentServiceDefEntry 5 }

cucsEquipmentServiceDefIntId OBJECT-TYPE
    SYNTAX       SnmpAdminString
    MAX-ACCESS   read-only
    STATUS       current
    DESCRIPTION
        "Cisco UCS equipment:ServiceDef:intId managed object property"
    ::= { cucsEquipmentServiceDefEntry 6 }

cucsEquipmentServiceDefName OBJECT-TYPE
    SYNTAX       SnmpAdminString
    MAX-ACCESS   read-only
    STATUS       current
    DESCRIPTION
        "Cisco UCS equipment:ServiceDef:name managed object property"
    ::= { cucsEquipmentServiceDefEntry 7 }

cucsEquipmentServiceDefRemovalConditions OBJECT-TYPE
    SYNTAX       CucsEquipmentRemovalConditions
    MAX-ACCESS   read-only
    STATUS       current
    DESCRIPTION
        "Cisco UCS equipment:ServiceDef:removalConditions
        managed object property"
    ::= { cucsEquipmentServiceDefEntry 8 }

cucsEquipmentServiceDefServicePhilosophy OBJECT-TYPE
    SYNTAX       SnmpAdminString
    MAX-ACCESS   read-only
    STATUS       current
    DESCRIPTION
        "Cisco UCS equipment:ServiceDef:servicePhilosophy
        managed object property"
    ::= { cucsEquipmentServiceDefEntry 9 }

cucsEquipmentServiceDefPolicyLevel OBJECT-TYPE
    SYNTAX       Gauge32
    MAX-ACCESS   read-only
    STATUS       current
    DESCRIPTION
        "Cisco UCS equipment:ServiceDef:policyLevel managed
        object property"
    ::= { cucsEquipmentServiceDefEntry 10 }

cucsEquipmentServiceDefPolicyOwner OBJECT-TYPE
    SYNTAX       CucsPolicyPolicyOwner
    MAX-ACCESS   read-only
    STATUS       current
    DESCRIPTION
        "Cisco UCS equipment:ServiceDef:policyOwner managed
        object property"
    ::= { cucsEquipmentServiceDefEntry 11 }

cucsEquipmentSlotArrayTable OBJECT-TYPE
    SYNTAX           SEQUENCE OF CucsEquipmentSlotArrayEntry
    MAX-ACCESS       not-accessible
    STATUS           current
    DESCRIPTION
        "Cisco UCS equipment:SlotArray managed object table"
    ::= { cucsEquipmentObjects 66 }

cucsEquipmentSlotArrayEntry OBJECT-TYPE
    SYNTAX           CucsEquipmentSlotArrayEntry
    MAX-ACCESS       not-accessible
    STATUS           current
    DESCRIPTION
        "Entry for the cucsEquipmentSlotArrayTable table."
    INDEX { cucsEquipmentSlotArrayInstanceId }
    ::= { cucsEquipmentSlotArrayTable 1 }

CucsEquipmentSlotArrayEntry ::= SEQUENCE {
    cucsEquipmentSlotArrayInstanceId                                 CucsManagedObjectId,
    cucsEquipmentSlotArrayDn                                         CucsManagedObjectDn,
    cucsEquipmentSlotArrayRn                                         SnmpAdminString,
    cucsEquipmentSlotArrayDescr                                      SnmpAdminString,
    cucsEquipmentSlotArrayFirstIndex                                 Gauge32,
    cucsEquipmentSlotArrayHeight                                     INTEGER,
    cucsEquipmentSlotArrayHorizontalStartOffset                      INTEGER,
    cucsEquipmentSlotArrayInlineGroupSeparation                      INTEGER,
    cucsEquipmentSlotArrayInlineGroupSize                            Gauge32,
    cucsEquipmentSlotArrayInlineOffset                               INTEGER,
    cucsEquipmentSlotArrayIntId                                      SnmpAdminString,
    cucsEquipmentSlotArrayLocation                                   CucsEquipmentSlotArrayLocation,
    cucsEquipmentSlotArrayName                                       SnmpAdminString,
    cucsEquipmentSlotArrayNumberOfSlots                              Gauge32,
    cucsEquipmentSlotArrayOrientation                                CucsEquipmentSlotArrayOrientation,
    cucsEquipmentSlotArraySelector                                   CucsEquipmentSlotArraySelector,
    cucsEquipmentSlotArraySlotsPerLine                               Gauge32,
    cucsEquipmentSlotArrayTransverseGroupSeparation                  INTEGER,
    cucsEquipmentSlotArrayTransverseGroupSize                        Gauge32,
    cucsEquipmentSlotArrayTransverseOffset                           INTEGER,
    cucsEquipmentSlotArrayVerticalStartOffset                        INTEGER,
    cucsEquipmentSlotArrayWidth                                      INTEGER,
    cucsEquipmentSlotArrayPolicyLevel                                Gauge32,
    cucsEquipmentSlotArrayPolicyOwner                                CucsPolicyPolicyOwner
}

cucsEquipmentSlotArrayInstanceId OBJECT-TYPE
    SYNTAX       CucsManagedObjectId
    MAX-ACCESS   not-accessible
    STATUS       current
    DESCRIPTION
        "Instance identifier of the managed object."
    ::= { cucsEquipmentSlotArrayEntry 1 }

cucsEquipmentSlotArrayDn OBJECT-TYPE
    SYNTAX       CucsManagedObjectDn
    MAX-ACCESS   read-only
    STATUS       current
    DESCRIPTION
        "Cisco UCS equipment:SlotArray:dn managed object property"
    ::= { cucsEquipmentSlotArrayEntry 2 }

cucsEquipmentSlotArrayRn OBJECT-TYPE
    SYNTAX       SnmpAdminString
    MAX-ACCESS   read-only
    STATUS       current
    DESCRIPTION
        "Cisco UCS equipment:SlotArray:rn managed object property"
    ::= { cucsEquipmentSlotArrayEntry 3 }

cucsEquipmentSlotArrayDescr OBJECT-TYPE
    SYNTAX       SnmpAdminString
    MAX-ACCESS   read-only
    STATUS       current
    DESCRIPTION
        "Cisco UCS equipment:SlotArray:descr managed object property"
    ::= { cucsEquipmentSlotArrayEntry 4 }

cucsEquipmentSlotArrayFirstIndex OBJECT-TYPE
    SYNTAX       Gauge32
    MAX-ACCESS   read-only
    STATUS       current
    DESCRIPTION
        "Cisco UCS equipment:SlotArray:firstIndex managed object property"
    ::= { cucsEquipmentSlotArrayEntry 5 }

cucsEquipmentSlotArrayHeight OBJECT-TYPE
    SYNTAX       INTEGER
    MAX-ACCESS   read-only
    STATUS       current
    DESCRIPTION
        "Cisco UCS equipment:SlotArray:height managed object property"
    ::= { cucsEquipmentSlotArrayEntry 6 }

cucsEquipmentSlotArrayHorizontalStartOffset OBJECT-TYPE
    SYNTAX       INTEGER
    MAX-ACCESS   read-only
    STATUS       current
    DESCRIPTION
        "Cisco UCS equipment:SlotArray:horizontalStartOffset
        managed object property"
    ::= { cucsEquipmentSlotArrayEntry 7 }

cucsEquipmentSlotArrayInlineGroupSeparation OBJECT-TYPE
    SYNTAX       INTEGER
    MAX-ACCESS   read-only
    STATUS       current
    DESCRIPTION
        "Cisco UCS equipment:SlotArray:inlineGroupSeparation
        managed object property"
    ::= { cucsEquipmentSlotArrayEntry 8 }

cucsEquipmentSlotArrayInlineGroupSize OBJECT-TYPE
    SYNTAX       Gauge32
    MAX-ACCESS   read-only
    STATUS       current
    DESCRIPTION
        "Cisco UCS equipment:SlotArray:inlineGroupSize
        managed object property"
    ::= { cucsEquipmentSlotArrayEntry 9 }

cucsEquipmentSlotArrayInlineOffset OBJECT-TYPE
    SYNTAX       INTEGER
    MAX-ACCESS   read-only
    STATUS       current
    DESCRIPTION
        "Cisco UCS equipment:SlotArray:inlineOffset managed
        object property"
    ::= { cucsEquipmentSlotArrayEntry 10 }

cucsEquipmentSlotArrayIntId OBJECT-TYPE
    SYNTAX       SnmpAdminString
    MAX-ACCESS   read-only
    STATUS       current
    DESCRIPTION
        "Cisco UCS equipment:SlotArray:intId managed object property"
    ::= { cucsEquipmentSlotArrayEntry 11 }

cucsEquipmentSlotArrayLocation OBJECT-TYPE
    SYNTAX       CucsEquipmentSlotArrayLocation
    MAX-ACCESS   read-only
    STATUS       current
    DESCRIPTION
        "Cisco UCS equipment:SlotArray:location managed object property"
    ::= { cucsEquipmentSlotArrayEntry 12 }

cucsEquipmentSlotArrayName OBJECT-TYPE
    SYNTAX       SnmpAdminString
    MAX-ACCESS   read-only
    STATUS       current
    DESCRIPTION
        "Cisco UCS equipment:SlotArray:name managed object property"
    ::= { cucsEquipmentSlotArrayEntry 13 }

cucsEquipmentSlotArrayNumberOfSlots OBJECT-TYPE
    SYNTAX       Gauge32
    MAX-ACCESS   read-only
    STATUS       current
    DESCRIPTION
        "Cisco UCS equipment:SlotArray:numberOfSlots managed
        object property"
    ::= { cucsEquipmentSlotArrayEntry 14 }

cucsEquipmentSlotArrayOrientation OBJECT-TYPE
    SYNTAX       CucsEquipmentSlotArrayOrientation
    MAX-ACCESS   read-only
    STATUS       current
    DESCRIPTION
        "Cisco UCS equipment:SlotArray:orientation managed
        object property"
    ::= { cucsEquipmentSlotArrayEntry 15 }

cucsEquipmentSlotArraySelector OBJECT-TYPE
    SYNTAX       CucsEquipmentSlotArraySelector
    MAX-ACCESS   read-only
    STATUS       current
    DESCRIPTION
        "Cisco UCS equipment:SlotArray:selector managed object property"
    ::= { cucsEquipmentSlotArrayEntry 16 }

cucsEquipmentSlotArraySlotsPerLine OBJECT-TYPE
    SYNTAX       Gauge32
    MAX-ACCESS   read-only
    STATUS       current
    DESCRIPTION
        "Cisco UCS equipment:SlotArray:slotsPerLine managed
        object property"
    ::= { cucsEquipmentSlotArrayEntry 17 }

cucsEquipmentSlotArrayTransverseGroupSeparation OBJECT-TYPE
    SYNTAX       INTEGER
    MAX-ACCESS   read-only
    STATUS       current
    DESCRIPTION
        "Cisco UCS equipment:SlotArray:transverseGroupSeparation
        managed object property"
    ::= { cucsEquipmentSlotArrayEntry 18 }

cucsEquipmentSlotArrayTransverseGroupSize OBJECT-TYPE
    SYNTAX       Gauge32
    MAX-ACCESS   read-only
    STATUS       current
    DESCRIPTION
        "Cisco UCS equipment:SlotArray:transverseGroupSize
        managed object property"
    ::= { cucsEquipmentSlotArrayEntry 19 }

cucsEquipmentSlotArrayTransverseOffset OBJECT-TYPE
    SYNTAX       INTEGER
    MAX-ACCESS   read-only
    STATUS       current
    DESCRIPTION
        "Cisco UCS equipment:SlotArray:transverseOffset
        managed object property"
    ::= { cucsEquipmentSlotArrayEntry 20 }

cucsEquipmentSlotArrayVerticalStartOffset OBJECT-TYPE
    SYNTAX       INTEGER
    MAX-ACCESS   read-only
    STATUS       current
    DESCRIPTION
        "Cisco UCS equipment:SlotArray:verticalStartOffset
        managed object property"
    ::= { cucsEquipmentSlotArrayEntry 21 }

cucsEquipmentSlotArrayWidth OBJECT-TYPE
    SYNTAX       INTEGER
    MAX-ACCESS   read-only
    STATUS       current
    DESCRIPTION
        "Cisco UCS equipment:SlotArray:width managed object property"
    ::= { cucsEquipmentSlotArrayEntry 22 }

cucsEquipmentSlotArrayPolicyLevel OBJECT-TYPE
    SYNTAX       Gauge32
    MAX-ACCESS   read-only
    STATUS       current
    DESCRIPTION
        "Cisco UCS equipment:SlotArray:policyLevel managed
        object property"
    ::= { cucsEquipmentSlotArrayEntry 23 }

cucsEquipmentSlotArrayPolicyOwner OBJECT-TYPE
    SYNTAX       CucsPolicyPolicyOwner
    MAX-ACCESS   read-only
    STATUS       current
    DESCRIPTION
        "Cisco UCS equipment:SlotArray:policyOwner managed
        object property"
    ::= { cucsEquipmentSlotArrayEntry 24 }

cucsEquipmentSlotArrayRefTable OBJECT-TYPE
    SYNTAX           SEQUENCE OF CucsEquipmentSlotArrayRefEntry
    MAX-ACCESS       not-accessible
    STATUS           current
    DESCRIPTION
        "Cisco UCS equipment:SlotArrayRef managed object table"
    ::= { cucsEquipmentObjects 67 }

cucsEquipmentSlotArrayRefEntry OBJECT-TYPE
    SYNTAX           CucsEquipmentSlotArrayRefEntry
    MAX-ACCESS       not-accessible
    STATUS           current
    DESCRIPTION
        "Entry for the cucsEquipmentSlotArrayRefTable table."
    INDEX { cucsEquipmentSlotArrayRefInstanceId }
    ::= { cucsEquipmentSlotArrayRefTable 1 }

CucsEquipmentSlotArrayRefEntry ::= SEQUENCE {
    cucsEquipmentSlotArrayRefInstanceId                              CucsManagedObjectId,
    cucsEquipmentSlotArrayRefDn                                      CucsManagedObjectDn,
    cucsEquipmentSlotArrayRefRn                                      SnmpAdminString,
    cucsEquipmentSlotArrayRefDescr                                   SnmpAdminString,
    cucsEquipmentSlotArrayRefIntId                                   SnmpAdminString,
    cucsEquipmentSlotArrayRefName                                    SnmpAdminString,
    cucsEquipmentSlotArrayRefNumberOfSlotsSpanned                    Gauge32,
    cucsEquipmentSlotArrayRefSlotSpanOrientation                     CucsEquipmentSlotSpanOrientation,
    cucsEquipmentSlotArrayRefTargetDn                                SnmpAdminString,
    cucsEquipmentSlotArrayRefPolicyLevel                             Gauge32,
    cucsEquipmentSlotArrayRefPolicyOwner                             CucsPolicyPolicyOwner
}

cucsEquipmentSlotArrayRefInstanceId OBJECT-TYPE
    SYNTAX       CucsManagedObjectId
    MAX-ACCESS   not-accessible
    STATUS       current
    DESCRIPTION
        "Instance identifier of the managed object."
    ::= { cucsEquipmentSlotArrayRefEntry 1 }

cucsEquipmentSlotArrayRefDn OBJECT-TYPE
    SYNTAX       CucsManagedObjectDn
    MAX-ACCESS   read-only
    STATUS       current
    DESCRIPTION
        "Cisco UCS equipment:SlotArrayRef:dn managed object property"
    ::= { cucsEquipmentSlotArrayRefEntry 2 }

cucsEquipmentSlotArrayRefRn OBJECT-TYPE
    SYNTAX       SnmpAdminString
    MAX-ACCESS   read-only
    STATUS       current
    DESCRIPTION
        "Cisco UCS equipment:SlotArrayRef:rn managed object property"
    ::= { cucsEquipmentSlotArrayRefEntry 3 }

cucsEquipmentSlotArrayRefDescr OBJECT-TYPE
    SYNTAX       SnmpAdminString
    MAX-ACCESS   read-only
    STATUS       current
    DESCRIPTION
        "Cisco UCS equipment:SlotArrayRef:descr managed object property"
    ::= { cucsEquipmentSlotArrayRefEntry 4 }

cucsEquipmentSlotArrayRefIntId OBJECT-TYPE
    SYNTAX       SnmpAdminString
    MAX-ACCESS   read-only
    STATUS       current
    DESCRIPTION
        "Cisco UCS equipment:SlotArrayRef:intId managed object property"
    ::= { cucsEquipmentSlotArrayRefEntry 5 }

cucsEquipmentSlotArrayRefName OBJECT-TYPE
    SYNTAX       SnmpAdminString
    MAX-ACCESS   read-only
    STATUS       current
    DESCRIPTION
        "Cisco UCS equipment:SlotArrayRef:name managed object property"
    ::= { cucsEquipmentSlotArrayRefEntry 6 }

cucsEquipmentSlotArrayRefNumberOfSlotsSpanned OBJECT-TYPE
    SYNTAX       Gauge32
    MAX-ACCESS   read-only
    STATUS       current
    DESCRIPTION
        "Cisco UCS equipment:SlotArrayRef:numberOfSlotsSpanned
        managed object property"
    ::= { cucsEquipmentSlotArrayRefEntry 7 }

cucsEquipmentSlotArrayRefSlotSpanOrientation OBJECT-TYPE
    SYNTAX       CucsEquipmentSlotSpanOrientation
    MAX-ACCESS   read-only
    STATUS       current
    DESCRIPTION
        "Cisco UCS equipment:SlotArrayRef:slotSpanOrientation
        managed object property"
    ::= { cucsEquipmentSlotArrayRefEntry 8 }

cucsEquipmentSlotArrayRefTargetDn OBJECT-TYPE
    SYNTAX       SnmpAdminString
    MAX-ACCESS   read-only
    STATUS       current
    DESCRIPTION
        "Cisco UCS equipment:SlotArrayRef:targetDn managed
        object property"
    ::= { cucsEquipmentSlotArrayRefEntry 9 }

cucsEquipmentSlotArrayRefPolicyLevel OBJECT-TYPE
    SYNTAX       Gauge32
    MAX-ACCESS   read-only
    STATUS       current
    DESCRIPTION
        "Cisco UCS equipment:SlotArrayRef:policyLevel managed
        object property"
    ::= { cucsEquipmentSlotArrayRefEntry 10 }

cucsEquipmentSlotArrayRefPolicyOwner OBJECT-TYPE
    SYNTAX       CucsPolicyPolicyOwner
    MAX-ACCESS   read-only
    STATUS       current
    DESCRIPTION
        "Cisco UCS equipment:SlotArrayRef:policyOwner managed
        object property"
    ::= { cucsEquipmentSlotArrayRefEntry 11 }

cucsEquipmentSwitchCapTable OBJECT-TYPE
    SYNTAX           SEQUENCE OF CucsEquipmentSwitchCapEntry
    MAX-ACCESS       not-accessible
    STATUS           current
    DESCRIPTION
        "Cisco UCS equipment:SwitchCap managed object table"
    ::= { cucsEquipmentObjects 68 }

cucsEquipmentSwitchCapEntry OBJECT-TYPE
    SYNTAX           CucsEquipmentSwitchCapEntry
    MAX-ACCESS       not-accessible
    STATUS           current
    DESCRIPTION
        "Entry for the cucsEquipmentSwitchCapTable table."
    INDEX { cucsEquipmentSwitchCapInstanceId }
    ::= { cucsEquipmentSwitchCapTable 1 }

CucsEquipmentSwitchCapEntry ::= SEQUENCE {
    cucsEquipmentSwitchCapInstanceId                                 CucsManagedObjectId,
    cucsEquipmentSwitchCapDn                                         CucsManagedObjectDn,
    cucsEquipmentSwitchCapRn                                         SnmpAdminString,
    cucsEquipmentSwitchCapDescr                                      SnmpAdminString,
    cucsEquipmentSwitchCapIntId                                      SnmpAdminString,
    cucsEquipmentSwitchCapMaxEth1gPort                               Gauge32,
    cucsEquipmentSwitchCapMaxEth1gSlot                               Gauge32,
    cucsEquipmentSwitchCapName                                       SnmpAdminString,
    cucsEquipmentSwitchCapFanModulesSupported                        TruthValue,
    cucsEquipmentSwitchCapLocatorBeaconSupported                     TruthValue,
    cucsEquipmentSwitchCapMaxActiveSpanSessionCount                  Gauge32,
    cucsEquipmentSwitchCapMgmtDaughterCardSlotId                     Gauge32,
    cucsEquipmentSwitchCapMaxEthPcMembers                            Gauge32,
    cucsEquipmentSwitchCapMaxFcoePcMembers                           Gauge32,
    cucsEquipmentSwitchCapPolicyLevel                                Gauge32,
    cucsEquipmentSwitchCapPolicyOwner                                CucsPolicyPolicyOwner
}

cucsEquipmentSwitchCapInstanceId OBJECT-TYPE
    SYNTAX       CucsManagedObjectId
    MAX-ACCESS   not-accessible
    STATUS       current
    DESCRIPTION
        "Instance identifier of the managed object."
    ::= { cucsEquipmentSwitchCapEntry 1 }

cucsEquipmentSwitchCapDn OBJECT-TYPE
    SYNTAX       CucsManagedObjectDn
    MAX-ACCESS   read-only
    STATUS       current
    DESCRIPTION
        "Cisco UCS equipment:SwitchCap:dn managed object property"
    ::= { cucsEquipmentSwitchCapEntry 2 }

cucsEquipmentSwitchCapRn OBJECT-TYPE
    SYNTAX       SnmpAdminString
    MAX-ACCESS   read-only
    STATUS       current
    DESCRIPTION
        "Cisco UCS equipment:SwitchCap:rn managed object property"
    ::= { cucsEquipmentSwitchCapEntry 3 }

cucsEquipmentSwitchCapDescr OBJECT-TYPE
    SYNTAX       SnmpAdminString
    MAX-ACCESS   read-only
    STATUS       current
    DESCRIPTION
        "Cisco UCS equipment:SwitchCap:descr managed object property"
    ::= { cucsEquipmentSwitchCapEntry 4 }

cucsEquipmentSwitchCapIntId OBJECT-TYPE
    SYNTAX       SnmpAdminString
    MAX-ACCESS   read-only
    STATUS       current
    DESCRIPTION
        "Cisco UCS equipment:SwitchCap:intId managed object property"
    ::= { cucsEquipmentSwitchCapEntry 5 }

cucsEquipmentSwitchCapMaxEth1gPort OBJECT-TYPE
    SYNTAX       Gauge32
    MAX-ACCESS   read-only
    STATUS       current
    DESCRIPTION
        "Cisco UCS equipment:SwitchCap:maxEth1gPort managed
        object property"
    ::= { cucsEquipmentSwitchCapEntry 6 }

cucsEquipmentSwitchCapMaxEth1gSlot OBJECT-TYPE
    SYNTAX       Gauge32
    MAX-ACCESS   read-only
    STATUS       current
    DESCRIPTION
        "Cisco UCS equipment:SwitchCap:maxEth1gSlot managed
        object property"
    ::= { cucsEquipmentSwitchCapEntry 7 }

cucsEquipmentSwitchCapName OBJECT-TYPE
    SYNTAX       SnmpAdminString
    MAX-ACCESS   read-only
    STATUS       current
    DESCRIPTION
        "Cisco UCS equipment:SwitchCap:name managed object property"
    ::= { cucsEquipmentSwitchCapEntry 8 }

cucsEquipmentSwitchCapFanModulesSupported OBJECT-TYPE
    SYNTAX       TruthValue
    MAX-ACCESS   read-only
    STATUS       current
    DESCRIPTION
        "Cisco UCS equipment:SwitchCap:fanModulesSupported
        managed object property"
    ::= { cucsEquipmentSwitchCapEntry 9 }

cucsEquipmentSwitchCapLocatorBeaconSupported OBJECT-TYPE
    SYNTAX       TruthValue
    MAX-ACCESS   read-only
    STATUS       current
    DESCRIPTION
        "Cisco UCS equipment:SwitchCap:locatorBeaconSupported
        managed object property"
    ::= { cucsEquipmentSwitchCapEntry 10 }

cucsEquipmentSwitchCapMaxActiveSpanSessionCount OBJECT-TYPE
    SYNTAX       Gauge32
    MAX-ACCESS   read-only
    STATUS       current
    DESCRIPTION
        "Cisco UCS equipment:SwitchCap:maxActiveSpanSessionCount
        managed object property"
    ::= { cucsEquipmentSwitchCapEntry 11 }

cucsEquipmentSwitchCapMgmtDaughterCardSlotId OBJECT-TYPE
    SYNTAX       Gauge32
    MAX-ACCESS   read-only
    STATUS       current
    DESCRIPTION
        "Cisco UCS equipment:SwitchCap:mgmtDaughterCardSlotId
        managed object property"
    ::= { cucsEquipmentSwitchCapEntry 12 }

cucsEquipmentSwitchCapMaxEthPcMembers OBJECT-TYPE
    SYNTAX       Gauge32
    MAX-ACCESS   read-only
    STATUS       current
    DESCRIPTION
        "Cisco UCS equipment:SwitchCap:maxEthPcMembers
        managed object property"
    ::= { cucsEquipmentSwitchCapEntry 13 }

cucsEquipmentSwitchCapMaxFcoePcMembers OBJECT-TYPE
    SYNTAX       Gauge32
    MAX-ACCESS   read-only
    STATUS       current
    DESCRIPTION
        "Cisco UCS equipment:SwitchCap:maxFcoePcMembers
        managed object property"
    ::= { cucsEquipmentSwitchCapEntry 14 }

cucsEquipmentSwitchCapPolicyLevel OBJECT-TYPE
    SYNTAX       Gauge32
    MAX-ACCESS   read-only
    STATUS       current
    DESCRIPTION
        "Cisco UCS equipment:SwitchCap:policyLevel managed
        object property"
    ::= { cucsEquipmentSwitchCapEntry 15 }

cucsEquipmentSwitchCapPolicyOwner OBJECT-TYPE
    SYNTAX       CucsPolicyPolicyOwner
    MAX-ACCESS   read-only
    STATUS       current
    DESCRIPTION
        "Cisco UCS equipment:SwitchCap:policyOwner managed
        object property"
    ::= { cucsEquipmentSwitchCapEntry 16 }

cucsEquipmentSwitchCapProviderTable OBJECT-TYPE
    SYNTAX           SEQUENCE OF CucsEquipmentSwitchCapProviderEntry
    MAX-ACCESS       not-accessible
    STATUS           current
    DESCRIPTION
        "Cisco UCS equipment:SwitchCapProvider managed object table"
    ::= { cucsEquipmentObjects 69 }

cucsEquipmentSwitchCapProviderEntry OBJECT-TYPE
    SYNTAX           CucsEquipmentSwitchCapProviderEntry
    MAX-ACCESS       not-accessible
    STATUS           current
    DESCRIPTION
        "Entry for the cucsEquipmentSwitchCapProviderTable table."
    INDEX { cucsEquipmentSwitchCapProviderInstanceId }
    ::= { cucsEquipmentSwitchCapProviderTable 1 }

CucsEquipmentSwitchCapProviderEntry ::= SEQUENCE {
    cucsEquipmentSwitchCapProviderInstanceId                         CucsManagedObjectId,
    cucsEquipmentSwitchCapProviderDn                                 CucsManagedObjectDn,
    cucsEquipmentSwitchCapProviderRn                                 SnmpAdminString,
    cucsEquipmentSwitchCapProviderDeprecated                         TruthValue,
    cucsEquipmentSwitchCapProviderGencount                           Gauge32,
    cucsEquipmentSwitchCapProviderMgmtPlaneVer                       SnmpAdminString,
    cucsEquipmentSwitchCapProviderModel                              SnmpAdminString,
    cucsEquipmentSwitchCapProviderRevision                           SnmpAdminString,
    cucsEquipmentSwitchCapProviderVendor                             SnmpAdminString,
    cucsEquipmentSwitchCapProviderPromCardType                       Gauge32,
    cucsEquipmentSwitchCapProviderDeleted                            TruthValue,
    cucsEquipmentSwitchCapProviderElementLoadFailures                Gauge32,
    cucsEquipmentSwitchCapProviderElementsLoaded                     Gauge32,
    cucsEquipmentSwitchCapProviderLoadErrors                         Gauge32,
    cucsEquipmentSwitchCapProviderLoadWarnings                       Gauge32
}

cucsEquipmentSwitchCapProviderInstanceId OBJECT-TYPE
    SYNTAX       CucsManagedObjectId
    MAX-ACCESS   not-accessible
    STATUS       current
    DESCRIPTION
        "Instance identifier of the managed object."
    ::= { cucsEquipmentSwitchCapProviderEntry 1 }

cucsEquipmentSwitchCapProviderDn OBJECT-TYPE
    SYNTAX       CucsManagedObjectDn
    MAX-ACCESS   read-only
    STATUS       current
    DESCRIPTION
        "Cisco UCS equipment:SwitchCapProvider:dn managed object property"
    ::= { cucsEquipmentSwitchCapProviderEntry 2 }

cucsEquipmentSwitchCapProviderRn OBJECT-TYPE
    SYNTAX       SnmpAdminString
    MAX-ACCESS   read-only
    STATUS       current
    DESCRIPTION
        "Cisco UCS equipment:SwitchCapProvider:rn managed object property"
    ::= { cucsEquipmentSwitchCapProviderEntry 3 }

cucsEquipmentSwitchCapProviderDeprecated OBJECT-TYPE
    SYNTAX       TruthValue
    MAX-ACCESS   read-only
    STATUS       current
    DESCRIPTION
        "Cisco UCS equipment:SwitchCapProvider:deprecated
        managed object property"
    ::= { cucsEquipmentSwitchCapProviderEntry 4 }

cucsEquipmentSwitchCapProviderGencount OBJECT-TYPE
    SYNTAX       Gauge32
    MAX-ACCESS   read-only
    STATUS       current
    DESCRIPTION
        "Cisco UCS equipment:SwitchCapProvider:gencount
        managed object property"
    ::= { cucsEquipmentSwitchCapProviderEntry 5 }

cucsEquipmentSwitchCapProviderMgmtPlaneVer OBJECT-TYPE
    SYNTAX       SnmpAdminString
    MAX-ACCESS   read-only
    STATUS       current
    DESCRIPTION
        "Cisco UCS equipment:SwitchCapProvider:mgmtPlaneVer
        managed object property"
    ::= { cucsEquipmentSwitchCapProviderEntry 6 }

cucsEquipmentSwitchCapProviderModel OBJECT-TYPE
    SYNTAX       SnmpAdminString
    MAX-ACCESS   read-only
    STATUS       current
    DESCRIPTION
        "Cisco UCS equipment:SwitchCapProvider:model managed
        object property"
    ::= { cucsEquipmentSwitchCapProviderEntry 7 }

cucsEquipmentSwitchCapProviderRevision OBJECT-TYPE
    SYNTAX       SnmpAdminString
    MAX-ACCESS   read-only
    STATUS       current
    DESCRIPTION
        "Cisco UCS equipment:SwitchCapProvider:revision
        managed object property"
    ::= { cucsEquipmentSwitchCapProviderEntry 8 }

cucsEquipmentSwitchCapProviderVendor OBJECT-TYPE
    SYNTAX       SnmpAdminString
    MAX-ACCESS   read-only
    STATUS       current
    DESCRIPTION
        "Cisco UCS equipment:SwitchCapProvider:vendor managed
        object property"
    ::= { cucsEquipmentSwitchCapProviderEntry 9 }

cucsEquipmentSwitchCapProviderPromCardType OBJECT-TYPE
    SYNTAX       Gauge32
    MAX-ACCESS   read-only
    STATUS       current
    DESCRIPTION
        "Cisco UCS equipment:SwitchCapProvider:promCardType
        managed object property"
    ::= { cucsEquipmentSwitchCapProviderEntry 10 }

cucsEquipmentSwitchCapProviderDeleted OBJECT-TYPE
    SYNTAX       TruthValue
    MAX-ACCESS   read-only
    STATUS       current
    DESCRIPTION
        "Cisco UCS equipment:SwitchCapProvider:deleted
        managed object property"
    ::= { cucsEquipmentSwitchCapProviderEntry 11 }

cucsEquipmentSwitchCapProviderElementLoadFailures OBJECT-TYPE
    SYNTAX       Gauge32
    MAX-ACCESS   read-only
    STATUS       current
    DESCRIPTION
        "Cisco UCS equipment:SwitchCapProvider:elementLoadFailures
        managed object property"
    ::= { cucsEquipmentSwitchCapProviderEntry 12 }

cucsEquipmentSwitchCapProviderElementsLoaded OBJECT-TYPE
    SYNTAX       Gauge32
    MAX-ACCESS   read-only
    STATUS       current
    DESCRIPTION
        "Cisco UCS equipment:SwitchCapProvider:elementsLoaded
        managed object property"
    ::= { cucsEquipmentSwitchCapProviderEntry 13 }

cucsEquipmentSwitchCapProviderLoadErrors OBJECT-TYPE
    SYNTAX       Gauge32
    MAX-ACCESS   read-only
    STATUS       current
    DESCRIPTION
        "Cisco UCS equipment:SwitchCapProvider:loadErrors
        managed object property"
    ::= { cucsEquipmentSwitchCapProviderEntry 14 }

cucsEquipmentSwitchCapProviderLoadWarnings OBJECT-TYPE
    SYNTAX       Gauge32
    MAX-ACCESS   read-only
    STATUS       current
    DESCRIPTION
        "Cisco UCS equipment:SwitchCapProvider:loadWarnings
        managed object property"
    ::= { cucsEquipmentSwitchCapProviderEntry 15 }

cucsEquipmentSwitchCardTable OBJECT-TYPE
    SYNTAX           SEQUENCE OF CucsEquipmentSwitchCardEntry
    MAX-ACCESS       not-accessible
    STATUS           current
    DESCRIPTION
        "Cisco UCS equipment:SwitchCard managed object table"
    ::= { cucsEquipmentObjects 70 }

cucsEquipmentSwitchCardEntry OBJECT-TYPE
    SYNTAX           CucsEquipmentSwitchCardEntry
    MAX-ACCESS       not-accessible
    STATUS           current
    DESCRIPTION
        "Entry for the cucsEquipmentSwitchCardTable table."
    INDEX { cucsEquipmentSwitchCardInstanceId }
    ::= { cucsEquipmentSwitchCardTable 1 }

CucsEquipmentSwitchCardEntry ::= SEQUENCE {
    cucsEquipmentSwitchCardInstanceId                                CucsManagedObjectId,
    cucsEquipmentSwitchCardDn                                        CucsManagedObjectDn,
    cucsEquipmentSwitchCardRn                                        SnmpAdminString,
    cucsEquipmentSwitchCardDescr                                     SnmpAdminString,
    cucsEquipmentSwitchCardFltAggr                                   Unsigned64,
    cucsEquipmentSwitchCardId                                        Gauge32,
    cucsEquipmentSwitchCardModel                                     SnmpAdminString,
    cucsEquipmentSwitchCardNumPorts                                  Gauge32,
    cucsEquipmentSwitchCardOperState                                 CucsEquipmentOperability,
    cucsEquipmentSwitchCardOperability                               CucsEquipmentOperability,
    cucsEquipmentSwitchCardPerf                                      CucsEquipmentSensorThresholdStatus,
    cucsEquipmentSwitchCardPower                                     CucsEquipmentPowerState,
    cucsEquipmentSwitchCardPresence                                  CucsEquipmentPresence,
    cucsEquipmentSwitchCardRevision                                  SnmpAdminString,
    cucsEquipmentSwitchCardSerial                                    SnmpAdminString,
    cucsEquipmentSwitchCardState                                     CucsEquipmentPowerState,
    cucsEquipmentSwitchCardThermal                                   CucsEquipmentSensorThresholdStatus,
    cucsEquipmentSwitchCardTs                                        DateAndTime,
    cucsEquipmentSwitchCardVendor                                    SnmpAdminString,
    cucsEquipmentSwitchCardVoltage                                   CucsEquipmentSensorThresholdStatus,
    cucsEquipmentSwitchCardOperQualifierReason                       SnmpAdminString
}

cucsEquipmentSwitchCardInstanceId OBJECT-TYPE
    SYNTAX       CucsManagedObjectId
    MAX-ACCESS   not-accessible
    STATUS       current
    DESCRIPTION
        "Instance identifier of the managed object."
    ::= { cucsEquipmentSwitchCardEntry 1 }

cucsEquipmentSwitchCardDn OBJECT-TYPE
    SYNTAX       CucsManagedObjectDn
    MAX-ACCESS   read-only
    STATUS       current
    DESCRIPTION
        "Cisco UCS equipment:SwitchCard:dn managed object property"
    ::= { cucsEquipmentSwitchCardEntry 2 }

cucsEquipmentSwitchCardRn OBJECT-TYPE
    SYNTAX       SnmpAdminString
    MAX-ACCESS   read-only
    STATUS       current
    DESCRIPTION
        "Cisco UCS equipment:SwitchCard:rn managed object property"
    ::= { cucsEquipmentSwitchCardEntry 3 }

cucsEquipmentSwitchCardDescr OBJECT-TYPE
    SYNTAX       SnmpAdminString
    MAX-ACCESS   read-only
    STATUS       current
    DESCRIPTION
        "Cisco UCS equipment:SwitchCard:descr managed object property"
    ::= { cucsEquipmentSwitchCardEntry 4 }

cucsEquipmentSwitchCardFltAggr OBJECT-TYPE
    SYNTAX       Unsigned64
    MAX-ACCESS   read-only
    STATUS       current
    DESCRIPTION
        "Cisco UCS equipment:SwitchCard:fltAggr managed object property"
    ::= { cucsEquipmentSwitchCardEntry 5 }

cucsEquipmentSwitchCardId OBJECT-TYPE
    SYNTAX       Gauge32
    MAX-ACCESS   read-only
    STATUS       current
    DESCRIPTION
        "Cisco UCS equipment:SwitchCard:id managed object property"
    ::= { cucsEquipmentSwitchCardEntry 6 }

cucsEquipmentSwitchCardModel OBJECT-TYPE
    SYNTAX       SnmpAdminString
    MAX-ACCESS   read-only
    STATUS       current
    DESCRIPTION
        "Cisco UCS equipment:SwitchCard:model managed object property"
    ::= { cucsEquipmentSwitchCardEntry 7 }

cucsEquipmentSwitchCardNumPorts OBJECT-TYPE
    SYNTAX       Gauge32
    MAX-ACCESS   read-only
    STATUS       current
    DESCRIPTION
        "Cisco UCS equipment:SwitchCard:numPorts managed object property"
    ::= { cucsEquipmentSwitchCardEntry 8 }

cucsEquipmentSwitchCardOperState OBJECT-TYPE
    SYNTAX       CucsEquipmentOperability
    MAX-ACCESS   read-only
    STATUS       current
    DESCRIPTION
        "Cisco UCS equipment:SwitchCard:operState managed object property"
    ::= { cucsEquipmentSwitchCardEntry 9 }

cucsEquipmentSwitchCardOperability OBJECT-TYPE
    SYNTAX       CucsEquipmentOperability
    MAX-ACCESS   read-only
    STATUS       current
    DESCRIPTION
        "Cisco UCS equipment:SwitchCard:operability managed
        object property"
    ::= { cucsEquipmentSwitchCardEntry 10 }

cucsEquipmentSwitchCardPerf OBJECT-TYPE
    SYNTAX       CucsEquipmentSensorThresholdStatus
    MAX-ACCESS   read-only
    STATUS       current
    DESCRIPTION
        "Cisco UCS equipment:SwitchCard:perf managed object property"
    ::= { cucsEquipmentSwitchCardEntry 11 }

cucsEquipmentSwitchCardPower OBJECT-TYPE
    SYNTAX       CucsEquipmentPowerState
    MAX-ACCESS   read-only
    STATUS       current
    DESCRIPTION
        "Cisco UCS equipment:SwitchCard:power managed object property"
    ::= { cucsEquipmentSwitchCardEntry 12 }

cucsEquipmentSwitchCardPresence OBJECT-TYPE
    SYNTAX       CucsEquipmentPresence
    MAX-ACCESS   read-only
    STATUS       current
    DESCRIPTION
        "Cisco UCS equipment:SwitchCard:presence managed object property"
    ::= { cucsEquipmentSwitchCardEntry 13 }

cucsEquipmentSwitchCardRevision OBJECT-TYPE
    SYNTAX       SnmpAdminString
    MAX-ACCESS   read-only
    STATUS       current
    DESCRIPTION
        "Cisco UCS equipment:SwitchCard:revision managed object property"
    ::= { cucsEquipmentSwitchCardEntry 14 }

cucsEquipmentSwitchCardSerial OBJECT-TYPE
    SYNTAX       SnmpAdminString
    MAX-ACCESS   read-only
    STATUS       current
    DESCRIPTION
        "Cisco UCS equipment:SwitchCard:serial managed object property"
    ::= { cucsEquipmentSwitchCardEntry 15 }

cucsEquipmentSwitchCardState OBJECT-TYPE
    SYNTAX       CucsEquipmentPowerState
    MAX-ACCESS   read-only
    STATUS       current
    DESCRIPTION
        "Cisco UCS equipment:SwitchCard:state managed object property"
    ::= { cucsEquipmentSwitchCardEntry 16 }

cucsEquipmentSwitchCardThermal OBJECT-TYPE
    SYNTAX       CucsEquipmentSensorThresholdStatus
    MAX-ACCESS   read-only
    STATUS       current
    DESCRIPTION
        "Cisco UCS equipment:SwitchCard:thermal managed object property"
    ::= { cucsEquipmentSwitchCardEntry 17 }

cucsEquipmentSwitchCardTs OBJECT-TYPE
    SYNTAX       DateAndTime
    MAX-ACCESS   read-only
    STATUS       current
    DESCRIPTION
        "Cisco UCS equipment:SwitchCard:ts managed object property"
    ::= { cucsEquipmentSwitchCardEntry 18 }

cucsEquipmentSwitchCardVendor OBJECT-TYPE
    SYNTAX       SnmpAdminString
    MAX-ACCESS   read-only
    STATUS       current
    DESCRIPTION
        "Cisco UCS equipment:SwitchCard:vendor managed object property"
    ::= { cucsEquipmentSwitchCardEntry 19 }

cucsEquipmentSwitchCardVoltage OBJECT-TYPE
    SYNTAX       CucsEquipmentSensorThresholdStatus
    MAX-ACCESS   read-only
    STATUS       current
    DESCRIPTION
        "Cisco UCS equipment:SwitchCard:voltage managed object property"
    ::= { cucsEquipmentSwitchCardEntry 20 }

cucsEquipmentSwitchCardOperQualifierReason OBJECT-TYPE
    SYNTAX       SnmpAdminString
    MAX-ACCESS   read-only
    STATUS       current
    DESCRIPTION
        "Cisco UCS equipment:SwitchCard:operQualifierReason
        managed object property"
    ::= { cucsEquipmentSwitchCardEntry 21 }

cucsEquipmentUnifiedPortCapProviderTable OBJECT-TYPE
    SYNTAX           SEQUENCE OF CucsEquipmentUnifiedPortCapProviderEntry
    MAX-ACCESS       not-accessible
    STATUS           current
    DESCRIPTION
        "Cisco UCS equipment:UnifiedPortCapProvider managed object table"
    ::= { cucsEquipmentObjects 94 }

cucsEquipmentUnifiedPortCapProviderEntry OBJECT-TYPE
    SYNTAX           CucsEquipmentUnifiedPortCapProviderEntry
    MAX-ACCESS       not-accessible
    STATUS           current
    DESCRIPTION
        "Entry for the cucsEquipmentUnifiedPortCapProviderTable table."
    INDEX { cucsEquipmentUnifiedPortCapProviderInstanceId }
    ::= { cucsEquipmentUnifiedPortCapProviderTable 1 }

CucsEquipmentUnifiedPortCapProviderEntry ::= SEQUENCE {
    cucsEquipmentUnifiedPortCapProviderInstanceId                    CucsManagedObjectId,
    cucsEquipmentUnifiedPortCapProviderDn                            CucsManagedObjectDn,
    cucsEquipmentUnifiedPortCapProviderRn                            SnmpAdminString,
    cucsEquipmentUnifiedPortCapProviderDescr                         SnmpAdminString,
    cucsEquipmentUnifiedPortCapProviderIntId                         SnmpAdminString,
    cucsEquipmentUnifiedPortCapProviderName                          SnmpAdminString,
    cucsEquipmentUnifiedPortCapProviderSupportedAlgorithm            CucsEquipmentUnifiedPortAlgorithm,
    cucsEquipmentUnifiedPortCapProviderPolicyLevel                   Gauge32,
    cucsEquipmentUnifiedPortCapProviderPolicyOwner                   CucsPolicyPolicyOwner
}

cucsEquipmentUnifiedPortCapProviderInstanceId OBJECT-TYPE
    SYNTAX       CucsManagedObjectId
    MAX-ACCESS   not-accessible
    STATUS       current
    DESCRIPTION
        "Instance identifier of the managed object."
    ::= { cucsEquipmentUnifiedPortCapProviderEntry 1 }

cucsEquipmentUnifiedPortCapProviderDn OBJECT-TYPE
    SYNTAX       CucsManagedObjectDn
    MAX-ACCESS   read-only
    STATUS       current
    DESCRIPTION
        "Cisco UCS equipment:UnifiedPortCapProvider:dn
        managed object property"
    ::= { cucsEquipmentUnifiedPortCapProviderEntry 2 }

cucsEquipmentUnifiedPortCapProviderRn OBJECT-TYPE
    SYNTAX       SnmpAdminString
    MAX-ACCESS   read-only
    STATUS       current
    DESCRIPTION
        "Cisco UCS equipment:UnifiedPortCapProvider:rn
        managed object property"
    ::= { cucsEquipmentUnifiedPortCapProviderEntry 3 }

cucsEquipmentUnifiedPortCapProviderDescr OBJECT-TYPE
    SYNTAX       SnmpAdminString
    MAX-ACCESS   read-only
    STATUS       current
    DESCRIPTION
        "Cisco UCS equipment:UnifiedPortCapProvider:descr
        managed object property"
    ::= { cucsEquipmentUnifiedPortCapProviderEntry 4 }

cucsEquipmentUnifiedPortCapProviderIntId OBJECT-TYPE
    SYNTAX       SnmpAdminString
    MAX-ACCESS   read-only
    STATUS       current
    DESCRIPTION
        "Cisco UCS equipment:UnifiedPortCapProvider:intId
        managed object property"
    ::= { cucsEquipmentUnifiedPortCapProviderEntry 5 }

cucsEquipmentUnifiedPortCapProviderName OBJECT-TYPE
    SYNTAX       SnmpAdminString
    MAX-ACCESS   read-only
    STATUS       current
    DESCRIPTION
        "Cisco UCS equipment:UnifiedPortCapProvider:name
        managed object property"
    ::= { cucsEquipmentUnifiedPortCapProviderEntry 6 }

cucsEquipmentUnifiedPortCapProviderSupportedAlgorithm OBJECT-TYPE
    SYNTAX       CucsEquipmentUnifiedPortAlgorithm
    MAX-ACCESS   read-only
    STATUS       current
    DESCRIPTION
        "Cisco UCS equipment:UnifiedPortCapProvider:supportedAlgorithm
        managed object property"
    ::= { cucsEquipmentUnifiedPortCapProviderEntry 7 }

cucsEquipmentUnifiedPortCapProviderPolicyLevel OBJECT-TYPE
    SYNTAX       Gauge32
    MAX-ACCESS   read-only
    STATUS       current
    DESCRIPTION
        "Cisco UCS equipment:UnifiedPortCapProvider:policyLevel
        managed object property"
    ::= { cucsEquipmentUnifiedPortCapProviderEntry 8 }

cucsEquipmentUnifiedPortCapProviderPolicyOwner OBJECT-TYPE
    SYNTAX       CucsPolicyPolicyOwner
    MAX-ACCESS   read-only
    STATUS       current
    DESCRIPTION
        "Cisco UCS equipment:UnifiedPortCapProvider:policyOwner
        managed object property"
    ::= { cucsEquipmentUnifiedPortCapProviderEntry 9 }

cucsEquipmentVersionConstraintTable OBJECT-TYPE
    SYNTAX           SEQUENCE OF CucsEquipmentVersionConstraintEntry
    MAX-ACCESS       not-accessible
    STATUS           current
    DESCRIPTION
        "Cisco UCS equipment:VersionConstraint managed object table"
    ::= { cucsEquipmentObjects 116 }

cucsEquipmentVersionConstraintEntry OBJECT-TYPE
    SYNTAX           CucsEquipmentVersionConstraintEntry
    MAX-ACCESS       not-accessible
    STATUS           current
    DESCRIPTION
        "Entry for the cucsEquipmentVersionConstraintTable table."
    INDEX { cucsEquipmentVersionConstraintInstanceId }
    ::= { cucsEquipmentVersionConstraintTable 1 }

CucsEquipmentVersionConstraintEntry ::= SEQUENCE {
    cucsEquipmentVersionConstraintInstanceId                         CucsManagedObjectId,
    cucsEquipmentVersionConstraintDn                                 CucsManagedObjectDn,
    cucsEquipmentVersionConstraintRn                                 SnmpAdminString,
    cucsEquipmentVersionConstraintMinVer1                            SnmpAdminString
}

cucsEquipmentVersionConstraintInstanceId OBJECT-TYPE
    SYNTAX       CucsManagedObjectId
    MAX-ACCESS   not-accessible
    STATUS       current
    DESCRIPTION
        "Instance identifier of the managed object."
    ::= { cucsEquipmentVersionConstraintEntry 1 }

cucsEquipmentVersionConstraintDn OBJECT-TYPE
    SYNTAX       CucsManagedObjectDn
    MAX-ACCESS   read-only
    STATUS       current
    DESCRIPTION
        "Cisco UCS equipment:VersionConstraint:dn managed object property"
    ::= { cucsEquipmentVersionConstraintEntry 2 }

cucsEquipmentVersionConstraintRn OBJECT-TYPE
    SYNTAX       SnmpAdminString
    MAX-ACCESS   read-only
    STATUS       current
    DESCRIPTION
        "Cisco UCS equipment:VersionConstraint:rn managed object property"
    ::= { cucsEquipmentVersionConstraintEntry 3 }

cucsEquipmentVersionConstraintMinVer1 OBJECT-TYPE
    SYNTAX       SnmpAdminString
    MAX-ACCESS   read-only
    STATUS       current
    DESCRIPTION
        "Cisco UCS equipment:VersionConstraint:minVer1
        managed object property"
    ::= { cucsEquipmentVersionConstraintEntry 4 }

cucsEquipmentXcvrTable OBJECT-TYPE
    SYNTAX           SEQUENCE OF CucsEquipmentXcvrEntry
    MAX-ACCESS       not-accessible
    STATUS           current
    DESCRIPTION
        "Cisco UCS equipment:Xcvr managed object table"
    ::= { cucsEquipmentObjects 76 }

cucsEquipmentXcvrEntry OBJECT-TYPE
    SYNTAX           CucsEquipmentXcvrEntry
    MAX-ACCESS       not-accessible
    STATUS           current
    DESCRIPTION
        "Entry for the cucsEquipmentXcvrTable table."
    INDEX { cucsEquipmentXcvrInstanceId }
    ::= { cucsEquipmentXcvrTable 1 }

CucsEquipmentXcvrEntry ::= SEQUENCE {
    cucsEquipmentXcvrInstanceId                                      CucsManagedObjectId,
    cucsEquipmentXcvrDn                                              CucsManagedObjectDn,
    cucsEquipmentXcvrRn                                              SnmpAdminString,
    cucsEquipmentXcvrId                                              CucsEquipmentXcvrId,
    cucsEquipmentXcvrModel                                           SnmpAdminString,
    cucsEquipmentXcvrRevision                                        SnmpAdminString,
    cucsEquipmentXcvrSerial                                          SnmpAdminString,
    cucsEquipmentXcvrType                                            CucsEquipmentXcvrType,
    cucsEquipmentXcvrVendor                                          SnmpAdminString,
    cucsEquipmentXcvrTs                                              DateAndTime
}

cucsEquipmentXcvrInstanceId OBJECT-TYPE
    SYNTAX       CucsManagedObjectId
    MAX-ACCESS   not-accessible
    STATUS       current
    DESCRIPTION
        "Instance identifier of the managed object."
    ::= { cucsEquipmentXcvrEntry 1 }

cucsEquipmentXcvrDn OBJECT-TYPE
    SYNTAX       CucsManagedObjectDn
    MAX-ACCESS   read-only
    STATUS       current
    DESCRIPTION
        "Cisco UCS equipment:Xcvr:dn managed object property"
    ::= { cucsEquipmentXcvrEntry 2 }

cucsEquipmentXcvrRn OBJECT-TYPE
    SYNTAX       SnmpAdminString
    MAX-ACCESS   read-only
    STATUS       current
    DESCRIPTION
        "Cisco UCS equipment:Xcvr:rn managed object property"
    ::= { cucsEquipmentXcvrEntry 3 }

cucsEquipmentXcvrId OBJECT-TYPE
    SYNTAX       CucsEquipmentXcvrId
    MAX-ACCESS   read-only
    STATUS       current
    DESCRIPTION
        "Cisco UCS equipment:Xcvr:id managed object property"
    ::= { cucsEquipmentXcvrEntry 4 }

cucsEquipmentXcvrModel OBJECT-TYPE
    SYNTAX       SnmpAdminString
    MAX-ACCESS   read-only
    STATUS       current
    DESCRIPTION
        "Cisco UCS equipment:Xcvr:model managed object property"
    ::= { cucsEquipmentXcvrEntry 5 }

cucsEquipmentXcvrRevision OBJECT-TYPE
    SYNTAX       SnmpAdminString
    MAX-ACCESS   read-only
    STATUS       current
    DESCRIPTION
        "Cisco UCS equipment:Xcvr:revision managed object property"
    ::= { cucsEquipmentXcvrEntry 6 }

cucsEquipmentXcvrSerial OBJECT-TYPE
    SYNTAX       SnmpAdminString
    MAX-ACCESS   read-only
    STATUS       current
    DESCRIPTION
        "Cisco UCS equipment:Xcvr:serial managed object property"
    ::= { cucsEquipmentXcvrEntry 7 }

cucsEquipmentXcvrType OBJECT-TYPE
    SYNTAX       CucsEquipmentXcvrType
    MAX-ACCESS   read-only
    STATUS       current
    DESCRIPTION
        "Cisco UCS equipment:Xcvr:type managed object property"
    ::= { cucsEquipmentXcvrEntry 8 }

cucsEquipmentXcvrVendor OBJECT-TYPE
    SYNTAX       SnmpAdminString
    MAX-ACCESS   read-only
    STATUS       current
    DESCRIPTION
        "Cisco UCS equipment:Xcvr:vendor managed object property"
    ::= { cucsEquipmentXcvrEntry 9 }

cucsEquipmentXcvrTs OBJECT-TYPE
    SYNTAX       DateAndTime
    MAX-ACCESS   read-only
    STATUS       current
    DESCRIPTION
        "Cisco UCS equipment:Xcvr:ts managed object property"
    ::= { cucsEquipmentXcvrEntry 10 }

END
