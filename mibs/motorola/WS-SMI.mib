--
-- WS-SMI.my
-- MIB generated by MG-SOFT Visual MIB Builder Version 6.0  Build 88
-- Monday, March 02, 2009 at 17:12:06
--

	WS-SMI DEFINITIONS ::= BEGIN

		IMPORTS
			enterprises, MODULE-IDENTITY, OBJECT-IDENTITY
				FROM SNMPv2-SMI
			wirelessProducts, altitude4700
				FROM EXTREME-BASE-MIB;



--
-- Node definitions
--

		-- 1.3.6.1.4.1.1916.2.131.15
		wingSysoidWm3700 OBJECT-IDENTITY
			STATUS current
			DESCRIPTION
				"WM3700 system object identifier"
			::= { wirelessProducts 15 }


		-- 1.3.6.1.4.1.1916.2.131.16
		wingSysoidWm3600 OBJECT-IDENTITY
			STATUS current
			DESCRIPTION
				"WM3600 system object identifier."
			::= { wirelessProducts 16 }


		-- 1.3.6.1.4.1.1916.2.131.18
		wingSysoidWm3400 OBJECT-IDENTITY
			STATUS current
			DESCRIPTION
				"WM3400 system object identifier."
			::= { wirelessProducts 18 }


		-- 1.3.6.1.4.1.1916.2.158.1
		altitude4700Sysoids OBJECT IDENTIFIER ::= { altitude4700 1 }


		-- 1.3.6.1.4.1.1916.2.158.1.6
		wingSysoidAp4710 OBJECT-IDENTITY
			STATUS current
			DESCRIPTION
				"AP4710 system object identifier"
			::= { altitude4700Sysoids 6 }


		-- 1.3.6.1.4.1.1916.2.158.1.7
		wingSysoidAp4750 OBJECT-IDENTITY
			STATUS current
			DESCRIPTION
				"AP4750 system object identifier"
			::= { altitude4700Sysoids 7 }



	END

--
-- WS-SMI.my
--
