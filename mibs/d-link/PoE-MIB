-- *****************************************************************************
--  common MIB   POE module MIB    
-- *****************************************************************************
-- Version 1.5
-- 2007/3/14
-- define for DES3028(P)/DES3052(P) by Jenny Zeng/Chengdu.
-- Add swPoESystemLegacyPDState and swPoESystemLedMode
-- *****************************************************************************
--
-- Version 1.4 
-- 2006/1/16
-- modify INDEX of swPoEPortInfoEntry from swPoEPortCtrlPortIndex to swPoEPortInfoPortIndex
-- *****************************************************************************
-- Version 1.3 
-- 2005/12/1
-- modify  object swPoEPortCtrlPowerLimit and add object swPoEPortCtrlUserDefined 
-- requested by Dlink Alex Lin

-- *****************************************************************************
-- Version 1.2 
-- 2005/7/19 05:17
-- modify power limit from 372 to 370
-- requested by Dlink Alex Lin(Lloyd)
-- *****************************************************************************
-- Version 1.1 
-- 2005/7/13 03:09
-- add swpoEPortInfoLedStatus in swPoEPortInfoTable
-- *****************************************************************************
-- Version 1.0 
-- 2005/6/22 11:21
-- 
-- *****************************************************************************

PoE-MIB DEFINITIONS ::= BEGIN


    IMPORTS
        MODULE-IDENTITY,OBJECT-TYPE     FROM SNMPv2-SMI
    	SnmpAdminString					FROM SNMP-FRAMEWORK-MIB
        dlink-common-mgmt				FROM DLINK-ID-REC-MIB
        DisplayString                   FROM RFC1213-MIB;

    swPoEMIB MODULE-IDENTITY
	    LAST-UPDATED "0007150000Z"
	    ORGANIZATION " "
	    CONTACT-INFO
	        "    "
	    DESCRIPTION
		    "The Structure of PoE management for the
		    proprietary enterprise."
        ::= { dlink-common-mgmt 24 }


	swPoESystemCtrl             OBJECT IDENTIFIER ::= { swPoEMIB 1 }
	swPoESystemInfo             OBJECT IDENTIFIER ::= { swPoEMIB 2 }
	swPoEPortCtrl               OBJECT IDENTIFIER ::= { swPoEMIB 3 }
	swPoEPortInfo               OBJECT IDENTIFIER ::= { swPoEMIB 4 }

-- ********************************************************************
--  swPoESystemCtrl             OBJECT IDENTIFIER ::= { PoEMIB 1 }
-- ********************************************************************
	swPoESystemPowerLimit OBJECT-TYPE
        SYNTAX  INTEGER(37..370)
        MAX-ACCESS  read-write
        STATUS  current
        DESCRIPTION
            "The power budget(in watts) of PoE sytem. Default setting is 370 W."
        ::= { swPoESystemCtrl 1 }

	swPoESystemPowerDisconnectMethod OBJECT-TYPE
		SYNTAX		INTEGER{
						denyNextPort(1),
						denyLowPriorityPort(2)
						}
        MAX-ACCESS  read-write
        STATUS  current
        DESCRIPTION
            "The power management disconnection method. When the total consumed power
            exceeds the power budget, the PoE controller initiates ports disconnection,
            to prevent overloading the power supply. The controller uses one of the
            following two ways to implement the disconnection.
            deny_next_port : 
            after the power budget has been exceeded, the next port
            attempting to power up is denied, regardless of its priority.
            deny_low_priority_port :
            after the power budget has been exceeded, the next
            port attempting to power up, causes the port with the lowest priority to
            shut down, to allow high-priority ports to power up.
            Default setting is deny_next_port."
        ::= { swPoESystemCtrl 2 }

--	swPoESystemManagementMode OBJECT-TYPE
--	SYNTAX	INTEGER{
--		power-limit(1),
--		auto(2)
--		}
--        MAX-ACCESS  read-write
--        STATUS  current
--        DESCRIPTION
--            "This mode can be either power_limit mode or auto mode.
--	     power_limit: If power supplied to the port exceeds the power limit
--		specified for it, this port will be shut down.
--	     auto: The system will automatically determine the PD class of the
--		device connected to the port in the first stage. Normally, the PD
--		can be classified as class 1, 2, or 3. If the PD can not be classified,
--		it will be classified as class 0. For class 0, it will assume that the PD
--		may consume the max power allowed. At the power feeding stage, if the power
--		supplied to the port exceeds the upper limit of the detected PD class, this
--		port will be shut down. For the upper limit for each class, it is 4W for
--		class 1 PD class, 7W for class 2, and 15.4W for class 3 PD and class 0 PD."
--        ::= { swPoESystemCtrl 3 }
        
        swPoESystemLedMode OBJECT-TYPE
	 SYNTAX INTEGER{
	 		normal(1),
	 		poe(2)
	 		}
	 MAX-ACCESS read-write
	 STATUS current
	 DESCRIPTION
	 	""
	 ::= { swPoESystemCtrl 4 }
	 
	 swPoESystemLegacyPDState OBJECT-TYPE
        	SYNTAX		INTEGER {
        					enabled(1),
        					disabled(2)
        			}
        	MAX-ACCESS	read-write
        	STATUS		current
        	DESCRIPTION
        		"Specifies the detection for legacy PDs to be disabled or enabled."
        	::= { swPoESystemCtrl 5 }
	 
-- ********************************************************************
--  swPoESystemInfo             OBJECT IDENTIFIER ::= { PoEMIB 2 }
-- ********************************************************************


	swPoESystemPowerConsumption OBJECT-TYPE
        SYNTAX  INTEGER (0..370)
        MAX-ACCESS  read-only
        STATUS  current
        DESCRIPTION
            "The actual momentary power consumption(in watts) in PoE system."
        ::= { swPoESystemInfo 1 }

	swPoESystemPowerRemained OBJECT-TYPE
        SYNTAX  INTEGER (0..370)
        MAX-ACCESS  read-only
        STATUS  current
        DESCRIPTION
            "The actual momentary remaining power(in watts) in PoE system."
        ::= { swPoESystemInfo 2 }

-- ********************************************************************
--  swPoEPortCtrl             OBJECT IDENTIFIER ::= { PoEMIB 3 }
-- ********************************************************************

	swPoEPortCtrlTable OBJECT-TYPE
		SYNTAX		SEQUENCE OF SwPoEPortCtrlEntry
		MAX-ACCESS  not-accessible
		STATUS		current
		DESCRIPTION
		      "A table that contains PoE configuration about every port."
		::= { swPoEPortCtrl 1 }

	swPoEPortCtrlEntry OBJECT-TYPE
		SYNTAX		SwPoEPortCtrlEntry
		MAX-ACCESS  not-accessible
		STATUS		current
		DESCRIPTION
		      "A list of PoE configuration for each port of the device."
		INDEX { swPoEPortCtrlPortIndex }
		::= { swPoEPortCtrlTable 1 }

	SwPoEPortCtrlEntry ::=
        SEQUENCE {
            swPoEPortCtrlPortIndex
                INTEGER,
			swPoEPortCtrlState
				INTEGER,
			swPoEPortCtrlPriority
			    INTEGER,
			swPoEPortCtrlPowerLimit
			    INTEGER,
			swPoEPortCtrlUserDefined
			    INTEGER
       }

	swPoEPortCtrlPortIndex OBJECT-TYPE
		SYNTAX		INTEGER(0..65535)
		MAX-ACCESS	read-only
		STATUS		current
		DESCRIPTION
			"This object indicates the module's port number.(1..Max port
			 number in the base module)."
		::= { swPoEPortCtrlEntry 1 }

	swPoEPortCtrlState OBJECT-TYPE
		SYNTAX		INTEGER{
						other(1),
						enable(2),
						disable(3)
						}
		MAX-ACCESS	read-write
		STATUS		current
		DESCRIPTION
			"The PoE port state. Enable or disable the PoE function on the specific port.
			Default setting is enable."
		::= { swPoEPortCtrlEntry 2 }

	swPoEPortCtrlPriority OBJECT-TYPE
		SYNTAX		INTEGER{
						critical(1),
						high(2),
						low(3)
						}
		MAX-ACCESS	read-write
		STATUS		current
		DESCRIPTION
			"The PoE port priority. Port priority affects power-up order(after a
			rest, the ports are powered up according to their priority) and shutdown
			order(when exceeding the power budget, the ports are shut down according
			to their priority if power_disconnect_method is set to deny_low_priority_port)
            Default setting is low."
		::= { swPoEPortCtrlEntry 3 }

	swPoEPortCtrlPowerLimit OBJECT-TYPE
		SYNTAX		INTEGER{			
					 class0(1),
					 class1(2),
					 class2(3),
					 class3(4),
					 user-defined(5)}
		MAX-ACCESS	read-write
		STATUS		current
		DESCRIPTION
			"There are 4 pre-defined values for users' convenience to set the upper 
			 power limit for class 0, class 1, class 2, class3
			 cass_0 : 15400mW (The maximum power provided by PSE(switch) is 12.95 W + power loss on cable)
			 cass_1 : 4000mW (The maximum power provided by PSE is 3.84 W + power loss on cable)
			 cass_2 : 7000mW (The maximum power provided by PSE is 6.49 W + power loss on cable)
			 case_3 : 15400mW (The maximum power provided by PSE is 12.95 W + power loss on cable)
			 user-defined : User can select this setting and configure the range in  swPoEPortCtrlUserDefined."               			
		::= { swPoEPortCtrlEntry 4 }
		
	swPoEPortCtrlUserDefined OBJECT-TYPE
		SYNTAX		INTEGER(1000..16800)
		MAX-ACCESS	read-write
		STATUS		current
		DESCRIPTION
			"User define per-port power limit(in milliwatts). If a port exceeds 10% of its power
			limit, the PoE system will shuts down that port. Default setting is 15400 mW.
			Note : this object is valid only while the swPoEPortCtrlPowerLimit object is configured as 
			user-defined ."
		::= { swPoEPortCtrlEntry 5 }		

-- ********************************************************************
--  swPoEPortInfo             OBJECT IDENTIFIER ::= { PoEMIB 4 }
-- ********************************************************************

	swPoEPortInfoTable OBJECT-TYPE
		SYNTAX		SEQUENCE OF SwPoEPortInfoEntry
		MAX-ACCESS  not-accessible
		STATUS		current
		DESCRIPTION
		      "A table that contains PoE monitoring information about every port."
		::= { swPoEPortInfo 1 }

	swPoEPortInfoEntry OBJECT-TYPE
		SYNTAX		SwPoEPortInfoEntry
		MAX-ACCESS  not-accessible
		STATUS		current
		DESCRIPTION
		      "A list of PoE information for each port of the device."
		INDEX { swPoEPortInfoPortIndex }
		::= { swPoEPortInfoTable 1 }

	SwPoEPortInfoEntry ::=
        SEQUENCE {
            swPoEPortInfoPortIndex
                INTEGER,
			swPoEPortInfoClass
				INTEGER,
			swPoEPortInfoPower
			    INTEGER,
			swPoEPortInfoVoltage
			    INTEGER,
			swPoEPortInfoCurrent
			    INTEGER,
			swPoEPortInfoStatus
				DisplayString,
		    	swpoEPortInfoLedStatus
		        	INTEGER
       }
	swPoEPortInfoPortIndex OBJECT-TYPE
		SYNTAX		INTEGER(0..65535)
		MAX-ACCESS	read-only
		STATUS		current
		DESCRIPTION
			"This object indicates the module's port number.(1..Max port
			 number in the base module)."
		::= { swPoEPortInfoEntry 1 }

	swPoEPortInfoClass OBJECT-TYPE
		SYNTAX		INTEGER (0..4)
		MAX-ACCESS	read-only
		STATUS		current
		DESCRIPTION
			"The actual power class of the PD according 802.3af definitions :
			class 0 : PD power consumption is within 0.44-12.95 watts ,
			class 1 : PD power consumption is within 0.44-3.84 watts ,
			class 2 : PD power consumption is within 3.84-6.49 watts ,
			class 3 : PD power consumption is within 6.49-12.95 watts ,
			class 4 : is reserved for future use."
		::= { swPoEPortInfoEntry 2 }

	swPoEPortInfoPower OBJECT-TYPE
		SYNTAX		INTEGER
		MAX-ACCESS	read-only
		STATUS		current
		DESCRIPTION
			"The actual port power consumption(in milliwatts)."
		::= { swPoEPortInfoEntry 3 }

	swPoEPortInfoVoltage OBJECT-TYPE
		SYNTAX		INTEGER
		MAX-ACCESS	read-only
		STATUS		current
		DESCRIPTION
			"The actual port momentary input line voltage(in decivolts)."
		::= { swPoEPortInfoEntry 4 }

	swPoEPortInfoCurrent OBJECT-TYPE
		SYNTAX		INTEGER
		MAX-ACCESS	read-only
		STATUS		current
		DESCRIPTION
			"The actual port momentary calculated currently(in milliamps)."
		::= { swPoEPortInfoEntry 5 }

	swPoEPortInfoStatus OBJECT-TYPE
		SYNTAX		DisplayString (SIZE (0..76))
		MAX-ACCESS	read-only
		STATUS		current
		DESCRIPTION
			"The string describe the actual PoE port current status."
		::= { swPoEPortInfoEntry 6 }

    swpoEPortInfoLedStatus  OBJECT-TYPE
        SYNTAX      INTEGER{
						on(1),
						off(2),
						error(3)
						}
		MAX-ACCESS	read-only
		STATUS		current
		DESCRIPTION
			"The Led display for PoE port status.
			on(1)   : power is provided to the port on which a 802.3af-compliant
			          or legacy PD which is connected,
			off(2)  : no power is provided to the port on which no error happens,
			error(3): some error happens on the port, like overload, underload, 
			          short,...or power budget exceeded conditions."
		::= { swPoEPortInfoEntry 7 }

END
