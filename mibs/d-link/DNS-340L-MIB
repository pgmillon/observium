--
-- DNS-340L.mib
--

-- Copyright (c) 2013 alphanetworks Inc.,
-- Module Name: DNS-340L.mib
-- Abstract:
-- Defines the DNS-340L NAS MIBs .
--

	DNS-340L-MIB DEFINITIONS ::= BEGIN


	IMPORTS
		OBJECT-TYPE, Integer32, enterprises,
		NOTIFICATION-TYPE
			FROM SNMPv2-SMI
		DisplayString
			FROM SNMPv2-TC;

--
--  OID definitions
--

	d-link		OBJECT IDENTIFIER ::= { enterprises 171}
	productID	OBJECT IDENTIFIER ::= { d-link 50}
	projectID	OBJECT IDENTIFIER ::= { productID 1}
	modelID 	OBJECT IDENTIFIER ::= { projectID 10}
	submodelID	OBJECT IDENTIFIER ::= { modelID 1}
	nasAgent	OBJECT IDENTIFIER ::= { submodelID 1}


--
-- Node definitions
--
			dns340LAgentVer OBJECT-TYPE
				SYNTAX DisplayString
				MAX-ACCESS read-only
				STATUS current
				DESCRIPTION
					"Version information for the agent of SNMP of DNS-340L."
				::= { nasAgent 1 }

-- ============================================================================

--
-- system information definitions
--
			dns340LSoftwareVersion OBJECT-TYPE
				SYNTAX DisplayString
				MAX-ACCESS read-only
				STATUS current
				DESCRIPTION
					"The device software version."
				::= { nasAgent 2 }

			dns340LHostName OBJECT-TYPE
				SYNTAX DisplayString
				MAX-ACCESS read-only
				STATUS current
				DESCRIPTION
					"The device host name."
				::= { nasAgent 3 }


			dns340LFTPServer OBJECT-TYPE
				SYNTAX DisplayString
				MAX-ACCESS read-only
				STATUS current
				DESCRIPTION
					"Ftp Server status.
					(Disable/Enable)"
				::= { nasAgent 5 }

			dns340LNetType OBJECT-TYPE
				SYNTAX DisplayString
				MAX-ACCESS read-only
				STATUS current
				DESCRIPTION
					"The Network type.
					(Workgroup/Active Directory)"
				::= { nasAgent 6 }

			dns340LTemperature OBJECT-TYPE
				SYNTAX DisplayString
				MAX-ACCESS read-only
				STATUS current
				DESCRIPTION
					"The temperature of the system."
				::= { nasAgent 7 }

			dns340LFanStatus OBJECT-TYPE
				SYNTAX DisplayString
				MAX-ACCESS read-only
				STATUS current
				DESCRIPTION
					"The status of the fan"
				::= { nasAgent 8 }

-- ============================================================================

			dns340LVolumeTable OBJECT-TYPE
			SYNTAX SEQUENCE OF Dns340LVolumeEntry
			MAX-ACCESS not-accessible
			STATUS current
			DESCRIPTION
				"A table of active volumes on the NAS device."
			::= { nasAgent 9 }

			dns340LVolumeEntry OBJECT-TYPE
			SYNTAX Dns340LVolumeEntry
			MAX-ACCESS not-accessible
			STATUS current
			DESCRIPTION
				"An entry in the volume table."
			INDEX { dns340LVolumeNum }
			::= { dns340LVolumeTable 1 }

			Dns340LVolumeEntry ::=
			SEQUENCE {
				dns340LVolumeNum
					Integer32,
				dns340LVolumeName
					DisplayString,
				dns340LVolumeFsType
					DisplayString,
				dns340LVolumeRaidLevel
					DisplayString,
				dns340LVolumeSize
					DisplayString,
				dns340LVolumeFreeSpace
					DisplayString
			 }

			dns340LVolumeNum OBJECT-TYPE
			SYNTAX Integer32
			MAX-ACCESS read-only
			STATUS current
			DESCRIPTION
				"Instance number of the volume entry."
			::= { dns340LVolumeEntry 1 }

			dns340LVolumeName OBJECT-TYPE
			SYNTAX DisplayString
			MAX-ACCESS read-only
			STATUS current
			DESCRIPTION
				"The name of the volume."
			::= { dns340LVolumeEntry 2 }

			dns340LVolumeFsType OBJECT-TYPE
			SYNTAX DisplayString
			MAX-ACCESS read-only
			STATUS current
			DESCRIPTION
				"The type of file system of the volume.
				Example : ext3 or ext4"
			::= { dns340LVolumeEntry 3 }

			dns340LVolumeRaidLevel OBJECT-TYPE
			SYNTAX DisplayString
			MAX-ACCESS read-only
			STATUS current
			DESCRIPTION
				"The RAID level of the volume. (STANDARD LINEAR RAID0 RAID1 RAID5 RAID10 RAID5+SPARE)"
			::= { dns340LVolumeEntry 4 }

			dns340LVolumeSize OBJECT-TYPE
			SYNTAX DisplayString
			MAX-ACCESS read-only
			STATUS current
			DESCRIPTION
				"The size of the volume in bytes."
			::= { dns340LVolumeEntry 5 }

			dns340LVolumeFreeSpace OBJECT-TYPE
			SYNTAX DisplayString
			MAX-ACCESS read-only
			STATUS current
			DESCRIPTION
				"Free space on the volume in bytes."
			::= { dns340LVolumeEntry 6 }

-- ============================================================================

		dns340LDiskTable OBJECT-TYPE
			SYNTAX SEQUENCE OF Dns340LDiskEntry
			MAX-ACCESS not-accessible
			STATUS current
			DESCRIPTION
				"A table of physical disks attached to the NAS device."
			::= { nasAgent 10 }

		dns340LDiskEntry OBJECT-TYPE
			SYNTAX Dns340LDiskEntry
			MAX-ACCESS not-accessible
			STATUS current
			DESCRIPTION
				"An entry in the physical disk table."
			INDEX { dns340LDiskNum }
			::= { dns340LDiskTable 1 }

		Dns340LDiskEntry ::=
			SEQUENCE {
				dns340LDiskNum
					Integer32,
				dns340LDiskVendor
					DisplayString,
				dns340LDiskModel
					DisplayString,
				dns340LDiskSerialNumber
					DisplayString,
        		dns340LDiskTemperature
					DisplayString,
				dns340LDiskCapacity
					DisplayString
			 }

		dns340LDiskNum OBJECT-TYPE
			SYNTAX Integer32
			MAX-ACCESS read-only
			STATUS current
			DESCRIPTION
				"Instance number of the disk entry."
			::= { dns340LDiskEntry 1 }

		dns340LDiskVendor OBJECT-TYPE
			SYNTAX DisplayString
			MAX-ACCESS read-only
			STATUS current
			DESCRIPTION
				"The vendor of the disk drive."
			::= { dns340LDiskEntry 2 }

		dns340LDiskModel OBJECT-TYPE
			SYNTAX DisplayString
			MAX-ACCESS read-only
			STATUS current
			DESCRIPTION
				"The disk drive's model name."
			::= { dns340LDiskEntry 3 }

		dns340LDiskSerialNumber OBJECT-TYPE
			SYNTAX DisplayString
			MAX-ACCESS read-only
			STATUS current
			DESCRIPTION
				"The disk drive's serial number."
			::= { dns340LDiskEntry 4 }

		dns340LDiskTemperature OBJECT-TYPE
			SYNTAX DisplayString
			MAX-ACCESS read-only
			STATUS current
			DESCRIPTION
				"The centigrade temperature of this disk."
			::= { dns340LDiskEntry 5 }

		dns340LDiskCapacity OBJECT-TYPE
			SYNTAX DisplayString
			MAX-ACCESS read-only
			STATUS current
			DESCRIPTION
				"The capacity of the disk in GB."
			::= { dns340LDiskEntry 6 }


-- ============================================================================

		dns340LUPSTable OBJECT-TYPE
			SYNTAX SEQUENCE OF Dns340LUPSEntry
			MAX-ACCESS not-accessible
			STATUS current
			DESCRIPTION
				"A table of UPS attached to the NAS device."
			::= { nasAgent 11 }

		dns340LUPSEntry OBJECT-TYPE
			SYNTAX Dns340LUPSEntry
			MAX-ACCESS not-accessible
			STATUS current
			DESCRIPTION
				"An entry in the UPS table."
			INDEX { dns340LUPSNum }
			::= { dns340LUPSTable 1 }

		Dns340LUPSEntry ::=
			SEQUENCE {
				dns340LUPSNum
					Integer32,
				dns340LUPSMode
					DisplayString,
				dns340LUPSManufacturer
					DisplayString,
				dns340LUPSProduct
					DisplayString,
				dns340LUPSBatteryCharge
					DisplayString,
				dns340LUPSStatus
					DisplayString,
			 }

		dns340LUPSNum OBJECT-TYPE
			SYNTAX Integer32
			MAX-ACCESS read-only
			STATUS current
			DESCRIPTION
				"Instance number of the UPS entry."
			::= { dns340LUPSEntry 1 }

		dns340LUPSMode OBJECT-TYPE
			SYNTAX DisplayString
			MAX-ACCESS read-only
			STATUS current
			DESCRIPTION
				"The mode of the UPS "
			::= { dns340LUPSEntry 2 }

		dns340LUPSManufacturer OBJECT-TYPE
			SYNTAX DisplayString
			MAX-ACCESS read-only
			STATUS current
			DESCRIPTION
				"The manufacturer of the UPS."
			::= { dns340LUPSEntry 3 }

		dns340LUPSProduct OBJECT-TYPE
			SYNTAX DisplayString
			MAX-ACCESS read-only
			STATUS current
			DESCRIPTION
				"The product name of the UPS."
			::= { dns340LUPSEntry 4 }

		dns340LUPSBatteryCharge OBJECT-TYPE
			SYNTAX DisplayString
			MAX-ACCESS read-only
			STATUS current
			DESCRIPTION
				"The battery charge of the UPS."
			::= { dns340LUPSEntry 5 }

		dns340LUPSStatus OBJECT-TYPE
			SYNTAX DisplayString
			MAX-ACCESS read-only
			STATUS current
			DESCRIPTION
				"The status of this UPS."
			::= { dns340LUPSEntry 6 }



-- ============================================================================
--
--  Notifications
--

	notifyEvts OBJECT IDENTIFIER ::= { nasAgent 200 }

	notifyPasswdChanged        NOTIFICATION-TYPE
    STATUS      current
    DESCRIPTION
        "An indication that the Administrator's password has been changed."
    ::= { notifyEvts 1 }

    notifyFirmwareUpgraded     NOTIFICATION-TYPE
    STATUS      current
    DESCRIPTION
        "An indication that firmware has been upgraded."
    ::= { notifyEvts 2 }

    notifyNetworkChanged        NOTIFICATION-TYPE
    STATUS      current
    DESCRIPTION
        "An indication that the network settings has been changed."
    ::= { notifyEvts 3 }

    notifyTemperatureExceeded        NOTIFICATION-TYPE
    STATUS      current
    DESCRIPTION
        "An indication that system temperature has exceeded."
    ::= { notifyEvts 4 }







--              ******************************************************

--              ******************************************************


	END

--
-- DNS-340L.mib
--
