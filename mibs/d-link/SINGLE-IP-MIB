-- SingleIP-MIB v 0.01  2003/7/14 03:22
-- --------------------------------------------------------------------------------------
-- Revision 0.02 2004/1/13
-- remove swSingleIPSetMSStatus object
-- --------------------------------------------------------------------------------------
-- Revision 0.03 2004/4/26 by Scott Sung for project-x
-- [1]Add singleIPMSNotify,singleIPMSNotifyPrefix,swSingleIPMSColdStart ... swSingleIPMSPowerRecover
-- [2]Add singleIPNotifyBidings
-- [3]Add swSingleIPNeighborTable
-- [4]modify swSingleIPMSID SYNTAX  INTEGER (1..32) ;swSingleIPCaSID SYNTAX  INTEGER (1..100)
-- [5]modify swSingleIPHoldtime DEFVAL { 100 } ; swSingleIPTimeInterval SYNTAX  INTEGER (30..90) 
--    DEFVAL { 30 }

-- -------------------------------------------------------------
SINGLE-IP-MIB DEFINITIONS ::= BEGIN


-- D-Link Common MIB   Single IP management module MIB      Ver 0.01

-- -------------------------------------------------------------
-- Single IP Management MIB
-- -------------------------------------------------------------


IMPORTS
 	IpAddress
 	    FROM RFC1155-SMI
    ifIndex
        FROM RFC1213-MIB
    MODULE-IDENTITY, OBJECT-TYPE
        FROM SNMPv2-SMI
    DisplayString ,MacAddress, RowStatus
            FROM SNMPv2-TC
    MODULE-COMPLIANCE, OBJECT-GROUP
        FROM SNMPv2-CONF

	dlink-common-mgmt	FROM DLINK-ID-REC-MIB;


swSingleIPMIB MODULE-IDENTITY
    LAST-UPDATED "9911220000Z"
    ORGANIZATION "Working Group"
    CONTACT-INFO
        "  "
    DESCRIPTION
        "The Single IP management MIB."
    ::= { dlink-common-mgmt 8}


swSingleIPMgmt OBJECT IDENTIFIER ::= { swSingleIPMIB 1 }

swSingleIPInfo OBJECT IDENTIFIER ::= { swSingleIPMgmt 1 }
swSingleIPCtrl OBJECT IDENTIFIER ::= { swSingleIPMgmt 2 }

-- swSingleIPMSTable OBJECT IDENTIFIER ::= { swSingleIPMgmt 3 }
-- swSingleIPCaSTable OBJECT IDENTIFIER ::= { swSingleIPMgmt 4 }
-- swSingleIPGroupTable OBJECT IDENTIFIER ::= { swSingleIPMgmt 5 }




-- -------------------------------------------------------------
-- swSingleIPInfo
-- -------------------------------------------------------------
        
 swSingleIPVersion OBJECT-TYPE
        SYNTAX  DisplayString  (SIZE (0..64))
        MAX-ACCESS  read-only
        STATUS  current
        DESCRIPTION
            "This object indicates the version of single IP management supported in the system."
        ::= { swSingleIPInfo 1}

 swSingleIPCapability OBJECT-TYPE
        SYNTAX  DisplayString  (SIZE (0..64))
        MAX-ACCESS  read-only
        STATUS  current
        DESCRIPTION
            "This object indicates the capability of the switch system."
        ::= { swSingleIPInfo 2}
        
 swSingleIPPlatform OBJECT-TYPE
        SYNTAX  DisplayString  (SIZE (0..64))
        MAX-ACCESS  read-only
        STATUS  current
        DESCRIPTION
            "This object indicates the platform of the switch system."
        ::= { swSingleIPInfo 3}
 
-- swSingleIPSetMSStatus OBJECT-TYPE
--        SYNTAX  INTEGER {
--        			other(0),
--                    set-as-ms-success(1),
--                    set-as-ms-fail(2),
--                    set-as-cas-success(3),
--                    set-as-cas-fail(4),
--                    password-invalid(5),
--                    community-invalid(6),
--                    updata-db-error(7),
--                    wait-ack(8)
--                }
--        MAX-ACCESS  read-only
--        STATUS  current
--        DESCRIPTION
--            "This object indicates the process status when set swSingleIPMSTable."
--        ::= { swSingleIPInfo 4}        
-- -------------------------------------------------------------
-- swSingleIPCtrl
-- -------------------------------------------------------------       

 swSingleIPAdmin OBJECT-TYPE
        SYNTAX  INTEGER {
                    other(1),
                    disabled(2),
                    enabled(3)
                }
        MAX-ACCESS  read-write
        STATUS  current
        DESCRIPTION
            "This object indicates Single IP management is enabled or disabled on the system."
        ::= { swSingleIPCtrl 1}
 
 swSingleIPRoleState OBJECT-TYPE
        SYNTAX  INTEGER {
                    cs(1),
                    cas(2),
                    ms(3)
                }
        MAX-ACCESS  read-write
        STATUS  current
        DESCRIPTION
            "This object indicates the role state of the switch system."
        ::= { swSingleIPCtrl 2}
                        
        
 swSingleIPHoldtime OBJECT-TYPE
        SYNTAX  INTEGER (100..255) 
        MAX-ACCESS  read-write
        STATUS  current
        DESCRIPTION
            "This object indicate the holdtime of the switch in second .
             default value is 180 , maximum value is 255 , minimum value is 100. 
			 "
        DEFVAL { 100 }
        ::= { swSingleIPCtrl 3 }        
        
 swSingleIPTimeInterval OBJECT-TYPE
        SYNTAX  INTEGER (30..90)
        MAX-ACCESS  read-write
        STATUS  current
        DESCRIPTION
            "This object indicate the time interval of the switch in second to periodical send out 
             Single IP protocol control packet.
             default value is 60 , maximum value is 120 , minimum value is 30  . 
             The swSingleIPTimeInterval will always <= swSingleIPHoldtime/2
			 "
        DEFVAL { 30 }
        ::= { swSingleIPCtrl 4 }           
        
-- -------------------------------------------------------------
-- swSingleIPMSTable
-- -------------------------------------------------------------           
      
    swSingleIPMSTable OBJECT-TYPE
        SYNTAX  SEQUENCE OF SwSingleIPMSEntry
        MAX-ACCESS  not-accessible
        STATUS  current
        DESCRIPTION
            "This table contain information of member switchs which belong to the 
            single IP management group  .
             A member will be joined into the group by row creation . Before a switch joined into
             a group as a member switch , it must exist in the candidate table list .  "
        ::= { swSingleIPMgmt 3 }
        
    swSingleIPMSEntry OBJECT-TYPE
        SYNTAX  SwSingleIPMSEntry 
        MAX-ACCESS  not-accessible
        STATUS  current
        DESCRIPTION
            "A list of information about member switchs belongs to the single IP management group."
        INDEX  { swSingleIPMSID }
        ::= { swSingleIPMSTable 1 }
      
    SwSingleIPMSEntry ::= 
        SEQUENCE {
            swSingleIPMSID
                INTEGER,
            swSingleIPMSDeviceName
                DisplayString,
            swSingleIPMSMacAddr
                MacAddress,
			swSingleIPMSFirmwareVer
                DisplayString,                
            swSingleIPMSCapability
                DisplayString,
            swSingleIPMSPlatform
                DisplayString,             
            swSingleIPMSHoldtime
                INTEGER,       
			swSingleIPMSCasSource
                INTEGER,       
			swSingleIPMSPassword
                OCTET STRING,       
            swSingleIPMSRowStatus
                RowStatus                                                         
        }
    swSingleIPMSID OBJECT-TYPE
        SYNTAX  INTEGER (1..32)
        MAX-ACCESS  read-only
        STATUS  current
        DESCRIPTION
            "The ID of the member switch ."
        ::= { swSingleIPMSEntry 1 }
    
    swSingleIPMSDeviceName OBJECT-TYPE
        SYNTAX  DisplayString (SIZE (0..64))
        MAX-ACCESS  read-only
        STATUS  current
        DESCRIPTION
            "Specifies that the name of switch ."
        ::= { swSingleIPMSEntry 2 }        
  
        
    swSingleIPMSMacAddr OBJECT-TYPE
        SYNTAX  MacAddress
        MAX-ACCESS  read-only
        STATUS  current
        DESCRIPTION
            "This object Specifies the MAC address of the member switch."
        ::= { swSingleIPMSEntry 3 }     
           
        
    swSingleIPMSFirmwareVer OBJECT-TYPE
        SYNTAX  DisplayString (SIZE (0..64))
        MAX-ACCESS  read-only
        STATUS  current
        DESCRIPTION
            "Specifies the firmware version of the switch ."
        ::= { swSingleIPMSEntry 4 }     
        
    swSingleIPMSCapability OBJECT-TYPE
        SYNTAX  DisplayString (SIZE (0..64))
        MAX-ACCESS  read-only
        STATUS  current
        DESCRIPTION
            "Specifies the Capability of the switch ."
        ::= { swSingleIPMSEntry 5 }     
        
    swSingleIPMSPlatform OBJECT-TYPE
        SYNTAX   DisplayString (SIZE (0..64))
        MAX-ACCESS  read-only
        STATUS  current
        DESCRIPTION
            "Specifies the platform of the switch ."
        ::= { swSingleIPMSEntry 6 }  
        
    swSingleIPMSHoldtime OBJECT-TYPE
        SYNTAX  INTEGER 
        MAX-ACCESS  read-only
        STATUS  current
        DESCRIPTION
            "Specifies the holdtime of Single IP management ptotocol send by  this member switch .
             " 
        ::= { swSingleIPMSEntry 7 }        
    
    swSingleIPMSCasSource OBJECT-TYPE
        SYNTAX  INTEGER 
        MAX-ACCESS  read-create
        STATUS  current
        DESCRIPTION
            "Specifies the CaS id when create MS entry. The object is used 
            only when create swSingleIPMSEntry. The value always shows 0." 
        ::= { swSingleIPMSEntry 8 }        
            
    swSingleIPMSPassword OBJECT-TYPE
        SYNTAX  OCTET STRING (SIZE (0..16))
        MAX-ACCESS  read-create
        STATUS  current
        DESCRIPTION
            "Specifies the Cas password when create MS entry. The object is used 
            only when create swSingleIPMSEntry. The value always shows zero length string."
        ::= { swSingleIPMSEntry 9}
                    
    swSingleIPMSRowStatus OBJECT-TYPE 
        SYNTAX  RowStatus
        MAX-ACCESS  read-create
        STATUS  current
        DESCRIPTION
            "This object indicates the status of this entry. 
            Create means set CaS to MS, and DESTROY means set MS to CaS"
        ::= { swSingleIPMSEntry 10 }                
        
-- -------------------------------------------------------------
-- swSingleIPCaSTable
-- -------------------------------------------------------------   
   swSingleIPCaSTable OBJECT-TYPE
        SYNTAX  SEQUENCE OF SwSingleIPCaSEntry
        MAX-ACCESS  not-accessible
        STATUS  current
        DESCRIPTION
            "This table contain information of candidate switchs.
             This table is a read only table list ,all information about candidate switchs will 
             maintain automatically by Single IP topology discovery protocol .  "
        ::= { swSingleIPMgmt 4 }
        
    swSingleIPCaSEntry OBJECT-TYPE
        SYNTAX  SwSingleIPCaSEntry 
        MAX-ACCESS  not-accessible
        STATUS  current
        DESCRIPTION
            "A list of information about candidate switchs belongs to the single IP management group."
        INDEX  { swSingleIPCaSID }
        ::= { swSingleIPCaSTable 1 }
      
    SwSingleIPCaSEntry ::= 
        SEQUENCE {
            swSingleIPCaSID
                INTEGER,
            swSingleIPCaSDeviceName
                DisplayString,
            swSingleIPCaSMacAddr
                MacAddress,
			swSingleIPCaSFirmwareVer
                DisplayString,                
            swSingleIPCaSCapability
                DisplayString,
            swSingleIPCaSPlatform
                DisplayString,             
            swSingleIPCaSHoldtime
                INTEGER
        }
    swSingleIPCaSID OBJECT-TYPE
        SYNTAX  INTEGER (1..100)
        MAX-ACCESS  read-only
        STATUS  current
        DESCRIPTION
            "The ID of the candidate switchs in the LAN learned by the command switch  ."
        ::= { swSingleIPCaSEntry 1 }
    
    swSingleIPCaSDeviceName OBJECT-TYPE
        SYNTAX  DisplayString (SIZE (0..64))
        MAX-ACCESS  read-only
        STATUS  current
        DESCRIPTION
            "Specifies that the name of switch ."
        ::= { swSingleIPCaSEntry 2 }        
  
        
    swSingleIPCaSMacAddr OBJECT-TYPE
        SYNTAX  MacAddress
        MAX-ACCESS  read-only
        STATUS  current
        DESCRIPTION
            "This object Specifies the MAC address of the candidate switch."
        ::= { swSingleIPCaSEntry 3 }     
           
        
    swSingleIPCaSFirmwareVer OBJECT-TYPE
        SYNTAX  DisplayString (SIZE (0..64))
        MAX-ACCESS  read-only
        STATUS  current
        DESCRIPTION
            "Specifies the firmware version of the switch ."
        ::= { swSingleIPCaSEntry 4 }     
        
    swSingleIPCaSCapability OBJECT-TYPE
        SYNTAX  DisplayString (SIZE (0..64))
        MAX-ACCESS  read-only
        STATUS  current
        DESCRIPTION
            "Specifies the Capability of the switch ."
        ::= { swSingleIPCaSEntry 5 }     
        
    swSingleIPCaSPlatform OBJECT-TYPE
        SYNTAX   DisplayString (SIZE (0..64))
        MAX-ACCESS  read-only
        STATUS  current
        DESCRIPTION
            "Specifies the platform of the switch ."
        ::= { swSingleIPCaSEntry 6 }  
        
    swSingleIPCaSHoldtime OBJECT-TYPE
        SYNTAX  INTEGER 
        MAX-ACCESS  read-only
        STATUS  current
        DESCRIPTION
            "Specifies the holdtime of Single IP management ptotocol send by  this candidate switch .
             " 
        ::= { swSingleIPCaSEntry 7 }        
        
                
-- -------------------------------------------------------------
-- swSingleIPGroupTable
-- -------------------------------------------------------------

   swSingleIPGroupTable OBJECT-TYPE
        SYNTAX  SEQUENCE OF SwSingleIPGroupEntry
        MAX-ACCESS  not-accessible
        STATUS  current
        DESCRIPTION
            "This table contain information of Single IP manaement groups learned by the Command 
             switch .
             This table is a read only table list ,all information about Single IP groups will 
             maintain automatically by Single IP topology discovery protocol .  "
        ::= { swSingleIPMgmt 5 }
        
    swSingleIPGroupEntry OBJECT-TYPE
        SYNTAX  SwSingleIPGroupEntry 
        MAX-ACCESS  not-accessible
        STATUS  current
        DESCRIPTION
            "A list of information about single IP management groups."
        INDEX  { swSingleIPGroupMacAddr }
        ::= { swSingleIPGroupTable 1 }
      
    SwSingleIPGroupEntry ::= 
        SEQUENCE {
            swSingleIPGroupMacAddr
                MacAddress,
            swSingleIPGroupName
                DisplayString,                             
            swSingleIPGroupDeviceName
                DisplayString,
            swSingleIPGroupMSNumber
                INTEGER,                    
			swSingleIPGroupFirmwareVer
                DisplayString,                
            swSingleIPGroupCapability
                DisplayString,
            swSingleIPGroupPlatform
                DisplayString,             
            swSingleIPGroupHoldtime
                INTEGER       
                                                      
        }
    
    swSingleIPGroupMacAddr OBJECT-TYPE
        SYNTAX  MacAddress
        MAX-ACCESS  read-only
        STATUS  current
        DESCRIPTION
            "This object Specifies the MAC address of the command switch."
        ::= { swSingleIPGroupEntry 1 }         
        
    swSingleIPGroupName OBJECT-TYPE
        SYNTAX  DisplayString (SIZE (0..64))
        MAX-ACCESS  read-only
        STATUS  current
        DESCRIPTION
            "Specifies that the name of the Single IP management group ."
        ::= { swSingleIPGroupEntry 2 }            
    
    swSingleIPGroupDeviceName OBJECT-TYPE
        SYNTAX  DisplayString (SIZE (0..64))
        MAX-ACCESS  read-only
        STATUS  current
        DESCRIPTION
            "Specifies that the name of command switch of the group ."
        ::= { swSingleIPGroupEntry 3 }        
                      
    swSingleIPGroupMSNumber OBJECT-TYPE
        SYNTAX  INTEGER 
        MAX-ACCESS  read-only
        STATUS  current
        DESCRIPTION
            "Specifies the member switch number of the group .
             " 
        ::= { swSingleIPGroupEntry 4 }     

        
    swSingleIPGroupFirmwareVer OBJECT-TYPE
        SYNTAX  DisplayString (SIZE (0..64))
        MAX-ACCESS  read-only
        STATUS  current
        DESCRIPTION
            "Specifies the firmware version of the switch ."
        ::= { swSingleIPGroupEntry 5 }   
          
        
    swSingleIPGroupCapability OBJECT-TYPE
        SYNTAX  DisplayString (SIZE (0..64))
        MAX-ACCESS  read-only
        STATUS  current
        DESCRIPTION
            "Specifies the Capability of the switch ."
        ::= { swSingleIPGroupEntry 6 }     
        
    swSingleIPGroupPlatform OBJECT-TYPE
        SYNTAX   DisplayString (SIZE (0..64))
        MAX-ACCESS  read-only
        STATUS  current
        DESCRIPTION
            "Specifies the platform of the switch ."
        ::= { swSingleIPGroupEntry 7 }  
        
    swSingleIPGroupHoldtime OBJECT-TYPE
        SYNTAX  INTEGER 
        MAX-ACCESS  read-only
        STATUS  current
        DESCRIPTION
            "Specifies the holdtime of Single IP management ptotocol send by  this command switch .
             " 
        ::= { swSingleIPGroupEntry 8 }        

-- -------------------------------------------------------------
-- swSingleIPNeighborTable
-- -------------------------------------------------------------

   swSingleIPNeighborTable OBJECT-TYPE
        SYNTAX  SEQUENCE OF SwSingleIPNeighborEntry
        MAX-ACCESS  not-accessible
        STATUS  current
        DESCRIPTION
            "This table contain information of Single IP manaement Neighbors learned by the switch .
             This table is a read only table list ,all information about Single IP Neighbors will 
             maintain automatically by Single IP topology protocol .  "
        ::= { swSingleIPMgmt 6 }
        
    swSingleIPNeighborEntry OBJECT-TYPE
        SYNTAX  SwSingleIPNeighborEntry 
        MAX-ACCESS  not-accessible
        STATUS  current
        DESCRIPTION
            "A list of information about single IP management Neighbors."
        INDEX  { swSingleIPNBReceivedPort,swSingleIPNBMacAddr }
        ::= { swSingleIPNeighborTable 1 }
      
    SwSingleIPNeighborEntry ::= 
        SEQUENCE {
        	swSingleIPNBReceivedPort
        		INTEGER, 
            swSingleIPNBMacAddr
                MacAddress,
            swSingleIPNBRoleState
                INTEGER                                                                      
        }
    
    swSingleIPNBReceivedPort OBJECT-TYPE
        SYNTAX  INTEGER 
        MAX-ACCESS  read-only
        STATUS  current
        DESCRIPTION
            "Specifies the received port of the Neighbor switch." 
        ::= { swSingleIPNeighborEntry 1 }         
    
    swSingleIPNBMacAddr OBJECT-TYPE
        SYNTAX  MacAddress
        MAX-ACCESS  read-only
        STATUS  current
        DESCRIPTION
            "This object Specifies the MAC address of the Neighbor switch."
        ::= { swSingleIPNeighborEntry 2 }         
                            
    swSingleIPNBRoleState OBJECT-TYPE
        SYNTAX  INTEGER {
                    commander(1),
                    candidate(2),
                    member(3)
                }
        MAX-ACCESS  read-only
        STATUS  current
        DESCRIPTION
            "This object Specifies the role state of the Neighbor switch." 
        ::= { swSingleIPNeighborEntry 3 }     

     -- Traps for use by SIM
      singleIPMSNotify OBJECT IDENTIFIER ::= {swSingleIPMIB 6}          
    
      singleIPMSNotifyPrefix OBJECT IDENTIFIER ::= {singleIPMSNotify 0}    
      swSingleIPMSColdStart NOTIFICATION-TYPE
          OBJECTS { swSingleIPMSID, swSingleIPMSMacAddr }
          STATUS  current 
          DESCRIPTION
                  "Commander switch will send swSingleIPMSColdStart notification to indicated
                   host when its Member generate cold start notification."
          ::= { singleIPMSNotifyPrefix 11 }

      swSingleIPMSWarmStart NOTIFICATION-TYPE
          OBJECTS { swSingleIPMSID, swSingleIPMSMacAddr }
          STATUS  current 
          DESCRIPTION
                  "Commander switch will send swSingleIPMSWarmStart notification to indicated
                   host when its Member generate warm start notification."
          ::= { singleIPMSNotifyPrefix 12 }                

      swSingleIPMSLinkDown NOTIFICATION-TYPE
          OBJECTS {  swSingleIPMSID, swSingleIPMSMacAddr,ifIndex }
          STATUS  current 
          DESCRIPTION
                  "Commander switch will send swSingleIPMSLinkDown notification to indicated
                   host when its Member generate link down notification."
          ::= { singleIPMSNotifyPrefix 13 }

      swSingleIPMSLinkUp NOTIFICATION-TYPE
          OBJECTS {  swSingleIPMSID, swSingleIPMSMacAddr,ifIndex }
          STATUS  current 
          DESCRIPTION
                  "If Commander switch will send swSingleIPMSLinkUp notification to indicated
                   host when its Member generate link up notification."
          ::= { singleIPMSNotifyPrefix 14 }               

      swSingleIPMSAuthFail NOTIFICATION-TYPE
          OBJECTS { swSingleIPMSID, swSingleIPMSMacAddr }
          STATUS  current 
          DESCRIPTION
                  "Commander switch will send swSingleIPMSAuthFail notification to indicated 
                  host when it Member generate authentation failure notification."
          ::= { singleIPMSNotifyPrefix 15 }    
          
      swSingleIPMSnewRoot NOTIFICATION-TYPE
          OBJECTS { swSingleIPMSID, swSingleIPMSMacAddr }
          STATUS  current 
          DESCRIPTION
                  "Commander switch will send swSingleIPMSnewRoot notification to indicated 
                  host when it Member generate new root notification."
          ::= { singleIPMSNotifyPrefix 16 }
          
      swSingleIPMSTopologyChange NOTIFICATION-TYPE
          OBJECTS { swSingleIPMSID, swSingleIPMSMacAddr }
          STATUS  current 
          DESCRIPTION
                  "Commander switch will send swSingleIPMSTopologyChange notification to 
                   indicated host when it Member generate topology chnage notification."
          ::= { singleIPMSNotifyPrefix 17 } 
          
      swSingleIPMSrisingAlarm NOTIFICATION-TYPE
          OBJECTS { swSingleIPMSID, swSingleIPMSMacAddr }
          STATUS  current 
          DESCRIPTION
                  "Commander switch will send swSingleIPMSrisingAlarm notification to 
                   indicated host when it Member generate rising Alarm notification."
          ::= { singleIPMSNotifyPrefix 18 } 
          
      swSingleIPMSfallingAlarm NOTIFICATION-TYPE
          OBJECTS { swSingleIPMSID,swSingleIPMSMacAddr }
          STATUS  current 
          DESCRIPTION
                  "Commander switch will send swSingleIPMSfallingAlarm notification to
                   indicated host when it Member generate falling Alarm notification."
          ::= { singleIPMSNotifyPrefix 19 }  
          
      swSingleIPMSmacNotification NOTIFICATION-TYPE
        OBJECTS { swSingleIPMSID,swSingleIPMSMacAddr,swSingleIPMSTrapMessage }
        STATUS  current        		
        DESCRIPTION
                  "Commander switch will send swSingleIPMSmacNotification notification to 
                   indicated host when it Member generate mac addresses variation notification."

		::= { singleIPMSNotifyPrefix 20}                          

	  swSingleIPMSPortTypeChange NOTIFICATION-TYPE
        OBJECTS { swSingleIPMSID,swSingleIPMSMacAddr,ifIndex,swSingleIPMSTrapMessage }
        STATUS  current        		
        DESCRIPTION
                  "Commander switch will send swSingleIPMSPortTypeChange notification to 
                   indicated host when it Member generate port type change notification."

		::= { singleIPMSNotifyPrefix 21 }                     
		
      swSingleIPMSPowerStatusChg  NOTIFICATION-TYPE
        OBJECTS { swSingleIPMSID,swSingleIPMSMacAddr,swSingleIPMSTrapMessage }
        STATUS          current
        DESCRIPTION     
                  "Commander switch will send swSingleIPMSPowerStatusChg notification to 
                   indicated host when it Member generate Power Status change notification."
        ::= { singleIPMSNotifyPrefix  22 }  


      swSingleIPMSPowerFailure  NOTIFICATION-TYPE
        OBJECTS { swSingleIPMSID,swSingleIPMSMacAddr,swSingleIPMSTrapMessage }
        STATUS          current
        DESCRIPTION     
                  "Commander switch will send swSingleIPMSPowerFailure notification to indicated
                   host when it Member generate Power Failure notification."
        ::= { singleIPMSNotifyPrefix  23 }  
        
      swSingleIPMSPowerRecover NOTIFICATION-TYPE
        OBJECTS { swSingleIPMSID,swSingleIPMSMacAddr,swSingleIPMSTrapMessage }
        STATUS          current
        DESCRIPTION     
                  "Commander switch will send swSingleIPMSPowerRecover notification to indicated 
                  host when it Member generate Power Recover notification."
        ::= { singleIPMSNotifyPrefix  24 }        	
-- -------------------------------------------------------------------------------------
-- ******************************************************************************************	
--	notificationBidings
-- ******************************************************************************************        		 
	 
    singleIPNotifyBidings OBJECT IDENTIFIER ::= { singleIPMSNotify 1 }
                
    swSingleIPMSTrapMessage OBJECT-TYPE
        SYNTAX     OCTET STRING(SIZE (0..1024))
        MAX-ACCESS read-only
        STATUS     current
        DESCRIPTION
            "The string that member switch sent."
        ::= { singleIPNotifyBidings 1 }                          
        
END
