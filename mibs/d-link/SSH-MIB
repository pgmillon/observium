-- SSH mib
-- ----------------------------------------------------------------------------
-- Draft Ver 0.2 2004/4/2 05:18下午 by yedda Liao
-- [1]add swSSHMaxSession,swSSHConnectionTimeout,swSSHListenedPort
-- [2]remove swSSHKeyExDAdmin
-- ----------------------------------------------------------------------------
-- SSH-MIB v 0.01  2003/1/13 03:50下午






SSH-MIB DEFINITIONS ::= BEGIN


-- D-Link Common MIB   SSH module MIB      Ver 1.1

-- ----------------------------------------------------------------------------
-- SSH System Access Control MIB
-- ----------------------------------------------------------------------------


IMPORTS
 	IpAddress
 	    FROM RFC1155-SMI
    MODULE-IDENTITY, OBJECT-TYPE
        FROM SNMPv2-SMI
    RowStatus,DisplayString
            FROM SNMPv2-TC
    MODULE-COMPLIANCE, OBJECT-GROUP
        FROM SNMPv2-CONF

	dlink-common-mgmt	FROM DLINK-ID-REC-MIB;


swSSHMIB MODULE-IDENTITY
    LAST-UPDATED "9911220000Z"
    ORGANIZATION "Working Group"
    CONTACT-INFO
        "  "
    DESCRIPTION
        "The D-Link Secure Shell module MIB."
    ::= { dlink-common-mgmt 6}

swSSHMgmt OBJECT IDENTIFIER ::= { swSSHMIB 1 }

-- ----------------------------------------------------------------------------
-- Textual Conventions
-- ----------------------------------------------------------------------------

 swSSHVersion OBJECT-TYPE
        SYNTAX  INTEGER(1..10)
        MAX-ACCESS  read-only
        STATUS  current
        DESCRIPTION
            "This object indicates the SSH version supported in the system."
        ::= { swSSHMgmt 1}

 swSSHAdmin OBJECT-TYPE
        SYNTAX  INTEGER {
                    other(1),
                    disabled(2),
                    enabled(3)
                }
        MAX-ACCESS  read-write
        STATUS  current
        DESCRIPTION
            "This object indicates the Secure Shell is enable or disable."
        ::= { swSSHMgmt 2}

 swSSHMaxAuthFailAttempts OBJECT-TYPE
        SYNTAX  INTEGER (1..99)
        MAX-ACCESS  read-write
        STATUS  current
        DESCRIPTION
            "This object indicates the tolerance in times of Authentication failure."
        ::= { swSSHMgmt 3}
 swSSHSessionKeyRekeying OBJECT-TYPE
        SYNTAX  INTEGER {
                        never(0),
                        ten-min(10),
                        thirty-min(30),
                        sixty-min(60)
                       }
        MAX-ACCESS  read-write
        STATUS  current
        DESCRIPTION
            "This object indicates the time interval in minutes to negotiate new session key
            for client and server."
        ::= { swSSHMgmt 4}

 swSSHMaxSession OBJECT-TYPE
        SYNTAX  INTEGER(0..655355)
        MAX-ACCESS  read-only
        STATUS  current
        DESCRIPTION
            "This object indicates the SSH supported max session the system."
        ::= { swSSHMgmt 5}

 swSSHConnectionTimeout OBJECT-TYPE
        SYNTAX  INTEGER(0..655355)
        MAX-ACCESS  read-only
        STATUS  current
        DESCRIPTION
            "This object indicates connection timeout."
        ::= { swSSHMgmt 6}

 swSSHListenedPort OBJECT-TYPE
        SYNTAX  INTEGER(0..65535)
        MAX-ACCESS  read-only
        STATUS  current
        DESCRIPTION
            "This object indicates listened port."
        ::= { swSSHMgmt 7}


-- ----------------------------------------------------------------------------
-- groups in the SSH MIB
-- ----------------------------------------------------------------------------


-- ----------------------------------------------------------------------------
 swSSHCtrlAlgGroup OBJECT IDENTIFIER ::= { swSSHMIB 3 }
-- ----------------------------------------------------------------------------
  swSSHEncryptAlgCtrl OBJECT IDENTIFIER ::= { swSSHCtrlAlgGroup 1 }

   swSSHEncryptAlg3DESAdmin OBJECT-TYPE
        SYNTAX  INTEGER {
                    other(1),
                    disabled(2),
                    enabled(3)
                }
        MAX-ACCESS  read-write
        STATUS  current
        DESCRIPTION
            "This object indicates the TDES encryption algorithm is enable or disable
			."
        ::= { swSSHEncryptAlgCtrl 1}

   swSSHEncryptAlgBlowfishAdmin OBJECT-TYPE
        SYNTAX  INTEGER {
                    other(1),
                    disabled(2),
                    enabled(3)
                }
        MAX-ACCESS  read-write
        STATUS  current
        DESCRIPTION
            "This object indicates the Blowfish encryption algorithm is enable or disable
			."
        ::= { swSSHEncryptAlgCtrl 2}

   swSSHEncryptAlgAES128Admin OBJECT-TYPE
        SYNTAX  INTEGER {
                    other(1),
                    disabled(2),
                    enabled(3)
                }
        MAX-ACCESS  read-write
        STATUS  current
        DESCRIPTION
            "This object indicates the AES128 encryption algorithm is enable or disable
			."
        ::= { swSSHEncryptAlgCtrl 3}

   swSSHEncryptAlgAES192Admin OBJECT-TYPE
        SYNTAX  INTEGER {
                    other(1),
                    disabled(2),
                    enabled(3)
                }
        MAX-ACCESS  read-write
        STATUS  current
        DESCRIPTION
            "This object indicates the AES192 encryption algorithm is enable or disable
			."
        ::= { swSSHEncryptAlgCtrl 4}

   swSSHEncryptAlgAES256Admin OBJECT-TYPE
        SYNTAX  INTEGER {
                    other(1),
                    disabled(2),
                    enabled(3)
                }
        MAX-ACCESS  read-write
        STATUS  current
        DESCRIPTION
            "This object indicates the AES256 encryption algorithm is enable or disable
			."
        ::= { swSSHEncryptAlgCtrl 5}

   swSSHEncryptAlgArcfourAdmin OBJECT-TYPE
        SYNTAX  INTEGER {
                    other(1),
                    disabled(2),
                    enabled(3)
                }
        MAX-ACCESS  read-write
        STATUS  current
        DESCRIPTION
            "This object indicates the Arcfour encryption algorithm is enable or disable
			."
        ::= { swSSHEncryptAlgCtrl 6}

   swSSHEncryptAlgCAST28Admin OBJECT-TYPE
        SYNTAX  INTEGER {
                    other(1),
                    disabled(2),
                    enabled(3)
                }
        MAX-ACCESS  read-write
        STATUS  current
        DESCRIPTION
            "This object indicates the CAST128 encryption algorithm is enable or disable
			."
        ::= { swSSHEncryptAlgCtrl 7}

   swSSHEncryptAlgTwofish128Admin OBJECT-TYPE
        SYNTAX  INTEGER {
                    other(1),
                    disabled(2),
                    enabled(3)
                }
        MAX-ACCESS  read-write
        STATUS  current
        DESCRIPTION
            "This object indicates the Twofish128 encryption algorithm is enable or disable
			."
        ::= { swSSHEncryptAlgCtrl 8}

   swSSHEncryptAlgTwofish192Admin OBJECT-TYPE
        SYNTAX  INTEGER {
                    other(1),
                    disabled(2),
                    enabled(3)
                }
        MAX-ACCESS  read-write
        STATUS  current
        DESCRIPTION
            "This object indicates the Twofish192 encryption algorithm is enable or disable
			."
        ::= { swSSHEncryptAlgCtrl 9}

   swSSHEncryptAlgTwofish256Admin OBJECT-TYPE
        SYNTAX  INTEGER {
                    other(1),
                    disabled(2),
                    enabled(3)
                }
        MAX-ACCESS  read-write
        STATUS  current
        DESCRIPTION
            "This object indicates the Twofish256 encryption algorithm is enable or disable
			."
        ::= { swSSHEncryptAlgCtrl 10}


-- ----------------------------------------------------------------------------
  swSSHAuthenMethodCtrl OBJECT IDENTIFIER ::= { swSSHCtrlAlgGroup 2 }
-- ----------------------------------------------------------------------------

   swSSHAuthenMethodPasswdAdmin OBJECT-TYPE
        SYNTAX  INTEGER {
                    other(1),
                    disabled(2),
                    enabled(3)
                }
        MAX-ACCESS  read-write
        STATUS  current
        DESCRIPTION
            "This object indicates password authentication enable or disable
			."
        ::= { swSSHAuthenMethodCtrl 1}

   swSSHAuthenMethodPubKeyAdmin OBJECT-TYPE
        SYNTAX  INTEGER {
                    other(1),
                    disabled(2),
                    enabled(3)
                }
        MAX-ACCESS  read-write
        STATUS  current
        DESCRIPTION
            "This object indicates Public Key authentication enable or disable
			."
        ::= { swSSHAuthenMethodCtrl 2}

   swSSHAuthenMethodHostKeyAdmin OBJECT-TYPE
        SYNTAX  INTEGER {
                    other(1),
                    disabled(2),
                    enabled(3)
                }
        MAX-ACCESS  read-write
        STATUS  current
        DESCRIPTION
            "This object indicates Host Key authentication enable or disable
			."
        ::= { swSSHAuthenMethodCtrl 3}
-- ----------------------------------------------------------------------------
   swSSHInteAlgCtrl OBJECT IDENTIFIER ::= { swSSHCtrlAlgGroup 3 }
-- ----------------------------------------------------------------------------
   swSSHInteAlgSHA1Admin OBJECT-TYPE
        SYNTAX  INTEGER {
                    other(1),
                    disabled(2),
                    enabled(3)
                }
        MAX-ACCESS  read-write
        STATUS  current
        DESCRIPTION
            "This object indicates HMAC-SHA1 algorithm enable or disable
			."
        ::= { swSSHInteAlgCtrl 1}

   swSSHInteAlgMD5Admin OBJECT-TYPE
        SYNTAX  INTEGER {
                    other(1),
                    disabled(2),
                    enabled(3)
                }
        MAX-ACCESS  read-write
        STATUS  current
        DESCRIPTION
            "This object indicates HMAC-MD5 algorithm enable or disable
			."
        ::= { swSSHInteAlgCtrl 2}



--  swSSHKeyExDAdmin OBJECT IDENTIFIER ::= { swSSHCtrlAlgGroup 4 }

--   swSSHKeyExDAdmin OBJECT-TYPE
--        SYNTAX  INTEGER {
--                    other(1),
--                    disabled(2),
--                    enabled(3)
--                }
--        MAX-ACCESS  read-write
--        STATUS  current
--        DESCRIPTION
--            "This object indicates  Diffie Hellman algorithm enable or disable
--			."
--        ::= { swSSHCtrlAlgGroup 4}

-- ----------------------------------------------------------------------------
swSSHPublKeyCtrl OBJECT IDENTIFIER ::= { swSSHCtrlAlgGroup 5 }
-- ----------------------------------------------------------------------------
   swSSHPublKeyRSAAdmin OBJECT-TYPE
        SYNTAX  INTEGER {
                    other(1),
                    disabled(2),
                    enabled(3)
                }
        MAX-ACCESS  read-write
        STATUS  current
        DESCRIPTION
            "This object indicates RSA algorithm enable or disable."
        ::= { swSSHPublKeyCtrl 1}

   swSSHPublKeyDSAAdmin OBJECT-TYPE
        SYNTAX  INTEGER {
                    other(1),
                    disabled(2),
                    enabled(3)
                }
        MAX-ACCESS  read-write
        STATUS  current
        DESCRIPTION
            "This object indicates DSA algorithm enable or disable."
        ::= { swSSHPublKeyCtrl 2}

-- ----------------------------------------------------------------------------



END
