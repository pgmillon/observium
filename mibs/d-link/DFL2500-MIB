--
-- DFL-2500 SMIv2 module
--

DFL2500-MIB DEFINITIONS ::= BEGIN

IMPORTS
    MODULE-COMPLIANCE, OBJECT-GROUP
        FROM SNMPv2-CONF
    Counter32, Counter64, Gauge32, Integer32, MODULE-IDENTITY, 
    OBJECT-TYPE, enterprises
        FROM SNMPv2-SMI
    DisplayString
        FROM SNMPv2-TC;

dfl2500-MIB MODULE-IDENTITY
    LAST-UPDATED "201009021139Z"
    ORGANIZATION 
        "D-Link Corporation"
    CONTACT-INFO 
        "Postal: D-Link Corporation
         No. 289, Sinhu 3rd Road,
         Neihu District, Taipei City 114,
         Taiwan, R.O.C.
         Tel: +886-2-66000123
         Fax: +886-2-55509988"
    DESCRIPTION 
        "The MIB module for D-Link DFL-2500 series product."
    
    REVISION  "201009021139Z"
    DESCRIPTION 
        "Added 64-bit counters"
    REVISION  "201003300900Z"
    DESCRIPTION 
        "Added values for SMTP ALG objects."
    REVISION  "200911100916Z"
    DESCRIPTION 
        "Added values for opened and closed connections per second"
    REVISION  "200811181605Z"
    DESCRIPTION 
        "Added value for timer usage"
    REVISION  "200810141227Z"
    DESCRIPTION 
        "Added values for memory usage and TCP buffer usage"    
    REVISION  "200710310000Z"
    DESCRIPTION 
        "Initial version."
    ::= { dfl2500MibModules 2 }


dlink OBJECT IDENTIFIER
    ::= { enterprises 171 }

netdefendMgmt OBJECT IDENTIFIER
    ::= { dlink 20 }

ipsFirewall OBJECT IDENTIFIER
    ::= { netdefendMgmt 1 }

dfl2500 OBJECT IDENTIFIER
    ::= { ipsFirewall 5 }

dfl2500OS OBJECT IDENTIFIER
    ::= { dfl2500 1 }

dfl2500OSStats OBJECT IDENTIFIER
    ::= { dfl2500OS 2 }

dfl2500reg OBJECT IDENTIFIER
    ::= { dfl2500 2 }

dfl2500MibModules OBJECT IDENTIFIER
    ::= { dfl2500reg 1 }

dfl2500MibConfs OBJECT IDENTIFIER
    ::= { dfl2500reg 2 }

dfl2500MibObjectGroups OBJECT IDENTIFIER
    ::= { dfl2500reg 3 }


dfl2500System OBJECT IDENTIFIER
    ::= { dfl2500OSStats 1 }

dfl2500SysCpuLoad OBJECT-TYPE
    SYNTAX      Gauge32
    MAX-ACCESS  read-only
    STATUS      current
    DESCRIPTION 
        "The system cpu load."
    ::= { dfl2500System 1 }

dfl2500SysForwardedBits OBJECT-TYPE
    SYNTAX      Counter32
    MAX-ACCESS  read-only
    STATUS      current
    DESCRIPTION
        "The number of bits forwarded through the gateway."
    ::= { dfl2500System 2 }

dfl2500SysForwardedPackets OBJECT-TYPE
    SYNTAX      Counter32
    MAX-ACCESS  read-only
    STATUS      current
    DESCRIPTION
        "Total number of forwarded packets."
    ::= { dfl2500System 3 }

dfl2500SysBuffUse OBJECT-TYPE
    SYNTAX      Gauge32
    MAX-ACCESS  read-only
    STATUS      current
    DESCRIPTION 
        "The current number of buffers in use."
    ::= { dfl2500System 4 }

dfl2500SysConns OBJECT-TYPE
    SYNTAX      Gauge32
    MAX-ACCESS  read-only
    STATUS      current
    DESCRIPTION 
        "The numer of connections."
    ::= { dfl2500System 5 }

dfl2500SysPerStateCounters OBJECT IDENTIFIER
    ::= { dfl2500System 6 }

dfl2500SysPscTcpSyn OBJECT-TYPE
    SYNTAX      Gauge32
    MAX-ACCESS  read-only
    STATUS      current
    DESCRIPTION 
        "Number of TCP connections in the SYN state."
    ::= { dfl2500SysPerStateCounters 1 }

dfl2500SysPscTcpOpen OBJECT-TYPE
    SYNTAX      Gauge32
    MAX-ACCESS  read-only
    STATUS      current
    DESCRIPTION 
        "Number of TCP connections in the OPEN state."
    ::= { dfl2500SysPerStateCounters 2 }

dfl2500SysPscTcpFin OBJECT-TYPE
    SYNTAX      Gauge32
    MAX-ACCESS  read-only
    STATUS      current
    DESCRIPTION 
        "Number of TCP connections in the FIN state."
    ::= { dfl2500SysPerStateCounters 3 }

dfl2500SysPscUdp OBJECT-TYPE
    SYNTAX      Gauge32
    MAX-ACCESS  read-only
    STATUS      current
    DESCRIPTION 
        "Number of UDP connections."
    ::= { dfl2500SysPerStateCounters 4 }

dfl2500SysPscIcmp OBJECT-TYPE
    SYNTAX      Gauge32
    MAX-ACCESS  read-only
    STATUS      current
    DESCRIPTION 
        "Number of ICMP connections."
    ::= { dfl2500SysPerStateCounters 5 }

dfl2500SysPscOther OBJECT-TYPE
    SYNTAX      Gauge32
    MAX-ACCESS  read-only
    STATUS      current
    DESCRIPTION 
        "Number of other connections."
    ::= { dfl2500SysPerStateCounters 6 }

dfl2500IfStatsTable OBJECT-TYPE
    SYNTAX      SEQUENCE OF Dfl2500IfStatsEntry
    MAX-ACCESS  not-accessible
    STATUS      current
    DESCRIPTION 
        "A table of DFL-2500 specific interfaces statistics"
    ::= { dfl2500System 7 }

dfl2500IfStatsEntry OBJECT-TYPE
    SYNTAX      Dfl2500IfStatsEntry
    MAX-ACCESS  not-accessible
    STATUS      current
    DESCRIPTION 
        "The row in a table of DFL-2500 specific interface statistics"
    INDEX       { dfl2500IfStatsIndex }
    ::= { dfl2500IfStatsTable 1 }

Dfl2500IfStatsEntry ::= SEQUENCE {
    dfl2500IfStatsIndex     Integer32,
    dfl2500IfName           DisplayString,
    dfl2500IfFragsIn        Counter32,
    dfl2500IfFragReassOk    Counter32,
    dfl2500IfFragReassFail  Counter32,
    dfl2500IfPktsInCnt      Counter32,
    dfl2500IfPktsOutCnt     Counter32,
    dfl2500IfBitsInCnt      Counter32,
    dfl2500IfBitsOutCnt     Counter32,
    dfl2500IfPktsTotCnt     Counter32,
    dfl2500IfBitsTotCnt     Counter32,
    dfl2500IfHCPktsInCnt    Counter64,
    dfl2500IfHCPktsOutCnt   Counter64,
    dfl2500IfHCBitsInCnt    Counter64,
    dfl2500IfHCBitsOutCnt   Counter64,
    dfl2500IfHCPktsTotCnt   Counter64,
    dfl2500IfHCBitsTotCnt   Counter64
}

dfl2500IfStatsIndex OBJECT-TYPE
    SYNTAX      Integer32 (1..2147483647)
    MAX-ACCESS  not-accessible
    STATUS      current
    DESCRIPTION 
        "Index of a row in dfl2500SysIfStatsTable"
    ::= { dfl2500IfStatsEntry 1 }

dfl2500IfName OBJECT-TYPE
    SYNTAX      DisplayString
    MAX-ACCESS  read-only
    STATUS      current
    DESCRIPTION 
        "The name of the interface."
    ::= { dfl2500IfStatsEntry 2 }

dfl2500IfFragsIn OBJECT-TYPE
    SYNTAX      Counter32
    MAX-ACCESS  read-only
    STATUS      current
    DESCRIPTION 
        "Number of IP packet fragments received 
         in the interface."
    ::= { dfl2500IfStatsEntry 3 }

dfl2500IfFragReassOk OBJECT-TYPE
    SYNTAX      Counter32
    MAX-ACCESS  read-only
    STATUS      current
    DESCRIPTION 
        "Number of complete IP packets successfully 
         reassembled from the fragments received in 
         the interface."
    ::= { dfl2500IfStatsEntry 4 }

dfl2500IfFragReassFail OBJECT-TYPE
    SYNTAX      Counter32
    MAX-ACCESS  read-only
    STATUS      current
    DESCRIPTION 
        "Number of packets that could not be reassembled, 
         either due to resource starvation, illegal fragmentation, 
         or just packet loss."
    ::= { dfl2500IfStatsEntry 5 }

dfl2500IfPktsInCnt OBJECT-TYPE
    SYNTAX      Counter32
    MAX-ACCESS  read-only
    STATUS      current
    DESCRIPTION 
        "Number of packets received by the interface."
    ::= { dfl2500IfStatsEntry 6 }

dfl2500IfPktsOutCnt OBJECT-TYPE
    SYNTAX      Counter32
    MAX-ACCESS  read-only
    STATUS      current
    DESCRIPTION 
        "Number of packets sent by the interface"
    ::= { dfl2500IfStatsEntry 7 }

dfl2500IfBitsInCnt OBJECT-TYPE
    SYNTAX      Counter32
    MAX-ACCESS  read-only
    STATUS      current
    DESCRIPTION 
        "Number of bits received by the interface"
    ::= { dfl2500IfStatsEntry 8 }

dfl2500IfBitsOutCnt OBJECT-TYPE
    SYNTAX      Counter32
    MAX-ACCESS  read-only
    STATUS      current
    DESCRIPTION 
        "Number of bits sent by the interface"
    ::= { dfl2500IfStatsEntry 9 }

dfl2500IfPktsTotCnt OBJECT-TYPE
    SYNTAX      Counter32
    MAX-ACCESS  read-only
    STATUS      current
    DESCRIPTION 
        "Totat number of packets transmited by the interface"
    ::= { dfl2500IfStatsEntry 10 }

dfl2500IfBitsTotCnt OBJECT-TYPE
    SYNTAX      Counter32
    MAX-ACCESS  read-only
    STATUS      current
    DESCRIPTION 
        "Totat number of bits transmited by the interface"
    ::= { dfl2500IfStatsEntry 11 }

dfl2500IfHCPktsInCnt OBJECT-TYPE
    SYNTAX      Counter64
    MAX-ACCESS  read-only
    STATUS      current
    DESCRIPTION 
        "Number of packets received by the interface.
        This object is a 64-bit version of dfl2500IfPktsInCnt."
    ::= { dfl2500IfStatsEntry 12 }

dfl2500IfHCPktsOutCnt OBJECT-TYPE
    SYNTAX      Counter64
    MAX-ACCESS  read-only
    STATUS      current
    DESCRIPTION 
        "Number of packets sent by the interface.
        This object is a 64-bit version of dfl2500IfPktsOutCnt."
    ::= { dfl2500IfStatsEntry 13 }

dfl2500IfHCBitsInCnt OBJECT-TYPE
    SYNTAX      Counter64
    MAX-ACCESS  read-only
    STATUS      current
    DESCRIPTION 
        "Number of bits received by the interface.
        This object is a 64-bit version of dfl2500IfBitsInCnt."
    ::= { dfl2500IfStatsEntry 14 }

dfl2500IfHCBitsOutCnt OBJECT-TYPE
    SYNTAX      Counter64
    MAX-ACCESS  read-only
    STATUS      current
    DESCRIPTION 
        "Number of bits sent by the interface.
        This object is a 64-bit version of dfl2500IfBitsOutCnt."
    ::= { dfl2500IfStatsEntry 15 }

dfl2500IfHCPktsTotCnt OBJECT-TYPE
    SYNTAX      Counter64
    MAX-ACCESS  read-only
    STATUS      current
    DESCRIPTION 
        "Totat number of packets transmited by the interface.
        This object is a 64-bit version of dfl2500IfPktsTotCnt."
    ::= { dfl2500IfStatsEntry 16 }

dfl2500IfHCBitsTotCnt OBJECT-TYPE
    SYNTAX      Counter64
    MAX-ACCESS  read-only
    STATUS      current
    DESCRIPTION 
        "Totat number of bits transmited by the interface. 
        This object is a 64-bit version of dfl2500IfBitsTotCnt."
    ::= { dfl2500IfStatsEntry 17 }

dfl2500IfRxRingTable OBJECT-TYPE
    SYNTAX      SEQUENCE OF Dfl2500IfRxRingEntry
    MAX-ACCESS  not-accessible
    STATUS      current
    DESCRIPTION 
        "A table of DFL-2500 specific interface Rx ring statistics"
    ::= { dfl2500System 8 }

dfl2500IfRxRingEntry OBJECT-TYPE
    SYNTAX      Dfl2500IfRxRingEntry
    MAX-ACCESS  not-accessible
    STATUS      current
    DESCRIPTION 
        "The row in a table of DFL-2500 specific interface Rx ring 
         statistics."
    INDEX       { dfl2500IfRxRingIndex }
    ::= { dfl2500IfRxRingTable 1 }

Dfl2500IfRxRingEntry ::= SEQUENCE {
    dfl2500IfRxRingIndex        Integer32,
    dfl2500IfRxRingFifoErrors   Counter32,
    dfl2500IfRxDespools         Gauge32,
    dfl2500IfRxAvgUse           Gauge32,
    dfl2500IfRxRingSaturation   Gauge32,
    dfl2500RxRingFlooded        Gauge32
}

dfl2500IfRxRingIndex OBJECT-TYPE
    SYNTAX      Integer32 (1..2147483647)
    MAX-ACCESS  not-accessible
    STATUS      current
    DESCRIPTION 
        "Index of a row in dfl2500IfRxRingTable."
    ::= { dfl2500IfRxRingEntry 1 }

dfl2500IfRxRingFifoErrors OBJECT-TYPE
    SYNTAX      Counter32
    MAX-ACCESS  read-only
    STATUS      current
    DESCRIPTION 
        "Rx Ring number of FIFO errors."
    ::= { dfl2500IfRxRingEntry 2 }

dfl2500IfRxDespools OBJECT-TYPE
    SYNTAX      Gauge32
    MAX-ACCESS  read-only
    STATUS      current
    DESCRIPTION 
        "Number of despool events per second."
    ::= { dfl2500IfRxRingEntry 3 }

dfl2500IfRxAvgUse OBJECT-TYPE
    SYNTAX      Gauge32
    MAX-ACCESS  read-only
    STATUS      current
    DESCRIPTION 
        "Rx Ring average usage."
    ::= { dfl2500IfRxRingEntry 4 }

dfl2500IfRxRingSaturation OBJECT-TYPE
    SYNTAX      Gauge32
    MAX-ACCESS  read-only
    STATUS      current
    DESCRIPTION 
        "Rx Ring sturation. Percentage of ring use per despool 
         event when the ring has been more than half full."
    ::= { dfl2500IfRxRingEntry 5 }

dfl2500RxRingFlooded OBJECT-TYPE
    SYNTAX      Gauge32
    MAX-ACCESS  read-only
    STATUS      current
    DESCRIPTION 
        "Rx Ring number of despool events for which 
         the ring has been completely flooded"
    ::= { dfl2500IfRxRingEntry 6 }

dfl2500IfTxRingTable OBJECT-TYPE
    SYNTAX      SEQUENCE OF Dfl2500IfTxRingEntry
    MAX-ACCESS  not-accessible
    STATUS      current
    DESCRIPTION 
        "A table of DFL-2500 specific interface Tx ring statistics"
    ::= { dfl2500System 9 }

dfl2500IfTxRingEntry OBJECT-TYPE
    SYNTAX      Dfl2500IfTxRingEntry
    MAX-ACCESS  not-accessible
    STATUS      current
    DESCRIPTION 
        "The row in a table of DFL-2500 specific interface Tx ring 
         statistics."
    INDEX       { dfl2500IfTxRingIndex }
    ::= { dfl2500IfTxRingTable 1 }

Dfl2500IfTxRingEntry ::= SEQUENCE {
    dfl2500IfTxRingIndex        Integer32,
    dfl2500IfTxDespools         Gauge32,
    dfl2500IfTxAvgUse           Gauge32,
    dfl2500IfTxRingSaturation   Gauge32,
    dfl2500RxTingFlooded        Gauge32
}

dfl2500IfTxRingIndex OBJECT-TYPE
    SYNTAX      Integer32 (1..2147483647)
    MAX-ACCESS  not-accessible
    STATUS      current
    DESCRIPTION 
        "Index of a row in dfl2500IfRxRingTable."
    ::= { dfl2500IfTxRingEntry 1 }

dfl2500IfTxDespools OBJECT-TYPE
    SYNTAX      Gauge32
    MAX-ACCESS  read-only
    STATUS      current
    DESCRIPTION 
        "Tx Ring number of despool event per second (polls when 
         there is at least one buffer in the ring)"
    ::= { dfl2500IfTxRingEntry 2 }

dfl2500IfTxAvgUse OBJECT-TYPE
    SYNTAX      Gauge32
    MAX-ACCESS  read-only
    STATUS      current
    DESCRIPTION 
        "Tx Ring number of despool events when the ring has 
         been completely flooded"
    ::= { dfl2500IfTxRingEntry 3 }

dfl2500IfTxRingSaturation OBJECT-TYPE
    SYNTAX      Gauge32
    MAX-ACCESS  read-only
    STATUS      current
    DESCRIPTION 
        "Tx Ring percentage of use per despool event when the 
         ring has been more than half full."
    ::= { dfl2500IfTxRingEntry 4 }

dfl2500RxTingFlooded OBJECT-TYPE
    SYNTAX      Gauge32
    MAX-ACCESS  read-only
    STATUS      current
    DESCRIPTION 
        "Tx Ring number of despool events for in which the ring has 
         been completely flooded"
    ::= { dfl2500IfTxRingEntry 5 }

dfl2500IfVlanStatsTable OBJECT-TYPE
    SYNTAX      SEQUENCE OF Dfl2500IfVlanStatsEntry
    MAX-ACCESS  not-accessible
    STATUS      current
    DESCRIPTION 
        "A table of DFL-2500 VLAN statistics"
    ::= { dfl2500System 10 }

dfl2500IfVlanStatsEntry OBJECT-TYPE
    SYNTAX      Dfl2500IfVlanStatsEntry
    MAX-ACCESS  not-accessible
    STATUS      current
    DESCRIPTION 
        "The row in a table of dfl2500IfVlanStatsTable. Each has an index 
         equal to the ifIndex of the corresponding physical interface"
    INDEX       { dfl2500IfVlanIndex }
    ::= { dfl2500IfVlanStatsTable 1 }

Dfl2500IfVlanStatsEntry ::= SEQUENCE {
    dfl2500IfVlanIndex              Integer32,
    dfl2500IfVlanUntaggedInPkts     Counter32,
    dfl2500IfVlanUntaggedOutPkts    Counter32,
    dfl2500IfVlanUntaggedTotPkts    Counter32,
    dfl2500IfVlanUntaggedInOctets   Counter32,
    dfl2500IfVlanUntaggedOutOctets  Counter32,
    dfl2500IfVlanUntaggedTotOctets  Counter32
}

dfl2500IfVlanIndex OBJECT-TYPE
    SYNTAX      Integer32 (1..2147483647)
    MAX-ACCESS  not-accessible
    STATUS      current
    DESCRIPTION 
        "Extended index of a row in dfl2500IfVlanStatsTable."
    ::= { dfl2500IfVlanStatsEntry 1 }

dfl2500IfVlanUntaggedInPkts OBJECT-TYPE
    SYNTAX      Counter32
    MAX-ACCESS  read-only
    STATUS      current
    DESCRIPTION 
        "Number of untaged packets untagged packets received by the interface."
    ::= { dfl2500IfVlanStatsEntry 2 }

dfl2500IfVlanUntaggedOutPkts OBJECT-TYPE
    SYNTAX      Counter32
    MAX-ACCESS  read-only
    STATUS      current
    DESCRIPTION 
        "Number of untagged packets sent by the interface."
    ::= { dfl2500IfVlanStatsEntry 3 }

dfl2500IfVlanUntaggedTotPkts OBJECT-TYPE
    SYNTAX      Counter32
    MAX-ACCESS  read-only
    STATUS      current
    DESCRIPTION 
        "Total number of untagged packets processed by the interface."
    ::= { dfl2500IfVlanStatsEntry 4 }

dfl2500IfVlanUntaggedInOctets OBJECT-TYPE
    SYNTAX      Counter32
    MAX-ACCESS  read-only
    STATUS      current
    DESCRIPTION 
        "Total number of octects in untagged packets received by the interface."
    ::= { dfl2500IfVlanStatsEntry 5 }

dfl2500IfVlanUntaggedOutOctets OBJECT-TYPE
    SYNTAX      Counter32
    MAX-ACCESS  read-only
    STATUS      current
    DESCRIPTION 
        "Total number of octects in untagged packets sent by the interface."
    ::= { dfl2500IfVlanStatsEntry 6 }

dfl2500IfVlanUntaggedTotOctets OBJECT-TYPE
    SYNTAX      Counter32
    MAX-ACCESS  read-only
    STATUS      current
    DESCRIPTION 
        "Total number of octects in untagged packets processed by the 
         interface."
    ::= { dfl2500IfVlanStatsEntry 7 }

dfl2500HWSensorTable OBJECT-TYPE
    SYNTAX      SEQUENCE OF Dfl2500HWSensorEntry
    MAX-ACCESS  not-accessible
    STATUS      current
    DESCRIPTION 
        "Table of hardware sensors."
    ::= { dfl2500System 11 }

dfl2500HWSensorEntry OBJECT-TYPE
    SYNTAX      Dfl2500HWSensorEntry
    MAX-ACCESS  not-accessible
    STATUS      current
    DESCRIPTION 
        "Entry  of table of hardware sensors."
    INDEX       { dfl2500HWSensorIndex }
    ::= { dfl2500HWSensorTable 1 }

Dfl2500HWSensorEntry ::= SEQUENCE {
    dfl2500HWSensorIndex    Integer32,
    dfl2500HWSensorName     DisplayString,
    dfl2500HWSensorValue    Gauge32,
    dfl2500HWSensorUnit     DisplayString
}

dfl2500HWSensorIndex OBJECT-TYPE
    SYNTAX      Integer32 (1..2147483647)
    MAX-ACCESS  not-accessible
    STATUS      current
    DESCRIPTION 
        "Index of the entries of the sensor table."
    ::= { dfl2500HWSensorEntry 1 }

dfl2500HWSensorName OBJECT-TYPE
    SYNTAX      DisplayString
    MAX-ACCESS  read-only
    STATUS      current
    DESCRIPTION 
        "The description of the sensor."
    ::= { dfl2500HWSensorEntry 2 }

dfl2500HWSensorValue OBJECT-TYPE
    SYNTAX      Gauge32
    MAX-ACCESS  read-only
    STATUS      current
    DESCRIPTION 
        "The value of the sensor."
    ::= { dfl2500HWSensorEntry 3 }

dfl2500HWSensorUnit OBJECT-TYPE
    SYNTAX      DisplayString
    MAX-ACCESS  read-only
    STATUS      current
    DESCRIPTION 
        "The description of the unit of the value mesured by sensor."
    ::= { dfl2500HWSensorEntry 4 }

dfl2500SysMemUsage OBJECT-TYPE
    SYNTAX      Gauge32
    MAX-ACCESS  read-only
    STATUS      current
    DESCRIPTION 
        "The current memory usage."
    ::= { dfl2500System 12 }

dfl2500SysTCPUsage OBJECT IDENTIFIER
    ::= { dfl2500System 13 }
    
dfl2500SysTCPRecvSmall OBJECT-TYPE
    SYNTAX      Gauge32
    MAX-ACCESS  read-only
    STATUS      current
    DESCRIPTION 
        "Small TCP receive windows usage."
    ::= { dfl2500SysTCPUsage 1 }

dfl2500SysTCPRecvLarge OBJECT-TYPE
    SYNTAX      Gauge32
    MAX-ACCESS  read-only
    STATUS      current
    DESCRIPTION 
        "Large TCP receive windows usage."
    ::= { dfl2500SysTCPUsage 2 }

dfl2500SysTCPSendSmall OBJECT-TYPE
    SYNTAX      Gauge32
    MAX-ACCESS  read-only
    STATUS      current
    DESCRIPTION 
        "Small TCP send windows usage."
    ::= { dfl2500SysTCPUsage 3 }

dfl2500SysTCPSendLarge OBJECT-TYPE
    SYNTAX      Gauge32
    MAX-ACCESS  read-only
    STATUS      current
    DESCRIPTION 
        "Large TCP send windows usage."
    ::= { dfl2500SysTCPUsage 4 }

dfl2500SysTimerUsage OBJECT-TYPE
    SYNTAX      Gauge32
    MAX-ACCESS  read-only
    STATUS      current
    DESCRIPTION 
        "The current number of timers in use."
    ::= { dfl2500System 14 }

dfl2500SysConnOPS OBJECT-TYPE
    SYNTAX      Gauge32
    MAX-ACCESS  read-only
    STATUS      current
    DESCRIPTION 
        "The number of connections opened per second."
    ::= { dfl2500System 15 }
    
dfl2500SysConnCPS OBJECT-TYPE
    SYNTAX      Gauge32
    MAX-ACCESS  read-only
    STATUS      current
    DESCRIPTION 
        "The number of connections closed per second."
    ::= { dfl2500System 16 }
    
dfl2500SysHCForwardedBits OBJECT-TYPE
    SYNTAX      Counter64
    MAX-ACCESS  read-only
    STATUS      current
    DESCRIPTION
        "The number of bits forwarded through the gateway."
    ::= { dfl2500System 17 }
    
dfl2500VPN OBJECT IDENTIFIER
    ::= { dfl2500OSStats 2 }

dfl2500IPsec OBJECT IDENTIFIER
    ::= { dfl2500VPN 1 }

dfl2500IPsecGlobal OBJECT IDENTIFIER
    ::= { dfl2500IPsec 1 }

dfl2500IPsecPhaseOneActive OBJECT-TYPE
    SYNTAX      Gauge32
    MAX-ACCESS  read-only
    STATUS      current
    DESCRIPTION 
        "Number of Phase-1 active negotiations"
    ::= { dfl2500IPsecGlobal 1 }

dfl2500IPsecPhaseOneAggrModeDone OBJECT-TYPE
    SYNTAX      Gauge32
    MAX-ACCESS  read-only
    STATUS      current
    DESCRIPTION 
        "Number of Phase-1 aggressive mode negotiations."
    ::= { dfl2500IPsecGlobal 2 }

dfl2500IPsecQuickModeActive OBJECT-TYPE
    SYNTAX      Gauge32
    MAX-ACCESS  read-only
    STATUS      current
    DESCRIPTION 
        "Number of quick mode active negotiations."
    ::= { dfl2500IPsecGlobal 3 }

dfl2500IPsecPhaseOneDone OBJECT-TYPE
    SYNTAX      Counter32
    MAX-ACCESS  read-only
    STATUS      current
    DESCRIPTION 
        "Number of Phase-1 negotiations done."
    ::= { dfl2500IPsecGlobal 4 }

dfl2500IPsecPhaseOneFailed OBJECT-TYPE
    SYNTAX      Counter32
    MAX-ACCESS  read-only
    STATUS      current
    DESCRIPTION 
        "Number of Phase-1 negotiations failed."
    ::= { dfl2500IPsecGlobal 5 }

dfl2500IPsecPhaseOneRekeyed OBJECT-TYPE
    SYNTAX      Counter32
    MAX-ACCESS  read-only
    STATUS      current
    DESCRIPTION 
        "Number of Phase-1 negotiations rekeyed."
    ::= { dfl2500IPsecGlobal 6 }

dfl2500IPsecQuickModeDone OBJECT-TYPE
    SYNTAX      Counter32
    MAX-ACCESS  read-only
    STATUS      current
    DESCRIPTION 
        "Number of quick mode  negotiations done."
    ::= { dfl2500IPsecGlobal 7 }

dfl2500IPsecQuickModeFailed OBJECT-TYPE
    SYNTAX      Counter32
    MAX-ACCESS  read-only
    STATUS      current
    DESCRIPTION 
        "Number of quick mode negotiations failed."
    ::= { dfl2500IPsecGlobal 8 }

dfl2500IPsecInfoDone OBJECT-TYPE
    SYNTAX      Counter32
    MAX-ACCESS  read-only
    STATUS      current
    DESCRIPTION 
        "Number of informational exchanges done.
         (Not available in IKEv1 implementations)"
    ::= { dfl2500IPsecGlobal 9 }

dfl2500IPsecInfoFailed OBJECT-TYPE
    SYNTAX      Counter32
    MAX-ACCESS  read-only
    STATUS      current
    DESCRIPTION 
        "Number of informational exchanges failed.
         (Not available in IKEv1 implementations)"
    ::= { dfl2500IPsecGlobal 10 }

dfl2500IPsecInOctetsComp OBJECT-TYPE
    SYNTAX      Counter64
    MAX-ACCESS  read-only
    STATUS      current
    DESCRIPTION 
        "Total octets in before decompression."
    ::= { dfl2500IPsecGlobal 11 }

dfl2500IPsecInOctetsUncomp OBJECT-TYPE
    SYNTAX      Counter64
    MAX-ACCESS  read-only
    STATUS      current
    DESCRIPTION 
        "Total octets in after decompression."
    ::= { dfl2500IPsecGlobal 12 }

dfl2500IPsecOutOctetsComp OBJECT-TYPE
    SYNTAX      Counter64
    MAX-ACCESS  read-only
    STATUS      current
    DESCRIPTION 
        "Total octets out after compression."
    ::= { dfl2500IPsecGlobal 13 }

dfl2500IPsecOutOctetsUncomp OBJECT-TYPE
    SYNTAX      Counter64
    MAX-ACCESS  read-only
    STATUS      current
    DESCRIPTION 
        "Total octets out before compression."
    ::= { dfl2500IPsecGlobal 14 }

dfl2500IPsecForwardedOctetsComp OBJECT-TYPE
    SYNTAX      Counter64
    MAX-ACCESS  read-only
    STATUS      current
    DESCRIPTION 
        "Total octets forwarded after compression."
    ::= { dfl2500IPsecGlobal 15 }

dfl2500IPsecForwardedOctetsUcomp OBJECT-TYPE
    SYNTAX      Counter64
    MAX-ACCESS  read-only
    STATUS      current
    DESCRIPTION 
        "Total octets forwarded before compression."
    ::= { dfl2500IPsecGlobal 16 }

dfl2500IPsecInPackets OBJECT-TYPE
    SYNTAX      Counter64
    MAX-ACCESS  read-only
    STATUS      current
    DESCRIPTION 
        "Total packets in."
    ::= { dfl2500IPsecGlobal 17 }

dfl2500IPsecOutPackets OBJECT-TYPE
    SYNTAX      Counter64
    MAX-ACCESS  read-only
    STATUS      current
    DESCRIPTION 
        "Total packets Out."
    ::= { dfl2500IPsecGlobal 18 }

dfl2500IPsecForwardedPackets OBJECT-TYPE
    SYNTAX      Counter64
    MAX-ACCESS  read-only
    STATUS      current
    DESCRIPTION 
        "Total packets forwarded."
    ::= { dfl2500IPsecGlobal 19 }

dfl2500IPsecActiveTransforms OBJECT-TYPE
    SYNTAX      Gauge32
    MAX-ACCESS  read-only
    STATUS      current
    DESCRIPTION 
        "Number of currently active transforms."
    ::= { dfl2500IPsecGlobal 20 }

dfl2500IPsecTotalTransforms OBJECT-TYPE
    SYNTAX      Counter32
    MAX-ACCESS  read-only
    STATUS      current
    DESCRIPTION 
        "Total number of transform records created."
    ::= { dfl2500IPsecGlobal 21 }

dfl2500IPsecOutOfTransforms OBJECT-TYPE
    SYNTAX      Counter32
    MAX-ACCESS  read-only
    STATUS      current
    DESCRIPTION 
        "Number of packets dropped due to no available transform object.
         (Not available in IKEv1 implementations)"
    ::= { dfl2500IPsecGlobal 22 }

dfl2500IPsecTotalRekeys OBJECT-TYPE
    SYNTAX      Counter32
    MAX-ACCESS  read-only
    STATUS      current
    DESCRIPTION 
        "Total number of rekeys performed."
    ::= { dfl2500IPsecGlobal 23 }

dfl2500Rules OBJECT IDENTIFIER
    ::= { dfl2500OSStats 3 }

dfl2500RuleUseTable OBJECT-TYPE
    SYNTAX      SEQUENCE OF Dfl2500RuleUseEntry
    MAX-ACCESS  not-accessible
    STATUS      current
    DESCRIPTION 
        "A list of general rules usage statistics."
    ::= { dfl2500Rules 2 }

dfl2500RuleUseEntry OBJECT-TYPE
    SYNTAX      Dfl2500RuleUseEntry
    MAX-ACCESS  not-accessible
    STATUS      current
    DESCRIPTION 
        "The statistics over a rule usage."
    INDEX       { dfl2500RuleIndex }
    ::= { dfl2500RuleUseTable 1 }

Dfl2500RuleUseEntry ::= SEQUENCE {
    dfl2500RuleIndex    Integer32,
    dfl2500RuleName     DisplayString,
    dfl2500RuleUse      Counter32
}

dfl2500RuleIndex OBJECT-TYPE
    SYNTAX      Integer32 (1..2147483647)
    MAX-ACCESS  not-accessible
    STATUS      current
    DESCRIPTION 
        "The rule usage index."
    ::= { dfl2500RuleUseEntry 1 }

dfl2500RuleName OBJECT-TYPE
    SYNTAX      DisplayString
    MAX-ACCESS  read-only
    STATUS      current
    DESCRIPTION 
        "The name of the rule."
    ::= { dfl2500RuleUseEntry 2 }

dfl2500RuleUse OBJECT-TYPE
    SYNTAX      Counter32
    MAX-ACCESS  read-only
    STATUS      current
    DESCRIPTION 
        "The number of times o rule was used."
    ::= { dfl2500RuleUseEntry 3 }

dfl2500IPPools OBJECT IDENTIFIER
    ::= { dfl2500OSStats 4 }

dfl2500IPPoolsNumber OBJECT-TYPE
    SYNTAX      Integer32
    MAX-ACCESS  read-only
    STATUS      current
    DESCRIPTION 
        "The number of ip pools"
    ::= { dfl2500IPPools 1 }

dfl2500IPPoolTable OBJECT-TYPE
    SYNTAX      SEQUENCE OF Dfl2500IPPoolEntry
    MAX-ACCESS  not-accessible
    STATUS      current
    DESCRIPTION 
        "A list of IP pools"
    ::= { dfl2500IPPools 2 }

dfl2500IPPoolEntry OBJECT-TYPE
    SYNTAX      Dfl2500IPPoolEntry
    MAX-ACCESS  not-accessible
    STATUS      current
    DESCRIPTION 
        "The attributes of an ip pool"
    INDEX       { dfl2500IPPoolIndex }
    ::= { dfl2500IPPoolTable 1 }

Dfl2500IPPoolEntry ::= SEQUENCE {
    dfl2500IPPoolIndex          Integer32,
    dfl2500IPPoolName           DisplayString,
    dfl2500IPPoolPrepare        Gauge32,
    dfl2500IPPoolFree           Gauge32,
    dfl2500IPPoolMisses         Gauge32,
    dfl2500IPPoolClientFails    Gauge32,
    dfl2500IPPoolUsed           Gauge32
}

dfl2500IPPoolIndex OBJECT-TYPE
    SYNTAX      Integer32 (1..2147483647)
    MAX-ACCESS  not-accessible
    STATUS      current
    DESCRIPTION 
        "The ip pool index"
    ::= { dfl2500IPPoolEntry 1 }

dfl2500IPPoolName OBJECT-TYPE
    SYNTAX      DisplayString
    MAX-ACCESS  read-only
    STATUS      current
    DESCRIPTION 
        "The ip pool name"
    ::= { dfl2500IPPoolEntry 2 }

dfl2500IPPoolPrepare OBJECT-TYPE
    SYNTAX      Gauge32
    MAX-ACCESS  read-only
    STATUS      current
    DESCRIPTION 
        "Number of IP pool objects in prepare mode."
    ::= { dfl2500IPPoolEntry 3 }

dfl2500IPPoolFree OBJECT-TYPE
    SYNTAX      Gauge32
    MAX-ACCESS  read-only
    STATUS      current
    DESCRIPTION 
        "Number of available IPs in the pool."
    ::= { dfl2500IPPoolEntry 4 }

dfl2500IPPoolMisses OBJECT-TYPE
    SYNTAX      Gauge32
    MAX-ACCESS  read-only
    STATUS      current
    DESCRIPTION 
        "Mumber of missed IP pool negotiations for other reasons
         than lack of available IP numbers."
    ::= { dfl2500IPPoolEntry 5 }

dfl2500IPPoolClientFails OBJECT-TYPE
    SYNTAX      Gauge32
    MAX-ACCESS  read-only
    STATUS      current
    DESCRIPTION 
        "Number of failed IP pool transactions."
    ::= { dfl2500IPPoolEntry 6 }

dfl2500IPPoolUsed OBJECT-TYPE
    SYNTAX      Gauge32
    MAX-ACCESS  read-only
    STATUS      current
    DESCRIPTION 
        "Number of IP numbers in use from the pool."
    ::= { dfl2500IPPoolEntry 7 }

dfl2500DHCPServer OBJECT IDENTIFIER
    ::= { dfl2500OSStats 5 }

dfl2500DHCPTotalRejected OBJECT-TYPE
    SYNTAX      Gauge32
    MAX-ACCESS  read-only
    STATUS      current
    DESCRIPTION 
        "Total number of rejected packets (all rules)."
    ::= { dfl2500DHCPServer 1 }

dfl2500DHCPRuleTable OBJECT-TYPE
    SYNTAX      SEQUENCE OF Dfl2500DHCPRuleEntry
    MAX-ACCESS  not-accessible
    STATUS      current
    DESCRIPTION 
        "A list of all DHCP server rules usage statistics."
    ::= { dfl2500DHCPServer 2 }

dfl2500DHCPRuleEntry OBJECT-TYPE
    SYNTAX      Dfl2500DHCPRuleEntry
    MAX-ACCESS  not-accessible
    STATUS      current
    DESCRIPTION 
        "The attributes of a DHCP server rule statistics."
    INDEX       { dfl2500DHCPRuleIndex }
    ::= { dfl2500DHCPRuleTable 1 }

Dfl2500DHCPRuleEntry ::= SEQUENCE {
    dfl2500DHCPRuleIndex                Integer32,
    dfl2500DHCPRuleName                 DisplayString,
    dfl2500DHCPRuleUsage                Gauge32,
    dfl2500DHCPRuleUsagePercent         Gauge32,
    dfl2500DHCPActiveClients            Gauge32,
    dfl2500DHCPActiveClientsPercent     Gauge32,
    dfl2500DHCPRejectedRequests         Gauge32,
    dfl2500DHCPTotalLeases              Gauge32
}

dfl2500DHCPRuleIndex OBJECT-TYPE
    SYNTAX      Integer32 (1..2147483647)
    MAX-ACCESS  not-accessible
    STATUS      current
    DESCRIPTION 
        "The DHCP server rule  index"
    ::= { dfl2500DHCPRuleEntry 1 }

dfl2500DHCPRuleName OBJECT-TYPE
    SYNTAX      DisplayString
    MAX-ACCESS  read-only
    STATUS      current
    DESCRIPTION 
        "The DHCP server rule name."
    ::= { dfl2500DHCPRuleEntry 2 }

dfl2500DHCPRuleUsage OBJECT-TYPE
    SYNTAX      Gauge32
    MAX-ACCESS  read-only
    STATUS      current
    DESCRIPTION 
        "Number of used IPs in the pool."
    ::= { dfl2500DHCPRuleEntry 3 }

dfl2500DHCPRuleUsagePercent OBJECT-TYPE
    SYNTAX      Gauge32
    MAX-ACCESS  read-only
    STATUS      current
    DESCRIPTION 
        "The percentage of the used IPs in 
         relation to the IP pool size."
    ::= { dfl2500DHCPRuleEntry 4 }

dfl2500DHCPActiveClients OBJECT-TYPE
    SYNTAX      Gauge32
    MAX-ACCESS  read-only
    STATUS      current
    DESCRIPTION 
        "Number of currently active clients."
    ::= { dfl2500DHCPRuleEntry 5 }

dfl2500DHCPActiveClientsPercent OBJECT-TYPE
    SYNTAX      Gauge32
    MAX-ACCESS  read-only
    STATUS      current
    DESCRIPTION 
        "The number of currently active clients 
         as a percentage of the pool size."
    ::= { dfl2500DHCPRuleEntry 6 }

dfl2500DHCPRejectedRequests OBJECT-TYPE
    SYNTAX      Gauge32
    MAX-ACCESS  read-only
    STATUS      current
    DESCRIPTION 
        "Number of rejected requests matching
         the current rule."
    ::= { dfl2500DHCPRuleEntry 7 }

dfl2500DHCPTotalLeases OBJECT-TYPE
    SYNTAX      Gauge32
    MAX-ACCESS  read-only
    STATUS      current
    DESCRIPTION 
        "Total number of leases in the pool."
    ::= { dfl2500DHCPRuleEntry 8 }

dfl2500UserAuth OBJECT IDENTIFIER
    ::= { dfl2500OSStats 6 }

dfl2500UserAuthHTTPUsers OBJECT-TYPE
    SYNTAX      Gauge32
    MAX-ACCESS  read-only
    STATUS      current
    DESCRIPTION 
        "Number of currently  logged in HTTP users."
    ::= { dfl2500UserAuth 1 }

dfl2500UserAuthXAUTHUsers OBJECT-TYPE
    SYNTAX      Gauge32
    MAX-ACCESS  read-only
    STATUS      current
    DESCRIPTION 
        "Number of currently logged in XAUTH users."
    ::= { dfl2500UserAuth 2 }

dfl2500UserAuthHTTPSUsers OBJECT-TYPE
    SYNTAX      Gauge32
    MAX-ACCESS  read-only
    STATUS      current
    DESCRIPTION 
        "Number of currently logged in HTTPS users."
    ::= { dfl2500UserAuth 3 }

dfl2500UserAuthPPPUsers OBJECT-TYPE
    SYNTAX      Gauge32
    MAX-ACCESS  read-only
    STATUS      current
    DESCRIPTION 
        "Number of currently logged in PPP users."
    ::= { dfl2500UserAuth 4 }

dfl2500UserAuthEAPUsers OBJECT-TYPE
    SYNTAX      Gauge32
    MAX-ACCESS  read-only
    STATUS      current
    DESCRIPTION 
        "Number of currently logged in EAP users."
    ::= { dfl2500UserAuth 5 }

dfl2500UserAuthRuleUseTable OBJECT-TYPE
    SYNTAX      SEQUENCE OF Dfl2500UserAuthRuleUseEntry
    MAX-ACCESS  not-accessible
    STATUS      current
    DESCRIPTION 
        "Table of user authentication rule usage."
    ::= { dfl2500UserAuth 6 }

dfl2500UserAuthRuleUseEntry OBJECT-TYPE
    SYNTAX      Dfl2500UserAuthRuleUseEntry
    MAX-ACCESS  not-accessible
    STATUS      current
    DESCRIPTION 
        "The attributes of an authentication rule 
         usage statistics."
    INDEX       { dfl2500UserAuthRuleIndex }
    ::= { dfl2500UserAuthRuleUseTable 1 }

Dfl2500UserAuthRuleUseEntry ::= SEQUENCE {
    dfl2500UserAuthRuleIndex    Integer32,
    dfl2500UserAuthRuleName     DisplayString,
    dfl2500UserAuthRuleUse      Counter32
}

dfl2500UserAuthRuleIndex OBJECT-TYPE
    SYNTAX      Integer32 (1..2147483647)
    MAX-ACCESS  not-accessible
    STATUS      current
    DESCRIPTION 
        "The rule usage index."
    ::= { dfl2500UserAuthRuleUseEntry 1 }

dfl2500UserAuthRuleName OBJECT-TYPE
    SYNTAX      DisplayString
    MAX-ACCESS  read-only
    STATUS      current
    DESCRIPTION 
        "The name of the rule."
    ::= { dfl2500UserAuthRuleUseEntry 2 }

dfl2500UserAuthRuleUse OBJECT-TYPE
    SYNTAX      Counter32
    MAX-ACCESS  read-only
    STATUS      current
    DESCRIPTION 
        "The number of times o rule was used."
    ::= { dfl2500UserAuthRuleUseEntry 3 }

dfl2500LinkMonitor OBJECT IDENTIFIER
    ::= { dfl2500OSStats 7 }

dfl2500LinkMonGrp OBJECT-TYPE
    SYNTAX      Integer32
    MAX-ACCESS  read-only
    STATUS      current
    DESCRIPTION 
        "The number of groups of monitored links"
    ::= { dfl2500LinkMonitor 1 }

dfl2500LinkMonGrpTable OBJECT-TYPE
    SYNTAX      SEQUENCE OF Dfl2500LinkMonGrpEntry
    MAX-ACCESS  not-accessible
    STATUS      current
    DESCRIPTION 
        "Table of link monitor groups."
    ::= { dfl2500LinkMonitor 2 }

dfl2500LinkMonGrpEntry OBJECT-TYPE
    SYNTAX      Dfl2500LinkMonGrpEntry
    MAX-ACCESS  not-accessible
    STATUS      current
    DESCRIPTION 
        "The attributes of a link monitor group"
    INDEX       { dfl2500LinkMonGrpIndex }
    ::= { dfl2500LinkMonGrpTable 1 }

Dfl2500LinkMonGrpEntry ::= SEQUENCE {
    dfl2500LinkMonGrpIndex      Integer32,
    dfl2500LinkMonGrpName       DisplayString,
    dfl2500LinkMonGrpHostsUp    Gauge32
}

dfl2500LinkMonGrpIndex OBJECT-TYPE
    SYNTAX      Integer32 (1..2147483647)
    MAX-ACCESS  not-accessible
    STATUS      current
    DESCRIPTION 
        "The index row in the table of link monitor groups."
    ::= { dfl2500LinkMonGrpEntry 1 }

dfl2500LinkMonGrpName OBJECT-TYPE
    SYNTAX      DisplayString
    MAX-ACCESS  read-only
    STATUS      current
    DESCRIPTION 
        "The link monitor group name."
    ::= { dfl2500LinkMonGrpEntry 2 }

dfl2500LinkMonGrpHostsUp OBJECT-TYPE
    SYNTAX      Gauge32
    MAX-ACCESS  read-only
    STATUS      current
    DESCRIPTION 
        "The percentage of monitored hosts available."
    ::= { dfl2500LinkMonGrpEntry 3 }

dfl2500LinkMonHostTable OBJECT-TYPE
    SYNTAX      SEQUENCE OF Dfl2500LinkMonHostEntry
    MAX-ACCESS  not-accessible
    STATUS      current
    DESCRIPTION 
        "Table of link monitored hosts in a link monnitor group."
    ::= { dfl2500LinkMonitor 3 }

dfl2500LinkMonHostEntry OBJECT-TYPE
    SYNTAX      Dfl2500LinkMonHostEntry
    MAX-ACCESS  not-accessible
    STATUS      current
    DESCRIPTION 
        "The attributes of a monitored host."
    INDEX       { dfl2500LinkMonGrpIndex, dfl2500LinkMonHostIndex }
    ::= { dfl2500LinkMonHostTable 1 }

Dfl2500LinkMonHostEntry ::= SEQUENCE {
    dfl2500LinkMonHostIndex             Integer32,
    dfl2500LinkMonHostId                DisplayString,
    dfl2500LinkMonHostShortTermLoss     Gauge32,
    dfl2500LinkMonHostPacketsLost       Counter32
}

dfl2500LinkMonHostIndex OBJECT-TYPE
    SYNTAX      Integer32 (1..2147483647)
    MAX-ACCESS  not-accessible
    STATUS      current
    DESCRIPTION 
        "The index an host in the table of link monitor hosts."
    ::= { dfl2500LinkMonHostEntry 1 }

dfl2500LinkMonHostId OBJECT-TYPE
    SYNTAX      DisplayString
    MAX-ACCESS  read-only
    STATUS      current
    DESCRIPTION 
        "The monitored host identifier."
    ::= { dfl2500LinkMonHostEntry 2 }

dfl2500LinkMonHostShortTermLoss OBJECT-TYPE
    SYNTAX      Gauge32
    MAX-ACCESS  read-only
    STATUS      current
    DESCRIPTION 
        "The percentage of short term losst packets."
    ::= { dfl2500LinkMonHostEntry 3 }

dfl2500LinkMonHostPacketsLost OBJECT-TYPE
    SYNTAX      Counter32
    MAX-ACCESS  read-only
    STATUS      current
    DESCRIPTION 
        "Total number of lost monitoring packets."
    ::= { dfl2500LinkMonHostEntry 4 }

dfl2500Pipes OBJECT IDENTIFIER
    ::= { dfl2500OSStats 8 }

dfl2500PipeUsers OBJECT-TYPE
    SYNTAX      Gauge32
    MAX-ACCESS  read-only
    STATUS      current
    DESCRIPTION 
        "The current number of users, as defined by the grouping 
         settings of each pipe, being tracked in the pipes system. 
         Note that this value corresponds to the number of users 
         active in each time slice of 1/20th of a second, and not 
         to the number of users having open connections."
    ::= { dfl2500Pipes 1 }

dfl2500PipeTable OBJECT-TYPE
    SYNTAX      SEQUENCE OF Dfl2500PipeEntry
    MAX-ACCESS  not-accessible
    STATUS      current
    DESCRIPTION 
        "Table of pipes"
    ::= { dfl2500Pipes 2 }

dfl2500PipeEntry OBJECT-TYPE
    SYNTAX      Dfl2500PipeEntry
    MAX-ACCESS  not-accessible
    STATUS      current
    DESCRIPTION 
        "A entry of the pipes table"
    INDEX       { dfl2500PipeIndex }
    ::= { dfl2500PipeTable 1 }

Dfl2500PipeEntry ::= SEQUENCE {
    dfl2500PipeIndex            Integer32,
    dfl2500PipeName             DisplayString,
    dfl2500PipeMinPrec          Integer32,
    dfl2500PipeMaxPrec          Integer32,
    dfl2500PipeDefPrec          Integer32,
    dfl2500PipeNumPrec          Integer32,
    dfl2500PipeNumUsers         Gauge32,
    dfl2500PipeCurrentBps       Gauge32,
    dfl2500PipeCurrentPps       Gauge32,
    dfl2500PipeDelayedPackets   Counter32,
    dfl2500PipeDropedPackets    Counter32
}

dfl2500PipeIndex OBJECT-TYPE
    SYNTAX      Integer32 (1..2147483647)
    MAX-ACCESS  not-accessible
    STATUS      current
    DESCRIPTION 
        "The pipe index"
    ::= { dfl2500PipeEntry 1 }

dfl2500PipeName OBJECT-TYPE
    SYNTAX      DisplayString
    MAX-ACCESS  read-only
    STATUS      current
    DESCRIPTION 
        "The name of the pipe"
    ::= { dfl2500PipeEntry 2 }

dfl2500PipeMinPrec OBJECT-TYPE
    SYNTAX      Integer32
    MAX-ACCESS  read-only
    STATUS      current
    DESCRIPTION 
        "The minimum of the range of pipe precedences."
    ::= { dfl2500PipeEntry 3 }

dfl2500PipeMaxPrec OBJECT-TYPE
    SYNTAX      Integer32
    MAX-ACCESS  read-only
    STATUS      current
    DESCRIPTION 
        "The maximum of the range of pipe precedences."
    ::= { dfl2500PipeEntry 4 }

dfl2500PipeDefPrec OBJECT-TYPE
    SYNTAX      Integer32
    MAX-ACCESS  read-only
    STATUS      current
    DESCRIPTION 
        "The precedence assigned to a packet for which has not one
         allready done by a Pipe Rule."
    ::= { dfl2500PipeEntry 5 }

dfl2500PipeNumPrec OBJECT-TYPE
    SYNTAX      Integer32
    MAX-ACCESS  read-only
    STATUS      current
    DESCRIPTION 
        "The number of pipe precedences"
    ::= { dfl2500PipeEntry 6 }

dfl2500PipeNumUsers OBJECT-TYPE
    SYNTAX      Gauge32
    MAX-ACCESS  read-only
    STATUS      current
    DESCRIPTION 
        "The current number of users, as defined by the grouping settings
         of each pipe, being tracked in the pipes system. This value 
         corresponds to the number of users active in each time slice 
         and not to the number of users having  open connections."
    ::= { dfl2500PipeEntry 7 }

dfl2500PipeCurrentBps OBJECT-TYPE
    SYNTAX      Gauge32
    MAX-ACCESS  read-only
    STATUS      current
    DESCRIPTION 
        "The current throughput of a pipe, in bits per second, as a sum of 
         the corresponding values for all precedences."
    ::= { dfl2500PipeEntry 8 }

dfl2500PipeCurrentPps OBJECT-TYPE
    SYNTAX      Gauge32
    MAX-ACCESS  read-only
    STATUS      current
    DESCRIPTION 
        "The current throughput of a pipe, in packets per second, as a sum of 
         the corresponding values for all precedences."
    ::= { dfl2500PipeEntry 9 }

dfl2500PipeDelayedPackets OBJECT-TYPE
    SYNTAX      Counter32
    MAX-ACCESS  read-only
    STATUS      current
    DESCRIPTION 
        "The number of times packets have been delayed as a result of a pipe, 
         or pipe user having used up its allotted bandwidth. Note that one single
         packet may be delayed several times; if a pipe is really full, this 
         count may exceed the number of packets actually passing through the 
         pipe."
    ::= { dfl2500PipeEntry 10 }

dfl2500PipeDropedPackets OBJECT-TYPE
    SYNTAX      Counter32
    MAX-ACCESS  read-only
    STATUS      current
    DESCRIPTION 
        "The number of packets dropped by a pipe. Packets are dropped when 
         CorePlus is running out of packet buffers. This occurs when excessive 
         amounts of packets need to be queued for later delivery. The packet 
         dropped is always the one that has been queued the longest time 
         globally, which means that the connection suffering from packet loss 
         will be the one most overloading the system."
    ::= { dfl2500PipeEntry 11 }

dfl2500PipePrecTable OBJECT-TYPE
    SYNTAX      SEQUENCE OF Dfl2500PipePrecEntry
    MAX-ACCESS  not-accessible
    STATUS      current
    DESCRIPTION 
        "There is a one to many relation between a pipe and its precedences.
         The number of precedences is a instance attribute of each pipe.
         This table extends the pipes table in order to express the relation 
         between a pipe and the respective precedences."
    ::= { dfl2500Pipes 3 }

dfl2500PipePrecEntry OBJECT-TYPE
    SYNTAX      Dfl2500PipePrecEntry
    MAX-ACCESS  not-accessible
    STATUS      current
    DESCRIPTION 
        "An entry of the table of pipe pecedences. These table entries 
         are chracterized by been indexed by two values. The first index
         the same as the pipe index of the corresponding row in table of 
         pipes and the second index is the index of the set of precedences 
         of the corresponding pipe."
    INDEX       { dfl2500PipeIndex, dfl2500PipePrecIndex }
    ::= { dfl2500PipePrecTable 1 }

Dfl2500PipePrecEntry ::= SEQUENCE {
    dfl2500PipePrecIndex            Integer32,
    dfl2500PipePrec                 Integer32,
    dfl2500PipePrecBps              Gauge32,
    dfl2500PipePrecTotalPps         Gauge32,
    dfl2500PipePrecReservedBps      Gauge32,
    dfl2500PipePrecDynLimBps        Gauge32,
    dfl2500PipePrecDynUsrLimBps     Gauge32,
    dfl2500PipePrecDelayedPackets   Counter32,
    dfl2500PipePrecDropedPackets    Counter32
}

dfl2500PipePrecIndex OBJECT-TYPE
    SYNTAX      Integer32 (1..2147483647)
    MAX-ACCESS  not-accessible
    STATUS      current
    DESCRIPTION 
        "Index of a precedence of a specific pipe. This is the second index 
         of the entries of pipe precedence table described by object 
         dfl2500PipePrecEntry."
    ::= { dfl2500PipePrecEntry 1 }

dfl2500PipePrec OBJECT-TYPE
    SYNTAX      Integer32
    MAX-ACCESS  read-only
    STATUS      current
    DESCRIPTION 
        "The precedence value"
    ::= { dfl2500PipePrecEntry 2 }

dfl2500PipePrecBps OBJECT-TYPE
    SYNTAX      Gauge32
    MAX-ACCESS  read-only
    STATUS      current
    DESCRIPTION 
        "The current throughput of the pipe, in bits per second, with 
         the corresponding precedence."
    ::= { dfl2500PipePrecEntry 3 }

dfl2500PipePrecTotalPps OBJECT-TYPE
    SYNTAX      Gauge32
    MAX-ACCESS  read-only
    STATUS      current
    DESCRIPTION 
        "The current throughput of the pipe precedence, in packets per second."
    ::= { dfl2500PipePrecEntry 4 }

dfl2500PipePrecReservedBps OBJECT-TYPE
    SYNTAX      Gauge32
    MAX-ACCESS  read-only
    STATUS      current
    DESCRIPTION 
        "The current bandwidth allocated to the precedence."
    ::= { dfl2500PipePrecEntry 5 }

dfl2500PipePrecDynLimBps OBJECT-TYPE
    SYNTAX      Gauge32
    MAX-ACCESS  read-only
    STATUS      current
    DESCRIPTION 
        "The current bandwidth limit limit applied the precedence."
    ::= { dfl2500PipePrecEntry 6 }

dfl2500PipePrecDynUsrLimBps OBJECT-TYPE
    SYNTAX      Gauge32
    MAX-ACCESS  read-only
    STATUS      current
    DESCRIPTION 
        "The current precedence bandwidth limit per user of the pipe."
    ::= { dfl2500PipePrecEntry 7 }

dfl2500PipePrecDelayedPackets OBJECT-TYPE
    SYNTAX      Counter32
    MAX-ACCESS  read-only
    STATUS      current
    DESCRIPTION 
        "The number of times packets have been delayed as a result of a 
         precedence, or pipe user having used up its allotted bandwidth. 
         Note that one single packet may be delayed several times; if a 
         pipe is really full, this count may exceed the number of packets 
         of this precedence actually passing through the pipe."
    ::= { dfl2500PipePrecEntry 8 }

dfl2500PipePrecDropedPackets OBJECT-TYPE
    SYNTAX      Counter32
    MAX-ACCESS  read-only
    STATUS      current
    DESCRIPTION 
        "The number of pipe dropped packets with the corresponding precedence."
    ::= { dfl2500PipePrecEntry 9 }

dfl2500ALG OBJECT IDENTIFIER
    ::= { dfl2500OSStats 9 }

dfl2500AlgSessions OBJECT-TYPE
    SYNTAX      Gauge32
    MAX-ACCESS  read-only
    STATUS      current
    DESCRIPTION 
        "Total ALG sessions"
    ::= { dfl2500ALG 1 }

dfl2500AlgConnections OBJECT-TYPE
    SYNTAX      Gauge32
    MAX-ACCESS  read-only
    STATUS      current
    DESCRIPTION 
        "Total ALG connections"
    ::= { dfl2500ALG 2 }

dfl2500AlgTCPStreams OBJECT-TYPE
    SYNTAX      Gauge32
    MAX-ACCESS  read-only
    STATUS      current
    DESCRIPTION 
        "Total ALG TCP streams"
    ::= { dfl2500ALG 3 }

dfl2500HttpAlg OBJECT IDENTIFIER
    ::= { dfl2500ALG 4 }

dfl2500HttpAlgTable OBJECT-TYPE
    SYNTAX      SEQUENCE OF Dfl2500HttpAlgEntry
    MAX-ACCESS  not-accessible
    STATUS      current
    DESCRIPTION 
        "Table of HTTP ALG objects."
    ::= { dfl2500HttpAlg 1 }

dfl2500HttpAlgEntry OBJECT-TYPE
    SYNTAX      Dfl2500HttpAlgEntry
    MAX-ACCESS  not-accessible
    STATUS      current
    DESCRIPTION 
        "A row of the table of HTTP ALG objects."
    INDEX       { dfl2500HttpAlgIndex }
    ::= { dfl2500HttpAlgTable 1 }

Dfl2500HttpAlgEntry ::= SEQUENCE {
    dfl2500HttpAlgIndex             Integer32,
    dfl2500HttpAlgName              DisplayString,
    dfl2500HttpAlgTotalRequested    Gauge32,
    dfl2500HttpAlgTotalAllowed      Gauge32,
    dfl2500HttpAlgTotalBlocked      Gauge32
}

dfl2500HttpAlgIndex OBJECT-TYPE
    SYNTAX      Integer32 (1..2147483647)
    MAX-ACCESS  not-accessible
    STATUS      current
    DESCRIPTION 
        "The index of an entry of the  Table of HTTP ALG objects."
    ::= { dfl2500HttpAlgEntry 1 }

dfl2500HttpAlgName OBJECT-TYPE
    SYNTAX      DisplayString
    MAX-ACCESS  read-only
    STATUS      current
    DESCRIPTION 
        "The name of an HTTP ALG object."
    ::= { dfl2500HttpAlgEntry 2 }

dfl2500HttpAlgTotalRequested OBJECT-TYPE
    SYNTAX      Gauge32
    MAX-ACCESS  read-only
    STATUS      current
    DESCRIPTION 
        "Total number of URL requests."
    ::= { dfl2500HttpAlgEntry 3 }

dfl2500HttpAlgTotalAllowed OBJECT-TYPE
    SYNTAX      Gauge32
    MAX-ACCESS  read-only
    STATUS      current
    DESCRIPTION 
        "Total number of allowed URL requests."
    ::= { dfl2500HttpAlgEntry 4 }

dfl2500HttpAlgTotalBlocked OBJECT-TYPE
    SYNTAX      Gauge32
    MAX-ACCESS  read-only
    STATUS      current
    DESCRIPTION 
        "Total number of blocked URL requests."
    ::= { dfl2500HttpAlgEntry 5 }

dfl2500HttpAlgCntFltTable OBJECT-TYPE
    SYNTAX      SEQUENCE OF Dfl2500HttpAlgCntFltEntry
    MAX-ACCESS  not-accessible
    STATUS      current
    DESCRIPTION 
        "Table of HTTP ALG content filtering rules."
    ::= { dfl2500HttpAlg 2 }

dfl2500HttpAlgCntFltEntry OBJECT-TYPE
    SYNTAX      Dfl2500HttpAlgCntFltEntry
    MAX-ACCESS  not-accessible
    STATUS      current
    DESCRIPTION 
        "Entry of the table of HTTP ALG content filtering rules."
    INDEX       { dfl2500HttpAlgIndex, dfl2500HttpAlgCntFltIndex }
    ::= { dfl2500HttpAlgCntFltTable 1 }

Dfl2500HttpAlgCntFltEntry ::= SEQUENCE {
    dfl2500HttpAlgCntFltIndex       Integer32,
    dfl2500HttpAlgCntFltName        DisplayString,
    dfl2500HttpAlgCntFltRequests    Gauge32,
    dfl2500HttpAlgCntFltAllowed     Gauge32,
    dfl2500HttpAlgCntFltBlocked     Gauge32
}

dfl2500HttpAlgCntFltIndex OBJECT-TYPE
    SYNTAX      Integer32 (1..2147483647)
    MAX-ACCESS  not-accessible
    STATUS      current
    DESCRIPTION 
        "The index of an entry of the  Table of HTTP ALG 
         content filtering objects."
    ::= { dfl2500HttpAlgCntFltEntry 1 }

dfl2500HttpAlgCntFltName OBJECT-TYPE
    SYNTAX      DisplayString
    MAX-ACCESS  read-only
    STATUS      current
    DESCRIPTION 
        "The name of the a HTTP ALG content fitering."
    ::= { dfl2500HttpAlgCntFltEntry 2 }

dfl2500HttpAlgCntFltRequests OBJECT-TYPE
    SYNTAX      Gauge32
    MAX-ACCESS  read-only
    STATUS      current
    DESCRIPTION 
        "Total number of URLs intercepted by a content 
         filtering object."
    ::= { dfl2500HttpAlgCntFltEntry 3 }

dfl2500HttpAlgCntFltAllowed OBJECT-TYPE
    SYNTAX      Gauge32
    MAX-ACCESS  read-only
    STATUS      current
    DESCRIPTION 
        "Total number of URLs intercepted and allowed 
         by a content filtering object."
    ::= { dfl2500HttpAlgCntFltEntry 4 }

dfl2500HttpAlgCntFltBlocked OBJECT-TYPE
    SYNTAX      Gauge32
    MAX-ACCESS  read-only
    STATUS      current
    DESCRIPTION 
        "Total number of URLs intercepted and blocked 
         by a content filtering object."
    ::= { dfl2500HttpAlgCntFltEntry 5 }

dfl2500SmtpAlg OBJECT IDENTIFIER
    ::= { dfl2500ALG 5 }

dfl2500SmtpAlgTable OBJECT-TYPE
    SYNTAX  SEQUENCE OF Dfl2500SmtpAlgEntry
    MAX-ACCESS  not-accessible
    STATUS  current
    DESCRIPTION
  "Table of SMTP ALG objects."
    ::= { dfl2500SmtpAlg 1 }

dfl2500SmtpAlgEntry OBJECT-TYPE
   SYNTAX  Dfl2500SmtpAlgEntry
   MAX-ACCESS  not-accessible
    STATUS      current
    DESCRIPTION 
        "A row of the table of SMTP ALG objects."
    INDEX       { dfl2500SmtpAlgIndex }
    ::= { dfl2500SmtpAlgTable 1 }

Dfl2500SmtpAlgEntry ::= SEQUENCE {
    dfl2500SmtpAlgIndex           Integer32,
    dfl2500SmtpAlgName            DisplayString,
    dfl2500SmtpAlgTotCheckedSes   Gauge32,
    dfl2500SmtpAlgTotSpamSes      Gauge32,
    dfl2500SmtpAlgTotDroppedSes   Gauge32
}

dfl2500SmtpAlgIndex OBJECT-TYPE
    SYNTAX      Integer32 (1..2147483647)
    MAX-ACCESS  not-accessible
    STATUS      current
    DESCRIPTION 
        "The index of an entry of the  Table of SMTP ALG objects."
    ::= { dfl2500SmtpAlgEntry 1 }

dfl2500SmtpAlgName OBJECT-TYPE
    SYNTAX      DisplayString
    MAX-ACCESS  read-only
    STATUS      current
    DESCRIPTION 
        "The name of an SMTP ALG object."
    ::= { dfl2500SmtpAlgEntry 2 }

dfl2500SmtpAlgTotCheckedSes OBJECT-TYPE
    SYNTAX      Gauge32
    MAX-ACCESS  read-only
    STATUS      current
    DESCRIPTION 
        "Total sessions checked by the SMTP ALG of corresponding index."
    ::= { dfl2500SmtpAlgEntry 3 }

dfl2500SmtpAlgTotSpamSes OBJECT-TYPE
    SYNTAX      Gauge32
    MAX-ACCESS  read-only
    STATUS      current
    DESCRIPTION 
        "Total spam sessions detected by the SMTP ALG of corresponding index."
    ::= { dfl2500SmtpAlgEntry 4 }

dfl2500SmtpAlgTotDroppedSes OBJECT-TYPE
    SYNTAX      Gauge32
    MAX-ACCESS  read-only
    STATUS      current
    DESCRIPTION 
        "Total deroped sessions for the SMTP ALG of corresponding index."
    ::= { dfl2500SmtpAlgEntry 5 }


dfl2500SmtpAlgDnsBlTable OBJECT-TYPE
    SYNTAX  SEQUENCE OF Dfl2500SmtpAlgDnsBlEntry
    MAX-ACCESS  not-accessible
    STATUS  current
    DESCRIPTION
  "Table of SMTP ALG DNS balck list objects."
    ::= { dfl2500SmtpAlg 2 }


dfl2500SmtpAlgDnsBlEntry OBJECT-TYPE
   SYNTAX  Dfl2500SmtpAlgDnsBlEntry
   MAX-ACCESS  not-accessible
    STATUS      current
    DESCRIPTION 
        "A row of the table of SMTP ALG DNS black list objects."
    INDEX       { dfl2500SmtpAlgIndex, dfl2500SmtpAlgDnsBlIndex }
    ::= { dfl2500SmtpAlgDnsBlTable 1 }


Dfl2500SmtpAlgDnsBlEntry ::= SEQUENCE {
    dfl2500SmtpAlgDnsBlIndex  Integer32,
    dfl2500SmtpAlgDnsBlName    DisplayString,
    dfl2500SmtpAlgDnsBlChecked      Gauge32,
    dfl2500SmtpAlgDnsBlMatched  Gauge32,
    dfl2500SmtpAlgDnsBlFailChecks  Gauge32
}

dfl2500SmtpAlgDnsBlIndex OBJECT-TYPE
    SYNTAX      Integer32 (1..2147483647)
    MAX-ACCESS  not-accessible
    STATUS      current
    DESCRIPTION 
        "The index of an entry of the  SMTP ALG DNS black list objects." 
    ::= { dfl2500SmtpAlgDnsBlEntry 1 }

dfl2500SmtpAlgDnsBlName OBJECT-TYPE
    SYNTAX      DisplayString
    MAX-ACCESS  read-only
    STATUS      current
    DESCRIPTION 
  "The SMTP DNS black list name."
    ::= { dfl2500SmtpAlgDnsBlEntry 2 }

dfl2500SmtpAlgDnsBlChecked OBJECT-TYPE
    SYNTAX      Gauge32
    MAX-ACCESS  read-only
    STATUS      current
    DESCRIPTION 
  "Total sessions checked againt SMTP ALG DNS black list of corresponding index"
    ::= { dfl2500SmtpAlgDnsBlEntry 3 }

dfl2500SmtpAlgDnsBlMatched OBJECT-TYPE
    SYNTAX      Gauge32
    MAX-ACCESS  read-only
    STATUS      current
    DESCRIPTION 
  "Total sessions that matched SMTP ALG DNS black list of corresponding index"
    ::= { dfl2500SmtpAlgDnsBlEntry 4 }

dfl2500SmtpAlgDnsBlFailChecks OBJECT-TYPE
    SYNTAX      Gauge32
    MAX-ACCESS  read-only
    STATUS      current
    DESCRIPTION 
  "Total failed checks for the SMTP ALG DNS black list of corresponding index"
    ::= { dfl2500SmtpAlgDnsBlEntry 5 }

dfl2500DHCPRelay OBJECT IDENTIFIER
    ::= { dfl2500OSStats 11 }

dfl2500DHCPRelayCurClients OBJECT-TYPE
    SYNTAX      Gauge32
    MAX-ACCESS  read-only
    STATUS      current
    DESCRIPTION 
        "Total DHCP relay active relayed clients."
    ::= { dfl2500DHCPRelay 1 }

dfl2500DHCPRelayCurTrans OBJECT-TYPE
    SYNTAX      Gauge32
    MAX-ACCESS  read-only
    STATUS      current
    DESCRIPTION 
        "Ongoing DHCP relay transactions."
    ::= { dfl2500DHCPRelay 2 }

dfl2500DHCPRelayRejected OBJECT-TYPE
    SYNTAX      Gauge32
    MAX-ACCESS  read-only
    STATUS      current
    DESCRIPTION 
        "Total DHCP relay packets rejected."
    ::= { dfl2500DHCPRelay 3 }

dfl2500DHCPRelayRuleTable OBJECT-TYPE
    SYNTAX      SEQUENCE OF Dfl2500DHCPRelayRuleEntry
    MAX-ACCESS  not-accessible
    STATUS      current
    DESCRIPTION 
        "Table of DHCP relay rules."
    ::= { dfl2500DHCPRelay 4 }

dfl2500DHCPRelayRuleEntry OBJECT-TYPE
    SYNTAX      Dfl2500DHCPRelayRuleEntry
    MAX-ACCESS  not-accessible
    STATUS      current
    DESCRIPTION 
        "Entry of the table of DHCP relay rules"
    INDEX       { dfl2500DHCPRelayRuleIndex }
    ::= { dfl2500DHCPRelayRuleTable 1 }

Dfl2500DHCPRelayRuleEntry ::= SEQUENCE {
    dfl2500DHCPRelayRuleIndex       Integer32,
    dfl2500DHCPRelayRuleName        DisplayString,
    dfl2500DHCPRelayRuleHits        Gauge32,
    dfl2500DHCPRelayRuleCurClients  Gauge32,
    dfl2500DHCPRelayRuleRejCliPkts  Gauge32,
    dfl2500DHCPRelayRuleRejSrvPkts  Gauge32
}

dfl2500DHCPRelayRuleIndex OBJECT-TYPE
    SYNTAX      Integer32 (1..2147483647)
    MAX-ACCESS  not-accessible
    STATUS      current
    DESCRIPTION 
        "Index of the table of DHCP relay rules."
    ::= { dfl2500DHCPRelayRuleEntry 1 }

dfl2500DHCPRelayRuleName OBJECT-TYPE
    SYNTAX      DisplayString
    MAX-ACCESS  read-only
    STATUS      current
    DESCRIPTION 
        "Display name of a DHCP relay rule"
    ::= { dfl2500DHCPRelayRuleEntry 2 }

dfl2500DHCPRelayRuleHits OBJECT-TYPE
    SYNTAX      Gauge32
    MAX-ACCESS  read-only
    STATUS      current
    DESCRIPTION 
        "Number of the times the  DHCP relay rule with corresponding index was 
         used."
    ::= { dfl2500DHCPRelayRuleEntry 3 }

dfl2500DHCPRelayRuleCurClients OBJECT-TYPE
    SYNTAX      Gauge32
    MAX-ACCESS  read-only
    STATUS      current
    DESCRIPTION 
        "Number of ctive relayed clients by the DHCP relay rule with corresponding index."
    ::= { dfl2500DHCPRelayRuleEntry 4 }

dfl2500DHCPRelayRuleRejCliPkts OBJECT-TYPE
    SYNTAX      Gauge32
    MAX-ACCESS  read-only
    STATUS      current
    DESCRIPTION 
        "Number of client packets rejected by a rule."
    ::= { dfl2500DHCPRelayRuleEntry 5 }

dfl2500DHCPRelayRuleRejSrvPkts OBJECT-TYPE
    SYNTAX      Gauge32
    MAX-ACCESS  read-only
    STATUS      current
    DESCRIPTION 
        "Number of DHCP server packets rejected by the DHCP relay rule 
         with the corresponding index."
    ::= { dfl2500DHCPRelayRuleEntry 6 }

dfl2500HA OBJECT IDENTIFIER
    ::= { dfl2500OSStats 12 }

dfl2500HASyncSendQueueLength OBJECT-TYPE
    SYNTAX      Gauge32
    MAX-ACCESS  read-only
    STATUS      current
    DESCRIPTION 
        "Size of the queue used for the High Availability sync interface."
    ::= { dfl2500HA 1 }

dfl2500HASyncSendQueueUsagePkt OBJECT-TYPE
    SYNTAX      Gauge32
    MAX-ACCESS  read-only
    STATUS      current
    DESCRIPTION 
        "High Availability Sync interface queue usage in number of packets."
    ::= { dfl2500HA 2 }

dfl2500HASyncSendQueueUsageOct OBJECT-TYPE
    SYNTAX      Gauge32
    MAX-ACCESS  read-only
    STATUS      current
    DESCRIPTION 
        "High Availability Sync interface queue usage in number of octects."
    ::= { dfl2500HA 3 }

dfl2500HASyncSentPackets OBJECT-TYPE
    SYNTAX      Counter32
    MAX-ACCESS  read-only
    STATUS      current
    DESCRIPTION 
        "Number High Availability packets sent on Sync."
    ::= { dfl2500HA 4 }

dfl2500HASyncSendResentPackets OBJECT-TYPE
    SYNTAX      Counter32
    MAX-ACCESS  read-only
    STATUS      current
    DESCRIPTION 
        "Number of High Availability packets resent on Sync."
    ::= { dfl2500HA 5 }

dfl2500StatsConformance OBJECT IDENTIFIER
    ::= { dfl2500MibConfs 1 }

dfl2500StatsRegGroups OBJECT IDENTIFIER
    ::= { dfl2500MibObjectGroups 1 }

dfl2500SystemObjectGroup OBJECT-GROUP
    OBJECTS     { dfl2500SysCpuLoad, 
                  dfl2500SysForwardedBits, 
                  dfl2500SysForwardedPackets, 
                  dfl2500SysBuffUse, 
                  dfl2500SysConns, 
                  dfl2500HWSensorName, 
                  dfl2500HWSensorValue, 
                  dfl2500HWSensorUnit, 
                  dfl2500SysMemUsage, 
                  dfl2500SysTimerUsage, 
                  dfl2500SysConnOPS, 
                  dfl2500SysConnCPS,
                  dfl2500SysHCForwardedBits }
    STATUS      current
    DESCRIPTION 
        "System statistics Group"
    ::= { dfl2500StatsRegGroups 1 }

dfl2500IPsecObjectGroup OBJECT-GROUP
    OBJECTS     { dfl2500IPsecPhaseOneActive, 
                  dfl2500IPsecPhaseOneAggrModeDone, 
                  dfl2500IPsecQuickModeActive, 
                  dfl2500IPsecPhaseOneDone, 
                  dfl2500IPsecPhaseOneFailed, 
                  dfl2500IPsecPhaseOneRekeyed, 
                  dfl2500IPsecQuickModeDone, 
                  dfl2500IPsecQuickModeFailed, 
                  dfl2500IPsecInfoDone, 
                  dfl2500IPsecInfoFailed, 
                  dfl2500IPsecInOctetsComp, 
                  dfl2500IPsecInOctetsUncomp, 
                  dfl2500IPsecOutOctetsComp, 
                  dfl2500IPsecOutOctetsUncomp, 
                  dfl2500IPsecForwardedOctetsComp, 
                  dfl2500IPsecForwardedOctetsUcomp, 
                  dfl2500IPsecInPackets, 
                  dfl2500IPsecOutPackets, 
                  dfl2500IPsecForwardedPackets, 
                  dfl2500IPsecActiveTransforms, 
                  dfl2500IPsecTotalTransforms, 
                  dfl2500IPsecOutOfTransforms, 
                  dfl2500IPsecTotalRekeys }
    STATUS      current
    DESCRIPTION 
        "IPsec Group"
    ::= { dfl2500StatsRegGroups 2 }

dfl2500StateCountersGroup OBJECT-GROUP
    OBJECTS     { dfl2500SysPscTcpSyn, 
                  dfl2500SysPscTcpOpen, 
                  dfl2500SysPscTcpFin, 
                  dfl2500SysPscUdp, 
                  dfl2500SysPscIcmp, 
                  dfl2500SysPscOther }
    STATUS      current
    DESCRIPTION 
        "Per state counters"
    ::= { dfl2500StatsRegGroups 3 }

dfl2500IPPoolGroup OBJECT-GROUP
    OBJECTS     { dfl2500IPPoolsNumber, 
                  dfl2500IPPoolName, 
                  dfl2500IPPoolPrepare, 
                  dfl2500IPPoolFree, 
                  dfl2500IPPoolMisses, 
                  dfl2500IPPoolClientFails, 
                  dfl2500IPPoolUsed }
    STATUS      current
    DESCRIPTION 
        "IP pool entry objects group"
    ::= { dfl2500StatsRegGroups 4 }

dfl2500DHCPServerGroup OBJECT-GROUP
    OBJECTS     { dfl2500DHCPTotalRejected, 
                  dfl2500DHCPRuleName, 
                  dfl2500DHCPRuleUsage, 
                  dfl2500DHCPRuleUsagePercent, 
                  dfl2500DHCPActiveClients, 
                  dfl2500DHCPActiveClientsPercent, 
                  dfl2500DHCPRejectedRequests, 
                  dfl2500DHCPTotalLeases }
    STATUS      current
    DESCRIPTION 
        "DHCP server rules objects."
    ::= { dfl2500StatsRegGroups 5 }

dfl2500RuleUseGroup OBJECT-GROUP
    OBJECTS     { dfl2500RuleName, dfl2500RuleUse }
    STATUS      current
    DESCRIPTION 
        "Rule use objects."
    ::= { dfl2500StatsRegGroups 6 }

dfl2500UserAuthGroup OBJECT-GROUP
    OBJECTS     { dfl2500UserAuthHTTPUsers, dfl2500UserAuthXAUTHUsers, 
                  dfl2500UserAuthHTTPSUsers, dfl2500UserAuthPPPUsers, 
                  dfl2500UserAuthEAPUsers, dfl2500UserAuthRuleName, 
                  dfl2500UserAuthRuleUse }
    STATUS      current
    DESCRIPTION 
        "User auth objects."
    ::= { dfl2500StatsRegGroups 7 }

dfl2500IfStatsGroup OBJECT-GROUP
    OBJECTS     { dfl2500IfName, 
                  dfl2500IfFragsIn, 
                  dfl2500IfFragReassOk, 
                  dfl2500IfFragReassFail, 
                  dfl2500IfPktsInCnt, 
                  dfl2500IfPktsOutCnt, 
                  dfl2500IfBitsInCnt, 
                  dfl2500IfBitsOutCnt, 
                  dfl2500IfPktsTotCnt, 
                  dfl2500IfBitsTotCnt, 
                  dfl2500IfHCPktsInCnt, 
                  dfl2500IfHCPktsOutCnt, 
                  dfl2500IfHCBitsInCnt, 
                  dfl2500IfHCBitsOutCnt, 
                  dfl2500IfHCPktsTotCnt, 
                  dfl2500IfHCBitsTotCnt,
                  dfl2500IfRxRingFifoErrors, 
                  dfl2500IfRxDespools, 
                  dfl2500IfRxAvgUse, 
                  dfl2500IfRxRingSaturation, 
                  dfl2500RxRingFlooded, 
                  dfl2500IfTxDespools, 
                  dfl2500IfTxAvgUse, 
                  dfl2500IfTxRingSaturation, 
                  dfl2500RxTingFlooded }
    STATUS      current
    DESCRIPTION 
        "DFL-2500 interface statistics group."
    ::= { dfl2500StatsRegGroups 8 }

dfl2500LinkMonitorGroup OBJECT-GROUP
    OBJECTS     { dfl2500LinkMonGrp, 
                  dfl2500LinkMonGrpName, 
                  dfl2500LinkMonGrpHostsUp, 
                  dfl2500LinkMonHostId, 
                  dfl2500LinkMonHostShortTermLoss, 
                  dfl2500LinkMonHostPacketsLost }
    STATUS      current
    DESCRIPTION 
        "DFL-2500 link monitor statistics group"
    ::= { dfl2500StatsRegGroups 9 }

dfl2500PipesObjectGroup OBJECT-GROUP
    OBJECTS     { dfl2500PipeUsers, 
                  dfl2500PipeName, 
                  dfl2500PipeMinPrec, 
                  dfl2500PipeMaxPrec, 
                  dfl2500PipeDefPrec, 
                  dfl2500PipeNumPrec, 
                  dfl2500PipeNumUsers, 
                  dfl2500PipeCurrentBps, 
                  dfl2500PipeCurrentPps, 
                  dfl2500PipeDelayedPackets, 
                  dfl2500PipeDropedPackets, 
                  dfl2500PipePrec, 
                  dfl2500PipePrecBps, 
                  dfl2500PipePrecTotalPps, 
                  dfl2500PipePrecReservedBps, 
                  dfl2500PipePrecDynLimBps, 
                  dfl2500PipePrecDynUsrLimBps, 
                  dfl2500PipePrecDelayedPackets, 
                  dfl2500PipePrecDropedPackets }
    STATUS      current
    DESCRIPTION 
        "DFL-2500 pipes statistics group"
    ::= { dfl2500StatsRegGroups 10 }

dfl2500DHCPRelayObjectGroup OBJECT-GROUP
    OBJECTS     { dfl2500DHCPRelayCurClients, 
                  dfl2500DHCPRelayCurTrans, 
                  dfl2500DHCPRelayRejected, 
                  dfl2500DHCPRelayRuleName, 
                  dfl2500DHCPRelayRuleHits, 
                  dfl2500DHCPRelayRuleCurClients, 
                  dfl2500DHCPRelayRuleRejCliPkts, 
                  dfl2500DHCPRelayRuleRejSrvPkts }
    STATUS      current
    DESCRIPTION 
        "DFL-2500 DHCP relay statistics group"
    ::= { dfl2500StatsRegGroups 12 }

dfl2500AlgGroup OBJECT-GROUP
    OBJECTS     { dfl2500AlgSessions, 
                  dfl2500AlgConnections, 
                  dfl2500AlgTCPStreams, 
                  dfl2500HttpAlgName, 
                  dfl2500HttpAlgTotalRequested, 
                  dfl2500HttpAlgTotalAllowed, 
                  dfl2500HttpAlgTotalBlocked, 
                  dfl2500HttpAlgCntFltName, 
                  dfl2500HttpAlgCntFltRequests, 
                  dfl2500HttpAlgCntFltAllowed, 
                  dfl2500HttpAlgCntFltBlocked }
    STATUS      current
    DESCRIPTION 
        "DFL-2500 HTTP ALG statistics group"
    ::= { dfl2500StatsRegGroups 13 }

dfl2500HAGroup OBJECT-GROUP
    OBJECTS     { dfl2500HASyncSendQueueLength, 
                  dfl2500HASyncSendQueueUsagePkt, 
                  dfl2500HASyncSendQueueUsageOct, 
                  dfl2500HASyncSentPackets, 
                  dfl2500HASyncSendResentPackets }
    STATUS      current
    DESCRIPTION 
        "DFL-2500 HA statistics group"
    ::= { dfl2500StatsRegGroups 14 }

dfl2500IfVlanGroup OBJECT-GROUP
    OBJECTS     { dfl2500IfVlanUntaggedInPkts, 
                  dfl2500IfVlanUntaggedOutPkts, 
                  dfl2500IfVlanUntaggedTotPkts, 
                  dfl2500IfVlanUntaggedInOctets, 
                  dfl2500IfVlanUntaggedOutOctets, 
                  dfl2500IfVlanUntaggedTotOctets }
    STATUS      current
    DESCRIPTION 
        "DFL-2500 VLAN statistics group"
    ::= { dfl2500StatsRegGroups 15 }


dfl2500SmtpAlgGroup OBJECT-GROUP 
    OBJECTS { dfl2500SmtpAlgName,
              dfl2500SmtpAlgTotCheckedSes,
              dfl2500SmtpAlgTotSpamSes,
              dfl2500SmtpAlgTotDroppedSes,
              dfl2500SmtpAlgDnsBlName,    
              dfl2500SmtpAlgDnsBlChecked,     
              dfl2500SmtpAlgDnsBlMatched,  
              dfl2500SmtpAlgDnsBlFailChecks }
   STATUS current
   DESCRIPTION
       "Clavister SMTP ALG objects group"
   ::= { dfl2500StatsRegGroups 16 }
   
dfl2500SysTCPGroup OBJECT-GROUP 
    OBJECTS { dfl2500SysTCPRecvSmall,
              dfl2500SysTCPRecvLarge,
              dfl2500SysTCPSendSmall,
              dfl2500SysTCPSendLarge }
    STATUS current
    DESCRIPTION
      "DFL-2500 TCP buffer usage group"
    ::= { dfl2500StatsRegGroups 17 }



dfl2500StatsCompliance MODULE-COMPLIANCE
    STATUS      current
    DESCRIPTION 
        "Module Compliance"

    MODULE      -- this module

        MANDATORY-GROUPS        
                { dfl2500SystemObjectGroup, 
                  dfl2500IPsecObjectGroup, 
                  dfl2500StateCountersGroup, 
                  dfl2500IPPoolGroup, 
                  dfl2500DHCPServerGroup, 
                  dfl2500RuleUseGroup, 
                  dfl2500UserAuthGroup, 
                  dfl2500IfStatsGroup, 
                  dfl2500LinkMonitorGroup, 
                  dfl2500PipesObjectGroup, 
                  dfl2500DHCPRelayObjectGroup, 
                  dfl2500AlgGroup, 
                  dfl2500HAGroup, 
                  dfl2500IfVlanGroup, 
                  dfl2500SmtpAlgGroup, 
                  dfl2500SysTCPGroup }

    ::= { dfl2500StatsConformance 1 }

END -- end of module DFL2500-MIB.
