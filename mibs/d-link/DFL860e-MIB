--
-- DFL-860e SMIv2 module
--

DFL860e-MIB DEFINITIONS ::= BEGIN

IMPORTS
    MODULE-COMPLIANCE, OBJECT-GROUP
        FROM SNMPv2-CONF
    Counter32, Counter64, Gauge32, Integer32, MODULE-IDENTITY, 
    OBJECT-TYPE, enterprises
        FROM SNMPv2-SMI
    DisplayString
        FROM SNMPv2-TC;

dfl860e-MIB MODULE-IDENTITY
    LAST-UPDATED "201009021139Z"
    ORGANIZATION 
        "D-Link Corporation"
    CONTACT-INFO 
        "Postal: D-Link Corporation
         No. 289, Sinhu 3rd Road,
         Neihu District, Taipei City 114,
         Taiwan, R.O.C.
         Tel: +886-2-66000123
         Fax: +886-2-55509988"
    DESCRIPTION 
        "The MIB module for D-Link DFL-860e series product."
    
    REVISION  "201009021139Z"
    DESCRIPTION 
        "Added 64-bit counters"
    REVISION  "201003300900Z"
    DESCRIPTION 
        "Added values for SMTP ALG objects."
    REVISION  "200911100916Z"
    DESCRIPTION 
        "Added values for opened and closed connections per second"
    REVISION  "200811181605Z"
    DESCRIPTION 
        "Added value for timer usage"
    REVISION  "200810141227Z"
    DESCRIPTION 
        "Added values for memory usage and TCP buffer usage"    
    REVISION  "200710310000Z"
    DESCRIPTION 
        "Initial version."
    ::= { dfl860eMibModules 2 }


dlink OBJECT IDENTIFIER
    ::= { enterprises 171 }

netdefendMgmt OBJECT IDENTIFIER
    ::= { dlink 20 }

utmFirewall OBJECT IDENTIFIER
    ::= { netdefendMgmt 2 }

dfl860e OBJECT IDENTIFIER
    ::= { utmFirewall 7 }

dfl860eOS OBJECT IDENTIFIER
    ::= { dfl860e 1 }

dfl860eOSStats OBJECT IDENTIFIER
    ::= { dfl860eOS 2 }

dfl860ereg OBJECT IDENTIFIER
    ::= { dfl860e 2 }

dfl860eMibModules OBJECT IDENTIFIER
    ::= { dfl860ereg 1 }

dfl860eMibConfs OBJECT IDENTIFIER
    ::= { dfl860ereg 2 }

dfl860eMibObjectGroups OBJECT IDENTIFIER
    ::= { dfl860ereg 3 }


dfl860eSystem OBJECT IDENTIFIER
    ::= { dfl860eOSStats 1 }

dfl860eSysCpuLoad OBJECT-TYPE
    SYNTAX      Gauge32
    MAX-ACCESS  read-only
    STATUS      current
    DESCRIPTION 
        "The system cpu load."
    ::= { dfl860eSystem 1 }

dfl860eSysForwardedBits OBJECT-TYPE
    SYNTAX      Counter32
    MAX-ACCESS  read-only
    STATUS      current
    DESCRIPTION
        "The number of bits forwarded through the gateway."
    ::= { dfl860eSystem 2 }

dfl860eSysForwardedPackets OBJECT-TYPE
    SYNTAX      Counter32
    MAX-ACCESS  read-only
    STATUS      current
    DESCRIPTION
        "Total number of forwarded packets."
    ::= { dfl860eSystem 3 }

dfl860eSysBuffUse OBJECT-TYPE
    SYNTAX      Gauge32
    MAX-ACCESS  read-only
    STATUS      current
    DESCRIPTION 
        "The current number of buffers in use."
    ::= { dfl860eSystem 4 }

dfl860eSysConns OBJECT-TYPE
    SYNTAX      Gauge32
    MAX-ACCESS  read-only
    STATUS      current
    DESCRIPTION 
        "The numer of connections."
    ::= { dfl860eSystem 5 }

dfl860eSysPerStateCounters OBJECT IDENTIFIER
    ::= { dfl860eSystem 6 }

dfl860eSysPscTcpSyn OBJECT-TYPE
    SYNTAX      Gauge32
    MAX-ACCESS  read-only
    STATUS      current
    DESCRIPTION 
        "Number of TCP connections in the SYN state."
    ::= { dfl860eSysPerStateCounters 1 }

dfl860eSysPscTcpOpen OBJECT-TYPE
    SYNTAX      Gauge32
    MAX-ACCESS  read-only
    STATUS      current
    DESCRIPTION 
        "Number of TCP connections in the OPEN state."
    ::= { dfl860eSysPerStateCounters 2 }

dfl860eSysPscTcpFin OBJECT-TYPE
    SYNTAX      Gauge32
    MAX-ACCESS  read-only
    STATUS      current
    DESCRIPTION 
        "Number of TCP connections in the FIN state."
    ::= { dfl860eSysPerStateCounters 3 }

dfl860eSysPscUdp OBJECT-TYPE
    SYNTAX      Gauge32
    MAX-ACCESS  read-only
    STATUS      current
    DESCRIPTION 
        "Number of UDP connections."
    ::= { dfl860eSysPerStateCounters 4 }

dfl860eSysPscIcmp OBJECT-TYPE
    SYNTAX      Gauge32
    MAX-ACCESS  read-only
    STATUS      current
    DESCRIPTION 
        "Number of ICMP connections."
    ::= { dfl860eSysPerStateCounters 5 }

dfl860eSysPscOther OBJECT-TYPE
    SYNTAX      Gauge32
    MAX-ACCESS  read-only
    STATUS      current
    DESCRIPTION 
        "Number of other connections."
    ::= { dfl860eSysPerStateCounters 6 }

dfl860eIfStatsTable OBJECT-TYPE
    SYNTAX      SEQUENCE OF Dfl860eIfStatsEntry
    MAX-ACCESS  not-accessible
    STATUS      current
    DESCRIPTION 
        "A table of DFL-860e specific interfaces statistics"
    ::= { dfl860eSystem 7 }

dfl860eIfStatsEntry OBJECT-TYPE
    SYNTAX      Dfl860eIfStatsEntry
    MAX-ACCESS  not-accessible
    STATUS      current
    DESCRIPTION 
        "The row in a table of DFL-860e specific interface statistics"
    INDEX       { dfl860eIfStatsIndex }
    ::= { dfl860eIfStatsTable 1 }

Dfl860eIfStatsEntry ::= SEQUENCE {
    dfl860eIfStatsIndex     Integer32,
    dfl860eIfName           DisplayString,
    dfl860eIfFragsIn        Counter32,
    dfl860eIfFragReassOk    Counter32,
    dfl860eIfFragReassFail  Counter32,
    dfl860eIfPktsInCnt      Counter32,
    dfl860eIfPktsOutCnt     Counter32,
    dfl860eIfBitsInCnt      Counter32,
    dfl860eIfBitsOutCnt     Counter32,
    dfl860eIfPktsTotCnt     Counter32,
    dfl860eIfBitsTotCnt     Counter32,
    dfl860eIfHCPktsInCnt    Counter64,
    dfl860eIfHCPktsOutCnt   Counter64,
    dfl860eIfHCBitsInCnt    Counter64,
    dfl860eIfHCBitsOutCnt   Counter64,
    dfl860eIfHCPktsTotCnt   Counter64,
    dfl860eIfHCBitsTotCnt   Counter64
}

dfl860eIfStatsIndex OBJECT-TYPE
    SYNTAX      Integer32 (1..2147483647)
    MAX-ACCESS  not-accessible
    STATUS      current
    DESCRIPTION 
        "Index of a row in dfl860eSysIfStatsTable"
    ::= { dfl860eIfStatsEntry 1 }

dfl860eIfName OBJECT-TYPE
    SYNTAX      DisplayString
    MAX-ACCESS  read-only
    STATUS      current
    DESCRIPTION 
        "The name of the interface."
    ::= { dfl860eIfStatsEntry 2 }

dfl860eIfFragsIn OBJECT-TYPE
    SYNTAX      Counter32
    MAX-ACCESS  read-only
    STATUS      current
    DESCRIPTION 
        "Number of IP packet fragments received 
         in the interface."
    ::= { dfl860eIfStatsEntry 3 }

dfl860eIfFragReassOk OBJECT-TYPE
    SYNTAX      Counter32
    MAX-ACCESS  read-only
    STATUS      current
    DESCRIPTION 
        "Number of complete IP packets successfully 
         reassembled from the fragments received in 
         the interface."
    ::= { dfl860eIfStatsEntry 4 }

dfl860eIfFragReassFail OBJECT-TYPE
    SYNTAX      Counter32
    MAX-ACCESS  read-only
    STATUS      current
    DESCRIPTION 
        "Number of packets that could not be reassembled, 
         either due to resource starvation, illegal fragmentation, 
         or just packet loss."
    ::= { dfl860eIfStatsEntry 5 }

dfl860eIfPktsInCnt OBJECT-TYPE
    SYNTAX      Counter32
    MAX-ACCESS  read-only
    STATUS      current
    DESCRIPTION 
        "Number of packets received by the interface."
    ::= { dfl860eIfStatsEntry 6 }

dfl860eIfPktsOutCnt OBJECT-TYPE
    SYNTAX      Counter32
    MAX-ACCESS  read-only
    STATUS      current
    DESCRIPTION 
        "Number of packets sent by the interface"
    ::= { dfl860eIfStatsEntry 7 }

dfl860eIfBitsInCnt OBJECT-TYPE
    SYNTAX      Counter32
    MAX-ACCESS  read-only
    STATUS      current
    DESCRIPTION 
        "Number of bits received by the interface"
    ::= { dfl860eIfStatsEntry 8 }

dfl860eIfBitsOutCnt OBJECT-TYPE
    SYNTAX      Counter32
    MAX-ACCESS  read-only
    STATUS      current
    DESCRIPTION 
        "Number of bits sent by the interface"
    ::= { dfl860eIfStatsEntry 9 }

dfl860eIfPktsTotCnt OBJECT-TYPE
    SYNTAX      Counter32
    MAX-ACCESS  read-only
    STATUS      current
    DESCRIPTION 
        "Totat number of packets transmited by the interface"
    ::= { dfl860eIfStatsEntry 10 }

dfl860eIfBitsTotCnt OBJECT-TYPE
    SYNTAX      Counter32
    MAX-ACCESS  read-only
    STATUS      current
    DESCRIPTION 
        "Totat number of bits transmited by the interface"
    ::= { dfl860eIfStatsEntry 11 }

dfl860eIfHCPktsInCnt OBJECT-TYPE
    SYNTAX      Counter64
    MAX-ACCESS  read-only
    STATUS      current
    DESCRIPTION 
        "Number of packets received by the interface.
        This object is a 64-bit version of dfl860eIfPktsInCnt."
    ::= { dfl860eIfStatsEntry 12 }

dfl860eIfHCPktsOutCnt OBJECT-TYPE
    SYNTAX      Counter64
    MAX-ACCESS  read-only
    STATUS      current
    DESCRIPTION 
        "Number of packets sent by the interface.
        This object is a 64-bit version of dfl860eIfPktsOutCnt."
    ::= { dfl860eIfStatsEntry 13 }

dfl860eIfHCBitsInCnt OBJECT-TYPE
    SYNTAX      Counter64
    MAX-ACCESS  read-only
    STATUS      current
    DESCRIPTION 
        "Number of bits received by the interface.
        This object is a 64-bit version of dfl860eIfBitsInCnt."
    ::= { dfl860eIfStatsEntry 14 }

dfl860eIfHCBitsOutCnt OBJECT-TYPE
    SYNTAX      Counter64
    MAX-ACCESS  read-only
    STATUS      current
    DESCRIPTION 
        "Number of bits sent by the interface.
        This object is a 64-bit version of dfl860eIfBitsOutCnt."
    ::= { dfl860eIfStatsEntry 15 }

dfl860eIfHCPktsTotCnt OBJECT-TYPE
    SYNTAX      Counter64
    MAX-ACCESS  read-only
    STATUS      current
    DESCRIPTION 
        "Totat number of packets transmited by the interface.
        This object is a 64-bit version of dfl860eIfPktsTotCnt."
    ::= { dfl860eIfStatsEntry 16 }

dfl860eIfHCBitsTotCnt OBJECT-TYPE
    SYNTAX      Counter64
    MAX-ACCESS  read-only
    STATUS      current
    DESCRIPTION 
        "Totat number of bits transmited by the interface. 
        This object is a 64-bit version of dfl860eIfBitsTotCnt."
    ::= { dfl860eIfStatsEntry 17 }

dfl860eIfRxRingTable OBJECT-TYPE
    SYNTAX      SEQUENCE OF Dfl860eIfRxRingEntry
    MAX-ACCESS  not-accessible
    STATUS      current
    DESCRIPTION 
        "A table of DFL-860e specific interface Rx ring statistics"
    ::= { dfl860eSystem 8 }

dfl860eIfRxRingEntry OBJECT-TYPE
    SYNTAX      Dfl860eIfRxRingEntry
    MAX-ACCESS  not-accessible
    STATUS      current
    DESCRIPTION 
        "The row in a table of DFL-860e specific interface Rx ring 
         statistics."
    INDEX       { dfl860eIfRxRingIndex }
    ::= { dfl860eIfRxRingTable 1 }

Dfl860eIfRxRingEntry ::= SEQUENCE {
    dfl860eIfRxRingIndex        Integer32,
    dfl860eIfRxRingFifoErrors   Counter32,
    dfl860eIfRxDespools         Gauge32,
    dfl860eIfRxAvgUse           Gauge32,
    dfl860eIfRxRingSaturation   Gauge32,
    dfl860eRxRingFlooded        Gauge32
}

dfl860eIfRxRingIndex OBJECT-TYPE
    SYNTAX      Integer32 (1..2147483647)
    MAX-ACCESS  not-accessible
    STATUS      current
    DESCRIPTION 
        "Index of a row in dfl860eIfRxRingTable."
    ::= { dfl860eIfRxRingEntry 1 }

dfl860eIfRxRingFifoErrors OBJECT-TYPE
    SYNTAX      Counter32
    MAX-ACCESS  read-only
    STATUS      current
    DESCRIPTION 
        "Rx Ring number of FIFO errors."
    ::= { dfl860eIfRxRingEntry 2 }

dfl860eIfRxDespools OBJECT-TYPE
    SYNTAX      Gauge32
    MAX-ACCESS  read-only
    STATUS      current
    DESCRIPTION 
        "Number of despool events per second."
    ::= { dfl860eIfRxRingEntry 3 }

dfl860eIfRxAvgUse OBJECT-TYPE
    SYNTAX      Gauge32
    MAX-ACCESS  read-only
    STATUS      current
    DESCRIPTION 
        "Rx Ring average usage."
    ::= { dfl860eIfRxRingEntry 4 }

dfl860eIfRxRingSaturation OBJECT-TYPE
    SYNTAX      Gauge32
    MAX-ACCESS  read-only
    STATUS      current
    DESCRIPTION 
        "Rx Ring sturation. Percentage of ring use per despool 
         event when the ring has been more than half full."
    ::= { dfl860eIfRxRingEntry 5 }

dfl860eRxRingFlooded OBJECT-TYPE
    SYNTAX      Gauge32
    MAX-ACCESS  read-only
    STATUS      current
    DESCRIPTION 
        "Rx Ring number of despool events for which 
         the ring has been completely flooded"
    ::= { dfl860eIfRxRingEntry 6 }

dfl860eIfTxRingTable OBJECT-TYPE
    SYNTAX      SEQUENCE OF Dfl860eIfTxRingEntry
    MAX-ACCESS  not-accessible
    STATUS      current
    DESCRIPTION 
        "A table of DFL-860e specific interface Tx ring statistics"
    ::= { dfl860eSystem 9 }

dfl860eIfTxRingEntry OBJECT-TYPE
    SYNTAX      Dfl860eIfTxRingEntry
    MAX-ACCESS  not-accessible
    STATUS      current
    DESCRIPTION 
        "The row in a table of DFL-860e specific interface Tx ring 
         statistics."
    INDEX       { dfl860eIfTxRingIndex }
    ::= { dfl860eIfTxRingTable 1 }

Dfl860eIfTxRingEntry ::= SEQUENCE {
    dfl860eIfTxRingIndex        Integer32,
    dfl860eIfTxDespools         Gauge32,
    dfl860eIfTxAvgUse           Gauge32,
    dfl860eIfTxRingSaturation   Gauge32,
    dfl860eRxTingFlooded        Gauge32
}

dfl860eIfTxRingIndex OBJECT-TYPE
    SYNTAX      Integer32 (1..2147483647)
    MAX-ACCESS  not-accessible
    STATUS      current
    DESCRIPTION 
        "Index of a row in dfl860eIfRxRingTable."
    ::= { dfl860eIfTxRingEntry 1 }

dfl860eIfTxDespools OBJECT-TYPE
    SYNTAX      Gauge32
    MAX-ACCESS  read-only
    STATUS      current
    DESCRIPTION 
        "Tx Ring number of despool event per second (polls when 
         there is at least one buffer in the ring)"
    ::= { dfl860eIfTxRingEntry 2 }

dfl860eIfTxAvgUse OBJECT-TYPE
    SYNTAX      Gauge32
    MAX-ACCESS  read-only
    STATUS      current
    DESCRIPTION 
        "Tx Ring number of despool events when the ring has 
         been completely flooded"
    ::= { dfl860eIfTxRingEntry 3 }

dfl860eIfTxRingSaturation OBJECT-TYPE
    SYNTAX      Gauge32
    MAX-ACCESS  read-only
    STATUS      current
    DESCRIPTION 
        "Tx Ring percentage of use per despool event when the 
         ring has been more than half full."
    ::= { dfl860eIfTxRingEntry 4 }

dfl860eRxTingFlooded OBJECT-TYPE
    SYNTAX      Gauge32
    MAX-ACCESS  read-only
    STATUS      current
    DESCRIPTION 
        "Tx Ring number of despool events for in which the ring has 
         been completely flooded"
    ::= { dfl860eIfTxRingEntry 5 }

dfl860eIfVlanStatsTable OBJECT-TYPE
    SYNTAX      SEQUENCE OF Dfl860eIfVlanStatsEntry
    MAX-ACCESS  not-accessible
    STATUS      current
    DESCRIPTION 
        "A table of DFL-860e VLAN statistics"
    ::= { dfl860eSystem 10 }

dfl860eIfVlanStatsEntry OBJECT-TYPE
    SYNTAX      Dfl860eIfVlanStatsEntry
    MAX-ACCESS  not-accessible
    STATUS      current
    DESCRIPTION 
        "The row in a table of dfl860eIfVlanStatsTable. Each has an index 
         equal to the ifIndex of the corresponding physical interface"
    INDEX       { dfl860eIfVlanIndex }
    ::= { dfl860eIfVlanStatsTable 1 }

Dfl860eIfVlanStatsEntry ::= SEQUENCE {
    dfl860eIfVlanIndex              Integer32,
    dfl860eIfVlanUntaggedInPkts     Counter32,
    dfl860eIfVlanUntaggedOutPkts    Counter32,
    dfl860eIfVlanUntaggedTotPkts    Counter32,
    dfl860eIfVlanUntaggedInOctets   Counter32,
    dfl860eIfVlanUntaggedOutOctets  Counter32,
    dfl860eIfVlanUntaggedTotOctets  Counter32
}

dfl860eIfVlanIndex OBJECT-TYPE
    SYNTAX      Integer32 (1..2147483647)
    MAX-ACCESS  not-accessible
    STATUS      current
    DESCRIPTION 
        "Extended index of a row in dfl860eIfVlanStatsTable."
    ::= { dfl860eIfVlanStatsEntry 1 }

dfl860eIfVlanUntaggedInPkts OBJECT-TYPE
    SYNTAX      Counter32
    MAX-ACCESS  read-only
    STATUS      current
    DESCRIPTION 
        "Number of untaged packets untagged packets received by the interface."
    ::= { dfl860eIfVlanStatsEntry 2 }

dfl860eIfVlanUntaggedOutPkts OBJECT-TYPE
    SYNTAX      Counter32
    MAX-ACCESS  read-only
    STATUS      current
    DESCRIPTION 
        "Number of untagged packets sent by the interface."
    ::= { dfl860eIfVlanStatsEntry 3 }

dfl860eIfVlanUntaggedTotPkts OBJECT-TYPE
    SYNTAX      Counter32
    MAX-ACCESS  read-only
    STATUS      current
    DESCRIPTION 
        "Total number of untagged packets processed by the interface."
    ::= { dfl860eIfVlanStatsEntry 4 }

dfl860eIfVlanUntaggedInOctets OBJECT-TYPE
    SYNTAX      Counter32
    MAX-ACCESS  read-only
    STATUS      current
    DESCRIPTION 
        "Total number of octects in untagged packets received by the interface."
    ::= { dfl860eIfVlanStatsEntry 5 }

dfl860eIfVlanUntaggedOutOctets OBJECT-TYPE
    SYNTAX      Counter32
    MAX-ACCESS  read-only
    STATUS      current
    DESCRIPTION 
        "Total number of octects in untagged packets sent by the interface."
    ::= { dfl860eIfVlanStatsEntry 6 }

dfl860eIfVlanUntaggedTotOctets OBJECT-TYPE
    SYNTAX      Counter32
    MAX-ACCESS  read-only
    STATUS      current
    DESCRIPTION 
        "Total number of octects in untagged packets processed by the 
         interface."
    ::= { dfl860eIfVlanStatsEntry 7 }

dfl860eHWSensorTable OBJECT-TYPE
    SYNTAX      SEQUENCE OF Dfl860eHWSensorEntry
    MAX-ACCESS  not-accessible
    STATUS      current
    DESCRIPTION 
        "Table of hardware sensors."
    ::= { dfl860eSystem 11 }

dfl860eHWSensorEntry OBJECT-TYPE
    SYNTAX      Dfl860eHWSensorEntry
    MAX-ACCESS  not-accessible
    STATUS      current
    DESCRIPTION 
        "Entry  of table of hardware sensors."
    INDEX       { dfl860eHWSensorIndex }
    ::= { dfl860eHWSensorTable 1 }

Dfl860eHWSensorEntry ::= SEQUENCE {
    dfl860eHWSensorIndex    Integer32,
    dfl860eHWSensorName     DisplayString,
    dfl860eHWSensorValue    Gauge32,
    dfl860eHWSensorUnit     DisplayString
}

dfl860eHWSensorIndex OBJECT-TYPE
    SYNTAX      Integer32 (1..2147483647)
    MAX-ACCESS  not-accessible
    STATUS      current
    DESCRIPTION 
        "Index of the entries of the sensor table."
    ::= { dfl860eHWSensorEntry 1 }

dfl860eHWSensorName OBJECT-TYPE
    SYNTAX      DisplayString
    MAX-ACCESS  read-only
    STATUS      current
    DESCRIPTION 
        "The description of the sensor."
    ::= { dfl860eHWSensorEntry 2 }

dfl860eHWSensorValue OBJECT-TYPE
    SYNTAX      Gauge32
    MAX-ACCESS  read-only
    STATUS      current
    DESCRIPTION 
        "The value of the sensor."
    ::= { dfl860eHWSensorEntry 3 }

dfl860eHWSensorUnit OBJECT-TYPE
    SYNTAX      DisplayString
    MAX-ACCESS  read-only
    STATUS      current
    DESCRIPTION 
        "The description of the unit of the value mesured by sensor."
    ::= { dfl860eHWSensorEntry 4 }

dfl860eSysMemUsage OBJECT-TYPE
    SYNTAX      Gauge32
    MAX-ACCESS  read-only
    STATUS      current
    DESCRIPTION 
        "The current memory usage."
    ::= { dfl860eSystem 12 }

dfl860eSysTCPUsage OBJECT IDENTIFIER
    ::= { dfl860eSystem 13 }
    
dfl860eSysTCPRecvSmall OBJECT-TYPE
    SYNTAX      Gauge32
    MAX-ACCESS  read-only
    STATUS      current
    DESCRIPTION 
        "Small TCP receive windows usage."
    ::= { dfl860eSysTCPUsage 1 }

dfl860eSysTCPRecvLarge OBJECT-TYPE
    SYNTAX      Gauge32
    MAX-ACCESS  read-only
    STATUS      current
    DESCRIPTION 
        "Large TCP receive windows usage."
    ::= { dfl860eSysTCPUsage 2 }

dfl860eSysTCPSendSmall OBJECT-TYPE
    SYNTAX      Gauge32
    MAX-ACCESS  read-only
    STATUS      current
    DESCRIPTION 
        "Small TCP send windows usage."
    ::= { dfl860eSysTCPUsage 3 }

dfl860eSysTCPSendLarge OBJECT-TYPE
    SYNTAX      Gauge32
    MAX-ACCESS  read-only
    STATUS      current
    DESCRIPTION 
        "Large TCP send windows usage."
    ::= { dfl860eSysTCPUsage 4 }

dfl860eSysTimerUsage OBJECT-TYPE
    SYNTAX      Gauge32
    MAX-ACCESS  read-only
    STATUS      current
    DESCRIPTION 
        "The current number of timers in use."
    ::= { dfl860eSystem 14 }

dfl860eSysConnOPS OBJECT-TYPE
    SYNTAX      Gauge32
    MAX-ACCESS  read-only
    STATUS      current
    DESCRIPTION 
        "The number of connections opened per second."
    ::= { dfl860eSystem 15 }
    
dfl860eSysConnCPS OBJECT-TYPE
    SYNTAX      Gauge32
    MAX-ACCESS  read-only
    STATUS      current
    DESCRIPTION 
        "The number of connections closed per second."
    ::= { dfl860eSystem 16 }
    
dfl860eSysHCForwardedBits OBJECT-TYPE
    SYNTAX      Counter64
    MAX-ACCESS  read-only
    STATUS      current
    DESCRIPTION
        "The number of bits forwarded through the gateway."
    ::= { dfl860eSystem 17 }
    
dfl860eVPN OBJECT IDENTIFIER
    ::= { dfl860eOSStats 2 }

dfl860eIPsec OBJECT IDENTIFIER
    ::= { dfl860eVPN 1 }

dfl860eIPsecGlobal OBJECT IDENTIFIER
    ::= { dfl860eIPsec 1 }

dfl860eIPsecPhaseOneActive OBJECT-TYPE
    SYNTAX      Gauge32
    MAX-ACCESS  read-only
    STATUS      current
    DESCRIPTION 
        "Number of Phase-1 active negotiations"
    ::= { dfl860eIPsecGlobal 1 }

dfl860eIPsecPhaseOneAggrModeDone OBJECT-TYPE
    SYNTAX      Gauge32
    MAX-ACCESS  read-only
    STATUS      current
    DESCRIPTION 
        "Number of Phase-1 aggressive mode negotiations."
    ::= { dfl860eIPsecGlobal 2 }

dfl860eIPsecQuickModeActive OBJECT-TYPE
    SYNTAX      Gauge32
    MAX-ACCESS  read-only
    STATUS      current
    DESCRIPTION 
        "Number of quick mode active negotiations."
    ::= { dfl860eIPsecGlobal 3 }

dfl860eIPsecPhaseOneDone OBJECT-TYPE
    SYNTAX      Counter32
    MAX-ACCESS  read-only
    STATUS      current
    DESCRIPTION 
        "Number of Phase-1 negotiations done."
    ::= { dfl860eIPsecGlobal 4 }

dfl860eIPsecPhaseOneFailed OBJECT-TYPE
    SYNTAX      Counter32
    MAX-ACCESS  read-only
    STATUS      current
    DESCRIPTION 
        "Number of Phase-1 negotiations failed."
    ::= { dfl860eIPsecGlobal 5 }

dfl860eIPsecPhaseOneRekeyed OBJECT-TYPE
    SYNTAX      Counter32
    MAX-ACCESS  read-only
    STATUS      current
    DESCRIPTION 
        "Number of Phase-1 negotiations rekeyed."
    ::= { dfl860eIPsecGlobal 6 }

dfl860eIPsecQuickModeDone OBJECT-TYPE
    SYNTAX      Counter32
    MAX-ACCESS  read-only
    STATUS      current
    DESCRIPTION 
        "Number of quick mode  negotiations done."
    ::= { dfl860eIPsecGlobal 7 }

dfl860eIPsecQuickModeFailed OBJECT-TYPE
    SYNTAX      Counter32
    MAX-ACCESS  read-only
    STATUS      current
    DESCRIPTION 
        "Number of quick mode negotiations failed."
    ::= { dfl860eIPsecGlobal 8 }

dfl860eIPsecInfoDone OBJECT-TYPE
    SYNTAX      Counter32
    MAX-ACCESS  read-only
    STATUS      current
    DESCRIPTION 
        "Number of informational exchanges done.
         (Not available in IKEv1 implementations)"
    ::= { dfl860eIPsecGlobal 9 }

dfl860eIPsecInfoFailed OBJECT-TYPE
    SYNTAX      Counter32
    MAX-ACCESS  read-only
    STATUS      current
    DESCRIPTION 
        "Number of informational exchanges failed.
         (Not available in IKEv1 implementations)"
    ::= { dfl860eIPsecGlobal 10 }

dfl860eIPsecInOctetsComp OBJECT-TYPE
    SYNTAX      Counter64
    MAX-ACCESS  read-only
    STATUS      current
    DESCRIPTION 
        "Total octets in before decompression."
    ::= { dfl860eIPsecGlobal 11 }

dfl860eIPsecInOctetsUncomp OBJECT-TYPE
    SYNTAX      Counter64
    MAX-ACCESS  read-only
    STATUS      current
    DESCRIPTION 
        "Total octets in after decompression."
    ::= { dfl860eIPsecGlobal 12 }

dfl860eIPsecOutOctetsComp OBJECT-TYPE
    SYNTAX      Counter64
    MAX-ACCESS  read-only
    STATUS      current
    DESCRIPTION 
        "Total octets out after compression."
    ::= { dfl860eIPsecGlobal 13 }

dfl860eIPsecOutOctetsUncomp OBJECT-TYPE
    SYNTAX      Counter64
    MAX-ACCESS  read-only
    STATUS      current
    DESCRIPTION 
        "Total octets out before compression."
    ::= { dfl860eIPsecGlobal 14 }

dfl860eIPsecForwardedOctetsComp OBJECT-TYPE
    SYNTAX      Counter64
    MAX-ACCESS  read-only
    STATUS      current
    DESCRIPTION 
        "Total octets forwarded after compression."
    ::= { dfl860eIPsecGlobal 15 }

dfl860eIPsecForwardedOctetsUcomp OBJECT-TYPE
    SYNTAX      Counter64
    MAX-ACCESS  read-only
    STATUS      current
    DESCRIPTION 
        "Total octets forwarded before compression."
    ::= { dfl860eIPsecGlobal 16 }

dfl860eIPsecInPackets OBJECT-TYPE
    SYNTAX      Counter64
    MAX-ACCESS  read-only
    STATUS      current
    DESCRIPTION 
        "Total packets in."
    ::= { dfl860eIPsecGlobal 17 }

dfl860eIPsecOutPackets OBJECT-TYPE
    SYNTAX      Counter64
    MAX-ACCESS  read-only
    STATUS      current
    DESCRIPTION 
        "Total packets Out."
    ::= { dfl860eIPsecGlobal 18 }

dfl860eIPsecForwardedPackets OBJECT-TYPE
    SYNTAX      Counter64
    MAX-ACCESS  read-only
    STATUS      current
    DESCRIPTION 
        "Total packets forwarded."
    ::= { dfl860eIPsecGlobal 19 }

dfl860eIPsecActiveTransforms OBJECT-TYPE
    SYNTAX      Gauge32
    MAX-ACCESS  read-only
    STATUS      current
    DESCRIPTION 
        "Number of currently active transforms."
    ::= { dfl860eIPsecGlobal 20 }

dfl860eIPsecTotalTransforms OBJECT-TYPE
    SYNTAX      Counter32
    MAX-ACCESS  read-only
    STATUS      current
    DESCRIPTION 
        "Total number of transform records created."
    ::= { dfl860eIPsecGlobal 21 }

dfl860eIPsecOutOfTransforms OBJECT-TYPE
    SYNTAX      Counter32
    MAX-ACCESS  read-only
    STATUS      current
    DESCRIPTION 
        "Number of packets dropped due to no available transform object.
         (Not available in IKEv1 implementations)"
    ::= { dfl860eIPsecGlobal 22 }

dfl860eIPsecTotalRekeys OBJECT-TYPE
    SYNTAX      Counter32
    MAX-ACCESS  read-only
    STATUS      current
    DESCRIPTION 
        "Total number of rekeys performed."
    ::= { dfl860eIPsecGlobal 23 }

dfl860eRules OBJECT IDENTIFIER
    ::= { dfl860eOSStats 3 }

dfl860eRuleUseTable OBJECT-TYPE
    SYNTAX      SEQUENCE OF Dfl860eRuleUseEntry
    MAX-ACCESS  not-accessible
    STATUS      current
    DESCRIPTION 
        "A list of general rules usage statistics."
    ::= { dfl860eRules 2 }

dfl860eRuleUseEntry OBJECT-TYPE
    SYNTAX      Dfl860eRuleUseEntry
    MAX-ACCESS  not-accessible
    STATUS      current
    DESCRIPTION 
        "The statistics over a rule usage."
    INDEX       { dfl860eRuleIndex }
    ::= { dfl860eRuleUseTable 1 }

Dfl860eRuleUseEntry ::= SEQUENCE {
    dfl860eRuleIndex    Integer32,
    dfl860eRuleName     DisplayString,
    dfl860eRuleUse      Counter32
}

dfl860eRuleIndex OBJECT-TYPE
    SYNTAX      Integer32 (1..2147483647)
    MAX-ACCESS  not-accessible
    STATUS      current
    DESCRIPTION 
        "The rule usage index."
    ::= { dfl860eRuleUseEntry 1 }

dfl860eRuleName OBJECT-TYPE
    SYNTAX      DisplayString
    MAX-ACCESS  read-only
    STATUS      current
    DESCRIPTION 
        "The name of the rule."
    ::= { dfl860eRuleUseEntry 2 }

dfl860eRuleUse OBJECT-TYPE
    SYNTAX      Counter32
    MAX-ACCESS  read-only
    STATUS      current
    DESCRIPTION 
        "The number of times o rule was used."
    ::= { dfl860eRuleUseEntry 3 }

dfl860eIPPools OBJECT IDENTIFIER
    ::= { dfl860eOSStats 4 }

dfl860eIPPoolsNumber OBJECT-TYPE
    SYNTAX      Integer32
    MAX-ACCESS  read-only
    STATUS      current
    DESCRIPTION 
        "The number of ip pools"
    ::= { dfl860eIPPools 1 }

dfl860eIPPoolTable OBJECT-TYPE
    SYNTAX      SEQUENCE OF Dfl860eIPPoolEntry
    MAX-ACCESS  not-accessible
    STATUS      current
    DESCRIPTION 
        "A list of IP pools"
    ::= { dfl860eIPPools 2 }

dfl860eIPPoolEntry OBJECT-TYPE
    SYNTAX      Dfl860eIPPoolEntry
    MAX-ACCESS  not-accessible
    STATUS      current
    DESCRIPTION 
        "The attributes of an ip pool"
    INDEX       { dfl860eIPPoolIndex }
    ::= { dfl860eIPPoolTable 1 }

Dfl860eIPPoolEntry ::= SEQUENCE {
    dfl860eIPPoolIndex          Integer32,
    dfl860eIPPoolName           DisplayString,
    dfl860eIPPoolPrepare        Gauge32,
    dfl860eIPPoolFree           Gauge32,
    dfl860eIPPoolMisses         Gauge32,
    dfl860eIPPoolClientFails    Gauge32,
    dfl860eIPPoolUsed           Gauge32
}

dfl860eIPPoolIndex OBJECT-TYPE
    SYNTAX      Integer32 (1..2147483647)
    MAX-ACCESS  not-accessible
    STATUS      current
    DESCRIPTION 
        "The ip pool index"
    ::= { dfl860eIPPoolEntry 1 }

dfl860eIPPoolName OBJECT-TYPE
    SYNTAX      DisplayString
    MAX-ACCESS  read-only
    STATUS      current
    DESCRIPTION 
        "The ip pool name"
    ::= { dfl860eIPPoolEntry 2 }

dfl860eIPPoolPrepare OBJECT-TYPE
    SYNTAX      Gauge32
    MAX-ACCESS  read-only
    STATUS      current
    DESCRIPTION 
        "Number of IP pool objects in prepare mode."
    ::= { dfl860eIPPoolEntry 3 }

dfl860eIPPoolFree OBJECT-TYPE
    SYNTAX      Gauge32
    MAX-ACCESS  read-only
    STATUS      current
    DESCRIPTION 
        "Number of available IPs in the pool."
    ::= { dfl860eIPPoolEntry 4 }

dfl860eIPPoolMisses OBJECT-TYPE
    SYNTAX      Gauge32
    MAX-ACCESS  read-only
    STATUS      current
    DESCRIPTION 
        "Mumber of missed IP pool negotiations for other reasons
         than lack of available IP numbers."
    ::= { dfl860eIPPoolEntry 5 }

dfl860eIPPoolClientFails OBJECT-TYPE
    SYNTAX      Gauge32
    MAX-ACCESS  read-only
    STATUS      current
    DESCRIPTION 
        "Number of failed IP pool transactions."
    ::= { dfl860eIPPoolEntry 6 }

dfl860eIPPoolUsed OBJECT-TYPE
    SYNTAX      Gauge32
    MAX-ACCESS  read-only
    STATUS      current
    DESCRIPTION 
        "Number of IP numbers in use from the pool."
    ::= { dfl860eIPPoolEntry 7 }

dfl860eDHCPServer OBJECT IDENTIFIER
    ::= { dfl860eOSStats 5 }

dfl860eDHCPTotalRejected OBJECT-TYPE
    SYNTAX      Gauge32
    MAX-ACCESS  read-only
    STATUS      current
    DESCRIPTION 
        "Total number of rejected packets (all rules)."
    ::= { dfl860eDHCPServer 1 }

dfl860eDHCPRuleTable OBJECT-TYPE
    SYNTAX      SEQUENCE OF Dfl860eDHCPRuleEntry
    MAX-ACCESS  not-accessible
    STATUS      current
    DESCRIPTION 
        "A list of all DHCP server rules usage statistics."
    ::= { dfl860eDHCPServer 2 }

dfl860eDHCPRuleEntry OBJECT-TYPE
    SYNTAX      Dfl860eDHCPRuleEntry
    MAX-ACCESS  not-accessible
    STATUS      current
    DESCRIPTION 
        "The attributes of a DHCP server rule statistics."
    INDEX       { dfl860eDHCPRuleIndex }
    ::= { dfl860eDHCPRuleTable 1 }

Dfl860eDHCPRuleEntry ::= SEQUENCE {
    dfl860eDHCPRuleIndex                Integer32,
    dfl860eDHCPRuleName                 DisplayString,
    dfl860eDHCPRuleUsage                Gauge32,
    dfl860eDHCPRuleUsagePercent         Gauge32,
    dfl860eDHCPActiveClients            Gauge32,
    dfl860eDHCPActiveClientsPercent     Gauge32,
    dfl860eDHCPRejectedRequests         Gauge32,
    dfl860eDHCPTotalLeases              Gauge32
}

dfl860eDHCPRuleIndex OBJECT-TYPE
    SYNTAX      Integer32 (1..2147483647)
    MAX-ACCESS  not-accessible
    STATUS      current
    DESCRIPTION 
        "The DHCP server rule  index"
    ::= { dfl860eDHCPRuleEntry 1 }

dfl860eDHCPRuleName OBJECT-TYPE
    SYNTAX      DisplayString
    MAX-ACCESS  read-only
    STATUS      current
    DESCRIPTION 
        "The DHCP server rule name."
    ::= { dfl860eDHCPRuleEntry 2 }

dfl860eDHCPRuleUsage OBJECT-TYPE
    SYNTAX      Gauge32
    MAX-ACCESS  read-only
    STATUS      current
    DESCRIPTION 
        "Number of used IPs in the pool."
    ::= { dfl860eDHCPRuleEntry 3 }

dfl860eDHCPRuleUsagePercent OBJECT-TYPE
    SYNTAX      Gauge32
    MAX-ACCESS  read-only
    STATUS      current
    DESCRIPTION 
        "The percentage of the used IPs in 
         relation to the IP pool size."
    ::= { dfl860eDHCPRuleEntry 4 }

dfl860eDHCPActiveClients OBJECT-TYPE
    SYNTAX      Gauge32
    MAX-ACCESS  read-only
    STATUS      current
    DESCRIPTION 
        "Number of currently active clients."
    ::= { dfl860eDHCPRuleEntry 5 }

dfl860eDHCPActiveClientsPercent OBJECT-TYPE
    SYNTAX      Gauge32
    MAX-ACCESS  read-only
    STATUS      current
    DESCRIPTION 
        "The number of currently active clients 
         as a percentage of the pool size."
    ::= { dfl860eDHCPRuleEntry 6 }

dfl860eDHCPRejectedRequests OBJECT-TYPE
    SYNTAX      Gauge32
    MAX-ACCESS  read-only
    STATUS      current
    DESCRIPTION 
        "Number of rejected requests matching
         the current rule."
    ::= { dfl860eDHCPRuleEntry 7 }

dfl860eDHCPTotalLeases OBJECT-TYPE
    SYNTAX      Gauge32
    MAX-ACCESS  read-only
    STATUS      current
    DESCRIPTION 
        "Total number of leases in the pool."
    ::= { dfl860eDHCPRuleEntry 8 }

dfl860eUserAuth OBJECT IDENTIFIER
    ::= { dfl860eOSStats 6 }

dfl860eUserAuthHTTPUsers OBJECT-TYPE
    SYNTAX      Gauge32
    MAX-ACCESS  read-only
    STATUS      current
    DESCRIPTION 
        "Number of currently  logged in HTTP users."
    ::= { dfl860eUserAuth 1 }

dfl860eUserAuthXAUTHUsers OBJECT-TYPE
    SYNTAX      Gauge32
    MAX-ACCESS  read-only
    STATUS      current
    DESCRIPTION 
        "Number of currently logged in XAUTH users."
    ::= { dfl860eUserAuth 2 }

dfl860eUserAuthHTTPSUsers OBJECT-TYPE
    SYNTAX      Gauge32
    MAX-ACCESS  read-only
    STATUS      current
    DESCRIPTION 
        "Number of currently logged in HTTPS users."
    ::= { dfl860eUserAuth 3 }

dfl860eUserAuthPPPUsers OBJECT-TYPE
    SYNTAX      Gauge32
    MAX-ACCESS  read-only
    STATUS      current
    DESCRIPTION 
        "Number of currently logged in PPP users."
    ::= { dfl860eUserAuth 4 }

dfl860eUserAuthEAPUsers OBJECT-TYPE
    SYNTAX      Gauge32
    MAX-ACCESS  read-only
    STATUS      current
    DESCRIPTION 
        "Number of currently logged in EAP users."
    ::= { dfl860eUserAuth 5 }

dfl860eUserAuthRuleUseTable OBJECT-TYPE
    SYNTAX      SEQUENCE OF Dfl860eUserAuthRuleUseEntry
    MAX-ACCESS  not-accessible
    STATUS      current
    DESCRIPTION 
        "Table of user authentication rule usage."
    ::= { dfl860eUserAuth 6 }

dfl860eUserAuthRuleUseEntry OBJECT-TYPE
    SYNTAX      Dfl860eUserAuthRuleUseEntry
    MAX-ACCESS  not-accessible
    STATUS      current
    DESCRIPTION 
        "The attributes of an authentication rule 
         usage statistics."
    INDEX       { dfl860eUserAuthRuleIndex }
    ::= { dfl860eUserAuthRuleUseTable 1 }

Dfl860eUserAuthRuleUseEntry ::= SEQUENCE {
    dfl860eUserAuthRuleIndex    Integer32,
    dfl860eUserAuthRuleName     DisplayString,
    dfl860eUserAuthRuleUse      Counter32
}

dfl860eUserAuthRuleIndex OBJECT-TYPE
    SYNTAX      Integer32 (1..2147483647)
    MAX-ACCESS  not-accessible
    STATUS      current
    DESCRIPTION 
        "The rule usage index."
    ::= { dfl860eUserAuthRuleUseEntry 1 }

dfl860eUserAuthRuleName OBJECT-TYPE
    SYNTAX      DisplayString
    MAX-ACCESS  read-only
    STATUS      current
    DESCRIPTION 
        "The name of the rule."
    ::= { dfl860eUserAuthRuleUseEntry 2 }

dfl860eUserAuthRuleUse OBJECT-TYPE
    SYNTAX      Counter32
    MAX-ACCESS  read-only
    STATUS      current
    DESCRIPTION 
        "The number of times o rule was used."
    ::= { dfl860eUserAuthRuleUseEntry 3 }

dfl860eLinkMonitor OBJECT IDENTIFIER
    ::= { dfl860eOSStats 7 }

dfl860eLinkMonGrp OBJECT-TYPE
    SYNTAX      Integer32
    MAX-ACCESS  read-only
    STATUS      current
    DESCRIPTION 
        "The number of groups of monitored links"
    ::= { dfl860eLinkMonitor 1 }

dfl860eLinkMonGrpTable OBJECT-TYPE
    SYNTAX      SEQUENCE OF Dfl860eLinkMonGrpEntry
    MAX-ACCESS  not-accessible
    STATUS      current
    DESCRIPTION 
        "Table of link monitor groups."
    ::= { dfl860eLinkMonitor 2 }

dfl860eLinkMonGrpEntry OBJECT-TYPE
    SYNTAX      Dfl860eLinkMonGrpEntry
    MAX-ACCESS  not-accessible
    STATUS      current
    DESCRIPTION 
        "The attributes of a link monitor group"
    INDEX       { dfl860eLinkMonGrpIndex }
    ::= { dfl860eLinkMonGrpTable 1 }

Dfl860eLinkMonGrpEntry ::= SEQUENCE {
    dfl860eLinkMonGrpIndex      Integer32,
    dfl860eLinkMonGrpName       DisplayString,
    dfl860eLinkMonGrpHostsUp    Gauge32
}

dfl860eLinkMonGrpIndex OBJECT-TYPE
    SYNTAX      Integer32 (1..2147483647)
    MAX-ACCESS  not-accessible
    STATUS      current
    DESCRIPTION 
        "The index row in the table of link monitor groups."
    ::= { dfl860eLinkMonGrpEntry 1 }

dfl860eLinkMonGrpName OBJECT-TYPE
    SYNTAX      DisplayString
    MAX-ACCESS  read-only
    STATUS      current
    DESCRIPTION 
        "The link monitor group name."
    ::= { dfl860eLinkMonGrpEntry 2 }

dfl860eLinkMonGrpHostsUp OBJECT-TYPE
    SYNTAX      Gauge32
    MAX-ACCESS  read-only
    STATUS      current
    DESCRIPTION 
        "The percentage of monitored hosts available."
    ::= { dfl860eLinkMonGrpEntry 3 }

dfl860eLinkMonHostTable OBJECT-TYPE
    SYNTAX      SEQUENCE OF Dfl860eLinkMonHostEntry
    MAX-ACCESS  not-accessible
    STATUS      current
    DESCRIPTION 
        "Table of link monitored hosts in a link monnitor group."
    ::= { dfl860eLinkMonitor 3 }

dfl860eLinkMonHostEntry OBJECT-TYPE
    SYNTAX      Dfl860eLinkMonHostEntry
    MAX-ACCESS  not-accessible
    STATUS      current
    DESCRIPTION 
        "The attributes of a monitored host."
    INDEX       { dfl860eLinkMonGrpIndex, dfl860eLinkMonHostIndex }
    ::= { dfl860eLinkMonHostTable 1 }

Dfl860eLinkMonHostEntry ::= SEQUENCE {
    dfl860eLinkMonHostIndex             Integer32,
    dfl860eLinkMonHostId                DisplayString,
    dfl860eLinkMonHostShortTermLoss     Gauge32,
    dfl860eLinkMonHostPacketsLost       Counter32
}

dfl860eLinkMonHostIndex OBJECT-TYPE
    SYNTAX      Integer32 (1..2147483647)
    MAX-ACCESS  not-accessible
    STATUS      current
    DESCRIPTION 
        "The index an host in the table of link monitor hosts."
    ::= { dfl860eLinkMonHostEntry 1 }

dfl860eLinkMonHostId OBJECT-TYPE
    SYNTAX      DisplayString
    MAX-ACCESS  read-only
    STATUS      current
    DESCRIPTION 
        "The monitored host identifier."
    ::= { dfl860eLinkMonHostEntry 2 }

dfl860eLinkMonHostShortTermLoss OBJECT-TYPE
    SYNTAX      Gauge32
    MAX-ACCESS  read-only
    STATUS      current
    DESCRIPTION 
        "The percentage of short term losst packets."
    ::= { dfl860eLinkMonHostEntry 3 }

dfl860eLinkMonHostPacketsLost OBJECT-TYPE
    SYNTAX      Counter32
    MAX-ACCESS  read-only
    STATUS      current
    DESCRIPTION 
        "Total number of lost monitoring packets."
    ::= { dfl860eLinkMonHostEntry 4 }

dfl860ePipes OBJECT IDENTIFIER
    ::= { dfl860eOSStats 8 }

dfl860ePipeUsers OBJECT-TYPE
    SYNTAX      Gauge32
    MAX-ACCESS  read-only
    STATUS      current
    DESCRIPTION 
        "The current number of users, as defined by the grouping 
         settings of each pipe, being tracked in the pipes system. 
         Note that this value corresponds to the number of users 
         active in each time slice of 1/20th of a second, and not 
         to the number of users having open connections."
    ::= { dfl860ePipes 1 }

dfl860ePipeTable OBJECT-TYPE
    SYNTAX      SEQUENCE OF Dfl860ePipeEntry
    MAX-ACCESS  not-accessible
    STATUS      current
    DESCRIPTION 
        "Table of pipes"
    ::= { dfl860ePipes 2 }

dfl860ePipeEntry OBJECT-TYPE
    SYNTAX      Dfl860ePipeEntry
    MAX-ACCESS  not-accessible
    STATUS      current
    DESCRIPTION 
        "A entry of the pipes table"
    INDEX       { dfl860ePipeIndex }
    ::= { dfl860ePipeTable 1 }

Dfl860ePipeEntry ::= SEQUENCE {
    dfl860ePipeIndex            Integer32,
    dfl860ePipeName             DisplayString,
    dfl860ePipeMinPrec          Integer32,
    dfl860ePipeMaxPrec          Integer32,
    dfl860ePipeDefPrec          Integer32,
    dfl860ePipeNumPrec          Integer32,
    dfl860ePipeNumUsers         Gauge32,
    dfl860ePipeCurrentBps       Gauge32,
    dfl860ePipeCurrentPps       Gauge32,
    dfl860ePipeDelayedPackets   Counter32,
    dfl860ePipeDropedPackets    Counter32
}

dfl860ePipeIndex OBJECT-TYPE
    SYNTAX      Integer32 (1..2147483647)
    MAX-ACCESS  not-accessible
    STATUS      current
    DESCRIPTION 
        "The pipe index"
    ::= { dfl860ePipeEntry 1 }

dfl860ePipeName OBJECT-TYPE
    SYNTAX      DisplayString
    MAX-ACCESS  read-only
    STATUS      current
    DESCRIPTION 
        "The name of the pipe"
    ::= { dfl860ePipeEntry 2 }

dfl860ePipeMinPrec OBJECT-TYPE
    SYNTAX      Integer32
    MAX-ACCESS  read-only
    STATUS      current
    DESCRIPTION 
        "The minimum of the range of pipe precedences."
    ::= { dfl860ePipeEntry 3 }

dfl860ePipeMaxPrec OBJECT-TYPE
    SYNTAX      Integer32
    MAX-ACCESS  read-only
    STATUS      current
    DESCRIPTION 
        "The maximum of the range of pipe precedences."
    ::= { dfl860ePipeEntry 4 }

dfl860ePipeDefPrec OBJECT-TYPE
    SYNTAX      Integer32
    MAX-ACCESS  read-only
    STATUS      current
    DESCRIPTION 
        "The precedence assigned to a packet for which has not one
         allready done by a Pipe Rule."
    ::= { dfl860ePipeEntry 5 }

dfl860ePipeNumPrec OBJECT-TYPE
    SYNTAX      Integer32
    MAX-ACCESS  read-only
    STATUS      current
    DESCRIPTION 
        "The number of pipe precedences"
    ::= { dfl860ePipeEntry 6 }

dfl860ePipeNumUsers OBJECT-TYPE
    SYNTAX      Gauge32
    MAX-ACCESS  read-only
    STATUS      current
    DESCRIPTION 
        "The current number of users, as defined by the grouping settings
         of each pipe, being tracked in the pipes system. This value 
         corresponds to the number of users active in each time slice 
         and not to the number of users having  open connections."
    ::= { dfl860ePipeEntry 7 }

dfl860ePipeCurrentBps OBJECT-TYPE
    SYNTAX      Gauge32
    MAX-ACCESS  read-only
    STATUS      current
    DESCRIPTION 
        "The current throughput of a pipe, in bits per second, as a sum of 
         the corresponding values for all precedences."
    ::= { dfl860ePipeEntry 8 }

dfl860ePipeCurrentPps OBJECT-TYPE
    SYNTAX      Gauge32
    MAX-ACCESS  read-only
    STATUS      current
    DESCRIPTION 
        "The current throughput of a pipe, in packets per second, as a sum of 
         the corresponding values for all precedences."
    ::= { dfl860ePipeEntry 9 }

dfl860ePipeDelayedPackets OBJECT-TYPE
    SYNTAX      Counter32
    MAX-ACCESS  read-only
    STATUS      current
    DESCRIPTION 
        "The number of times packets have been delayed as a result of a pipe, 
         or pipe user having used up its allotted bandwidth. Note that one single
         packet may be delayed several times; if a pipe is really full, this 
         count may exceed the number of packets actually passing through the 
         pipe."
    ::= { dfl860ePipeEntry 10 }

dfl860ePipeDropedPackets OBJECT-TYPE
    SYNTAX      Counter32
    MAX-ACCESS  read-only
    STATUS      current
    DESCRIPTION 
        "The number of packets dropped by a pipe. Packets are dropped when 
         CorePlus is running out of packet buffers. This occurs when excessive 
         amounts of packets need to be queued for later delivery. The packet 
         dropped is always the one that has been queued the longest time 
         globally, which means that the connection suffering from packet loss 
         will be the one most overloading the system."
    ::= { dfl860ePipeEntry 11 }

dfl860ePipePrecTable OBJECT-TYPE
    SYNTAX      SEQUENCE OF Dfl860ePipePrecEntry
    MAX-ACCESS  not-accessible
    STATUS      current
    DESCRIPTION 
        "There is a one to many relation between a pipe and its precedences.
         The number of precedences is a instance attribute of each pipe.
         This table extends the pipes table in order to express the relation 
         between a pipe and the respective precedences."
    ::= { dfl860ePipes 3 }

dfl860ePipePrecEntry OBJECT-TYPE
    SYNTAX      Dfl860ePipePrecEntry
    MAX-ACCESS  not-accessible
    STATUS      current
    DESCRIPTION 
        "An entry of the table of pipe pecedences. These table entries 
         are chracterized by been indexed by two values. The first index
         the same as the pipe index of the corresponding row in table of 
         pipes and the second index is the index of the set of precedences 
         of the corresponding pipe."
    INDEX       { dfl860ePipeIndex, dfl860ePipePrecIndex }
    ::= { dfl860ePipePrecTable 1 }

Dfl860ePipePrecEntry ::= SEQUENCE {
    dfl860ePipePrecIndex            Integer32,
    dfl860ePipePrec                 Integer32,
    dfl860ePipePrecBps              Gauge32,
    dfl860ePipePrecTotalPps         Gauge32,
    dfl860ePipePrecReservedBps      Gauge32,
    dfl860ePipePrecDynLimBps        Gauge32,
    dfl860ePipePrecDynUsrLimBps     Gauge32,
    dfl860ePipePrecDelayedPackets   Counter32,
    dfl860ePipePrecDropedPackets    Counter32
}

dfl860ePipePrecIndex OBJECT-TYPE
    SYNTAX      Integer32 (1..2147483647)
    MAX-ACCESS  not-accessible
    STATUS      current
    DESCRIPTION 
        "Index of a precedence of a specific pipe. This is the second index 
         of the entries of pipe precedence table described by object 
         dfl860ePipePrecEntry."
    ::= { dfl860ePipePrecEntry 1 }

dfl860ePipePrec OBJECT-TYPE
    SYNTAX      Integer32
    MAX-ACCESS  read-only
    STATUS      current
    DESCRIPTION 
        "The precedence value"
    ::= { dfl860ePipePrecEntry 2 }

dfl860ePipePrecBps OBJECT-TYPE
    SYNTAX      Gauge32
    MAX-ACCESS  read-only
    STATUS      current
    DESCRIPTION 
        "The current throughput of the pipe, in bits per second, with 
         the corresponding precedence."
    ::= { dfl860ePipePrecEntry 3 }

dfl860ePipePrecTotalPps OBJECT-TYPE
    SYNTAX      Gauge32
    MAX-ACCESS  read-only
    STATUS      current
    DESCRIPTION 
        "The current throughput of the pipe precedence, in packets per second."
    ::= { dfl860ePipePrecEntry 4 }

dfl860ePipePrecReservedBps OBJECT-TYPE
    SYNTAX      Gauge32
    MAX-ACCESS  read-only
    STATUS      current
    DESCRIPTION 
        "The current bandwidth allocated to the precedence."
    ::= { dfl860ePipePrecEntry 5 }

dfl860ePipePrecDynLimBps OBJECT-TYPE
    SYNTAX      Gauge32
    MAX-ACCESS  read-only
    STATUS      current
    DESCRIPTION 
        "The current bandwidth limit limit applied the precedence."
    ::= { dfl860ePipePrecEntry 6 }

dfl860ePipePrecDynUsrLimBps OBJECT-TYPE
    SYNTAX      Gauge32
    MAX-ACCESS  read-only
    STATUS      current
    DESCRIPTION 
        "The current precedence bandwidth limit per user of the pipe."
    ::= { dfl860ePipePrecEntry 7 }

dfl860ePipePrecDelayedPackets OBJECT-TYPE
    SYNTAX      Counter32
    MAX-ACCESS  read-only
    STATUS      current
    DESCRIPTION 
        "The number of times packets have been delayed as a result of a 
         precedence, or pipe user having used up its allotted bandwidth. 
         Note that one single packet may be delayed several times; if a 
         pipe is really full, this count may exceed the number of packets 
         of this precedence actually passing through the pipe."
    ::= { dfl860ePipePrecEntry 8 }

dfl860ePipePrecDropedPackets OBJECT-TYPE
    SYNTAX      Counter32
    MAX-ACCESS  read-only
    STATUS      current
    DESCRIPTION 
        "The number of pipe dropped packets with the corresponding precedence."
    ::= { dfl860ePipePrecEntry 9 }

dfl860eALG OBJECT IDENTIFIER
    ::= { dfl860eOSStats 9 }

dfl860eAlgSessions OBJECT-TYPE
    SYNTAX      Gauge32
    MAX-ACCESS  read-only
    STATUS      current
    DESCRIPTION 
        "Total ALG sessions"
    ::= { dfl860eALG 1 }

dfl860eAlgConnections OBJECT-TYPE
    SYNTAX      Gauge32
    MAX-ACCESS  read-only
    STATUS      current
    DESCRIPTION 
        "Total ALG connections"
    ::= { dfl860eALG 2 }

dfl860eAlgTCPStreams OBJECT-TYPE
    SYNTAX      Gauge32
    MAX-ACCESS  read-only
    STATUS      current
    DESCRIPTION 
        "Total ALG TCP streams"
    ::= { dfl860eALG 3 }

dfl860eHttpAlg OBJECT IDENTIFIER
    ::= { dfl860eALG 4 }

dfl860eHttpAlgTable OBJECT-TYPE
    SYNTAX      SEQUENCE OF Dfl860eHttpAlgEntry
    MAX-ACCESS  not-accessible
    STATUS      current
    DESCRIPTION 
        "Table of HTTP ALG objects."
    ::= { dfl860eHttpAlg 1 }

dfl860eHttpAlgEntry OBJECT-TYPE
    SYNTAX      Dfl860eHttpAlgEntry
    MAX-ACCESS  not-accessible
    STATUS      current
    DESCRIPTION 
        "A row of the table of HTTP ALG objects."
    INDEX       { dfl860eHttpAlgIndex }
    ::= { dfl860eHttpAlgTable 1 }

Dfl860eHttpAlgEntry ::= SEQUENCE {
    dfl860eHttpAlgIndex             Integer32,
    dfl860eHttpAlgName              DisplayString,
    dfl860eHttpAlgTotalRequested    Gauge32,
    dfl860eHttpAlgTotalAllowed      Gauge32,
    dfl860eHttpAlgTotalBlocked      Gauge32
}

dfl860eHttpAlgIndex OBJECT-TYPE
    SYNTAX      Integer32 (1..2147483647)
    MAX-ACCESS  not-accessible
    STATUS      current
    DESCRIPTION 
        "The index of an entry of the  Table of HTTP ALG objects."
    ::= { dfl860eHttpAlgEntry 1 }

dfl860eHttpAlgName OBJECT-TYPE
    SYNTAX      DisplayString
    MAX-ACCESS  read-only
    STATUS      current
    DESCRIPTION 
        "The name of an HTTP ALG object."
    ::= { dfl860eHttpAlgEntry 2 }

dfl860eHttpAlgTotalRequested OBJECT-TYPE
    SYNTAX      Gauge32
    MAX-ACCESS  read-only
    STATUS      current
    DESCRIPTION 
        "Total number of URL requests."
    ::= { dfl860eHttpAlgEntry 3 }

dfl860eHttpAlgTotalAllowed OBJECT-TYPE
    SYNTAX      Gauge32
    MAX-ACCESS  read-only
    STATUS      current
    DESCRIPTION 
        "Total number of allowed URL requests."
    ::= { dfl860eHttpAlgEntry 4 }

dfl860eHttpAlgTotalBlocked OBJECT-TYPE
    SYNTAX      Gauge32
    MAX-ACCESS  read-only
    STATUS      current
    DESCRIPTION 
        "Total number of blocked URL requests."
    ::= { dfl860eHttpAlgEntry 5 }

dfl860eHttpAlgCntFltTable OBJECT-TYPE
    SYNTAX      SEQUENCE OF Dfl860eHttpAlgCntFltEntry
    MAX-ACCESS  not-accessible
    STATUS      current
    DESCRIPTION 
        "Table of HTTP ALG content filtering rules."
    ::= { dfl860eHttpAlg 2 }

dfl860eHttpAlgCntFltEntry OBJECT-TYPE
    SYNTAX      Dfl860eHttpAlgCntFltEntry
    MAX-ACCESS  not-accessible
    STATUS      current
    DESCRIPTION 
        "Entry of the table of HTTP ALG content filtering rules."
    INDEX       { dfl860eHttpAlgIndex, dfl860eHttpAlgCntFltIndex }
    ::= { dfl860eHttpAlgCntFltTable 1 }

Dfl860eHttpAlgCntFltEntry ::= SEQUENCE {
    dfl860eHttpAlgCntFltIndex       Integer32,
    dfl860eHttpAlgCntFltName        DisplayString,
    dfl860eHttpAlgCntFltRequests    Gauge32,
    dfl860eHttpAlgCntFltAllowed     Gauge32,
    dfl860eHttpAlgCntFltBlocked     Gauge32
}

dfl860eHttpAlgCntFltIndex OBJECT-TYPE
    SYNTAX      Integer32 (1..2147483647)
    MAX-ACCESS  not-accessible
    STATUS      current
    DESCRIPTION 
        "The index of an entry of the  Table of HTTP ALG 
         content filtering objects."
    ::= { dfl860eHttpAlgCntFltEntry 1 }

dfl860eHttpAlgCntFltName OBJECT-TYPE
    SYNTAX      DisplayString
    MAX-ACCESS  read-only
    STATUS      current
    DESCRIPTION 
        "The name of the a HTTP ALG content fitering."
    ::= { dfl860eHttpAlgCntFltEntry 2 }

dfl860eHttpAlgCntFltRequests OBJECT-TYPE
    SYNTAX      Gauge32
    MAX-ACCESS  read-only
    STATUS      current
    DESCRIPTION 
        "Total number of URLs intercepted by a content 
         filtering object."
    ::= { dfl860eHttpAlgCntFltEntry 3 }

dfl860eHttpAlgCntFltAllowed OBJECT-TYPE
    SYNTAX      Gauge32
    MAX-ACCESS  read-only
    STATUS      current
    DESCRIPTION 
        "Total number of URLs intercepted and allowed 
         by a content filtering object."
    ::= { dfl860eHttpAlgCntFltEntry 4 }

dfl860eHttpAlgCntFltBlocked OBJECT-TYPE
    SYNTAX      Gauge32
    MAX-ACCESS  read-only
    STATUS      current
    DESCRIPTION 
        "Total number of URLs intercepted and blocked 
         by a content filtering object."
    ::= { dfl860eHttpAlgCntFltEntry 5 }

dfl860eSmtpAlg OBJECT IDENTIFIER
    ::= { dfl860eALG 5 }

dfl860eSmtpAlgTable OBJECT-TYPE
    SYNTAX  SEQUENCE OF Dfl860eSmtpAlgEntry
    MAX-ACCESS  not-accessible
    STATUS  current
    DESCRIPTION
  "Table of SMTP ALG objects."
    ::= { dfl860eSmtpAlg 1 }

dfl860eSmtpAlgEntry OBJECT-TYPE
   SYNTAX  Dfl860eSmtpAlgEntry
   MAX-ACCESS  not-accessible
    STATUS      current
    DESCRIPTION 
        "A row of the table of SMTP ALG objects."
    INDEX       { dfl860eSmtpAlgIndex }
    ::= { dfl860eSmtpAlgTable 1 }

Dfl860eSmtpAlgEntry ::= SEQUENCE {
    dfl860eSmtpAlgIndex           Integer32,
    dfl860eSmtpAlgName            DisplayString,
    dfl860eSmtpAlgTotCheckedSes   Gauge32,
    dfl860eSmtpAlgTotSpamSes      Gauge32,
    dfl860eSmtpAlgTotDroppedSes   Gauge32
}

dfl860eSmtpAlgIndex OBJECT-TYPE
    SYNTAX      Integer32 (1..2147483647)
    MAX-ACCESS  not-accessible
    STATUS      current
    DESCRIPTION 
        "The index of an entry of the  Table of SMTP ALG objects."
    ::= { dfl860eSmtpAlgEntry 1 }

dfl860eSmtpAlgName OBJECT-TYPE
    SYNTAX      DisplayString
    MAX-ACCESS  read-only
    STATUS      current
    DESCRIPTION 
        "The name of an SMTP ALG object."
    ::= { dfl860eSmtpAlgEntry 2 }

dfl860eSmtpAlgTotCheckedSes OBJECT-TYPE
    SYNTAX      Gauge32
    MAX-ACCESS  read-only
    STATUS      current
    DESCRIPTION 
        "Total sessions checked by the SMTP ALG of corresponding index."
    ::= { dfl860eSmtpAlgEntry 3 }

dfl860eSmtpAlgTotSpamSes OBJECT-TYPE
    SYNTAX      Gauge32
    MAX-ACCESS  read-only
    STATUS      current
    DESCRIPTION 
        "Total spam sessions detected by the SMTP ALG of corresponding index."
    ::= { dfl860eSmtpAlgEntry 4 }

dfl860eSmtpAlgTotDroppedSes OBJECT-TYPE
    SYNTAX      Gauge32
    MAX-ACCESS  read-only
    STATUS      current
    DESCRIPTION 
        "Total deroped sessions for the SMTP ALG of corresponding index."
    ::= { dfl860eSmtpAlgEntry 5 }


dfl860eSmtpAlgDnsBlTable OBJECT-TYPE
    SYNTAX  SEQUENCE OF Dfl860eSmtpAlgDnsBlEntry
    MAX-ACCESS  not-accessible
    STATUS  current
    DESCRIPTION
  "Table of SMTP ALG DNS balck list objects."
    ::= { dfl860eSmtpAlg 2 }


dfl860eSmtpAlgDnsBlEntry OBJECT-TYPE
   SYNTAX  Dfl860eSmtpAlgDnsBlEntry
   MAX-ACCESS  not-accessible
    STATUS      current
    DESCRIPTION 
        "A row of the table of SMTP ALG DNS black list objects."
    INDEX       { dfl860eSmtpAlgIndex, dfl860eSmtpAlgDnsBlIndex }
    ::= { dfl860eSmtpAlgDnsBlTable 1 }


Dfl860eSmtpAlgDnsBlEntry ::= SEQUENCE {
    dfl860eSmtpAlgDnsBlIndex  Integer32,
    dfl860eSmtpAlgDnsBlName    DisplayString,
    dfl860eSmtpAlgDnsBlChecked      Gauge32,
    dfl860eSmtpAlgDnsBlMatched  Gauge32,
    dfl860eSmtpAlgDnsBlFailChecks  Gauge32
}

dfl860eSmtpAlgDnsBlIndex OBJECT-TYPE
    SYNTAX      Integer32 (1..2147483647)
    MAX-ACCESS  not-accessible
    STATUS      current
    DESCRIPTION 
        "The index of an entry of the  SMTP ALG DNS black list objects." 
    ::= { dfl860eSmtpAlgDnsBlEntry 1 }

dfl860eSmtpAlgDnsBlName OBJECT-TYPE
    SYNTAX      DisplayString
    MAX-ACCESS  read-only
    STATUS      current
    DESCRIPTION 
  "The SMTP DNS black list name."
    ::= { dfl860eSmtpAlgDnsBlEntry 2 }

dfl860eSmtpAlgDnsBlChecked OBJECT-TYPE
    SYNTAX      Gauge32
    MAX-ACCESS  read-only
    STATUS      current
    DESCRIPTION 
  "Total sessions checked againt SMTP ALG DNS black list of corresponding index"
    ::= { dfl860eSmtpAlgDnsBlEntry 3 }

dfl860eSmtpAlgDnsBlMatched OBJECT-TYPE
    SYNTAX      Gauge32
    MAX-ACCESS  read-only
    STATUS      current
    DESCRIPTION 
  "Total sessions that matched SMTP ALG DNS black list of corresponding index"
    ::= { dfl860eSmtpAlgDnsBlEntry 4 }

dfl860eSmtpAlgDnsBlFailChecks OBJECT-TYPE
    SYNTAX      Gauge32
    MAX-ACCESS  read-only
    STATUS      current
    DESCRIPTION 
  "Total failed checks for the SMTP ALG DNS black list of corresponding index"
    ::= { dfl860eSmtpAlgDnsBlEntry 5 }

dfl860eDHCPRelay OBJECT IDENTIFIER
    ::= { dfl860eOSStats 11 }

dfl860eDHCPRelayCurClients OBJECT-TYPE
    SYNTAX      Gauge32
    MAX-ACCESS  read-only
    STATUS      current
    DESCRIPTION 
        "Total DHCP relay active relayed clients."
    ::= { dfl860eDHCPRelay 1 }

dfl860eDHCPRelayCurTrans OBJECT-TYPE
    SYNTAX      Gauge32
    MAX-ACCESS  read-only
    STATUS      current
    DESCRIPTION 
        "Ongoing DHCP relay transactions."
    ::= { dfl860eDHCPRelay 2 }

dfl860eDHCPRelayRejected OBJECT-TYPE
    SYNTAX      Gauge32
    MAX-ACCESS  read-only
    STATUS      current
    DESCRIPTION 
        "Total DHCP relay packets rejected."
    ::= { dfl860eDHCPRelay 3 }

dfl860eDHCPRelayRuleTable OBJECT-TYPE
    SYNTAX      SEQUENCE OF Dfl860eDHCPRelayRuleEntry
    MAX-ACCESS  not-accessible
    STATUS      current
    DESCRIPTION 
        "Table of DHCP relay rules."
    ::= { dfl860eDHCPRelay 4 }

dfl860eDHCPRelayRuleEntry OBJECT-TYPE
    SYNTAX      Dfl860eDHCPRelayRuleEntry
    MAX-ACCESS  not-accessible
    STATUS      current
    DESCRIPTION 
        "Entry of the table of DHCP relay rules"
    INDEX       { dfl860eDHCPRelayRuleIndex }
    ::= { dfl860eDHCPRelayRuleTable 1 }

Dfl860eDHCPRelayRuleEntry ::= SEQUENCE {
    dfl860eDHCPRelayRuleIndex       Integer32,
    dfl860eDHCPRelayRuleName        DisplayString,
    dfl860eDHCPRelayRuleHits        Gauge32,
    dfl860eDHCPRelayRuleCurClients  Gauge32,
    dfl860eDHCPRelayRuleRejCliPkts  Gauge32,
    dfl860eDHCPRelayRuleRejSrvPkts  Gauge32
}

dfl860eDHCPRelayRuleIndex OBJECT-TYPE
    SYNTAX      Integer32 (1..2147483647)
    MAX-ACCESS  not-accessible
    STATUS      current
    DESCRIPTION 
        "Index of the table of DHCP relay rules."
    ::= { dfl860eDHCPRelayRuleEntry 1 }

dfl860eDHCPRelayRuleName OBJECT-TYPE
    SYNTAX      DisplayString
    MAX-ACCESS  read-only
    STATUS      current
    DESCRIPTION 
        "Display name of a DHCP relay rule"
    ::= { dfl860eDHCPRelayRuleEntry 2 }

dfl860eDHCPRelayRuleHits OBJECT-TYPE
    SYNTAX      Gauge32
    MAX-ACCESS  read-only
    STATUS      current
    DESCRIPTION 
        "Number of the times the  DHCP relay rule with corresponding index was 
         used."
    ::= { dfl860eDHCPRelayRuleEntry 3 }

dfl860eDHCPRelayRuleCurClients OBJECT-TYPE
    SYNTAX      Gauge32
    MAX-ACCESS  read-only
    STATUS      current
    DESCRIPTION 
        "Number of ctive relayed clients by the DHCP relay rule with corresponding index."
    ::= { dfl860eDHCPRelayRuleEntry 4 }

dfl860eDHCPRelayRuleRejCliPkts OBJECT-TYPE
    SYNTAX      Gauge32
    MAX-ACCESS  read-only
    STATUS      current
    DESCRIPTION 
        "Number of client packets rejected by a rule."
    ::= { dfl860eDHCPRelayRuleEntry 5 }

dfl860eDHCPRelayRuleRejSrvPkts OBJECT-TYPE
    SYNTAX      Gauge32
    MAX-ACCESS  read-only
    STATUS      current
    DESCRIPTION 
        "Number of DHCP server packets rejected by the DHCP relay rule 
         with the corresponding index."
    ::= { dfl860eDHCPRelayRuleEntry 6 }

dfl860eHA OBJECT IDENTIFIER
    ::= { dfl860eOSStats 12 }

dfl860eHASyncSendQueueLength OBJECT-TYPE
    SYNTAX      Gauge32
    MAX-ACCESS  read-only
    STATUS      current
    DESCRIPTION 
        "Size of the queue used for the High Availability sync interface."
    ::= { dfl860eHA 1 }

dfl860eHASyncSendQueueUsagePkt OBJECT-TYPE
    SYNTAX      Gauge32
    MAX-ACCESS  read-only
    STATUS      current
    DESCRIPTION 
        "High Availability Sync interface queue usage in number of packets."
    ::= { dfl860eHA 2 }

dfl860eHASyncSendQueueUsageOct OBJECT-TYPE
    SYNTAX      Gauge32
    MAX-ACCESS  read-only
    STATUS      current
    DESCRIPTION 
        "High Availability Sync interface queue usage in number of octects."
    ::= { dfl860eHA 3 }

dfl860eHASyncSentPackets OBJECT-TYPE
    SYNTAX      Counter32
    MAX-ACCESS  read-only
    STATUS      current
    DESCRIPTION 
        "Number High Availability packets sent on Sync."
    ::= { dfl860eHA 4 }

dfl860eHASyncSendResentPackets OBJECT-TYPE
    SYNTAX      Counter32
    MAX-ACCESS  read-only
    STATUS      current
    DESCRIPTION 
        "Number of High Availability packets resent on Sync."
    ::= { dfl860eHA 5 }

dfl860eStatsConformance OBJECT IDENTIFIER
    ::= { dfl860eMibConfs 1 }

dfl860eStatsRegGroups OBJECT IDENTIFIER
    ::= { dfl860eMibObjectGroups 1 }

dfl860eSystemObjectGroup OBJECT-GROUP
    OBJECTS     { dfl860eSysCpuLoad, 
                  dfl860eSysForwardedBits, 
                  dfl860eSysForwardedPackets, 
                  dfl860eSysBuffUse, 
                  dfl860eSysConns, 
                  dfl860eHWSensorName, 
                  dfl860eHWSensorValue, 
                  dfl860eHWSensorUnit, 
                  dfl860eSysMemUsage, 
                  dfl860eSysTimerUsage, 
                  dfl860eSysConnOPS, 
                  dfl860eSysConnCPS,
                  dfl860eSysHCForwardedBits }
    STATUS      current
    DESCRIPTION 
        "System statistics Group"
    ::= { dfl860eStatsRegGroups 1 }

dfl860eIPsecObjectGroup OBJECT-GROUP
    OBJECTS     { dfl860eIPsecPhaseOneActive, 
                  dfl860eIPsecPhaseOneAggrModeDone, 
                  dfl860eIPsecQuickModeActive, 
                  dfl860eIPsecPhaseOneDone, 
                  dfl860eIPsecPhaseOneFailed, 
                  dfl860eIPsecPhaseOneRekeyed, 
                  dfl860eIPsecQuickModeDone, 
                  dfl860eIPsecQuickModeFailed, 
                  dfl860eIPsecInfoDone, 
                  dfl860eIPsecInfoFailed, 
                  dfl860eIPsecInOctetsComp, 
                  dfl860eIPsecInOctetsUncomp, 
                  dfl860eIPsecOutOctetsComp, 
                  dfl860eIPsecOutOctetsUncomp, 
                  dfl860eIPsecForwardedOctetsComp, 
                  dfl860eIPsecForwardedOctetsUcomp, 
                  dfl860eIPsecInPackets, 
                  dfl860eIPsecOutPackets, 
                  dfl860eIPsecForwardedPackets, 
                  dfl860eIPsecActiveTransforms, 
                  dfl860eIPsecTotalTransforms, 
                  dfl860eIPsecOutOfTransforms, 
                  dfl860eIPsecTotalRekeys }
    STATUS      current
    DESCRIPTION 
        "IPsec Group"
    ::= { dfl860eStatsRegGroups 2 }

dfl860eStateCountersGroup OBJECT-GROUP
    OBJECTS     { dfl860eSysPscTcpSyn, 
                  dfl860eSysPscTcpOpen, 
                  dfl860eSysPscTcpFin, 
                  dfl860eSysPscUdp, 
                  dfl860eSysPscIcmp, 
                  dfl860eSysPscOther }
    STATUS      current
    DESCRIPTION 
        "Per state counters"
    ::= { dfl860eStatsRegGroups 3 }

dfl860eIPPoolGroup OBJECT-GROUP
    OBJECTS     { dfl860eIPPoolsNumber, 
                  dfl860eIPPoolName, 
                  dfl860eIPPoolPrepare, 
                  dfl860eIPPoolFree, 
                  dfl860eIPPoolMisses, 
                  dfl860eIPPoolClientFails, 
                  dfl860eIPPoolUsed }
    STATUS      current
    DESCRIPTION 
        "IP pool entry objects group"
    ::= { dfl860eStatsRegGroups 4 }

dfl860eDHCPServerGroup OBJECT-GROUP
    OBJECTS     { dfl860eDHCPTotalRejected, 
                  dfl860eDHCPRuleName, 
                  dfl860eDHCPRuleUsage, 
                  dfl860eDHCPRuleUsagePercent, 
                  dfl860eDHCPActiveClients, 
                  dfl860eDHCPActiveClientsPercent, 
                  dfl860eDHCPRejectedRequests, 
                  dfl860eDHCPTotalLeases }
    STATUS      current
    DESCRIPTION 
        "DHCP server rules objects."
    ::= { dfl860eStatsRegGroups 5 }

dfl860eRuleUseGroup OBJECT-GROUP
    OBJECTS     { dfl860eRuleName, dfl860eRuleUse }
    STATUS      current
    DESCRIPTION 
        "Rule use objects."
    ::= { dfl860eStatsRegGroups 6 }

dfl860eUserAuthGroup OBJECT-GROUP
    OBJECTS     { dfl860eUserAuthHTTPUsers, dfl860eUserAuthXAUTHUsers, 
                  dfl860eUserAuthHTTPSUsers, dfl860eUserAuthPPPUsers, 
                  dfl860eUserAuthEAPUsers, dfl860eUserAuthRuleName, 
                  dfl860eUserAuthRuleUse }
    STATUS      current
    DESCRIPTION 
        "User auth objects."
    ::= { dfl860eStatsRegGroups 7 }

dfl860eIfStatsGroup OBJECT-GROUP
    OBJECTS     { dfl860eIfName, 
                  dfl860eIfFragsIn, 
                  dfl860eIfFragReassOk, 
                  dfl860eIfFragReassFail, 
                  dfl860eIfPktsInCnt, 
                  dfl860eIfPktsOutCnt, 
                  dfl860eIfBitsInCnt, 
                  dfl860eIfBitsOutCnt, 
                  dfl860eIfPktsTotCnt, 
                  dfl860eIfBitsTotCnt, 
                  dfl860eIfHCPktsInCnt, 
                  dfl860eIfHCPktsOutCnt, 
                  dfl860eIfHCBitsInCnt, 
                  dfl860eIfHCBitsOutCnt, 
                  dfl860eIfHCPktsTotCnt, 
                  dfl860eIfHCBitsTotCnt,
                  dfl860eIfRxRingFifoErrors, 
                  dfl860eIfRxDespools, 
                  dfl860eIfRxAvgUse, 
                  dfl860eIfRxRingSaturation, 
                  dfl860eRxRingFlooded, 
                  dfl860eIfTxDespools, 
                  dfl860eIfTxAvgUse, 
                  dfl860eIfTxRingSaturation, 
                  dfl860eRxTingFlooded }
    STATUS      current
    DESCRIPTION 
        "DFL-860e interface statistics group."
    ::= { dfl860eStatsRegGroups 8 }

dfl860eLinkMonitorGroup OBJECT-GROUP
    OBJECTS     { dfl860eLinkMonGrp, 
                  dfl860eLinkMonGrpName, 
                  dfl860eLinkMonGrpHostsUp, 
                  dfl860eLinkMonHostId, 
                  dfl860eLinkMonHostShortTermLoss, 
                  dfl860eLinkMonHostPacketsLost }
    STATUS      current
    DESCRIPTION 
        "DFL-860e link monitor statistics group"
    ::= { dfl860eStatsRegGroups 9 }

dfl860ePipesObjectGroup OBJECT-GROUP
    OBJECTS     { dfl860ePipeUsers, 
                  dfl860ePipeName, 
                  dfl860ePipeMinPrec, 
                  dfl860ePipeMaxPrec, 
                  dfl860ePipeDefPrec, 
                  dfl860ePipeNumPrec, 
                  dfl860ePipeNumUsers, 
                  dfl860ePipeCurrentBps, 
                  dfl860ePipeCurrentPps, 
                  dfl860ePipeDelayedPackets, 
                  dfl860ePipeDropedPackets, 
                  dfl860ePipePrec, 
                  dfl860ePipePrecBps, 
                  dfl860ePipePrecTotalPps, 
                  dfl860ePipePrecReservedBps, 
                  dfl860ePipePrecDynLimBps, 
                  dfl860ePipePrecDynUsrLimBps, 
                  dfl860ePipePrecDelayedPackets, 
                  dfl860ePipePrecDropedPackets }
    STATUS      current
    DESCRIPTION 
        "DFL-860e pipes statistics group"
    ::= { dfl860eStatsRegGroups 10 }

dfl860eDHCPRelayObjectGroup OBJECT-GROUP
    OBJECTS     { dfl860eDHCPRelayCurClients, 
                  dfl860eDHCPRelayCurTrans, 
                  dfl860eDHCPRelayRejected, 
                  dfl860eDHCPRelayRuleName, 
                  dfl860eDHCPRelayRuleHits, 
                  dfl860eDHCPRelayRuleCurClients, 
                  dfl860eDHCPRelayRuleRejCliPkts, 
                  dfl860eDHCPRelayRuleRejSrvPkts }
    STATUS      current
    DESCRIPTION 
        "DFL-860e DHCP relay statistics group"
    ::= { dfl860eStatsRegGroups 12 }

dfl860eAlgGroup OBJECT-GROUP
    OBJECTS     { dfl860eAlgSessions, 
                  dfl860eAlgConnections, 
                  dfl860eAlgTCPStreams, 
                  dfl860eHttpAlgName, 
                  dfl860eHttpAlgTotalRequested, 
                  dfl860eHttpAlgTotalAllowed, 
                  dfl860eHttpAlgTotalBlocked, 
                  dfl860eHttpAlgCntFltName, 
                  dfl860eHttpAlgCntFltRequests, 
                  dfl860eHttpAlgCntFltAllowed, 
                  dfl860eHttpAlgCntFltBlocked }
    STATUS      current
    DESCRIPTION 
        "DFL-860e HTTP ALG statistics group"
    ::= { dfl860eStatsRegGroups 13 }

dfl860eHAGroup OBJECT-GROUP
    OBJECTS     { dfl860eHASyncSendQueueLength, 
                  dfl860eHASyncSendQueueUsagePkt, 
                  dfl860eHASyncSendQueueUsageOct, 
                  dfl860eHASyncSentPackets, 
                  dfl860eHASyncSendResentPackets }
    STATUS      current
    DESCRIPTION 
        "DFL-860e HA statistics group"
    ::= { dfl860eStatsRegGroups 14 }

dfl860eIfVlanGroup OBJECT-GROUP
    OBJECTS     { dfl860eIfVlanUntaggedInPkts, 
                  dfl860eIfVlanUntaggedOutPkts, 
                  dfl860eIfVlanUntaggedTotPkts, 
                  dfl860eIfVlanUntaggedInOctets, 
                  dfl860eIfVlanUntaggedOutOctets, 
                  dfl860eIfVlanUntaggedTotOctets }
    STATUS      current
    DESCRIPTION 
        "DFL-860e VLAN statistics group"
    ::= { dfl860eStatsRegGroups 15 }


dfl860eSmtpAlgGroup OBJECT-GROUP 
    OBJECTS { dfl860eSmtpAlgName,
              dfl860eSmtpAlgTotCheckedSes,
              dfl860eSmtpAlgTotSpamSes,
              dfl860eSmtpAlgTotDroppedSes,
              dfl860eSmtpAlgDnsBlName,    
              dfl860eSmtpAlgDnsBlChecked,     
              dfl860eSmtpAlgDnsBlMatched,  
              dfl860eSmtpAlgDnsBlFailChecks }
   STATUS current
   DESCRIPTION
       "Clavister SMTP ALG objects group"
   ::= { dfl860eStatsRegGroups 16 }
   
dfl860eSysTCPGroup OBJECT-GROUP 
    OBJECTS { dfl860eSysTCPRecvSmall,
              dfl860eSysTCPRecvLarge,
              dfl860eSysTCPSendSmall,
              dfl860eSysTCPSendLarge }
    STATUS current
    DESCRIPTION
      "DFL-860e TCP buffer usage group"
    ::= { dfl860eStatsRegGroups 17 }



dfl860eStatsCompliance MODULE-COMPLIANCE
    STATUS      current
    DESCRIPTION 
        "Module Compliance"

    MODULE      -- this module

        MANDATORY-GROUPS        
                { dfl860eSystemObjectGroup, 
                  dfl860eIPsecObjectGroup, 
                  dfl860eStateCountersGroup, 
                  dfl860eIPPoolGroup, 
                  dfl860eDHCPServerGroup, 
                  dfl860eRuleUseGroup, 
                  dfl860eUserAuthGroup, 
                  dfl860eIfStatsGroup, 
                  dfl860eLinkMonitorGroup, 
                  dfl860ePipesObjectGroup, 
                  dfl860eDHCPRelayObjectGroup, 
                  dfl860eAlgGroup, 
                  dfl860eHAGroup, 
                  dfl860eIfVlanGroup, 
                  dfl860eSmtpAlgGroup, 
                  dfl860eSysTCPGroup }

    ::= { dfl860eStatsConformance 1 }

END -- end of module DFL860e-MIB.
