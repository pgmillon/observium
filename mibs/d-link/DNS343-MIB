--
-- DNS343.mib
--

-- Copyright (c) 2001-2010 alphanetworks Inc.,
-- Module Name: DNS343.mib
-- Abstract:
-- Defines the DNS343 NAS MIBs .
-- 

	DNS343-MIB DEFINITIONS ::= BEGIN
	

	IMPORTS 
		OBJECT-TYPE, Integer32, enterprises, 
		NOTIFICATION-TYPE
			FROM SNMPv2-SMI
		DisplayString
			FROM SNMPv2-TC;

--
--  OID definitions
--
	
	d-link		OBJECT IDENTIFIER ::= { enterprises 171}
	productID	OBJECT IDENTIFIER ::= { d-link 50}
	projectID	OBJECT IDENTIFIER ::= { productID 1}
	modelID 	OBJECT IDENTIFIER ::= { projectID 4}	
	submodelID	OBJECT IDENTIFIER ::= { modelID 1}	
	nasAgent	OBJECT IDENTIFIER ::= { submodelID 1}
	
	
--
-- Node definitions
--
			dns343AgentVer OBJECT-TYPE
				SYNTAX DisplayString
				MAX-ACCESS read-only
				STATUS current
				DESCRIPTION
					"version information for the agent of SNMP of DNS343."
				::= { nasAgent 1 }	

-- ============================================================================		

--
-- system information definitions
--
			dns343SoftwareVersion OBJECT-TYPE
				SYNTAX DisplayString
				MAX-ACCESS read-only
				STATUS current
				DESCRIPTION
					"The device software version."
				::= { nasAgent 2 }

			dns343HostName OBJECT-TYPE
				SYNTAX DisplayString
				MAX-ACCESS read-only
				STATUS current
				DESCRIPTION
					"The device host name."
				::= { nasAgent 3 }
				
			dns343DHCPServer OBJECT-TYPE
				SYNTAX DisplayString
				MAX-ACCESS read-only
				STATUS current
				DESCRIPTION
					"DHCP Server status.
					1 : enable
					0 : disable
					"
				::= { nasAgent 4 }
				
			dns343FTPServer OBJECT-TYPE
				SYNTAX DisplayString
				MAX-ACCESS read-only
				STATUS current
				DESCRIPTION
					"Ftp Server status.
					1 : enable
					0 : disable
					"
				::= { nasAgent 5 }
				
			dns343NetType OBJECT-TYPE
				SYNTAX DisplayString
				MAX-ACCESS read-only
				STATUS current
				DESCRIPTION
					"The Network type. 
					(	0 : Workgroup 
						1 : Active Directory)"
				::= { nasAgent 6 }
				
			dns343Temperature OBJECT-TYPE
				SYNTAX DisplayString
				MAX-ACCESS read-only
				STATUS current
				DESCRIPTION
					"The temperature of the system."
				::= { nasAgent 7 }
				
			dns343FanStatus OBJECT-TYPE
				SYNTAX DisplayString
				MAX-ACCESS read-only
				STATUS current
				DESCRIPTION
					"The status of the fan0 & fan1."
				::= { nasAgent 8 }
				
-- ============================================================================
			
			dns343VolumeTable OBJECT-TYPE                                                 
			SYNTAX SEQUENCE OF Dns343VolumeEntry                                      
			MAX-ACCESS not-accessible                                               
			STATUS current                                                    
			DESCRIPTION                                                         
				"A table of active volumes on the NAS device."                  
			::= { nasAgent 9 }
			
			dns343VolumeEntry OBJECT-TYPE                                                 
			SYNTAX Dns343VolumeEntry
			MAX-ACCESS not-accessible
			STATUS current
			DESCRIPTION
				"An entry in the volume table."
			INDEX { dns343VolumeNum }
			::= { dns343VolumeTable 1 }
			
			Dns343VolumeEntry ::=
			SEQUENCE { 
				dns343VolumeNum
					Integer32,
				dns343VolumeName
					DisplayString,
				dns343VolumeFsType
					DisplayString,	
				dns343VolumeRaidLevel
					DisplayString,			
				dns343VolumeSize
					DisplayString,
				dns343VolumeFreeSpace
					DisplayString
			 }
			 
			dns343VolumeNum OBJECT-TYPE
			SYNTAX Integer32
			MAX-ACCESS read-only
			STATUS current
			DESCRIPTION
				"Instance number of the volume entry."
			::= { dns343VolumeEntry 1 }
			
			dns343VolumeName OBJECT-TYPE
			SYNTAX DisplayString
			MAX-ACCESS read-only
			STATUS current
			DESCRIPTION
				"The name of the volume."
			::= { dns343VolumeEntry 2 }
			
			dns343VolumeFsType OBJECT-TYPE
			SYNTAX DisplayString
			MAX-ACCESS read-only
			STATUS current
			DESCRIPTION
				"The type of file systme of the volume. 
				Example : ext2 or ext3"
			::= { dns343VolumeEntry 3 }
			
			dns343VolumeRaidLevel OBJECT-TYPE
			SYNTAX DisplayString
			MAX-ACCESS read-only
			STATUS current
			DESCRIPTION
				"The RAID level of the volume. (RAID0 RAID1 RAID5 LINEAR NORMAL)"
			::= { dns343VolumeEntry 4 }
			
			dns343VolumeSize OBJECT-TYPE
			SYNTAX DisplayString
			MAX-ACCESS read-only
			STATUS current
			DESCRIPTION
				"The size of the volume in bytes."
			::= { dns343VolumeEntry 5 }
			
			dns343VolumeFreeSpace OBJECT-TYPE
			SYNTAX DisplayString
			MAX-ACCESS read-only
			STATUS current
			DESCRIPTION
				"Free space on the volume in bytes."
			::= { dns343VolumeEntry 6 }
			
-- ============================================================================

		dns343DiskTable OBJECT-TYPE
			SYNTAX SEQUENCE OF Dns343DiskEntry
			MAX-ACCESS not-accessible
			STATUS current
			DESCRIPTION
				"A table of physical disks attached to the NAS device."
			::= { nasAgent 10 }

		dns343DiskEntry OBJECT-TYPE
			SYNTAX Dns343DiskEntry
			MAX-ACCESS not-accessible
			STATUS current
			DESCRIPTION
				"An entry in the physical disk table."
			INDEX { dns343DiskNum }
			::= { dns343DiskTable 1 }
			
		Dns343DiskEntry ::=
			SEQUENCE { 
				dns343DiskNum
					Integer32,
				dns343DiskVendor
					DisplayString,
				dns343DiskModel
					DisplayString,
				dns343DiskSerialNumber
					DisplayString,
        		dns343DiskTemperature
					DisplayString,
				dns343DiskCapacity
					DisplayString
			 }
			 
		dns343DiskNum OBJECT-TYPE
			SYNTAX Integer32
			MAX-ACCESS read-only
			STATUS current
			DESCRIPTION
				"Instance number of the disk entry."
			::= { dns343DiskEntry 1 }			 
			 
		dns343DiskVendor OBJECT-TYPE
			SYNTAX DisplayString
			MAX-ACCESS read-only
			STATUS current
			DESCRIPTION
				"The vendor of the disk drive."
			::= { dns343DiskEntry 2 }
			
		dns343DiskModel OBJECT-TYPE
			SYNTAX DisplayString
			MAX-ACCESS read-only
			STATUS current
			DESCRIPTION
				"The disk drive's model name."
			::= { dns343DiskEntry 3 }
			
		dns343DiskSerialNumber OBJECT-TYPE
			SYNTAX DisplayString
			MAX-ACCESS read-only
			STATUS current
			DESCRIPTION
				"The disk drive's serial number."
			::= { dns343DiskEntry 4 }			
			 
		dns343DiskTemperature OBJECT-TYPE
			SYNTAX DisplayString
			MAX-ACCESS read-only
			STATUS current
			DESCRIPTION
				"The centigrade temperature of this disk."
			::= { dns343DiskEntry 5 }
			
		dns343DiskCapacity OBJECT-TYPE
			SYNTAX DisplayString
			MAX-ACCESS read-only
			STATUS current
			DESCRIPTION
				"The capacity of the disk in GB."
			::= { dns343DiskEntry 6 }
			
-- ============================================================================
--
--  Notifications
--

	notifyEvts OBJECT IDENTIFIER ::= { nasAgent 200 }

	notifyPasswdChanged        NOTIFICATION-TYPE
    STATUS      current
    DESCRIPTION
        "An indication that the Administrator's password has been changed."
    ::= { notifyEvts 1 }

    notifyFirmwareUpgraded     NOTIFICATION-TYPE
    STATUS      current
    DESCRIPTION
        "An indication that firmware has been upgraded."
    ::= { notifyEvts 2 }
    
    notifyNetworkChanged        NOTIFICATION-TYPE
    STATUS      current
    DESCRIPTION
        "An indication that the network settings has been changed."
    ::= { notifyEvts 3 }

    notifyTemperatureExceeded        NOTIFICATION-TYPE
    STATUS      current
    DESCRIPTION
        "An indication that system temperature has exceeded."
    ::= { notifyEvts 4 }




    
    			
			 
--              ******************************************************
			
--              ******************************************************
			
	
	END

--
-- DNS343.mib
--
