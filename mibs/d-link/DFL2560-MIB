--
-- DFL-2560 SMIv2 module
--

DFL2560-MIB DEFINITIONS ::= BEGIN

IMPORTS
    MODULE-COMPLIANCE, OBJECT-GROUP
        FROM SNMPv2-CONF
    Counter32, Counter64, Gauge32, Integer32, MODULE-IDENTITY, 
    OBJECT-TYPE, enterprises
        FROM SNMPv2-SMI
    DisplayString
        FROM SNMPv2-TC;

dfl2560-MIB MODULE-IDENTITY
    LAST-UPDATED "201009021139Z"
    ORGANIZATION 
        "D-Link Corporation"
    CONTACT-INFO 
        "Postal: D-Link Corporation
         No. 289, Sinhu 3rd Road,
         Neihu District, Taipei City 114,
         Taiwan, R.O.C.
         Tel: +886-2-66000123
         Fax: +886-2-55509988"
    DESCRIPTION 
        "The MIB module for D-Link DFL-2560 series product."
    
    REVISION  "201009021139Z"
    DESCRIPTION 
        "Added 64-bit counters"
    REVISION  "201003300900Z"
    DESCRIPTION 
        "Added values for SMTP ALG objects."
    REVISION  "200911100916Z"
    DESCRIPTION 
        "Added values for opened and closed connections per second"
    REVISION  "200811181605Z"
    DESCRIPTION 
        "Added value for timer usage"
    REVISION  "200810141227Z"
    DESCRIPTION 
        "Added values for memory usage and TCP buffer usage"    
    REVISION  "200710310000Z"
    DESCRIPTION 
        "Initial version."
    ::= { dfl2560MibModules 2 }


dlink OBJECT IDENTIFIER
    ::= { enterprises 171 }

netdefendMgmt OBJECT IDENTIFIER
    ::= { dlink 20 }

utmFirewall OBJECT IDENTIFIER
    ::= { netdefendMgmt 2 }

dfl2560 OBJECT IDENTIFIER
    ::= { utmFirewall 4 }

dfl2560OS OBJECT IDENTIFIER
    ::= { dfl2560 1 }

dfl2560OSStats OBJECT IDENTIFIER
    ::= { dfl2560OS 2 }

dfl2560reg OBJECT IDENTIFIER
    ::= { dfl2560 2 }

dfl2560MibModules OBJECT IDENTIFIER
    ::= { dfl2560reg 1 }

dfl2560MibConfs OBJECT IDENTIFIER
    ::= { dfl2560reg 2 }

dfl2560MibObjectGroups OBJECT IDENTIFIER
    ::= { dfl2560reg 3 }


dfl2560System OBJECT IDENTIFIER
    ::= { dfl2560OSStats 1 }

dfl2560SysCpuLoad OBJECT-TYPE
    SYNTAX      Gauge32
    MAX-ACCESS  read-only
    STATUS      current
    DESCRIPTION 
        "The system cpu load."
    ::= { dfl2560System 1 }

dfl2560SysForwardedBits OBJECT-TYPE
    SYNTAX      Counter32
    MAX-ACCESS  read-only
    STATUS      current
    DESCRIPTION
        "The number of bits forwarded through the gateway."
    ::= { dfl2560System 2 }

dfl2560SysForwardedPackets OBJECT-TYPE
    SYNTAX      Counter32
    MAX-ACCESS  read-only
    STATUS      current
    DESCRIPTION
        "Total number of forwarded packets."
    ::= { dfl2560System 3 }

dfl2560SysBuffUse OBJECT-TYPE
    SYNTAX      Gauge32
    MAX-ACCESS  read-only
    STATUS      current
    DESCRIPTION 
        "The current number of buffers in use."
    ::= { dfl2560System 4 }

dfl2560SysConns OBJECT-TYPE
    SYNTAX      Gauge32
    MAX-ACCESS  read-only
    STATUS      current
    DESCRIPTION 
        "The numer of connections."
    ::= { dfl2560System 5 }

dfl2560SysPerStateCounters OBJECT IDENTIFIER
    ::= { dfl2560System 6 }

dfl2560SysPscTcpSyn OBJECT-TYPE
    SYNTAX      Gauge32
    MAX-ACCESS  read-only
    STATUS      current
    DESCRIPTION 
        "Number of TCP connections in the SYN state."
    ::= { dfl2560SysPerStateCounters 1 }

dfl2560SysPscTcpOpen OBJECT-TYPE
    SYNTAX      Gauge32
    MAX-ACCESS  read-only
    STATUS      current
    DESCRIPTION 
        "Number of TCP connections in the OPEN state."
    ::= { dfl2560SysPerStateCounters 2 }

dfl2560SysPscTcpFin OBJECT-TYPE
    SYNTAX      Gauge32
    MAX-ACCESS  read-only
    STATUS      current
    DESCRIPTION 
        "Number of TCP connections in the FIN state."
    ::= { dfl2560SysPerStateCounters 3 }

dfl2560SysPscUdp OBJECT-TYPE
    SYNTAX      Gauge32
    MAX-ACCESS  read-only
    STATUS      current
    DESCRIPTION 
        "Number of UDP connections."
    ::= { dfl2560SysPerStateCounters 4 }

dfl2560SysPscIcmp OBJECT-TYPE
    SYNTAX      Gauge32
    MAX-ACCESS  read-only
    STATUS      current
    DESCRIPTION 
        "Number of ICMP connections."
    ::= { dfl2560SysPerStateCounters 5 }

dfl2560SysPscOther OBJECT-TYPE
    SYNTAX      Gauge32
    MAX-ACCESS  read-only
    STATUS      current
    DESCRIPTION 
        "Number of other connections."
    ::= { dfl2560SysPerStateCounters 6 }

dfl2560IfStatsTable OBJECT-TYPE
    SYNTAX      SEQUENCE OF Dfl2560IfStatsEntry
    MAX-ACCESS  not-accessible
    STATUS      current
    DESCRIPTION 
        "A table of DFL-2560 specific interfaces statistics"
    ::= { dfl2560System 7 }

dfl2560IfStatsEntry OBJECT-TYPE
    SYNTAX      Dfl2560IfStatsEntry
    MAX-ACCESS  not-accessible
    STATUS      current
    DESCRIPTION 
        "The row in a table of DFL-2560 specific interface statistics"
    INDEX       { dfl2560IfStatsIndex }
    ::= { dfl2560IfStatsTable 1 }

Dfl2560IfStatsEntry ::= SEQUENCE {
    dfl2560IfStatsIndex     Integer32,
    dfl2560IfName           DisplayString,
    dfl2560IfFragsIn        Counter32,
    dfl2560IfFragReassOk    Counter32,
    dfl2560IfFragReassFail  Counter32,
    dfl2560IfPktsInCnt      Counter32,
    dfl2560IfPktsOutCnt     Counter32,
    dfl2560IfBitsInCnt      Counter32,
    dfl2560IfBitsOutCnt     Counter32,
    dfl2560IfPktsTotCnt     Counter32,
    dfl2560IfBitsTotCnt     Counter32,
    dfl2560IfHCPktsInCnt    Counter64,
    dfl2560IfHCPktsOutCnt   Counter64,
    dfl2560IfHCBitsInCnt    Counter64,
    dfl2560IfHCBitsOutCnt   Counter64,
    dfl2560IfHCPktsTotCnt   Counter64,
    dfl2560IfHCBitsTotCnt   Counter64
}

dfl2560IfStatsIndex OBJECT-TYPE
    SYNTAX      Integer32 (1..2147483647)
    MAX-ACCESS  not-accessible
    STATUS      current
    DESCRIPTION 
        "Index of a row in dfl2560SysIfStatsTable"
    ::= { dfl2560IfStatsEntry 1 }

dfl2560IfName OBJECT-TYPE
    SYNTAX      DisplayString
    MAX-ACCESS  read-only
    STATUS      current
    DESCRIPTION 
        "The name of the interface."
    ::= { dfl2560IfStatsEntry 2 }

dfl2560IfFragsIn OBJECT-TYPE
    SYNTAX      Counter32
    MAX-ACCESS  read-only
    STATUS      current
    DESCRIPTION 
        "Number of IP packet fragments received 
         in the interface."
    ::= { dfl2560IfStatsEntry 3 }

dfl2560IfFragReassOk OBJECT-TYPE
    SYNTAX      Counter32
    MAX-ACCESS  read-only
    STATUS      current
    DESCRIPTION 
        "Number of complete IP packets successfully 
         reassembled from the fragments received in 
         the interface."
    ::= { dfl2560IfStatsEntry 4 }

dfl2560IfFragReassFail OBJECT-TYPE
    SYNTAX      Counter32
    MAX-ACCESS  read-only
    STATUS      current
    DESCRIPTION 
        "Number of packets that could not be reassembled, 
         either due to resource starvation, illegal fragmentation, 
         or just packet loss."
    ::= { dfl2560IfStatsEntry 5 }

dfl2560IfPktsInCnt OBJECT-TYPE
    SYNTAX      Counter32
    MAX-ACCESS  read-only
    STATUS      current
    DESCRIPTION 
        "Number of packets received by the interface."
    ::= { dfl2560IfStatsEntry 6 }

dfl2560IfPktsOutCnt OBJECT-TYPE
    SYNTAX      Counter32
    MAX-ACCESS  read-only
    STATUS      current
    DESCRIPTION 
        "Number of packets sent by the interface"
    ::= { dfl2560IfStatsEntry 7 }

dfl2560IfBitsInCnt OBJECT-TYPE
    SYNTAX      Counter32
    MAX-ACCESS  read-only
    STATUS      current
    DESCRIPTION 
        "Number of bits received by the interface"
    ::= { dfl2560IfStatsEntry 8 }

dfl2560IfBitsOutCnt OBJECT-TYPE
    SYNTAX      Counter32
    MAX-ACCESS  read-only
    STATUS      current
    DESCRIPTION 
        "Number of bits sent by the interface"
    ::= { dfl2560IfStatsEntry 9 }

dfl2560IfPktsTotCnt OBJECT-TYPE
    SYNTAX      Counter32
    MAX-ACCESS  read-only
    STATUS      current
    DESCRIPTION 
        "Totat number of packets transmited by the interface"
    ::= { dfl2560IfStatsEntry 10 }

dfl2560IfBitsTotCnt OBJECT-TYPE
    SYNTAX      Counter32
    MAX-ACCESS  read-only
    STATUS      current
    DESCRIPTION 
        "Totat number of bits transmited by the interface"
    ::= { dfl2560IfStatsEntry 11 }

dfl2560IfHCPktsInCnt OBJECT-TYPE
    SYNTAX      Counter64
    MAX-ACCESS  read-only
    STATUS      current
    DESCRIPTION 
        "Number of packets received by the interface.
        This object is a 64-bit version of dfl2560IfPktsInCnt."
    ::= { dfl2560IfStatsEntry 12 }

dfl2560IfHCPktsOutCnt OBJECT-TYPE
    SYNTAX      Counter64
    MAX-ACCESS  read-only
    STATUS      current
    DESCRIPTION 
        "Number of packets sent by the interface.
        This object is a 64-bit version of dfl2560IfPktsOutCnt."
    ::= { dfl2560IfStatsEntry 13 }

dfl2560IfHCBitsInCnt OBJECT-TYPE
    SYNTAX      Counter64
    MAX-ACCESS  read-only
    STATUS      current
    DESCRIPTION 
        "Number of bits received by the interface.
        This object is a 64-bit version of dfl2560IfBitsInCnt."
    ::= { dfl2560IfStatsEntry 14 }

dfl2560IfHCBitsOutCnt OBJECT-TYPE
    SYNTAX      Counter64
    MAX-ACCESS  read-only
    STATUS      current
    DESCRIPTION 
        "Number of bits sent by the interface.
        This object is a 64-bit version of dfl2560IfBitsOutCnt."
    ::= { dfl2560IfStatsEntry 15 }

dfl2560IfHCPktsTotCnt OBJECT-TYPE
    SYNTAX      Counter64
    MAX-ACCESS  read-only
    STATUS      current
    DESCRIPTION 
        "Totat number of packets transmited by the interface.
        This object is a 64-bit version of dfl2560IfPktsTotCnt."
    ::= { dfl2560IfStatsEntry 16 }

dfl2560IfHCBitsTotCnt OBJECT-TYPE
    SYNTAX      Counter64
    MAX-ACCESS  read-only
    STATUS      current
    DESCRIPTION 
        "Totat number of bits transmited by the interface. 
        This object is a 64-bit version of dfl2560IfBitsTotCnt."
    ::= { dfl2560IfStatsEntry 17 }

dfl2560IfRxRingTable OBJECT-TYPE
    SYNTAX      SEQUENCE OF Dfl2560IfRxRingEntry
    MAX-ACCESS  not-accessible
    STATUS      current
    DESCRIPTION 
        "A table of DFL-2560 specific interface Rx ring statistics"
    ::= { dfl2560System 8 }

dfl2560IfRxRingEntry OBJECT-TYPE
    SYNTAX      Dfl2560IfRxRingEntry
    MAX-ACCESS  not-accessible
    STATUS      current
    DESCRIPTION 
        "The row in a table of DFL-2560 specific interface Rx ring 
         statistics."
    INDEX       { dfl2560IfRxRingIndex }
    ::= { dfl2560IfRxRingTable 1 }

Dfl2560IfRxRingEntry ::= SEQUENCE {
    dfl2560IfRxRingIndex        Integer32,
    dfl2560IfRxRingFifoErrors   Counter32,
    dfl2560IfRxDespools         Gauge32,
    dfl2560IfRxAvgUse           Gauge32,
    dfl2560IfRxRingSaturation   Gauge32,
    dfl2560RxRingFlooded        Gauge32
}

dfl2560IfRxRingIndex OBJECT-TYPE
    SYNTAX      Integer32 (1..2147483647)
    MAX-ACCESS  not-accessible
    STATUS      current
    DESCRIPTION 
        "Index of a row in dfl2560IfRxRingTable."
    ::= { dfl2560IfRxRingEntry 1 }

dfl2560IfRxRingFifoErrors OBJECT-TYPE
    SYNTAX      Counter32
    MAX-ACCESS  read-only
    STATUS      current
    DESCRIPTION 
        "Rx Ring number of FIFO errors."
    ::= { dfl2560IfRxRingEntry 2 }

dfl2560IfRxDespools OBJECT-TYPE
    SYNTAX      Gauge32
    MAX-ACCESS  read-only
    STATUS      current
    DESCRIPTION 
        "Number of despool events per second."
    ::= { dfl2560IfRxRingEntry 3 }

dfl2560IfRxAvgUse OBJECT-TYPE
    SYNTAX      Gauge32
    MAX-ACCESS  read-only
    STATUS      current
    DESCRIPTION 
        "Rx Ring average usage."
    ::= { dfl2560IfRxRingEntry 4 }

dfl2560IfRxRingSaturation OBJECT-TYPE
    SYNTAX      Gauge32
    MAX-ACCESS  read-only
    STATUS      current
    DESCRIPTION 
        "Rx Ring sturation. Percentage of ring use per despool 
         event when the ring has been more than half full."
    ::= { dfl2560IfRxRingEntry 5 }

dfl2560RxRingFlooded OBJECT-TYPE
    SYNTAX      Gauge32
    MAX-ACCESS  read-only
    STATUS      current
    DESCRIPTION 
        "Rx Ring number of despool events for which 
         the ring has been completely flooded"
    ::= { dfl2560IfRxRingEntry 6 }

dfl2560IfTxRingTable OBJECT-TYPE
    SYNTAX      SEQUENCE OF Dfl2560IfTxRingEntry
    MAX-ACCESS  not-accessible
    STATUS      current
    DESCRIPTION 
        "A table of DFL-2560 specific interface Tx ring statistics"
    ::= { dfl2560System 9 }

dfl2560IfTxRingEntry OBJECT-TYPE
    SYNTAX      Dfl2560IfTxRingEntry
    MAX-ACCESS  not-accessible
    STATUS      current
    DESCRIPTION 
        "The row in a table of DFL-2560 specific interface Tx ring 
         statistics."
    INDEX       { dfl2560IfTxRingIndex }
    ::= { dfl2560IfTxRingTable 1 }

Dfl2560IfTxRingEntry ::= SEQUENCE {
    dfl2560IfTxRingIndex        Integer32,
    dfl2560IfTxDespools         Gauge32,
    dfl2560IfTxAvgUse           Gauge32,
    dfl2560IfTxRingSaturation   Gauge32,
    dfl2560RxTingFlooded        Gauge32
}

dfl2560IfTxRingIndex OBJECT-TYPE
    SYNTAX      Integer32 (1..2147483647)
    MAX-ACCESS  not-accessible
    STATUS      current
    DESCRIPTION 
        "Index of a row in dfl2560IfRxRingTable."
    ::= { dfl2560IfTxRingEntry 1 }

dfl2560IfTxDespools OBJECT-TYPE
    SYNTAX      Gauge32
    MAX-ACCESS  read-only
    STATUS      current
    DESCRIPTION 
        "Tx Ring number of despool event per second (polls when 
         there is at least one buffer in the ring)"
    ::= { dfl2560IfTxRingEntry 2 }

dfl2560IfTxAvgUse OBJECT-TYPE
    SYNTAX      Gauge32
    MAX-ACCESS  read-only
    STATUS      current
    DESCRIPTION 
        "Tx Ring number of despool events when the ring has 
         been completely flooded"
    ::= { dfl2560IfTxRingEntry 3 }

dfl2560IfTxRingSaturation OBJECT-TYPE
    SYNTAX      Gauge32
    MAX-ACCESS  read-only
    STATUS      current
    DESCRIPTION 
        "Tx Ring percentage of use per despool event when the 
         ring has been more than half full."
    ::= { dfl2560IfTxRingEntry 4 }

dfl2560RxTingFlooded OBJECT-TYPE
    SYNTAX      Gauge32
    MAX-ACCESS  read-only
    STATUS      current
    DESCRIPTION 
        "Tx Ring number of despool events for in which the ring has 
         been completely flooded"
    ::= { dfl2560IfTxRingEntry 5 }

dfl2560IfVlanStatsTable OBJECT-TYPE
    SYNTAX      SEQUENCE OF Dfl2560IfVlanStatsEntry
    MAX-ACCESS  not-accessible
    STATUS      current
    DESCRIPTION 
        "A table of DFL-2560 VLAN statistics"
    ::= { dfl2560System 10 }

dfl2560IfVlanStatsEntry OBJECT-TYPE
    SYNTAX      Dfl2560IfVlanStatsEntry
    MAX-ACCESS  not-accessible
    STATUS      current
    DESCRIPTION 
        "The row in a table of dfl2560IfVlanStatsTable. Each has an index 
         equal to the ifIndex of the corresponding physical interface"
    INDEX       { dfl2560IfVlanIndex }
    ::= { dfl2560IfVlanStatsTable 1 }

Dfl2560IfVlanStatsEntry ::= SEQUENCE {
    dfl2560IfVlanIndex              Integer32,
    dfl2560IfVlanUntaggedInPkts     Counter32,
    dfl2560IfVlanUntaggedOutPkts    Counter32,
    dfl2560IfVlanUntaggedTotPkts    Counter32,
    dfl2560IfVlanUntaggedInOctets   Counter32,
    dfl2560IfVlanUntaggedOutOctets  Counter32,
    dfl2560IfVlanUntaggedTotOctets  Counter32
}

dfl2560IfVlanIndex OBJECT-TYPE
    SYNTAX      Integer32 (1..2147483647)
    MAX-ACCESS  not-accessible
    STATUS      current
    DESCRIPTION 
        "Extended index of a row in dfl2560IfVlanStatsTable."
    ::= { dfl2560IfVlanStatsEntry 1 }

dfl2560IfVlanUntaggedInPkts OBJECT-TYPE
    SYNTAX      Counter32
    MAX-ACCESS  read-only
    STATUS      current
    DESCRIPTION 
        "Number of untaged packets untagged packets received by the interface."
    ::= { dfl2560IfVlanStatsEntry 2 }

dfl2560IfVlanUntaggedOutPkts OBJECT-TYPE
    SYNTAX      Counter32
    MAX-ACCESS  read-only
    STATUS      current
    DESCRIPTION 
        "Number of untagged packets sent by the interface."
    ::= { dfl2560IfVlanStatsEntry 3 }

dfl2560IfVlanUntaggedTotPkts OBJECT-TYPE
    SYNTAX      Counter32
    MAX-ACCESS  read-only
    STATUS      current
    DESCRIPTION 
        "Total number of untagged packets processed by the interface."
    ::= { dfl2560IfVlanStatsEntry 4 }

dfl2560IfVlanUntaggedInOctets OBJECT-TYPE
    SYNTAX      Counter32
    MAX-ACCESS  read-only
    STATUS      current
    DESCRIPTION 
        "Total number of octects in untagged packets received by the interface."
    ::= { dfl2560IfVlanStatsEntry 5 }

dfl2560IfVlanUntaggedOutOctets OBJECT-TYPE
    SYNTAX      Counter32
    MAX-ACCESS  read-only
    STATUS      current
    DESCRIPTION 
        "Total number of octects in untagged packets sent by the interface."
    ::= { dfl2560IfVlanStatsEntry 6 }

dfl2560IfVlanUntaggedTotOctets OBJECT-TYPE
    SYNTAX      Counter32
    MAX-ACCESS  read-only
    STATUS      current
    DESCRIPTION 
        "Total number of octects in untagged packets processed by the 
         interface."
    ::= { dfl2560IfVlanStatsEntry 7 }

dfl2560HWSensorTable OBJECT-TYPE
    SYNTAX      SEQUENCE OF Dfl2560HWSensorEntry
    MAX-ACCESS  not-accessible
    STATUS      current
    DESCRIPTION 
        "Table of hardware sensors."
    ::= { dfl2560System 11 }

dfl2560HWSensorEntry OBJECT-TYPE
    SYNTAX      Dfl2560HWSensorEntry
    MAX-ACCESS  not-accessible
    STATUS      current
    DESCRIPTION 
        "Entry  of table of hardware sensors."
    INDEX       { dfl2560HWSensorIndex }
    ::= { dfl2560HWSensorTable 1 }

Dfl2560HWSensorEntry ::= SEQUENCE {
    dfl2560HWSensorIndex    Integer32,
    dfl2560HWSensorName     DisplayString,
    dfl2560HWSensorValue    Gauge32,
    dfl2560HWSensorUnit     DisplayString
}

dfl2560HWSensorIndex OBJECT-TYPE
    SYNTAX      Integer32 (1..2147483647)
    MAX-ACCESS  not-accessible
    STATUS      current
    DESCRIPTION 
        "Index of the entries of the sensor table."
    ::= { dfl2560HWSensorEntry 1 }

dfl2560HWSensorName OBJECT-TYPE
    SYNTAX      DisplayString
    MAX-ACCESS  read-only
    STATUS      current
    DESCRIPTION 
        "The description of the sensor."
    ::= { dfl2560HWSensorEntry 2 }

dfl2560HWSensorValue OBJECT-TYPE
    SYNTAX      Gauge32
    MAX-ACCESS  read-only
    STATUS      current
    DESCRIPTION 
        "The value of the sensor."
    ::= { dfl2560HWSensorEntry 3 }

dfl2560HWSensorUnit OBJECT-TYPE
    SYNTAX      DisplayString
    MAX-ACCESS  read-only
    STATUS      current
    DESCRIPTION 
        "The description of the unit of the value mesured by sensor."
    ::= { dfl2560HWSensorEntry 4 }

dfl2560SysMemUsage OBJECT-TYPE
    SYNTAX      Gauge32
    MAX-ACCESS  read-only
    STATUS      current
    DESCRIPTION 
        "The current memory usage."
    ::= { dfl2560System 12 }

dfl2560SysTCPUsage OBJECT IDENTIFIER
    ::= { dfl2560System 13 }
    
dfl2560SysTCPRecvSmall OBJECT-TYPE
    SYNTAX      Gauge32
    MAX-ACCESS  read-only
    STATUS      current
    DESCRIPTION 
        "Small TCP receive windows usage."
    ::= { dfl2560SysTCPUsage 1 }

dfl2560SysTCPRecvLarge OBJECT-TYPE
    SYNTAX      Gauge32
    MAX-ACCESS  read-only
    STATUS      current
    DESCRIPTION 
        "Large TCP receive windows usage."
    ::= { dfl2560SysTCPUsage 2 }

dfl2560SysTCPSendSmall OBJECT-TYPE
    SYNTAX      Gauge32
    MAX-ACCESS  read-only
    STATUS      current
    DESCRIPTION 
        "Small TCP send windows usage."
    ::= { dfl2560SysTCPUsage 3 }

dfl2560SysTCPSendLarge OBJECT-TYPE
    SYNTAX      Gauge32
    MAX-ACCESS  read-only
    STATUS      current
    DESCRIPTION 
        "Large TCP send windows usage."
    ::= { dfl2560SysTCPUsage 4 }

dfl2560SysTimerUsage OBJECT-TYPE
    SYNTAX      Gauge32
    MAX-ACCESS  read-only
    STATUS      current
    DESCRIPTION 
        "The current number of timers in use."
    ::= { dfl2560System 14 }

dfl2560SysConnOPS OBJECT-TYPE
    SYNTAX      Gauge32
    MAX-ACCESS  read-only
    STATUS      current
    DESCRIPTION 
        "The number of connections opened per second."
    ::= { dfl2560System 15 }
    
dfl2560SysConnCPS OBJECT-TYPE
    SYNTAX      Gauge32
    MAX-ACCESS  read-only
    STATUS      current
    DESCRIPTION 
        "The number of connections closed per second."
    ::= { dfl2560System 16 }
    
dfl2560SysHCForwardedBits OBJECT-TYPE
    SYNTAX      Counter64
    MAX-ACCESS  read-only
    STATUS      current
    DESCRIPTION
        "The number of bits forwarded through the gateway."
    ::= { dfl2560System 17 }
    
dfl2560VPN OBJECT IDENTIFIER
    ::= { dfl2560OSStats 2 }

dfl2560IPsec OBJECT IDENTIFIER
    ::= { dfl2560VPN 1 }

dfl2560IPsecGlobal OBJECT IDENTIFIER
    ::= { dfl2560IPsec 1 }

dfl2560IPsecPhaseOneActive OBJECT-TYPE
    SYNTAX      Gauge32
    MAX-ACCESS  read-only
    STATUS      current
    DESCRIPTION 
        "Number of Phase-1 active negotiations"
    ::= { dfl2560IPsecGlobal 1 }

dfl2560IPsecPhaseOneAggrModeDone OBJECT-TYPE
    SYNTAX      Gauge32
    MAX-ACCESS  read-only
    STATUS      current
    DESCRIPTION 
        "Number of Phase-1 aggressive mode negotiations."
    ::= { dfl2560IPsecGlobal 2 }

dfl2560IPsecQuickModeActive OBJECT-TYPE
    SYNTAX      Gauge32
    MAX-ACCESS  read-only
    STATUS      current
    DESCRIPTION 
        "Number of quick mode active negotiations."
    ::= { dfl2560IPsecGlobal 3 }

dfl2560IPsecPhaseOneDone OBJECT-TYPE
    SYNTAX      Counter32
    MAX-ACCESS  read-only
    STATUS      current
    DESCRIPTION 
        "Number of Phase-1 negotiations done."
    ::= { dfl2560IPsecGlobal 4 }

dfl2560IPsecPhaseOneFailed OBJECT-TYPE
    SYNTAX      Counter32
    MAX-ACCESS  read-only
    STATUS      current
    DESCRIPTION 
        "Number of Phase-1 negotiations failed."
    ::= { dfl2560IPsecGlobal 5 }

dfl2560IPsecPhaseOneRekeyed OBJECT-TYPE
    SYNTAX      Counter32
    MAX-ACCESS  read-only
    STATUS      current
    DESCRIPTION 
        "Number of Phase-1 negotiations rekeyed."
    ::= { dfl2560IPsecGlobal 6 }

dfl2560IPsecQuickModeDone OBJECT-TYPE
    SYNTAX      Counter32
    MAX-ACCESS  read-only
    STATUS      current
    DESCRIPTION 
        "Number of quick mode  negotiations done."
    ::= { dfl2560IPsecGlobal 7 }

dfl2560IPsecQuickModeFailed OBJECT-TYPE
    SYNTAX      Counter32
    MAX-ACCESS  read-only
    STATUS      current
    DESCRIPTION 
        "Number of quick mode negotiations failed."
    ::= { dfl2560IPsecGlobal 8 }

dfl2560IPsecInfoDone OBJECT-TYPE
    SYNTAX      Counter32
    MAX-ACCESS  read-only
    STATUS      current
    DESCRIPTION 
        "Number of informational exchanges done.
         (Not available in IKEv1 implementations)"
    ::= { dfl2560IPsecGlobal 9 }

dfl2560IPsecInfoFailed OBJECT-TYPE
    SYNTAX      Counter32
    MAX-ACCESS  read-only
    STATUS      current
    DESCRIPTION 
        "Number of informational exchanges failed.
         (Not available in IKEv1 implementations)"
    ::= { dfl2560IPsecGlobal 10 }

dfl2560IPsecInOctetsComp OBJECT-TYPE
    SYNTAX      Counter64
    MAX-ACCESS  read-only
    STATUS      current
    DESCRIPTION 
        "Total octets in before decompression."
    ::= { dfl2560IPsecGlobal 11 }

dfl2560IPsecInOctetsUncomp OBJECT-TYPE
    SYNTAX      Counter64
    MAX-ACCESS  read-only
    STATUS      current
    DESCRIPTION 
        "Total octets in after decompression."
    ::= { dfl2560IPsecGlobal 12 }

dfl2560IPsecOutOctetsComp OBJECT-TYPE
    SYNTAX      Counter64
    MAX-ACCESS  read-only
    STATUS      current
    DESCRIPTION 
        "Total octets out after compression."
    ::= { dfl2560IPsecGlobal 13 }

dfl2560IPsecOutOctetsUncomp OBJECT-TYPE
    SYNTAX      Counter64
    MAX-ACCESS  read-only
    STATUS      current
    DESCRIPTION 
        "Total octets out before compression."
    ::= { dfl2560IPsecGlobal 14 }

dfl2560IPsecForwardedOctetsComp OBJECT-TYPE
    SYNTAX      Counter64
    MAX-ACCESS  read-only
    STATUS      current
    DESCRIPTION 
        "Total octets forwarded after compression."
    ::= { dfl2560IPsecGlobal 15 }

dfl2560IPsecForwardedOctetsUcomp OBJECT-TYPE
    SYNTAX      Counter64
    MAX-ACCESS  read-only
    STATUS      current
    DESCRIPTION 
        "Total octets forwarded before compression."
    ::= { dfl2560IPsecGlobal 16 }

dfl2560IPsecInPackets OBJECT-TYPE
    SYNTAX      Counter64
    MAX-ACCESS  read-only
    STATUS      current
    DESCRIPTION 
        "Total packets in."
    ::= { dfl2560IPsecGlobal 17 }

dfl2560IPsecOutPackets OBJECT-TYPE
    SYNTAX      Counter64
    MAX-ACCESS  read-only
    STATUS      current
    DESCRIPTION 
        "Total packets Out."
    ::= { dfl2560IPsecGlobal 18 }

dfl2560IPsecForwardedPackets OBJECT-TYPE
    SYNTAX      Counter64
    MAX-ACCESS  read-only
    STATUS      current
    DESCRIPTION 
        "Total packets forwarded."
    ::= { dfl2560IPsecGlobal 19 }

dfl2560IPsecActiveTransforms OBJECT-TYPE
    SYNTAX      Gauge32
    MAX-ACCESS  read-only
    STATUS      current
    DESCRIPTION 
        "Number of currently active transforms."
    ::= { dfl2560IPsecGlobal 20 }

dfl2560IPsecTotalTransforms OBJECT-TYPE
    SYNTAX      Counter32
    MAX-ACCESS  read-only
    STATUS      current
    DESCRIPTION 
        "Total number of transform records created."
    ::= { dfl2560IPsecGlobal 21 }

dfl2560IPsecOutOfTransforms OBJECT-TYPE
    SYNTAX      Counter32
    MAX-ACCESS  read-only
    STATUS      current
    DESCRIPTION 
        "Number of packets dropped due to no available transform object.
         (Not available in IKEv1 implementations)"
    ::= { dfl2560IPsecGlobal 22 }

dfl2560IPsecTotalRekeys OBJECT-TYPE
    SYNTAX      Counter32
    MAX-ACCESS  read-only
    STATUS      current
    DESCRIPTION 
        "Total number of rekeys performed."
    ::= { dfl2560IPsecGlobal 23 }

dfl2560Rules OBJECT IDENTIFIER
    ::= { dfl2560OSStats 3 }

dfl2560RuleUseTable OBJECT-TYPE
    SYNTAX      SEQUENCE OF Dfl2560RuleUseEntry
    MAX-ACCESS  not-accessible
    STATUS      current
    DESCRIPTION 
        "A list of general rules usage statistics."
    ::= { dfl2560Rules 2 }

dfl2560RuleUseEntry OBJECT-TYPE
    SYNTAX      Dfl2560RuleUseEntry
    MAX-ACCESS  not-accessible
    STATUS      current
    DESCRIPTION 
        "The statistics over a rule usage."
    INDEX       { dfl2560RuleIndex }
    ::= { dfl2560RuleUseTable 1 }

Dfl2560RuleUseEntry ::= SEQUENCE {
    dfl2560RuleIndex    Integer32,
    dfl2560RuleName     DisplayString,
    dfl2560RuleUse      Counter32
}

dfl2560RuleIndex OBJECT-TYPE
    SYNTAX      Integer32 (1..2147483647)
    MAX-ACCESS  not-accessible
    STATUS      current
    DESCRIPTION 
        "The rule usage index."
    ::= { dfl2560RuleUseEntry 1 }

dfl2560RuleName OBJECT-TYPE
    SYNTAX      DisplayString
    MAX-ACCESS  read-only
    STATUS      current
    DESCRIPTION 
        "The name of the rule."
    ::= { dfl2560RuleUseEntry 2 }

dfl2560RuleUse OBJECT-TYPE
    SYNTAX      Counter32
    MAX-ACCESS  read-only
    STATUS      current
    DESCRIPTION 
        "The number of times o rule was used."
    ::= { dfl2560RuleUseEntry 3 }

dfl2560IPPools OBJECT IDENTIFIER
    ::= { dfl2560OSStats 4 }

dfl2560IPPoolsNumber OBJECT-TYPE
    SYNTAX      Integer32
    MAX-ACCESS  read-only
    STATUS      current
    DESCRIPTION 
        "The number of ip pools"
    ::= { dfl2560IPPools 1 }

dfl2560IPPoolTable OBJECT-TYPE
    SYNTAX      SEQUENCE OF Dfl2560IPPoolEntry
    MAX-ACCESS  not-accessible
    STATUS      current
    DESCRIPTION 
        "A list of IP pools"
    ::= { dfl2560IPPools 2 }

dfl2560IPPoolEntry OBJECT-TYPE
    SYNTAX      Dfl2560IPPoolEntry
    MAX-ACCESS  not-accessible
    STATUS      current
    DESCRIPTION 
        "The attributes of an ip pool"
    INDEX       { dfl2560IPPoolIndex }
    ::= { dfl2560IPPoolTable 1 }

Dfl2560IPPoolEntry ::= SEQUENCE {
    dfl2560IPPoolIndex          Integer32,
    dfl2560IPPoolName           DisplayString,
    dfl2560IPPoolPrepare        Gauge32,
    dfl2560IPPoolFree           Gauge32,
    dfl2560IPPoolMisses         Gauge32,
    dfl2560IPPoolClientFails    Gauge32,
    dfl2560IPPoolUsed           Gauge32
}

dfl2560IPPoolIndex OBJECT-TYPE
    SYNTAX      Integer32 (1..2147483647)
    MAX-ACCESS  not-accessible
    STATUS      current
    DESCRIPTION 
        "The ip pool index"
    ::= { dfl2560IPPoolEntry 1 }

dfl2560IPPoolName OBJECT-TYPE
    SYNTAX      DisplayString
    MAX-ACCESS  read-only
    STATUS      current
    DESCRIPTION 
        "The ip pool name"
    ::= { dfl2560IPPoolEntry 2 }

dfl2560IPPoolPrepare OBJECT-TYPE
    SYNTAX      Gauge32
    MAX-ACCESS  read-only
    STATUS      current
    DESCRIPTION 
        "Number of IP pool objects in prepare mode."
    ::= { dfl2560IPPoolEntry 3 }

dfl2560IPPoolFree OBJECT-TYPE
    SYNTAX      Gauge32
    MAX-ACCESS  read-only
    STATUS      current
    DESCRIPTION 
        "Number of available IPs in the pool."
    ::= { dfl2560IPPoolEntry 4 }

dfl2560IPPoolMisses OBJECT-TYPE
    SYNTAX      Gauge32
    MAX-ACCESS  read-only
    STATUS      current
    DESCRIPTION 
        "Mumber of missed IP pool negotiations for other reasons
         than lack of available IP numbers."
    ::= { dfl2560IPPoolEntry 5 }

dfl2560IPPoolClientFails OBJECT-TYPE
    SYNTAX      Gauge32
    MAX-ACCESS  read-only
    STATUS      current
    DESCRIPTION 
        "Number of failed IP pool transactions."
    ::= { dfl2560IPPoolEntry 6 }

dfl2560IPPoolUsed OBJECT-TYPE
    SYNTAX      Gauge32
    MAX-ACCESS  read-only
    STATUS      current
    DESCRIPTION 
        "Number of IP numbers in use from the pool."
    ::= { dfl2560IPPoolEntry 7 }

dfl2560DHCPServer OBJECT IDENTIFIER
    ::= { dfl2560OSStats 5 }

dfl2560DHCPTotalRejected OBJECT-TYPE
    SYNTAX      Gauge32
    MAX-ACCESS  read-only
    STATUS      current
    DESCRIPTION 
        "Total number of rejected packets (all rules)."
    ::= { dfl2560DHCPServer 1 }

dfl2560DHCPRuleTable OBJECT-TYPE
    SYNTAX      SEQUENCE OF Dfl2560DHCPRuleEntry
    MAX-ACCESS  not-accessible
    STATUS      current
    DESCRIPTION 
        "A list of all DHCP server rules usage statistics."
    ::= { dfl2560DHCPServer 2 }

dfl2560DHCPRuleEntry OBJECT-TYPE
    SYNTAX      Dfl2560DHCPRuleEntry
    MAX-ACCESS  not-accessible
    STATUS      current
    DESCRIPTION 
        "The attributes of a DHCP server rule statistics."
    INDEX       { dfl2560DHCPRuleIndex }
    ::= { dfl2560DHCPRuleTable 1 }

Dfl2560DHCPRuleEntry ::= SEQUENCE {
    dfl2560DHCPRuleIndex                Integer32,
    dfl2560DHCPRuleName                 DisplayString,
    dfl2560DHCPRuleUsage                Gauge32,
    dfl2560DHCPRuleUsagePercent         Gauge32,
    dfl2560DHCPActiveClients            Gauge32,
    dfl2560DHCPActiveClientsPercent     Gauge32,
    dfl2560DHCPRejectedRequests         Gauge32,
    dfl2560DHCPTotalLeases              Gauge32
}

dfl2560DHCPRuleIndex OBJECT-TYPE
    SYNTAX      Integer32 (1..2147483647)
    MAX-ACCESS  not-accessible
    STATUS      current
    DESCRIPTION 
        "The DHCP server rule  index"
    ::= { dfl2560DHCPRuleEntry 1 }

dfl2560DHCPRuleName OBJECT-TYPE
    SYNTAX      DisplayString
    MAX-ACCESS  read-only
    STATUS      current
    DESCRIPTION 
        "The DHCP server rule name."
    ::= { dfl2560DHCPRuleEntry 2 }

dfl2560DHCPRuleUsage OBJECT-TYPE
    SYNTAX      Gauge32
    MAX-ACCESS  read-only
    STATUS      current
    DESCRIPTION 
        "Number of used IPs in the pool."
    ::= { dfl2560DHCPRuleEntry 3 }

dfl2560DHCPRuleUsagePercent OBJECT-TYPE
    SYNTAX      Gauge32
    MAX-ACCESS  read-only
    STATUS      current
    DESCRIPTION 
        "The percentage of the used IPs in 
         relation to the IP pool size."
    ::= { dfl2560DHCPRuleEntry 4 }

dfl2560DHCPActiveClients OBJECT-TYPE
    SYNTAX      Gauge32
    MAX-ACCESS  read-only
    STATUS      current
    DESCRIPTION 
        "Number of currently active clients."
    ::= { dfl2560DHCPRuleEntry 5 }

dfl2560DHCPActiveClientsPercent OBJECT-TYPE
    SYNTAX      Gauge32
    MAX-ACCESS  read-only
    STATUS      current
    DESCRIPTION 
        "The number of currently active clients 
         as a percentage of the pool size."
    ::= { dfl2560DHCPRuleEntry 6 }

dfl2560DHCPRejectedRequests OBJECT-TYPE
    SYNTAX      Gauge32
    MAX-ACCESS  read-only
    STATUS      current
    DESCRIPTION 
        "Number of rejected requests matching
         the current rule."
    ::= { dfl2560DHCPRuleEntry 7 }

dfl2560DHCPTotalLeases OBJECT-TYPE
    SYNTAX      Gauge32
    MAX-ACCESS  read-only
    STATUS      current
    DESCRIPTION 
        "Total number of leases in the pool."
    ::= { dfl2560DHCPRuleEntry 8 }

dfl2560UserAuth OBJECT IDENTIFIER
    ::= { dfl2560OSStats 6 }

dfl2560UserAuthHTTPUsers OBJECT-TYPE
    SYNTAX      Gauge32
    MAX-ACCESS  read-only
    STATUS      current
    DESCRIPTION 
        "Number of currently  logged in HTTP users."
    ::= { dfl2560UserAuth 1 }

dfl2560UserAuthXAUTHUsers OBJECT-TYPE
    SYNTAX      Gauge32
    MAX-ACCESS  read-only
    STATUS      current
    DESCRIPTION 
        "Number of currently logged in XAUTH users."
    ::= { dfl2560UserAuth 2 }

dfl2560UserAuthHTTPSUsers OBJECT-TYPE
    SYNTAX      Gauge32
    MAX-ACCESS  read-only
    STATUS      current
    DESCRIPTION 
        "Number of currently logged in HTTPS users."
    ::= { dfl2560UserAuth 3 }

dfl2560UserAuthPPPUsers OBJECT-TYPE
    SYNTAX      Gauge32
    MAX-ACCESS  read-only
    STATUS      current
    DESCRIPTION 
        "Number of currently logged in PPP users."
    ::= { dfl2560UserAuth 4 }

dfl2560UserAuthEAPUsers OBJECT-TYPE
    SYNTAX      Gauge32
    MAX-ACCESS  read-only
    STATUS      current
    DESCRIPTION 
        "Number of currently logged in EAP users."
    ::= { dfl2560UserAuth 5 }

dfl2560UserAuthRuleUseTable OBJECT-TYPE
    SYNTAX      SEQUENCE OF Dfl2560UserAuthRuleUseEntry
    MAX-ACCESS  not-accessible
    STATUS      current
    DESCRIPTION 
        "Table of user authentication rule usage."
    ::= { dfl2560UserAuth 6 }

dfl2560UserAuthRuleUseEntry OBJECT-TYPE
    SYNTAX      Dfl2560UserAuthRuleUseEntry
    MAX-ACCESS  not-accessible
    STATUS      current
    DESCRIPTION 
        "The attributes of an authentication rule 
         usage statistics."
    INDEX       { dfl2560UserAuthRuleIndex }
    ::= { dfl2560UserAuthRuleUseTable 1 }

Dfl2560UserAuthRuleUseEntry ::= SEQUENCE {
    dfl2560UserAuthRuleIndex    Integer32,
    dfl2560UserAuthRuleName     DisplayString,
    dfl2560UserAuthRuleUse      Counter32
}

dfl2560UserAuthRuleIndex OBJECT-TYPE
    SYNTAX      Integer32 (1..2147483647)
    MAX-ACCESS  not-accessible
    STATUS      current
    DESCRIPTION 
        "The rule usage index."
    ::= { dfl2560UserAuthRuleUseEntry 1 }

dfl2560UserAuthRuleName OBJECT-TYPE
    SYNTAX      DisplayString
    MAX-ACCESS  read-only
    STATUS      current
    DESCRIPTION 
        "The name of the rule."
    ::= { dfl2560UserAuthRuleUseEntry 2 }

dfl2560UserAuthRuleUse OBJECT-TYPE
    SYNTAX      Counter32
    MAX-ACCESS  read-only
    STATUS      current
    DESCRIPTION 
        "The number of times o rule was used."
    ::= { dfl2560UserAuthRuleUseEntry 3 }

dfl2560LinkMonitor OBJECT IDENTIFIER
    ::= { dfl2560OSStats 7 }

dfl2560LinkMonGrp OBJECT-TYPE
    SYNTAX      Integer32
    MAX-ACCESS  read-only
    STATUS      current
    DESCRIPTION 
        "The number of groups of monitored links"
    ::= { dfl2560LinkMonitor 1 }

dfl2560LinkMonGrpTable OBJECT-TYPE
    SYNTAX      SEQUENCE OF Dfl2560LinkMonGrpEntry
    MAX-ACCESS  not-accessible
    STATUS      current
    DESCRIPTION 
        "Table of link monitor groups."
    ::= { dfl2560LinkMonitor 2 }

dfl2560LinkMonGrpEntry OBJECT-TYPE
    SYNTAX      Dfl2560LinkMonGrpEntry
    MAX-ACCESS  not-accessible
    STATUS      current
    DESCRIPTION 
        "The attributes of a link monitor group"
    INDEX       { dfl2560LinkMonGrpIndex }
    ::= { dfl2560LinkMonGrpTable 1 }

Dfl2560LinkMonGrpEntry ::= SEQUENCE {
    dfl2560LinkMonGrpIndex      Integer32,
    dfl2560LinkMonGrpName       DisplayString,
    dfl2560LinkMonGrpHostsUp    Gauge32
}

dfl2560LinkMonGrpIndex OBJECT-TYPE
    SYNTAX      Integer32 (1..2147483647)
    MAX-ACCESS  not-accessible
    STATUS      current
    DESCRIPTION 
        "The index row in the table of link monitor groups."
    ::= { dfl2560LinkMonGrpEntry 1 }

dfl2560LinkMonGrpName OBJECT-TYPE
    SYNTAX      DisplayString
    MAX-ACCESS  read-only
    STATUS      current
    DESCRIPTION 
        "The link monitor group name."
    ::= { dfl2560LinkMonGrpEntry 2 }

dfl2560LinkMonGrpHostsUp OBJECT-TYPE
    SYNTAX      Gauge32
    MAX-ACCESS  read-only
    STATUS      current
    DESCRIPTION 
        "The percentage of monitored hosts available."
    ::= { dfl2560LinkMonGrpEntry 3 }

dfl2560LinkMonHostTable OBJECT-TYPE
    SYNTAX      SEQUENCE OF Dfl2560LinkMonHostEntry
    MAX-ACCESS  not-accessible
    STATUS      current
    DESCRIPTION 
        "Table of link monitored hosts in a link monnitor group."
    ::= { dfl2560LinkMonitor 3 }

dfl2560LinkMonHostEntry OBJECT-TYPE
    SYNTAX      Dfl2560LinkMonHostEntry
    MAX-ACCESS  not-accessible
    STATUS      current
    DESCRIPTION 
        "The attributes of a monitored host."
    INDEX       { dfl2560LinkMonGrpIndex, dfl2560LinkMonHostIndex }
    ::= { dfl2560LinkMonHostTable 1 }

Dfl2560LinkMonHostEntry ::= SEQUENCE {
    dfl2560LinkMonHostIndex             Integer32,
    dfl2560LinkMonHostId                DisplayString,
    dfl2560LinkMonHostShortTermLoss     Gauge32,
    dfl2560LinkMonHostPacketsLost       Counter32
}

dfl2560LinkMonHostIndex OBJECT-TYPE
    SYNTAX      Integer32 (1..2147483647)
    MAX-ACCESS  not-accessible
    STATUS      current
    DESCRIPTION 
        "The index an host in the table of link monitor hosts."
    ::= { dfl2560LinkMonHostEntry 1 }

dfl2560LinkMonHostId OBJECT-TYPE
    SYNTAX      DisplayString
    MAX-ACCESS  read-only
    STATUS      current
    DESCRIPTION 
        "The monitored host identifier."
    ::= { dfl2560LinkMonHostEntry 2 }

dfl2560LinkMonHostShortTermLoss OBJECT-TYPE
    SYNTAX      Gauge32
    MAX-ACCESS  read-only
    STATUS      current
    DESCRIPTION 
        "The percentage of short term losst packets."
    ::= { dfl2560LinkMonHostEntry 3 }

dfl2560LinkMonHostPacketsLost OBJECT-TYPE
    SYNTAX      Counter32
    MAX-ACCESS  read-only
    STATUS      current
    DESCRIPTION 
        "Total number of lost monitoring packets."
    ::= { dfl2560LinkMonHostEntry 4 }

dfl2560Pipes OBJECT IDENTIFIER
    ::= { dfl2560OSStats 8 }

dfl2560PipeUsers OBJECT-TYPE
    SYNTAX      Gauge32
    MAX-ACCESS  read-only
    STATUS      current
    DESCRIPTION 
        "The current number of users, as defined by the grouping 
         settings of each pipe, being tracked in the pipes system. 
         Note that this value corresponds to the number of users 
         active in each time slice of 1/20th of a second, and not 
         to the number of users having open connections."
    ::= { dfl2560Pipes 1 }

dfl2560PipeTable OBJECT-TYPE
    SYNTAX      SEQUENCE OF Dfl2560PipeEntry
    MAX-ACCESS  not-accessible
    STATUS      current
    DESCRIPTION 
        "Table of pipes"
    ::= { dfl2560Pipes 2 }

dfl2560PipeEntry OBJECT-TYPE
    SYNTAX      Dfl2560PipeEntry
    MAX-ACCESS  not-accessible
    STATUS      current
    DESCRIPTION 
        "A entry of the pipes table"
    INDEX       { dfl2560PipeIndex }
    ::= { dfl2560PipeTable 1 }

Dfl2560PipeEntry ::= SEQUENCE {
    dfl2560PipeIndex            Integer32,
    dfl2560PipeName             DisplayString,
    dfl2560PipeMinPrec          Integer32,
    dfl2560PipeMaxPrec          Integer32,
    dfl2560PipeDefPrec          Integer32,
    dfl2560PipeNumPrec          Integer32,
    dfl2560PipeNumUsers         Gauge32,
    dfl2560PipeCurrentBps       Gauge32,
    dfl2560PipeCurrentPps       Gauge32,
    dfl2560PipeDelayedPackets   Counter32,
    dfl2560PipeDropedPackets    Counter32
}

dfl2560PipeIndex OBJECT-TYPE
    SYNTAX      Integer32 (1..2147483647)
    MAX-ACCESS  not-accessible
    STATUS      current
    DESCRIPTION 
        "The pipe index"
    ::= { dfl2560PipeEntry 1 }

dfl2560PipeName OBJECT-TYPE
    SYNTAX      DisplayString
    MAX-ACCESS  read-only
    STATUS      current
    DESCRIPTION 
        "The name of the pipe"
    ::= { dfl2560PipeEntry 2 }

dfl2560PipeMinPrec OBJECT-TYPE
    SYNTAX      Integer32
    MAX-ACCESS  read-only
    STATUS      current
    DESCRIPTION 
        "The minimum of the range of pipe precedences."
    ::= { dfl2560PipeEntry 3 }

dfl2560PipeMaxPrec OBJECT-TYPE
    SYNTAX      Integer32
    MAX-ACCESS  read-only
    STATUS      current
    DESCRIPTION 
        "The maximum of the range of pipe precedences."
    ::= { dfl2560PipeEntry 4 }

dfl2560PipeDefPrec OBJECT-TYPE
    SYNTAX      Integer32
    MAX-ACCESS  read-only
    STATUS      current
    DESCRIPTION 
        "The precedence assigned to a packet for which has not one
         allready done by a Pipe Rule."
    ::= { dfl2560PipeEntry 5 }

dfl2560PipeNumPrec OBJECT-TYPE
    SYNTAX      Integer32
    MAX-ACCESS  read-only
    STATUS      current
    DESCRIPTION 
        "The number of pipe precedences"
    ::= { dfl2560PipeEntry 6 }

dfl2560PipeNumUsers OBJECT-TYPE
    SYNTAX      Gauge32
    MAX-ACCESS  read-only
    STATUS      current
    DESCRIPTION 
        "The current number of users, as defined by the grouping settings
         of each pipe, being tracked in the pipes system. This value 
         corresponds to the number of users active in each time slice 
         and not to the number of users having  open connections."
    ::= { dfl2560PipeEntry 7 }

dfl2560PipeCurrentBps OBJECT-TYPE
    SYNTAX      Gauge32
    MAX-ACCESS  read-only
    STATUS      current
    DESCRIPTION 
        "The current throughput of a pipe, in bits per second, as a sum of 
         the corresponding values for all precedences."
    ::= { dfl2560PipeEntry 8 }

dfl2560PipeCurrentPps OBJECT-TYPE
    SYNTAX      Gauge32
    MAX-ACCESS  read-only
    STATUS      current
    DESCRIPTION 
        "The current throughput of a pipe, in packets per second, as a sum of 
         the corresponding values for all precedences."
    ::= { dfl2560PipeEntry 9 }

dfl2560PipeDelayedPackets OBJECT-TYPE
    SYNTAX      Counter32
    MAX-ACCESS  read-only
    STATUS      current
    DESCRIPTION 
        "The number of times packets have been delayed as a result of a pipe, 
         or pipe user having used up its allotted bandwidth. Note that one single
         packet may be delayed several times; if a pipe is really full, this 
         count may exceed the number of packets actually passing through the 
         pipe."
    ::= { dfl2560PipeEntry 10 }

dfl2560PipeDropedPackets OBJECT-TYPE
    SYNTAX      Counter32
    MAX-ACCESS  read-only
    STATUS      current
    DESCRIPTION 
        "The number of packets dropped by a pipe. Packets are dropped when 
         CorePlus is running out of packet buffers. This occurs when excessive 
         amounts of packets need to be queued for later delivery. The packet 
         dropped is always the one that has been queued the longest time 
         globally, which means that the connection suffering from packet loss 
         will be the one most overloading the system."
    ::= { dfl2560PipeEntry 11 }

dfl2560PipePrecTable OBJECT-TYPE
    SYNTAX      SEQUENCE OF Dfl2560PipePrecEntry
    MAX-ACCESS  not-accessible
    STATUS      current
    DESCRIPTION 
        "There is a one to many relation between a pipe and its precedences.
         The number of precedences is a instance attribute of each pipe.
         This table extends the pipes table in order to express the relation 
         between a pipe and the respective precedences."
    ::= { dfl2560Pipes 3 }

dfl2560PipePrecEntry OBJECT-TYPE
    SYNTAX      Dfl2560PipePrecEntry
    MAX-ACCESS  not-accessible
    STATUS      current
    DESCRIPTION 
        "An entry of the table of pipe pecedences. These table entries 
         are chracterized by been indexed by two values. The first index
         the same as the pipe index of the corresponding row in table of 
         pipes and the second index is the index of the set of precedences 
         of the corresponding pipe."
    INDEX       { dfl2560PipeIndex, dfl2560PipePrecIndex }
    ::= { dfl2560PipePrecTable 1 }

Dfl2560PipePrecEntry ::= SEQUENCE {
    dfl2560PipePrecIndex            Integer32,
    dfl2560PipePrec                 Integer32,
    dfl2560PipePrecBps              Gauge32,
    dfl2560PipePrecTotalPps         Gauge32,
    dfl2560PipePrecReservedBps      Gauge32,
    dfl2560PipePrecDynLimBps        Gauge32,
    dfl2560PipePrecDynUsrLimBps     Gauge32,
    dfl2560PipePrecDelayedPackets   Counter32,
    dfl2560PipePrecDropedPackets    Counter32
}

dfl2560PipePrecIndex OBJECT-TYPE
    SYNTAX      Integer32 (1..2147483647)
    MAX-ACCESS  not-accessible
    STATUS      current
    DESCRIPTION 
        "Index of a precedence of a specific pipe. This is the second index 
         of the entries of pipe precedence table described by object 
         dfl2560PipePrecEntry."
    ::= { dfl2560PipePrecEntry 1 }

dfl2560PipePrec OBJECT-TYPE
    SYNTAX      Integer32
    MAX-ACCESS  read-only
    STATUS      current
    DESCRIPTION 
        "The precedence value"
    ::= { dfl2560PipePrecEntry 2 }

dfl2560PipePrecBps OBJECT-TYPE
    SYNTAX      Gauge32
    MAX-ACCESS  read-only
    STATUS      current
    DESCRIPTION 
        "The current throughput of the pipe, in bits per second, with 
         the corresponding precedence."
    ::= { dfl2560PipePrecEntry 3 }

dfl2560PipePrecTotalPps OBJECT-TYPE
    SYNTAX      Gauge32
    MAX-ACCESS  read-only
    STATUS      current
    DESCRIPTION 
        "The current throughput of the pipe precedence, in packets per second."
    ::= { dfl2560PipePrecEntry 4 }

dfl2560PipePrecReservedBps OBJECT-TYPE
    SYNTAX      Gauge32
    MAX-ACCESS  read-only
    STATUS      current
    DESCRIPTION 
        "The current bandwidth allocated to the precedence."
    ::= { dfl2560PipePrecEntry 5 }

dfl2560PipePrecDynLimBps OBJECT-TYPE
    SYNTAX      Gauge32
    MAX-ACCESS  read-only
    STATUS      current
    DESCRIPTION 
        "The current bandwidth limit limit applied the precedence."
    ::= { dfl2560PipePrecEntry 6 }

dfl2560PipePrecDynUsrLimBps OBJECT-TYPE
    SYNTAX      Gauge32
    MAX-ACCESS  read-only
    STATUS      current
    DESCRIPTION 
        "The current precedence bandwidth limit per user of the pipe."
    ::= { dfl2560PipePrecEntry 7 }

dfl2560PipePrecDelayedPackets OBJECT-TYPE
    SYNTAX      Counter32
    MAX-ACCESS  read-only
    STATUS      current
    DESCRIPTION 
        "The number of times packets have been delayed as a result of a 
         precedence, or pipe user having used up its allotted bandwidth. 
         Note that one single packet may be delayed several times; if a 
         pipe is really full, this count may exceed the number of packets 
         of this precedence actually passing through the pipe."
    ::= { dfl2560PipePrecEntry 8 }

dfl2560PipePrecDropedPackets OBJECT-TYPE
    SYNTAX      Counter32
    MAX-ACCESS  read-only
    STATUS      current
    DESCRIPTION 
        "The number of pipe dropped packets with the corresponding precedence."
    ::= { dfl2560PipePrecEntry 9 }

dfl2560ALG OBJECT IDENTIFIER
    ::= { dfl2560OSStats 9 }

dfl2560AlgSessions OBJECT-TYPE
    SYNTAX      Gauge32
    MAX-ACCESS  read-only
    STATUS      current
    DESCRIPTION 
        "Total ALG sessions"
    ::= { dfl2560ALG 1 }

dfl2560AlgConnections OBJECT-TYPE
    SYNTAX      Gauge32
    MAX-ACCESS  read-only
    STATUS      current
    DESCRIPTION 
        "Total ALG connections"
    ::= { dfl2560ALG 2 }

dfl2560AlgTCPStreams OBJECT-TYPE
    SYNTAX      Gauge32
    MAX-ACCESS  read-only
    STATUS      current
    DESCRIPTION 
        "Total ALG TCP streams"
    ::= { dfl2560ALG 3 }

dfl2560HttpAlg OBJECT IDENTIFIER
    ::= { dfl2560ALG 4 }

dfl2560HttpAlgTable OBJECT-TYPE
    SYNTAX      SEQUENCE OF Dfl2560HttpAlgEntry
    MAX-ACCESS  not-accessible
    STATUS      current
    DESCRIPTION 
        "Table of HTTP ALG objects."
    ::= { dfl2560HttpAlg 1 }

dfl2560HttpAlgEntry OBJECT-TYPE
    SYNTAX      Dfl2560HttpAlgEntry
    MAX-ACCESS  not-accessible
    STATUS      current
    DESCRIPTION 
        "A row of the table of HTTP ALG objects."
    INDEX       { dfl2560HttpAlgIndex }
    ::= { dfl2560HttpAlgTable 1 }

Dfl2560HttpAlgEntry ::= SEQUENCE {
    dfl2560HttpAlgIndex             Integer32,
    dfl2560HttpAlgName              DisplayString,
    dfl2560HttpAlgTotalRequested    Gauge32,
    dfl2560HttpAlgTotalAllowed      Gauge32,
    dfl2560HttpAlgTotalBlocked      Gauge32
}

dfl2560HttpAlgIndex OBJECT-TYPE
    SYNTAX      Integer32 (1..2147483647)
    MAX-ACCESS  not-accessible
    STATUS      current
    DESCRIPTION 
        "The index of an entry of the  Table of HTTP ALG objects."
    ::= { dfl2560HttpAlgEntry 1 }

dfl2560HttpAlgName OBJECT-TYPE
    SYNTAX      DisplayString
    MAX-ACCESS  read-only
    STATUS      current
    DESCRIPTION 
        "The name of an HTTP ALG object."
    ::= { dfl2560HttpAlgEntry 2 }

dfl2560HttpAlgTotalRequested OBJECT-TYPE
    SYNTAX      Gauge32
    MAX-ACCESS  read-only
    STATUS      current
    DESCRIPTION 
        "Total number of URL requests."
    ::= { dfl2560HttpAlgEntry 3 }

dfl2560HttpAlgTotalAllowed OBJECT-TYPE
    SYNTAX      Gauge32
    MAX-ACCESS  read-only
    STATUS      current
    DESCRIPTION 
        "Total number of allowed URL requests."
    ::= { dfl2560HttpAlgEntry 4 }

dfl2560HttpAlgTotalBlocked OBJECT-TYPE
    SYNTAX      Gauge32
    MAX-ACCESS  read-only
    STATUS      current
    DESCRIPTION 
        "Total number of blocked URL requests."
    ::= { dfl2560HttpAlgEntry 5 }

dfl2560HttpAlgCntFltTable OBJECT-TYPE
    SYNTAX      SEQUENCE OF Dfl2560HttpAlgCntFltEntry
    MAX-ACCESS  not-accessible
    STATUS      current
    DESCRIPTION 
        "Table of HTTP ALG content filtering rules."
    ::= { dfl2560HttpAlg 2 }

dfl2560HttpAlgCntFltEntry OBJECT-TYPE
    SYNTAX      Dfl2560HttpAlgCntFltEntry
    MAX-ACCESS  not-accessible
    STATUS      current
    DESCRIPTION 
        "Entry of the table of HTTP ALG content filtering rules."
    INDEX       { dfl2560HttpAlgIndex, dfl2560HttpAlgCntFltIndex }
    ::= { dfl2560HttpAlgCntFltTable 1 }

Dfl2560HttpAlgCntFltEntry ::= SEQUENCE {
    dfl2560HttpAlgCntFltIndex       Integer32,
    dfl2560HttpAlgCntFltName        DisplayString,
    dfl2560HttpAlgCntFltRequests    Gauge32,
    dfl2560HttpAlgCntFltAllowed     Gauge32,
    dfl2560HttpAlgCntFltBlocked     Gauge32
}

dfl2560HttpAlgCntFltIndex OBJECT-TYPE
    SYNTAX      Integer32 (1..2147483647)
    MAX-ACCESS  not-accessible
    STATUS      current
    DESCRIPTION 
        "The index of an entry of the  Table of HTTP ALG 
         content filtering objects."
    ::= { dfl2560HttpAlgCntFltEntry 1 }

dfl2560HttpAlgCntFltName OBJECT-TYPE
    SYNTAX      DisplayString
    MAX-ACCESS  read-only
    STATUS      current
    DESCRIPTION 
        "The name of the a HTTP ALG content fitering."
    ::= { dfl2560HttpAlgCntFltEntry 2 }

dfl2560HttpAlgCntFltRequests OBJECT-TYPE
    SYNTAX      Gauge32
    MAX-ACCESS  read-only
    STATUS      current
    DESCRIPTION 
        "Total number of URLs intercepted by a content 
         filtering object."
    ::= { dfl2560HttpAlgCntFltEntry 3 }

dfl2560HttpAlgCntFltAllowed OBJECT-TYPE
    SYNTAX      Gauge32
    MAX-ACCESS  read-only
    STATUS      current
    DESCRIPTION 
        "Total number of URLs intercepted and allowed 
         by a content filtering object."
    ::= { dfl2560HttpAlgCntFltEntry 4 }

dfl2560HttpAlgCntFltBlocked OBJECT-TYPE
    SYNTAX      Gauge32
    MAX-ACCESS  read-only
    STATUS      current
    DESCRIPTION 
        "Total number of URLs intercepted and blocked 
         by a content filtering object."
    ::= { dfl2560HttpAlgCntFltEntry 5 }

dfl2560SmtpAlg OBJECT IDENTIFIER
    ::= { dfl2560ALG 5 }

dfl2560SmtpAlgTable OBJECT-TYPE
    SYNTAX  SEQUENCE OF Dfl2560SmtpAlgEntry
    MAX-ACCESS  not-accessible
    STATUS  current
    DESCRIPTION
  "Table of SMTP ALG objects."
    ::= { dfl2560SmtpAlg 1 }

dfl2560SmtpAlgEntry OBJECT-TYPE
   SYNTAX  Dfl2560SmtpAlgEntry
   MAX-ACCESS  not-accessible
    STATUS      current
    DESCRIPTION 
        "A row of the table of SMTP ALG objects."
    INDEX       { dfl2560SmtpAlgIndex }
    ::= { dfl2560SmtpAlgTable 1 }

Dfl2560SmtpAlgEntry ::= SEQUENCE {
    dfl2560SmtpAlgIndex           Integer32,
    dfl2560SmtpAlgName            DisplayString,
    dfl2560SmtpAlgTotCheckedSes   Gauge32,
    dfl2560SmtpAlgTotSpamSes      Gauge32,
    dfl2560SmtpAlgTotDroppedSes   Gauge32
}

dfl2560SmtpAlgIndex OBJECT-TYPE
    SYNTAX      Integer32 (1..2147483647)
    MAX-ACCESS  not-accessible
    STATUS      current
    DESCRIPTION 
        "The index of an entry of the  Table of SMTP ALG objects."
    ::= { dfl2560SmtpAlgEntry 1 }

dfl2560SmtpAlgName OBJECT-TYPE
    SYNTAX      DisplayString
    MAX-ACCESS  read-only
    STATUS      current
    DESCRIPTION 
        "The name of an SMTP ALG object."
    ::= { dfl2560SmtpAlgEntry 2 }

dfl2560SmtpAlgTotCheckedSes OBJECT-TYPE
    SYNTAX      Gauge32
    MAX-ACCESS  read-only
    STATUS      current
    DESCRIPTION 
        "Total sessions checked by the SMTP ALG of corresponding index."
    ::= { dfl2560SmtpAlgEntry 3 }

dfl2560SmtpAlgTotSpamSes OBJECT-TYPE
    SYNTAX      Gauge32
    MAX-ACCESS  read-only
    STATUS      current
    DESCRIPTION 
        "Total spam sessions detected by the SMTP ALG of corresponding index."
    ::= { dfl2560SmtpAlgEntry 4 }

dfl2560SmtpAlgTotDroppedSes OBJECT-TYPE
    SYNTAX      Gauge32
    MAX-ACCESS  read-only
    STATUS      current
    DESCRIPTION 
        "Total deroped sessions for the SMTP ALG of corresponding index."
    ::= { dfl2560SmtpAlgEntry 5 }


dfl2560SmtpAlgDnsBlTable OBJECT-TYPE
    SYNTAX  SEQUENCE OF Dfl2560SmtpAlgDnsBlEntry
    MAX-ACCESS  not-accessible
    STATUS  current
    DESCRIPTION
  "Table of SMTP ALG DNS balck list objects."
    ::= { dfl2560SmtpAlg 2 }


dfl2560SmtpAlgDnsBlEntry OBJECT-TYPE
   SYNTAX  Dfl2560SmtpAlgDnsBlEntry
   MAX-ACCESS  not-accessible
    STATUS      current
    DESCRIPTION 
        "A row of the table of SMTP ALG DNS black list objects."
    INDEX       { dfl2560SmtpAlgIndex, dfl2560SmtpAlgDnsBlIndex }
    ::= { dfl2560SmtpAlgDnsBlTable 1 }


Dfl2560SmtpAlgDnsBlEntry ::= SEQUENCE {
    dfl2560SmtpAlgDnsBlIndex  Integer32,
    dfl2560SmtpAlgDnsBlName    DisplayString,
    dfl2560SmtpAlgDnsBlChecked      Gauge32,
    dfl2560SmtpAlgDnsBlMatched  Gauge32,
    dfl2560SmtpAlgDnsBlFailChecks  Gauge32
}

dfl2560SmtpAlgDnsBlIndex OBJECT-TYPE
    SYNTAX      Integer32 (1..2147483647)
    MAX-ACCESS  not-accessible
    STATUS      current
    DESCRIPTION 
        "The index of an entry of the  SMTP ALG DNS black list objects." 
    ::= { dfl2560SmtpAlgDnsBlEntry 1 }

dfl2560SmtpAlgDnsBlName OBJECT-TYPE
    SYNTAX      DisplayString
    MAX-ACCESS  read-only
    STATUS      current
    DESCRIPTION 
  "The SMTP DNS black list name."
    ::= { dfl2560SmtpAlgDnsBlEntry 2 }

dfl2560SmtpAlgDnsBlChecked OBJECT-TYPE
    SYNTAX      Gauge32
    MAX-ACCESS  read-only
    STATUS      current
    DESCRIPTION 
  "Total sessions checked againt SMTP ALG DNS black list of corresponding index"
    ::= { dfl2560SmtpAlgDnsBlEntry 3 }

dfl2560SmtpAlgDnsBlMatched OBJECT-TYPE
    SYNTAX      Gauge32
    MAX-ACCESS  read-only
    STATUS      current
    DESCRIPTION 
  "Total sessions that matched SMTP ALG DNS black list of corresponding index"
    ::= { dfl2560SmtpAlgDnsBlEntry 4 }

dfl2560SmtpAlgDnsBlFailChecks OBJECT-TYPE
    SYNTAX      Gauge32
    MAX-ACCESS  read-only
    STATUS      current
    DESCRIPTION 
  "Total failed checks for the SMTP ALG DNS black list of corresponding index"
    ::= { dfl2560SmtpAlgDnsBlEntry 5 }

dfl2560DHCPRelay OBJECT IDENTIFIER
    ::= { dfl2560OSStats 11 }

dfl2560DHCPRelayCurClients OBJECT-TYPE
    SYNTAX      Gauge32
    MAX-ACCESS  read-only
    STATUS      current
    DESCRIPTION 
        "Total DHCP relay active relayed clients."
    ::= { dfl2560DHCPRelay 1 }

dfl2560DHCPRelayCurTrans OBJECT-TYPE
    SYNTAX      Gauge32
    MAX-ACCESS  read-only
    STATUS      current
    DESCRIPTION 
        "Ongoing DHCP relay transactions."
    ::= { dfl2560DHCPRelay 2 }

dfl2560DHCPRelayRejected OBJECT-TYPE
    SYNTAX      Gauge32
    MAX-ACCESS  read-only
    STATUS      current
    DESCRIPTION 
        "Total DHCP relay packets rejected."
    ::= { dfl2560DHCPRelay 3 }

dfl2560DHCPRelayRuleTable OBJECT-TYPE
    SYNTAX      SEQUENCE OF Dfl2560DHCPRelayRuleEntry
    MAX-ACCESS  not-accessible
    STATUS      current
    DESCRIPTION 
        "Table of DHCP relay rules."
    ::= { dfl2560DHCPRelay 4 }

dfl2560DHCPRelayRuleEntry OBJECT-TYPE
    SYNTAX      Dfl2560DHCPRelayRuleEntry
    MAX-ACCESS  not-accessible
    STATUS      current
    DESCRIPTION 
        "Entry of the table of DHCP relay rules"
    INDEX       { dfl2560DHCPRelayRuleIndex }
    ::= { dfl2560DHCPRelayRuleTable 1 }

Dfl2560DHCPRelayRuleEntry ::= SEQUENCE {
    dfl2560DHCPRelayRuleIndex       Integer32,
    dfl2560DHCPRelayRuleName        DisplayString,
    dfl2560DHCPRelayRuleHits        Gauge32,
    dfl2560DHCPRelayRuleCurClients  Gauge32,
    dfl2560DHCPRelayRuleRejCliPkts  Gauge32,
    dfl2560DHCPRelayRuleRejSrvPkts  Gauge32
}

dfl2560DHCPRelayRuleIndex OBJECT-TYPE
    SYNTAX      Integer32 (1..2147483647)
    MAX-ACCESS  not-accessible
    STATUS      current
    DESCRIPTION 
        "Index of the table of DHCP relay rules."
    ::= { dfl2560DHCPRelayRuleEntry 1 }

dfl2560DHCPRelayRuleName OBJECT-TYPE
    SYNTAX      DisplayString
    MAX-ACCESS  read-only
    STATUS      current
    DESCRIPTION 
        "Display name of a DHCP relay rule"
    ::= { dfl2560DHCPRelayRuleEntry 2 }

dfl2560DHCPRelayRuleHits OBJECT-TYPE
    SYNTAX      Gauge32
    MAX-ACCESS  read-only
    STATUS      current
    DESCRIPTION 
        "Number of the times the  DHCP relay rule with corresponding index was 
         used."
    ::= { dfl2560DHCPRelayRuleEntry 3 }

dfl2560DHCPRelayRuleCurClients OBJECT-TYPE
    SYNTAX      Gauge32
    MAX-ACCESS  read-only
    STATUS      current
    DESCRIPTION 
        "Number of ctive relayed clients by the DHCP relay rule with corresponding index."
    ::= { dfl2560DHCPRelayRuleEntry 4 }

dfl2560DHCPRelayRuleRejCliPkts OBJECT-TYPE
    SYNTAX      Gauge32
    MAX-ACCESS  read-only
    STATUS      current
    DESCRIPTION 
        "Number of client packets rejected by a rule."
    ::= { dfl2560DHCPRelayRuleEntry 5 }

dfl2560DHCPRelayRuleRejSrvPkts OBJECT-TYPE
    SYNTAX      Gauge32
    MAX-ACCESS  read-only
    STATUS      current
    DESCRIPTION 
        "Number of DHCP server packets rejected by the DHCP relay rule 
         with the corresponding index."
    ::= { dfl2560DHCPRelayRuleEntry 6 }

dfl2560HA OBJECT IDENTIFIER
    ::= { dfl2560OSStats 12 }

dfl2560HASyncSendQueueLength OBJECT-TYPE
    SYNTAX      Gauge32
    MAX-ACCESS  read-only
    STATUS      current
    DESCRIPTION 
        "Size of the queue used for the High Availability sync interface."
    ::= { dfl2560HA 1 }

dfl2560HASyncSendQueueUsagePkt OBJECT-TYPE
    SYNTAX      Gauge32
    MAX-ACCESS  read-only
    STATUS      current
    DESCRIPTION 
        "High Availability Sync interface queue usage in number of packets."
    ::= { dfl2560HA 2 }

dfl2560HASyncSendQueueUsageOct OBJECT-TYPE
    SYNTAX      Gauge32
    MAX-ACCESS  read-only
    STATUS      current
    DESCRIPTION 
        "High Availability Sync interface queue usage in number of octects."
    ::= { dfl2560HA 3 }

dfl2560HASyncSentPackets OBJECT-TYPE
    SYNTAX      Counter32
    MAX-ACCESS  read-only
    STATUS      current
    DESCRIPTION 
        "Number High Availability packets sent on Sync."
    ::= { dfl2560HA 4 }

dfl2560HASyncSendResentPackets OBJECT-TYPE
    SYNTAX      Counter32
    MAX-ACCESS  read-only
    STATUS      current
    DESCRIPTION 
        "Number of High Availability packets resent on Sync."
    ::= { dfl2560HA 5 }

dfl2560StatsConformance OBJECT IDENTIFIER
    ::= { dfl2560MibConfs 1 }

dfl2560StatsRegGroups OBJECT IDENTIFIER
    ::= { dfl2560MibObjectGroups 1 }

dfl2560SystemObjectGroup OBJECT-GROUP
    OBJECTS     { dfl2560SysCpuLoad, 
                  dfl2560SysForwardedBits, 
                  dfl2560SysForwardedPackets, 
                  dfl2560SysBuffUse, 
                  dfl2560SysConns, 
                  dfl2560HWSensorName, 
                  dfl2560HWSensorValue, 
                  dfl2560HWSensorUnit, 
                  dfl2560SysMemUsage, 
                  dfl2560SysTimerUsage, 
                  dfl2560SysConnOPS, 
                  dfl2560SysConnCPS,
                  dfl2560SysHCForwardedBits }
    STATUS      current
    DESCRIPTION 
        "System statistics Group"
    ::= { dfl2560StatsRegGroups 1 }

dfl2560IPsecObjectGroup OBJECT-GROUP
    OBJECTS     { dfl2560IPsecPhaseOneActive, 
                  dfl2560IPsecPhaseOneAggrModeDone, 
                  dfl2560IPsecQuickModeActive, 
                  dfl2560IPsecPhaseOneDone, 
                  dfl2560IPsecPhaseOneFailed, 
                  dfl2560IPsecPhaseOneRekeyed, 
                  dfl2560IPsecQuickModeDone, 
                  dfl2560IPsecQuickModeFailed, 
                  dfl2560IPsecInfoDone, 
                  dfl2560IPsecInfoFailed, 
                  dfl2560IPsecInOctetsComp, 
                  dfl2560IPsecInOctetsUncomp, 
                  dfl2560IPsecOutOctetsComp, 
                  dfl2560IPsecOutOctetsUncomp, 
                  dfl2560IPsecForwardedOctetsComp, 
                  dfl2560IPsecForwardedOctetsUcomp, 
                  dfl2560IPsecInPackets, 
                  dfl2560IPsecOutPackets, 
                  dfl2560IPsecForwardedPackets, 
                  dfl2560IPsecActiveTransforms, 
                  dfl2560IPsecTotalTransforms, 
                  dfl2560IPsecOutOfTransforms, 
                  dfl2560IPsecTotalRekeys }
    STATUS      current
    DESCRIPTION 
        "IPsec Group"
    ::= { dfl2560StatsRegGroups 2 }

dfl2560StateCountersGroup OBJECT-GROUP
    OBJECTS     { dfl2560SysPscTcpSyn, 
                  dfl2560SysPscTcpOpen, 
                  dfl2560SysPscTcpFin, 
                  dfl2560SysPscUdp, 
                  dfl2560SysPscIcmp, 
                  dfl2560SysPscOther }
    STATUS      current
    DESCRIPTION 
        "Per state counters"
    ::= { dfl2560StatsRegGroups 3 }

dfl2560IPPoolGroup OBJECT-GROUP
    OBJECTS     { dfl2560IPPoolsNumber, 
                  dfl2560IPPoolName, 
                  dfl2560IPPoolPrepare, 
                  dfl2560IPPoolFree, 
                  dfl2560IPPoolMisses, 
                  dfl2560IPPoolClientFails, 
                  dfl2560IPPoolUsed }
    STATUS      current
    DESCRIPTION 
        "IP pool entry objects group"
    ::= { dfl2560StatsRegGroups 4 }

dfl2560DHCPServerGroup OBJECT-GROUP
    OBJECTS     { dfl2560DHCPTotalRejected, 
                  dfl2560DHCPRuleName, 
                  dfl2560DHCPRuleUsage, 
                  dfl2560DHCPRuleUsagePercent, 
                  dfl2560DHCPActiveClients, 
                  dfl2560DHCPActiveClientsPercent, 
                  dfl2560DHCPRejectedRequests, 
                  dfl2560DHCPTotalLeases }
    STATUS      current
    DESCRIPTION 
        "DHCP server rules objects."
    ::= { dfl2560StatsRegGroups 5 }

dfl2560RuleUseGroup OBJECT-GROUP
    OBJECTS     { dfl2560RuleName, dfl2560RuleUse }
    STATUS      current
    DESCRIPTION 
        "Rule use objects."
    ::= { dfl2560StatsRegGroups 6 }

dfl2560UserAuthGroup OBJECT-GROUP
    OBJECTS     { dfl2560UserAuthHTTPUsers, dfl2560UserAuthXAUTHUsers, 
                  dfl2560UserAuthHTTPSUsers, dfl2560UserAuthPPPUsers, 
                  dfl2560UserAuthEAPUsers, dfl2560UserAuthRuleName, 
                  dfl2560UserAuthRuleUse }
    STATUS      current
    DESCRIPTION 
        "User auth objects."
    ::= { dfl2560StatsRegGroups 7 }

dfl2560IfStatsGroup OBJECT-GROUP
    OBJECTS     { dfl2560IfName, 
                  dfl2560IfFragsIn, 
                  dfl2560IfFragReassOk, 
                  dfl2560IfFragReassFail, 
                  dfl2560IfPktsInCnt, 
                  dfl2560IfPktsOutCnt, 
                  dfl2560IfBitsInCnt, 
                  dfl2560IfBitsOutCnt, 
                  dfl2560IfPktsTotCnt, 
                  dfl2560IfBitsTotCnt, 
                  dfl2560IfHCPktsInCnt, 
                  dfl2560IfHCPktsOutCnt, 
                  dfl2560IfHCBitsInCnt, 
                  dfl2560IfHCBitsOutCnt, 
                  dfl2560IfHCPktsTotCnt, 
                  dfl2560IfHCBitsTotCnt,
                  dfl2560IfRxRingFifoErrors, 
                  dfl2560IfRxDespools, 
                  dfl2560IfRxAvgUse, 
                  dfl2560IfRxRingSaturation, 
                  dfl2560RxRingFlooded, 
                  dfl2560IfTxDespools, 
                  dfl2560IfTxAvgUse, 
                  dfl2560IfTxRingSaturation, 
                  dfl2560RxTingFlooded }
    STATUS      current
    DESCRIPTION 
        "DFL-2560 interface statistics group."
    ::= { dfl2560StatsRegGroups 8 }

dfl2560LinkMonitorGroup OBJECT-GROUP
    OBJECTS     { dfl2560LinkMonGrp, 
                  dfl2560LinkMonGrpName, 
                  dfl2560LinkMonGrpHostsUp, 
                  dfl2560LinkMonHostId, 
                  dfl2560LinkMonHostShortTermLoss, 
                  dfl2560LinkMonHostPacketsLost }
    STATUS      current
    DESCRIPTION 
        "DFL-2560 link monitor statistics group"
    ::= { dfl2560StatsRegGroups 9 }

dfl2560PipesObjectGroup OBJECT-GROUP
    OBJECTS     { dfl2560PipeUsers, 
                  dfl2560PipeName, 
                  dfl2560PipeMinPrec, 
                  dfl2560PipeMaxPrec, 
                  dfl2560PipeDefPrec, 
                  dfl2560PipeNumPrec, 
                  dfl2560PipeNumUsers, 
                  dfl2560PipeCurrentBps, 
                  dfl2560PipeCurrentPps, 
                  dfl2560PipeDelayedPackets, 
                  dfl2560PipeDropedPackets, 
                  dfl2560PipePrec, 
                  dfl2560PipePrecBps, 
                  dfl2560PipePrecTotalPps, 
                  dfl2560PipePrecReservedBps, 
                  dfl2560PipePrecDynLimBps, 
                  dfl2560PipePrecDynUsrLimBps, 
                  dfl2560PipePrecDelayedPackets, 
                  dfl2560PipePrecDropedPackets }
    STATUS      current
    DESCRIPTION 
        "DFL-2560 pipes statistics group"
    ::= { dfl2560StatsRegGroups 10 }

dfl2560DHCPRelayObjectGroup OBJECT-GROUP
    OBJECTS     { dfl2560DHCPRelayCurClients, 
                  dfl2560DHCPRelayCurTrans, 
                  dfl2560DHCPRelayRejected, 
                  dfl2560DHCPRelayRuleName, 
                  dfl2560DHCPRelayRuleHits, 
                  dfl2560DHCPRelayRuleCurClients, 
                  dfl2560DHCPRelayRuleRejCliPkts, 
                  dfl2560DHCPRelayRuleRejSrvPkts }
    STATUS      current
    DESCRIPTION 
        "DFL-2560 DHCP relay statistics group"
    ::= { dfl2560StatsRegGroups 12 }

dfl2560AlgGroup OBJECT-GROUP
    OBJECTS     { dfl2560AlgSessions, 
                  dfl2560AlgConnections, 
                  dfl2560AlgTCPStreams, 
                  dfl2560HttpAlgName, 
                  dfl2560HttpAlgTotalRequested, 
                  dfl2560HttpAlgTotalAllowed, 
                  dfl2560HttpAlgTotalBlocked, 
                  dfl2560HttpAlgCntFltName, 
                  dfl2560HttpAlgCntFltRequests, 
                  dfl2560HttpAlgCntFltAllowed, 
                  dfl2560HttpAlgCntFltBlocked }
    STATUS      current
    DESCRIPTION 
        "DFL-2560 HTTP ALG statistics group"
    ::= { dfl2560StatsRegGroups 13 }

dfl2560HAGroup OBJECT-GROUP
    OBJECTS     { dfl2560HASyncSendQueueLength, 
                  dfl2560HASyncSendQueueUsagePkt, 
                  dfl2560HASyncSendQueueUsageOct, 
                  dfl2560HASyncSentPackets, 
                  dfl2560HASyncSendResentPackets }
    STATUS      current
    DESCRIPTION 
        "DFL-2560 HA statistics group"
    ::= { dfl2560StatsRegGroups 14 }

dfl2560IfVlanGroup OBJECT-GROUP
    OBJECTS     { dfl2560IfVlanUntaggedInPkts, 
                  dfl2560IfVlanUntaggedOutPkts, 
                  dfl2560IfVlanUntaggedTotPkts, 
                  dfl2560IfVlanUntaggedInOctets, 
                  dfl2560IfVlanUntaggedOutOctets, 
                  dfl2560IfVlanUntaggedTotOctets }
    STATUS      current
    DESCRIPTION 
        "DFL-2560 VLAN statistics group"
    ::= { dfl2560StatsRegGroups 15 }


dfl2560SmtpAlgGroup OBJECT-GROUP 
    OBJECTS { dfl2560SmtpAlgName,
              dfl2560SmtpAlgTotCheckedSes,
              dfl2560SmtpAlgTotSpamSes,
              dfl2560SmtpAlgTotDroppedSes,
              dfl2560SmtpAlgDnsBlName,    
              dfl2560SmtpAlgDnsBlChecked,     
              dfl2560SmtpAlgDnsBlMatched,  
              dfl2560SmtpAlgDnsBlFailChecks }
   STATUS current
   DESCRIPTION
       "Clavister SMTP ALG objects group"
   ::= { dfl2560StatsRegGroups 16 }
   
dfl2560SysTCPGroup OBJECT-GROUP 
    OBJECTS { dfl2560SysTCPRecvSmall,
              dfl2560SysTCPRecvLarge,
              dfl2560SysTCPSendSmall,
              dfl2560SysTCPSendLarge }
    STATUS current
    DESCRIPTION
      "DFL-2560 TCP buffer usage group"
    ::= { dfl2560StatsRegGroups 17 }



dfl2560StatsCompliance MODULE-COMPLIANCE
    STATUS      current
    DESCRIPTION 
        "Module Compliance"

    MODULE      -- this module

        MANDATORY-GROUPS        
                { dfl2560SystemObjectGroup, 
                  dfl2560IPsecObjectGroup, 
                  dfl2560StateCountersGroup, 
                  dfl2560IPPoolGroup, 
                  dfl2560DHCPServerGroup, 
                  dfl2560RuleUseGroup, 
                  dfl2560UserAuthGroup, 
                  dfl2560IfStatsGroup, 
                  dfl2560LinkMonitorGroup, 
                  dfl2560PipesObjectGroup, 
                  dfl2560DHCPRelayObjectGroup, 
                  dfl2560AlgGroup, 
                  dfl2560HAGroup, 
                  dfl2560IfVlanGroup, 
                  dfl2560SmtpAlgGroup, 
                  dfl2560SysTCPGroup }

    ::= { dfl2560StatsConformance 1 }

END -- end of module DFL2560-MIB.
