ARISTA-TEST-MIB DEFINITIONS ::= BEGIN

IMPORTS
   MODULE-COMPLIANCE, 
   OBJECT-GROUP, NOTIFICATION-GROUP      FROM SNMPv2-CONF
   MODULE-IDENTITY, OBJECT-TYPE, 
   NOTIFICATION-TYPE                     FROM SNMPv2-SMI        -- [RFC2578]
   ZeroBasedCounter32                    FROM RMON2-MIB
   DisplayString                         FROM SNMPv2-TC         -- [RFC2579]
   aristaMibs                            FROM ARISTA-SMI-MIB;

aristaTestMIB MODULE-IDENTITY
   LAST-UPDATED "201103311300Z"       -- 31 March 2011
   ORGANIZATION "Arista Networks, Inc."
   CONTACT-INFO
      "Arista Networks, Inc.

       Postal: 5470 Great America Parkway
               Santa Clara, CA 9505

       Tel: +1 408 547-5500

       E-mail: snmp@aristanetworks.com"
   DESCRIPTION  "Arista Test MIB."
      REVISION           "201103311300Z"
      DESCRIPTION
         "Updated postal address and telephone"
      REVISION           "201012010000Z"
      DESCRIPTION
         "Initial revision."
   ::= { aristaMibs 3 }

aristaTestNotifications         OBJECT IDENTIFIER ::= { aristaTestMIB 0 }
aristaTestObjects               OBJECT IDENTIFIER ::= { aristaTestMIB 1 }
aristaTestConformance           OBJECT IDENTIFIER ::= { aristaTestMIB 2 }

--
-- ARISTA TEST MIB Objects
-- 

aristaTestNotificationCounter OBJECT-TYPE
   SYNTAX      ZeroBasedCounter32
   MAX-ACCESS  read-only
   STATUS      current
   DESCRIPTION
      "Notifications counter - the number of times this notification has been sent."
   ::= { aristaTestObjects 1 }

aristaTestNotificationComment OBJECT-TYPE
   SYNTAX      DisplayString (SIZE(0..255))
   MAX-ACCESS  read-only
   STATUS      current
   DESCRIPTION
      "Notification comment specified by the user executing the test command."
   ::= { aristaTestObjects 2 }

--
-- ARISTA TEST MIB Notifications
-- 

aristaTestNotificationPrefix OBJECT IDENTIFIER ::= { aristaTestNotifications 0 }

aristaTestNotification NOTIFICATION-TYPE
   OBJECTS { 
      aristaTestNotificationCounter,
      aristaTestNotificationComment
   }
   STATUS             current
   DESCRIPTION
      "Arista test notification. This notification is triggered whenever the user executes the -test snmp notification- Cli command."
  ::= { aristaTestNotificationPrefix 1 }

--
-- ARISTA TEST MIB Conformance
-- 

aristaTestCompliances OBJECT IDENTIFIER ::= { aristaTestConformance 1 }
aristaTestGroups      OBJECT IDENTIFIER ::= { aristaTestConformance 2 }

aristaTestCompliance MODULE-COMPLIANCE
   STATUS  current
   DESCRIPTION
      "The compliance statement for SNMP entities which implement
       the ARISTA TEST MIB."
   MODULE  -- this module
      MANDATORY-GROUPS { aristaTestObjectsGroup, 
                         aristaTestNotificationsGroup
       }
   ::= { aristaTestCompliances 1 }

aristaTestObjectsGroup    OBJECT-GROUP
   OBJECTS {
      aristaTestNotificationCounter,
      aristaTestNotificationComment    
   }
   STATUS  current
   DESCRIPTION
      "The collection of objects in the ARISTA TEST MIB."
   ::= { aristaTestGroups 1 }

aristaTestNotificationsGroup  NOTIFICATION-GROUP
   NOTIFICATIONS {
      aristaTestNotification
   }
   STATUS  current
   DESCRIPTION
      "The collection of notifications in the ARISTA TEST MIB."
    ::= { aristaTestGroups 2 }

END
