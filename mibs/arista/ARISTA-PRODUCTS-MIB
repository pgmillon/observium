-- ARISTA-PRODUCTS-MIB: Arista Networks product object identifier assignments
-- Copyright (c) 2008, 2009, 2010, 2011, 2012, 2013, 2014, 2015 Arista Networks, Inc.  All rights reserved.

ARISTA-PRODUCTS-MIB DEFINITIONS ::= BEGIN

IMPORTS
    MODULE-IDENTITY
        FROM SNMPv2-SMI
    aristaModules,
    aristaProducts
        FROM ARISTA-SMI-MIB;

aristaProductsMIB MODULE-IDENTITY
    LAST-UPDATED    "201504100000Z"
    ORGANIZATION "Arista Networks, Inc."
    CONTACT-INFO
        "Arista Networks, Inc.

         Postal: 5453 Great America Parkway
                 Santa Clara, CA 95054

         Tel: +1 408 547-5500

         E-mail: snmp@arista.com"
    DESCRIPTION
        "This module defines the object identifiers returned as values for
         sysObjectID or entPhysicalVendorType for Arista Networks hardware."
        REVISION      "201504100000Z"
        DESCRIPTION
                "Revised to include DCS-7260QX-64 and DCS-7260QX-64-SSD"
        REVISION      "201503190000Z"
        DESCRIPTION
                "Revised to include DCS-7504N"
        REVISION      "201412020000Z"
        DESCRIPTION
                "Revised to include DCS-7250QX-64-M"
        REVISION      "201408150000Z"
        DESCRIPTION
                "Updated postal and e-mail addresses"
        REVISION      "201407310930Z"
        DESCRIPTION
                "Revised to include DCS-7316."
        REVISION      "201407180900Z"
        DESCRIPTION
                "Revised to include DCS-7010T-48-DC"
        REVISION      "201405191600Z"
        DESCRIPTION
                "Revised to include DCS-7050TX-128-SSD"
        REVISION      "201404081600Z"
        DESCRIPTION
                "Revised to include DCS-7050TX-128"
        REVISION      "201404041609Z"
        DESCRIPTION
                "Revised to include DCS-7050TX-96-SSD"
        REVISION      "201404041608Z"
        DESCRIPTION
                "Revised to include DCS-7050TX-96"
        REVISION      "201404021200Z"
        DESCRIPTION
                "Revised to include DCS-7050TX-64-SSD and DCS-7050TX-48-SSD"
        REVISION      "201404021100Z"
        DESCRIPTION
                "Revised to include DCS-7050TX-64 and DCS-7050TX-48"
        REVISION      "201403111600Z"
        DESCRIPTION
                "Revised to include DCS-7050SX-64-SSD"
        REVISION      "201401021600Z"
        DESCRIPTION
                "Revised to include DCS-7050QX-32S-SSD"
        REVISION      "201401010900Z"
        DESCRIPTION
                "Revised to include DCS-7010T-48"
        REVISION      "201311240930Z"
        DESCRIPTION
                "Revised to include DCS-7050SX-72-SSD"
        REVISION      "201311240900Z"
        DESCRIPTION
                "Revised to include DCS-7050SX-72"
        REVISION      "201311240830Z"
        DESCRIPTION
                "Revised to include DCS-7050SX-96-SSD"
        REVISION      "201311240800Z"
        DESCRIPTION
                "Revised to include DCS-7050SX-96"
        REVISION      "201311231200Z"
        DESCRIPTION
                "Revised to include DCS-7280SE-72"
        REVISION      "201311231100Z"
        DESCRIPTION
                "Revised to include DCS-7280SE-64"
        REVISION      "201311190800Z"
        DESCRIPTION
                "Revised to include DCS-7050QX-32-SSD"
        REVISION      "201311130800Z"
        DESCRIPTION
                "Revised to include DCS-7050SX-64"
        REVISION      "201311010800Z"
        DESCRIPTION
                "Revised to include DCS-7050QX-32S"
        REVISION      "201310020800Z"
        DESCRIPTION
                "Revised to include DCS-7250QX-64, DCS-7250QX-64-SSD"
        REVISION      "201309261120Z"
        DESCRIPTION
                "Revised to include DCS-7304 and DCS-7308."
        REVISION      "201306080800Z"
        DESCRIPTION
                "Revised to include DCS-7050SX-128-SSD"
        REVISION      "201301260800Z"
        DESCRIPTION
                "Revised to include DCS-7050QX-32-CL-SSD"
        REVISION      "201212121212Z"
        DESCRIPTION
                "Revised to include DCS-7150S-64-CL, DCS-7150S-64-CL-SSD, DCS-7150S-52-CL and DCS-7150S-52-CL-SSD"
        REVISION      "201211280800Z"
        DESCRIPTION
                "Revised to include DCS-7050SX-128"
        REVISION      "201209030800Z"
        DESCRIPTION
                "Revised to include DCS-7050QX-32"
        REVISION      "201208310800Z"
        DESCRIPTION
                "Revised to include DCS-7150S-24, DCS-7150S-24-CL and DCS-7150S-24-CL-SSD"
        REVISION      "201204170800Z"
        DESCRIPTION
                "Revised to include DCS-7124FX-CL"
        REVISION      "201204030800Z"
        DESCRIPTION
                "Revised to include DCS-7050Q-16-SSD"
        REVISION      "201203090800Z"
        DESCRIPTION
                "Revised to include DCS-7124FX"
        REVISION      "201202200800Z"
        DESCRIPTION
                "Revised to include DCS-7050T-36"
        REVISION      "201202010800Z"
        DESCRIPTION
                "Revised to include DCS-7050T-52-SSD, and DCS-7050T-64-SSD"
        REVISION      "201109010800Z"
        DESCRIPTION
                "Revised to include DCS-7050Q-16"
        REVISION      "201108290800Z"
        DESCRIPTION
                "Revised to include DCS-7050S-52-SSD"
        REVISION      "201108040800Z"
        DESCRIPTION
                "Revised to include DCS-7050S-64-SSD"
        REVISION      "201107161400Z"
        DESCRIPTION
                "Revised to include DCS-7050T-52, and DCS-7050T-64"
        REVISION      "201106221800Z"
        DESCRIPTION
                "Revised to include DCS-7124SX-SSD"
        REVISION      "201103311300Z"
        DESCRIPTION
                "Updated postal address and telephone."
        REVISION      "201102240800Z"
        DESCRIPTION
                "Revised to include DCS-7050S-52 and DCS-7050S-64"
        REVISION      "201010241600Z"
        DESCRIPTION
                "Revised to include DCS-7048T-A"
        REVISION      "201009172040Z"
        DESCRIPTION
                "Revised to include DCS-7124SX."
        REVISION      "201004050942Z"
        DESCRIPTION
                "Revised to include DCS-7504."
        REVISION      "201004050941Z"
        DESCRIPTION
                "Revised to include DCS-7508."
        REVISION      "200906081558Z"
        DESCRIPTION
                "Revised to include DCS-7048T-4S."
        REVISION      "200904171505Z"
        DESCRIPTION
                "Revised to include DCS-7140T-8S and  DCS-7120T-4S."
        REVISION      "200809101415Z"
        DESCRIPTION
                "Revised to include DCS-7148S."
        REVISION      "200803031230Z"
        DESCRIPTION
                "Initial version."
    ::= { aristaModules 1 }
-- DCS-7124S 1RU 24-port SFP+ 10Gb Ethernet Switch
aristaDCS7124S OBJECT IDENTIFIER ::= { aristaProducts 3011 7124 3282 }
-- DCS-7148SX 1RU 48-port SFP+ 10Gb Ethernet Switch
aristaDCS7148SX OBJECT IDENTIFIER ::= { aristaProducts 3011 7148 3741 }
-- DCS-7148S 1RU 48-port SFP+ 10Gb Ethernet Switch
aristaDCS7148S OBJECT IDENTIFIER ::= { aristaProducts 3011 7148 3282 }
-- DCS-7120T-4S 1RU 20-port 10GBASE-T + 4 port SFP+ Ethernet Switch
aristaDCS7120T4S OBJECT IDENTIFIER ::= { aristaProducts 3011 7120 427 4 3282 }
-- DCS-7140T-8S 1RU 40-port 10GBASE-T + 8 port SFP+ Ethernet Switch
aristaDCS7140T8S OBJECT IDENTIFIER ::= { aristaProducts 3011 7140 427 8 3282 }
-- DCS-7048T-4S 1RU 48-port 1000BASE-T + 4 port SFP+ Ethernet Switch
aristaDCS7048T4S OBJECT IDENTIFIER ::= { aristaProducts 3011 7048 427 4 3282 }
-- DCS-7508 Switch Chassis. 2 Supervisor slots, 8 Linecard slots, 6 Fabric Module slots.
aristaDCS7508 OBJECT IDENTIFIER ::= { aristaProducts 3011 7508 }
-- DCS-7504 Switch Chassis. 2 Supervisor slots, 4 Linecard slots, 6 Fabric Module slots.
aristaDCS7504 OBJECT IDENTIFIER ::= { aristaProducts 3011 7504 }
-- DCS-7124SX 1RU 24-port SFP+ 10Gb Ethernet Switch
aristaDCS7124SX OBJECT IDENTIFIER ::= { aristaProducts 3011 7124 3741 }
-- DCS-7048T-A 1RU 48-port 1000BASE-T + 4 port SFP+ Ethernet Switch
aristaDCS7048TA OBJECT IDENTIFIER ::= { aristaProducts 3011 7048 427 3648 }
-- DCS-7050S-52 1RU 52-port SFP+ 10Gb Ethernet Switch
aristaDCS7050S52 OBJECT IDENTIFIER ::= { aristaProducts 3011 7050 3282 52 }
-- DCS-7050S-64 1RU 48-port SFP+ + 4-port QSFP+ Ethernet Switch
aristaDCS7050S64 OBJECT IDENTIFIER ::= { aristaProducts 3011 7050 3282 64 }
-- DCS-7124SX-SSD 1RU 24-port SFP+ 10Gb Ethernet Switch with SSD disk
aristaDCS7124SXSSD OBJECT IDENTIFIER ::= { aristaProducts 3011 7124 3741 761 }
-- DCS-7050T-52 1RU 48-port 10GBASE-T + 4 port SFP+ Ethernet Switch
aristaDCS7050T52 OBJECT IDENTIFIER ::= { aristaProducts 3011 7050 427 52 }
-- DCS-7050T-64 1RU 48-port 10GBASE-T + 4-port QSFP+ Ethernet Switch
aristaDCS7050T64 OBJECT IDENTIFIER ::= { aristaProducts 3011 7050 427 64 }
-- DCS-7050S-64-SSD 1RU 48-port SFP+ + 4-port QSFP+ Ethernet Switch with SSD disk
aristaDCS7050S64SSD OBJECT IDENTIFIER ::= { aristaProducts 3011 7050 3282 64 761 }
-- DCS-7050S-52-SSD 1RU 48-port SFP+ + 4-port SFP+ Ethernet Switch with SSD disk
aristaDCS7050S52SSD OBJECT IDENTIFIER ::= { aristaProducts 3011 7050 3282 52 761 }
-- DCS-7050Q-16 1RU 16-port QSFP+ + 4-port SFP+ Ethernet Switch
aristaDCS7050Q16 OBJECT IDENTIFIER ::= { aristaProducts 3011 7050 2512 16 }
-- DCS-7050T-52-SSD 1RU 48-port 10GBASE-T + 4 port SFP+ Ethernet Switch with SSD disk
aristaDCS7050T52SSD OBJECT IDENTIFIER ::= { aristaProducts 3011 7050 427 52 761 }
-- DCS-7050T-64-SSD 1RU 48-port 10GBASE-T + 4-port QSFP+ Ethernet Switch with SSD disk
aristaDCS7050T64SSD OBJECT IDENTIFIER ::= { aristaProducts 3011 7050 427 64 761 }
-- DCS-7050T-36 1RU 32-port 10GBASE-T + 4-port SFP+ Ethernet Switch
aristaDCS7050T36 OBJECT IDENTIFIER ::= { aristaProducts 3011 7050 427 36 }
-- DCS-7124FX 1RU 24-port SFP+ 10Gb Ethernet Switch with SSD disk and 160Gb Application Engine FPGA
aristaDCS7124FX OBJECT IDENTIFIER ::= { aristaProducts 3011 7124 2312 }
-- DCS-7050Q-16-SSD 1RU 16-port QSFP+ + 4-port SFP+ Ethernet Switch with SSD disk
aristaDCS7050Q16SSD OBJECT IDENTIFIER ::= { aristaProducts 3011 7050 2512 16 761 }
-- DCS-7124FX-CL 1RU 24-port SFP+ 10Gb Ethernet Switch with SSD disk, 160Gb Application Engine FPGA, and Clock module
aristaDCS7124FXCL OBJECT IDENTIFIER ::= { aristaProducts 3011 7124 2312 2745 }
-- DCS-7150S-24 1RU 24-port SFP+ Ethernet Switch
aristaDCS7150S24 OBJECT IDENTIFIER ::= { aristaProducts 3011 7150 3282 24 }
-- DCS-7150S-24-CL 1RU 24-port SFP+ Ethernet Switch with Clock module
aristaDCS7150S24CL OBJECT IDENTIFIER ::= { aristaProducts 3011 7150 3282 24 2745 }
-- DCS-7150S-24-CL-SSD 1RU 24-port SFP+ Ethernet Switch with Clock module and SSD disk
aristaDCS7150S24CLSSD OBJECT IDENTIFIER ::= { aristaProducts 3011 7150 3282 24 2745 761 }
-- DCS-7050QX-32 1RU 32-port QSFP+ Ethernet Switch
aristaDCS7050QX32 OBJECT IDENTIFIER ::= { aristaProducts 3011 7050 3095 32 }
-- DCS-7050SX-128 2RU 96-port SFP+ + 8-port QSFP+ Ethernet Switch
aristaDCS7050SX128 OBJECT IDENTIFIER ::= { aristaProducts 3011 7050 3741 128 }
-- DCS-7150S-52-CL 1RU 52-port SFP+ Ethernet Switch with Clock module
aristaDCS7150S52CL OBJECT IDENTIFIER ::= { aristaProducts 3011 7150 3282 52 2745 }
-- DCS-7150S-52-CL-SSD 1RU 52-port SFP+ Ethernet Switch with Clock module and SSD disk
aristaDCS7150S52CLSSD OBJECT IDENTIFIER ::= { aristaProducts 3011 7150 3282 52 2745 761 }
-- DCS-7150S-64-CL 1RU 48-port SFP+ + 4-port QSFP+ Ethernet Switch with Clock module
aristaDCS7150S64CL OBJECT IDENTIFIER ::= { aristaProducts 3011 7150 3282 64 2745 }
-- DCS-7150S-64-CL-SSD 1RU 48-port SFP+ + 4-port QSFP+ Ethernet Switch with Clock module and SSD disk
aristaDCS7150S64CLSSD OBJECT IDENTIFIER ::= { aristaProducts 3011 7150 3282 64 2745 761 }
-- DCS-7050QX-32-CL-SSD 1RU 32-port QSFP+ Ethernet Switch with Clock module and SSD disk
aristaDCS7050QX32CLSSD OBJECT IDENTIFIER ::= { aristaProducts 3011 7050 3095 32 2745 761 }
-- DCS-7050SX-128-SSD 2RU 96-port SFP+ + 8-port QSFP+ Ethernet Switch with SSD disk
aristaDCS7050SX128SSD OBJECT IDENTIFIER ::= { aristaProducts 3011 7050 3741 128 761 }
-- DCS-7304 Switch Chassis. 2 Supervisor slots, 4 Linecard slots, 4 Fabric Module slots.
aristaDCS7304 OBJECT IDENTIFIER ::= { aristaProducts 3011 7304 }
-- DCS-7308 Switch Chassis. 2 Supervisor slots, 8 Linecard slots, 4 Fabric Module slots.
aristaDCS7308 OBJECT IDENTIFIER ::= { aristaProducts 3011 7308 }
-- DCS-7250QX-64 2RU 64-port QSFP+ Ethernet Switch
aristaDCS7250QX64 OBJECT IDENTIFIER ::= { aristaProducts 3011 7250 3095 64 }
-- DCS-7250QX-64-SSD 2RU 64-port QSFP+ Ethernet Switch with SSD disk
aristaDCS7250QX64SSD OBJECT IDENTIFIER ::= { aristaProducts 3011 7250 3095 64 761 }
-- DCS-7050QX-32S 1RU 32-port QSFP+ + 4-port SFP+ Ethernet Switch
aristaDCS7050QX32S OBJECT IDENTIFIER ::= { aristaProducts 3011 7050 3095 32 3282 }
-- DCS-7050SX-64 1RU 48-port SFP+ + 4-port QSFP+ Ethernet Switch
aristaDCS7050SX64 OBJECT IDENTIFIER ::= { aristaProducts 3011 7050 3741 64 }
-- DCS-7050QX-32-SSD 1RU 32-port QSFP+ Ethernet Switch with SSD disk
aristaDCS7050QX32SSD OBJECT IDENTIFIER ::= { aristaProducts 3011 7050 3095 32 761 }
-- DCS-7280SE-64 1RU 48-port SFP+ + 4-port QSFP+ Ethernet Switch
aristaDCS7280SE64 OBJECT IDENTIFIER ::= { aristaProducts 3011 7280 3714 64 }
-- DCS-7280SE-72 1RU 48-port SFP+ + 2-port 100G Ethernet Switch
aristaDCS7280SE72 OBJECT IDENTIFIER ::= { aristaProducts 3011 7280 3714 72 }
-- DCS-7050SX-96 48x10GbE (SFP+) & 12x40GbE (4xMXP) Ethernet Switch
aristaDCS7050SX96 OBJECT IDENTIFIER ::= { aristaProducts 3011 7050 3741 96 }
-- DCS-7050SX-96-SSD 48x10GbE (SFP+) & 12x40GbE (4xMXP) Ethernet Switch with SSD disk
aristaDCS7050SX96SSD OBJECT IDENTIFIER ::= { aristaProducts 3011 7050 3741 96 761 }
-- DCS-7050SX-72 48x10GbE (SFP+) & 6x40GbE (2xMXP) Ethernet Switch
aristaDCS7050SX72 OBJECT IDENTIFIER ::= { aristaProducts 3011 7050 3741 72 }
-- DCS-7050SX-72-SSD 48x10GbE (SFP+) & 6x40GbE (2xMXP) Ethernet Switch with SSD disk
aristaDCS7050SX72SSD OBJECT IDENTIFIER ::= { aristaProducts 3011 7050 3741 72 761 }
-- DCS-7010T-48 1RU 48-port 1000BASE-T + 4 port SFP+ Ethernet Switch
aristaDCS7010T48 OBJECT IDENTIFIER ::= { aristaProducts 3011 7010 427 48 }
-- DCS-7050QX-32S-SSD 1RU 32-port QSFP+ + 4-port SFP+ Ethernet Switch with SSD disk
aristaDCS7050QX32SSSD OBJECT IDENTIFIER ::= { aristaProducts 3011 7050 3095 32 3282 761 }
-- DCS-7050SX-64-SSD 1RU 48-port SFP+ + 4-port QSFP+ Ethernet Switch with SSD disk
aristaDCS7050SX64SSD OBJECT IDENTIFIER ::= { aristaProducts 3011 7050 3741 64 761 }
-- DCS-7050TX-64 1RU 48-port 10GBASE-T + 4-port QSFP+ Ethernet Switch
aristaDCS7050TX64 OBJECT IDENTIFIER ::= { aristaProducts 3011 7050 1958 64 }
-- DCS-7050TX-48 1RU 32-port 10GBASE-T + 4-port QSFP+ Ethernet Switch
aristaDCS7050TX48 OBJECT IDENTIFIER ::= { aristaProducts 3011 7050 1958 48 }
-- DCS-7050TX-64-SSD 1RU 48-port 10GBASE-T + 4-port QSFP+ Ethernet Switch with SSD disk
aristaDCS7050TX64SSD OBJECT IDENTIFIER ::= { aristaProducts 3011 7050 1958 64 761 }
-- DCS-7050TX-48-SSD 1RU 32-port 10GBASE-T + 4-port QSFP+ Ethernet Switch with SSD disk
aristaDCS7050TX48SSD OBJECT IDENTIFIER ::= { aristaProducts 3011 7050 1958 48 761 }
-- DCS-7050TX-96 1RU 48-port 10GBASE-T + 4-port 100G Ethernet Switch
aristaDCS7050TX96 OBJECT IDENTIFIER ::= { aristaProducts 3011 7050 1958 96 }
-- DCS-7050TX-96-SSD 1RU 48-port 10GBASE-T + 4-port 100G Ethernet Switchwith SSD disk
aristaDCS7050TX96SSD OBJECT IDENTIFIER ::= { aristaProducts 3011 7050 1958 96 761 }
-- DCS-7050TX-128 2RU 96-port 10GBaseT + 8-port QSFP+ Ethernet Switch
aristaDCS7050TX128 OBJECT IDENTIFIER ::= { aristaProducts 3011 7050 1958 128 }
-- DCS-7050TX-128-SSD 2RU 96-port 10GBaseT + 8-port QSFP+ Ethernet Switch with SSD disk
aristaDCS7050TX128SSD OBJECT IDENTIFIER ::= { aristaProducts 3011 7050 1958 128 761 }
-- DCS-7010T-48-DC 1RU 48-port 1000BASE-T + 4 port SFP+ Ethernet Switch with DC Power Supply
aristaDCS7010T48DC OBJECT IDENTIFIER ::= { aristaProducts 3011 7010 427 48 2957 }
-- DCS-7316 Switch Chassis. 2 Supervisor slots, 16 Linecard slots, 4 Fabric Module slots.
aristaDCS7316 OBJECT IDENTIFIER ::= { aristaProducts 3011 7316 }
-- DCS-7250QX-64-M 2RU 64-port QSFP+ Ethernet Switch
aristaDCS7250QX64M OBJECT IDENTIFIER ::= { aristaProducts 3011 7250 3095 64 972 }
-- DCS-7504N Switch Chassis. 2 Supervisor slots, 4 Linecard slots, 6 Fabric Module slots, with AC or DC Power Supply
aristaDCS7504N OBJECT IDENTIFIER ::= { aristaProducts 3011 7504 1359 }
-- DCS-7260QX-64 64x40GbE QSFP+ & 2xSFP+ switch
aristaDCS7260QX64 OBJECT IDENTIFIER ::= { aristaProducts 3011 7260 3095 64 }
-- DCS-7260QX-64-SSD 64x40GbE QSFP+ & 2xSFP+ switch + SSD
aristaDCS7260QX64SSD OBJECT IDENTIFIER ::= { aristaProducts 3011 7260 3095 64 761 }

END
