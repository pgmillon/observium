RBTWS-INFO-RF-DETECT-MIB DEFINITIONS ::= BEGIN

IMPORTS
    MODULE-COMPLIANCE, OBJECT-GROUP
        FROM SNMPv2-CONF
    MODULE-IDENTITY, OBJECT-TYPE, Gauge32
        FROM SNMPv2-SMI
    DisplayString, MacAddress
        FROM SNMPv2-TC
    RbtwsChannelNum, RbtwsRssi
        FROM RBTWS-AP-TC
    RbtwsRFDetectNetworkingMode,
    RbtwsRFDetectClassification,
    RbtwsRFDetectClassificationReason
        FROM RBTWS-RF-DETECT-TC
    rbtwsMibs
        FROM RBTWS-ROOT-MIB;


rbtwsInfoRFDetectMib MODULE-IDENTITY
    LAST-UPDATED "200708301716Z"
    ORGANIZATION "Enterasys Networks"
    CONTACT-INFO
        "www.enterasys.com"
    DESCRIPTION
        "RF Detect MIB.

        Copyright 2007 Enterasys Networks, Inc.
        All rights reserved.
        This SNMP Management Information Base
        Specification (Specification) embodies
        confidential and proprietary intellectual property.

        This Specification is supplied 'AS IS' and Enterasys Networks
        makes no warranty, either express or implied, as to the use,
        operation, condition, or performance of the Specification."

    REVISION "200706270011Z"
    DESCRIPTION "v1.2.0: Added one scalar:
        rbtwsInfoRFDetectCurrentXmtrTableSize
        (for 6.2 release)"

    REVISION "200704180010Z"
    DESCRIPTION "v1.1.0: Added three new columnar objects:
        - rbtwsInfoRFDetectXmtrNetworkingMode,
        - rbtwsInfoRFDetectXmtrClassification,
        - rbtwsInfoRFDetectXmtrClassificationReason
        (for 6.2 release)"

    REVISION "200610110003Z"
    DESCRIPTION "v1.0.3: Initial version, for 6.0 release"

    ::= { rbtwsMibs 9 }


--
-- The RF Detect MIB Tree
--

rbtwsInfoRFDetectObjects      OBJECT IDENTIFIER ::= { rbtwsInfoRFDetectMib 1 }
rbtwsInfoRFDetectDataObjects  OBJECT IDENTIFIER ::= { rbtwsInfoRFDetectObjects 1 }

--
-- Object definitions
--

-- Transmitter table

rbtwsInfoRFDetectXmtrTable OBJECT-TYPE
    SYNTAX      SEQUENCE OF RbtwsInfoRFDetectXmtrEntry
    MAX-ACCESS  not-accessible
    STATUS      current
    DESCRIPTION
        "Transmitter table.
        May contain tens of thousands of entries
        (different Transmitter-Listener-Channel combinations)."
    ::= { rbtwsInfoRFDetectDataObjects 1 }

rbtwsInfoRFDetectXmtrEntry OBJECT-TYPE
    SYNTAX      RbtwsInfoRFDetectXmtrEntry
    MAX-ACCESS  not-accessible
    STATUS      current
    DESCRIPTION
        "Transmitter-Listener-Channel combination."
    INDEX { rbtwsInfoRFDetectXmtrTransmitterMacAddress,
            rbtwsInfoRFDetectXmtrListenerMacAddress,
            rbtwsInfoRFDetectXmtrChannelNum }
    ::= { rbtwsInfoRFDetectXmtrTable 1 }

RbtwsInfoRFDetectXmtrEntry ::= SEQUENCE {
    rbtwsInfoRFDetectXmtrTransmitterMacAddress  MacAddress,
    rbtwsInfoRFDetectXmtrListenerMacAddress     MacAddress,
    rbtwsInfoRFDetectXmtrChannelNum             RbtwsChannelNum,

    rbtwsInfoRFDetectXmtrRssi        RbtwsRssi,
    rbtwsInfoRFDetectXmtrSsid        DisplayString,

    rbtwsInfoRFDetectXmtrNetworkingMode        RbtwsRFDetectNetworkingMode,
    rbtwsInfoRFDetectXmtrClassification        RbtwsRFDetectClassification,
    rbtwsInfoRFDetectXmtrClassificationReason  RbtwsRFDetectClassificationReason
    }

rbtwsInfoRFDetectXmtrTransmitterMacAddress OBJECT-TYPE
    SYNTAX      MacAddress
    MAX-ACCESS  not-accessible
    STATUS      current
    DESCRIPTION
        "The MAC Address of this Transmitter."
    ::= { rbtwsInfoRFDetectXmtrEntry 1 }

rbtwsInfoRFDetectXmtrListenerMacAddress OBJECT-TYPE
    SYNTAX      MacAddress
    MAX-ACCESS  not-accessible
    STATUS      current
    DESCRIPTION
        "The MAC Address of this Listener."
    ::= { rbtwsInfoRFDetectXmtrEntry 2 }

rbtwsInfoRFDetectXmtrChannelNum OBJECT-TYPE
    SYNTAX      RbtwsChannelNum
    MAX-ACCESS  not-accessible
    STATUS      current
    DESCRIPTION
        "Channel Number this transmitter was using
        when this listener detected it."
    ::= { rbtwsInfoRFDetectXmtrEntry 3 }

rbtwsInfoRFDetectXmtrRssi OBJECT-TYPE
    SYNTAX      RbtwsRssi
    MAX-ACCESS  read-only
    STATUS      current
    DESCRIPTION
        "Received Signal Strength Indicator at this listener."
    ::= { rbtwsInfoRFDetectXmtrEntry 4 }

rbtwsInfoRFDetectXmtrSsid OBJECT-TYPE
    SYNTAX      DisplayString (SIZE(0..32))
    MAX-ACCESS  read-only
    STATUS      current
    DESCRIPTION
        "The service/SSID name this transmitter was using.
        Zero-length string when unknown or not applicable."
    ::= { rbtwsInfoRFDetectXmtrEntry 5 }

rbtwsInfoRFDetectXmtrNetworkingMode OBJECT-TYPE
    SYNTAX      RbtwsRFDetectNetworkingMode
    MAX-ACCESS  read-only
    STATUS      current
    DESCRIPTION
        "The way this transmitter is doing wireless networking:
        ad-hoc mode networking or
        infrastructure mode networking."
    ::= { rbtwsInfoRFDetectXmtrEntry 6 }

rbtwsInfoRFDetectXmtrClassification OBJECT-TYPE
    SYNTAX      RbtwsRFDetectClassification
    MAX-ACCESS  read-only
    STATUS      current
    DESCRIPTION
        "The RF classification of this transmitter."
    ::= { rbtwsInfoRFDetectXmtrEntry 7 }

rbtwsInfoRFDetectXmtrClassificationReason OBJECT-TYPE
    SYNTAX      RbtwsRFDetectClassificationReason
    MAX-ACCESS  read-only
    STATUS      current
    DESCRIPTION
        "The reason why this transmitter was classified by
        RF detection the way it is."
    ::= { rbtwsInfoRFDetectXmtrEntry 8 }


-- ==================================
--
-- Scalars
--

rbtwsInfoRFDetectCurrentXmtrTableSize OBJECT-TYPE
    SYNTAX      Gauge32
    MAX-ACCESS  read-only
    STATUS      current
    DESCRIPTION
        "Current number of Transmitter-Listener-Channel
        combinations found and recorded by RF detection."
    ::= { rbtwsInfoRFDetectDataObjects 2 }


-- =========================================================================
--
-- Conformance
--

rbtwsInfoRFDetectConformance  OBJECT IDENTIFIER ::= { rbtwsInfoRFDetectObjects 2 }
rbtwsInfoRFDetectCompliances  OBJECT IDENTIFIER ::= { rbtwsInfoRFDetectConformance 1 }
rbtwsInfoRFDetectGroups       OBJECT IDENTIFIER ::= { rbtwsInfoRFDetectConformance 2 }

-- Compliance

rbtwsInfoRFDetectCompliance MODULE-COMPLIANCE
    STATUS      current
    DESCRIPTION
        "The compliance statement for devices that implement
        the RF Detect MIB."
    MODULE  -- rbtwsInfoRFDetectMib

    MANDATORY-GROUPS { rbtwsInfoRFDetectXmtrGroup }

    GROUP rbtwsInfoRFDetectXmtrClassificationGroup
    DESCRIPTION
        "This group is implemented by systems running 6.2 release or later."

    GROUP rbtwsInfoRFDetectCurrentXmtrTableSizeGroup
    DESCRIPTION
        "This group is implemented by systems running 6.2 release or later."

    ::= { rbtwsInfoRFDetectCompliances 1 }

-- Units of Conformance

rbtwsInfoRFDetectXmtrGroup OBJECT-GROUP
    OBJECTS {
             rbtwsInfoRFDetectXmtrRssi,
             rbtwsInfoRFDetectXmtrSsid
            }
    STATUS      current
    DESCRIPTION
        "Mandatory group of objects implemented to provide
         RF Detect Transmitter info."
    ::= { rbtwsInfoRFDetectGroups 1 }

rbtwsInfoRFDetectXmtrClassificationGroup OBJECT-GROUP
    OBJECTS {
             rbtwsInfoRFDetectXmtrNetworkingMode,
             rbtwsInfoRFDetectXmtrClassification,
             rbtwsInfoRFDetectXmtrClassificationReason
            }
    STATUS      current
    DESCRIPTION
        "Group of objects implemented to provide
         RF Detect Classification info.
         Introduced in 6.2 release."
    ::= { rbtwsInfoRFDetectGroups 2 }

rbtwsInfoRFDetectCurrentXmtrTableSizeGroup OBJECT-GROUP
    OBJECTS { rbtwsInfoRFDetectCurrentXmtrTableSize }
    STATUS      current
    DESCRIPTION
        "Group for one object that provides the current
         number of Transmitter-Listener-Channel
         combinations found and recorded by RF detection.
         Introduced in 6.2 release."
    ::= { rbtwsInfoRFDetectGroups 3 }

END
