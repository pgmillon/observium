RBTWS-REGISTRATION-DEVICES-MIB DEFINITIONS ::= BEGIN

IMPORTS
    MODULE-IDENTITY
        FROM SNMPv2-SMI
    rbtwsRegistration
        FROM RBTWS-ROOT-MIB;

rbtwsRegistrationDevicesMib MODULE-IDENTITY
    LAST-UPDATED "200708220000Z"
    ORGANIZATION "Enterasys Networks"
    CONTACT-INFO
        "www.enterasys.com"
    DESCRIPTION
        "The MIB module for Enterasys Networks wireless device
        OID registrations.

        Copyright 2007 Enterasys Networks, Inc.
        All rights reserved.
        This SNMP Management Information Base
        Specification (Specification) embodies
        confidential and proprietary intellectual property.

        This Specification is supplied 'AS IS' and Enterasys Networks
        makes no warranty, either express or implied, as to the use,
        operation, condition, or performance of the Specification."

    REVISION "200708220000Z"
    DESCRIPTION "v1.0: initial version, published in 6.2 release"

    ::= { rbtwsRegistration 6 }


-- Wireless Switches:

rbtwsWirelessSwitch          OBJECT IDENTIFIER ::= { rbtwsRegistration 1 }

rbtwsSwitch8100      OBJECT IDENTIFIER ::= { rbtwsWirelessSwitch 1 }
rbtwsSwitch8200      OBJECT IDENTIFIER ::= { rbtwsWirelessSwitch 2 }
rbtwsSwitch8400      OBJECT IDENTIFIER ::= { rbtwsWirelessSwitch 3 }
rbtwsSwitch8110      OBJECT IDENTIFIER ::= { rbtwsWirelessSwitch 4 }
rbtwsSwitch8500      OBJECT IDENTIFIER ::= { rbtwsWirelessSwitch 5 }

END
