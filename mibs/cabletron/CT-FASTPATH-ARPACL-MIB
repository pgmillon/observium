CT-FASTPATH-ARPACL-MIB DEFINITIONS ::= BEGIN

-- LVL7 FASTPATH DHCP Server MIB
-- Copyright LVL7 Systems (2002-2008) All rights reserved.

-- This SNMP Management Information Specification
-- embodies LVL7 System's confidential and proprietary
-- intellectual property.  LVL7 Systems retains all title
-- and ownership in the Specification including any revisions.

-- This Specification is supplied "AS IS", LVL7 Systems
-- makes no warranty, either expressed or implied,
-- as to the use, operation, condition, or performance of the
-- Specification.

--  This module provides authoritative definitions for Cabletron's
--  CT-FASTPATH-ARPACL-MIB.
--
--  This module will be extended, as needed.
--
--  Enterasys Networks reserves the right to make changes in
--  specification and other information contained in this document
--  without prior notice.  The reader should consult Enterasys Networks
--  to determine whether any such changes have been made.
--
--  In no event shall Enterasys Networks be liable for any incidental,
--  indirect, special, or consequential damages whatsoever (including
--  but not limited to lost profits) arising out of or related to this
--  document or the information contained in it, even if Enterasys
--  Networks has been advised of, known, or should have known, the
--  possibility of such damages.
--
--  Enterasys grants vendors, end-users, and other interested parties
--  a non-exclusive license to use this Specification in connection
--  with the management of Enterasys and Cabletron products.
--
--  Copyright July 2008 Enterasys Networks, Inc.

IMPORTS
    MODULE-IDENTITY, OBJECT-TYPE, NOTIFICATION-TYPE, IpAddress,
    Integer32, Unsigned32, TimeTicks, Counter32
                                        FROM SNMPv2-SMI
    TEXTUAL-CONVENTION, RowStatus, RowPointer, MacAddress,
    StorageType, TruthValue, DisplayString, PhysAddress
                                        FROM SNMPv2-TC
-- Place this MIB on CTRON experimental branch.
    ctArpAclExpMib                      FROM CTRON-MIB-NAMES;

ctFastPathArpAclMIB MODULE-IDENTITY
    LAST-UPDATED "200807231519Z"  -- Wed Jul 23 15:19 UTC 2008
    ORGANIZATION "Enterasys Networks, Inc."
    CONTACT-INFO
        "Postal:  Enterasys Networks
                  50 Minuteman Rd.
                  Andover, MA 01810-1008
                  USA
         Phone:   +1 978 684 1000
         E-mail:  support@enterasys.com
         WWW:     http://www.enterasys.com"
      DESCRIPTION
          "The Enterasys MIB for FASTPATH ARP ACLs"
      ::= { ctArpAclExpMib 1 }



--**************************************************************************************
--    ctAgentArpAclGroup -> contains MIB objects for ARP ACLs 
--
--*************************************************************************************
    
   ctAgentArpAclGroup                OBJECT IDENTIFIER ::= {ctFastPathArpAclMIB 1 }
    
    
--*********************** ARP ACL Config Table ***********************
    
    ctAgentArpAclTable OBJECT-TYPE
         SYNTAX      SEQUENCE OF CtAgentArpAclEntry
         MAX-ACCESS  not-accessible
         STATUS      current
         DESCRIPTION
                     "A table of the ARP ACL entries"
         ::= { ctAgentArpAclGroup 1 }
    
    ctAgentArpAclEntry OBJECT-TYPE
         SYNTAX      CtAgentArpAclEntry
         MAX-ACCESS  not-accessible
         STATUS      current
         DESCRIPTION
                     "Represents entry for an ARP ACL"
         INDEX       { ctAgentArpAclName }
         ::= { ctAgentArpAclTable 1 }
    
    CtAgentArpAclEntry ::= SEQUENCE {
          ctAgentArpAclName
              DisplayString,
          ctAgentArpAclRowStatus
              RowStatus
          }
    
    ctAgentArpAclName OBJECT-TYPE
         SYNTAX      DisplayString (SIZE(1..31))
         MAX-ACCESS  read-create
         STATUS      current
         DESCRIPTION
                     "Name of the ARP ACL, which must consist of 1 to 31 alphanumeric
                      characters and uniquely identify this ARP ACL. This object must
                      be set to complete a new ARP ACL row instance."
         ::= { ctAgentArpAclEntry 1 }
    
    ctAgentArpAclRowStatus OBJECT-TYPE
         SYNTAX      RowStatus
         MAX-ACCESS  read-create
         STATUS      current
         DESCRIPTION
                     "The status of this conceptual row. Entries can not be deleted until all rows in
                     arpAclRuleTable with corresponding values of arpAclIndex have been deleted.
                     
                     active(1)       - this ACL instance is active
                     createAndGo(4)  - set to this value to create an instance
                     destroy(6)      - set to this value to delete an instance"
         ::= { ctAgentArpAclEntry 2 }
    
    
--*********************** ARP ACL Rule Config Table ***********************
    
    ctAgentArpAclRuleTable OBJECT-TYPE
         SYNTAX      SEQUENCE OF CtAgentArpAclRuleEntry
         MAX-ACCESS  not-accessible
         STATUS      current
         DESCRIPTION
                     "A table of the ARP ACL Rule entries"
         ::= { ctAgentArpAclGroup 2 }
    
    ctAgentArpAclRuleEntry OBJECT-TYPE
         SYNTAX      CtAgentArpAclRuleEntry
         MAX-ACCESS  not-accessible
         STATUS      current
         DESCRIPTION
                     "Represents entry for a set of ARP ACL-match rules"
         INDEX       { ctAgentArpAclName, ctAgentArpAclRuleMatchSenderIpAddr, ctAgentArpAclRuleMatchSenderMacAddr }
         ::= { ctAgentArpAclRuleTable 1 }
    
    CtAgentArpAclRuleEntry ::= SEQUENCE {
          ctAgentArpAclRuleMatchSenderIpAddr
              IpAddress,
          ctAgentArpAclRuleMatchSenderMacAddr
              MacAddress,
          ctAgentArpAclRuleRowStatus
              RowStatus
          }
    
    ctAgentArpAclRuleMatchSenderIpAddr OBJECT-TYPE
         SYNTAX      IpAddress
         MAX-ACCESS  read-create
         STATUS      current
         DESCRIPTION
                     "Sender IP address match value for the ARP ACL."
         ::= { ctAgentArpAclRuleEntry 1 }
    
    ctAgentArpAclRuleMatchSenderMacAddr OBJECT-TYPE
         SYNTAX      MacAddress
         MAX-ACCESS  read-create
         STATUS      current
         DESCRIPTION
                     "Sender MAC address match value for the ARP ACL."
         ::= { ctAgentArpAclRuleEntry 2 }
    
    ctAgentArpAclRuleRowStatus OBJECT-TYPE
         SYNTAX      RowStatus
         MAX-ACCESS  read-create
         STATUS      current
         DESCRIPTION
                     "The status of this conceptual row.

                     active(1)      - this ACL Rule is active
                     createAndGo(4) - set to this value to create an instance
                     destroy(6)     - set to this value to delete an instance"
         ::= { ctAgentArpAclRuleEntry 3 }


END
