SLA-MONITOR-MIB DEFINITIONS ::= BEGIN

IMPORTS
    Unsigned32, MODULE-IDENTITY, OBJECT-TYPE, NOTIFICATION-TYPE
            FROM SNMPv2-SMI
    MODULE-COMPLIANCE, OBJECT-GROUP
            FROM SNMPv2-CONF
    InetAddressType, InetAddress, InetPortNumber
            FROM INET-ADDRESS-MIB
    DisplayString
            FROM RFC1213-MIB                        
    Dscp
            FROM DIFFSERV-DSCP-TC
    policy
            FROM SYNOPTICS-ROOT-MIB;

slaMonitorMib  MODULE-IDENTITY
    LAST-UPDATED "201303050000Z"     -- March 5, 2013
    ORGANIZATION "Avaya Networks, Inc."
    CONTACT-INFO "
                  John Seligson
                  Avaya Networks, Inc.
                  4655 Great America Parkway
                  Santa Clara, CA 95054 USA
                  Phone: +1 408 496 3424
                  Email: jseligso@avaya.com"
    DESCRIPTION
            "An Avaya management module containing data 
             definitions related to the SLA Monitor Agent."

    REVISION "201303050000Z" -- 5 March 2013
    DESCRIPTION "Version 5: Added support for remote NTR and RTP test 
                 initiation and results retrieval using SNMP. Defined
                 attribute to support refusing server test requests."

    REVISION "201301310000Z" -- 31 Jan 2013
    DESCRIPTION "Version 4: Added slaMonitorAgentServerBypass and updated
                 conformance statements for cross-platform use."

    REVISION "201212110000Z" -- 11 Dec 2012
    DESCRIPTION "Version 3: Added slaMonitorAgentCertFileInstallAction,
                                  slaMonitorAgentCertFile for VSP9K/ERS8800"

    REVISION "201209190000Z" -- 19 September 2012
    DESCRIPTION "Version 2: Added slaMonitorAgentConfiguredAgentVrfName,
                                  slaMonitorAgentSlaParameter for VSP9K"

    REVISION "201209040000Z" -- 4 September 2012
    DESCRIPTION "Version 1: Initial version. Basic agent support."

    ::= { policy 8 }

slaMonitorMibNotifications 
            OBJECT IDENTIFIER ::= { slaMonitorMib 0 }

slaMonitorMibClasses 
            OBJECT IDENTIFIER ::= { slaMonitorMib 1 }

slaMonitorMibConformance 
            OBJECT IDENTIFIER ::= { slaMonitorMib 2 }

--
-- Avaya Networks SLA Monitor Agent Classes
--

slaMonitorAgtClasses OBJECT IDENTIFIER ::= { slaMonitorMibClasses 1 }

--
-- SLA Monitor Agent Configuration Objects
--

slaMonitorAgentStatus OBJECT-TYPE
    SYNTAX         INTEGER {
                        enabled(1),
                        disabled(2)
                   }
    MAX-ACCESS     read-write
    STATUS         current
    DESCRIPTION
        "The value of this attribute indicates whether
        the SLA Monitor agent is enabled or not. An agent
        that is enabled will respond to SLA Monitor
        server discovery packets. A disabled agent will 
        remain dormant until manually enabled."

    ::= { slaMonitorAgtClasses 1 }

slaMonitorAgentAddressType OBJECT-TYPE
    SYNTAX         InetAddressType
    MAX-ACCESS     read-only
    STATUS         current
    DESCRIPTION
        "The type of IP address used by the agent. This
        object is limited to IPv4 and IPv6 addresses."

    ::= { slaMonitorAgtClasses 2 }

slaMonitorAgentAddress OBJECT-TYPE
    SYNTAX         InetAddress
    MAX-ACCESS     read-only
    STATUS         current
    DESCRIPTION
        "The IP address currently used by the SLA Monitor agent."

    ::= { slaMonitorAgtClasses 3 }

slaMonitorAgentPort OBJECT-TYPE
    SYNTAX         InetPortNumber
    MAX-ACCESS     read-only
    STATUS         current
    DESCRIPTION
        "The UDP port currently used by the SLA Monitor 
        agent for agent-server communication."

    ::= { slaMonitorAgtClasses 4 }

slaMonitorAgentRegisteredWithServer OBJECT-TYPE
    SYNTAX         INTEGER {
                        registered(1),
                        notRegistered(2)
                   }
    MAX-ACCESS     read-only
    STATUS         current
    DESCRIPTION
        "The value of this attribute indicates whether
        the SLA Monitor agent is registered with an SLA
        Monitor server or not."

    ::= { slaMonitorAgtClasses 5 }

slaMonitorAgentRegisteredServerAddrType OBJECT-TYPE
    SYNTAX         InetAddressType
    MAX-ACCESS     read-only
    STATUS         current
    DESCRIPTION
        "The type of IP address used by the server. This
        object is limited to IPv4 and IPv6 addresses."

    ::= { slaMonitorAgtClasses 6 }

slaMonitorAgentRegisteredServerAddr OBJECT-TYPE
    SYNTAX         InetAddress
    MAX-ACCESS     read-only
    STATUS         current
    DESCRIPTION
        "The IP address of the SLA Monitor server with which
        the agent is currently registered."

    ::= { slaMonitorAgtClasses 7 }

slaMonitorAgentRegisteredServerPort OBJECT-TYPE
    SYNTAX         InetPortNumber
    MAX-ACCESS     read-only
    STATUS         current
    DESCRIPTION
        "The TCP port utilized by the SLA Monitor server with 
        which the agent is currently registered."

    ::= { slaMonitorAgtClasses 8 }

slaMonitorAgentRegistrationTime OBJECT-TYPE
    SYNTAX         Unsigned32
    UNITS          "seconds"
    MAX-ACCESS     read-only
    STATUS         current
    DESCRIPTION
        "Specifies the maximum amount of time, in seconds,
        until the current registration period expires."

    ::= { slaMonitorAgtClasses 9 }

slaMonitorAgentCliAvailable OBJECT-TYPE
    SYNTAX         INTEGER {
                        available(1),
                        notAvailable(2)
                   }
    MAX-ACCESS     read-write
    STATUS         current
    DESCRIPTION
        "The value of this attribute indicates whether
        the SLA Monitor agent CLI is available or not."

    ::= { slaMonitorAgtClasses 10 }

slaMonitorAgentCliTimeout OBJECT-TYPE
    SYNTAX         Unsigned32
    UNITS          "seconds"
    MAX-ACCESS     read-write
    STATUS         current
    DESCRIPTION
        "Specifies the maximum amount of time, in seconds,
        until the CLI session is automatically terminated.
        The value of this attribute is pertinent only if CLI
        timeouts are enabled (slaMonitorAgentCliTimeoutMode 
        equals 'enable(1)')."

    ::= { slaMonitorAgtClasses 11 }

slaMonitorAgentCliTimeoutMode OBJECT-TYPE
    SYNTAX         INTEGER {
                        enable(1),
                        disable(2)
                   }
    MAX-ACCESS     read-write
    STATUS         current
    DESCRIPTION
        "The value of this attribute indicates whether
        the SLA Monitor agent automatic CLI session
        timeout is enabled or not. When this attribute
        is set to 'enable(1)', a CLI session will 
        automatically timeout after slaMonitorAgentCliTimeout
        seconds."

    ::= { slaMonitorAgtClasses 12 }

slaMonitorAgentSupportedApps OBJECT-TYPE
    SYNTAX         BITS {
                        other(0),
                        ntr(1),    -- Network Traceroute
                        rtp(2)     -- Real Time Performance tests
                   }
    MAX-ACCESS     read-only
    STATUS         current
    DESCRIPTION
        "An enumeration of the SLA Monitor agent capabilities."

    ::= { slaMonitorAgtClasses 13 }

slaMonitorAgentConfiguredAgentAddrType OBJECT-TYPE
    SYNTAX         InetAddressType
    MAX-ACCESS     read-write
    STATUS         current
    DESCRIPTION
        "The type of IP address used by the agent. This
        object is limited to IPv4 and IPv6 addresses."

    ::= { slaMonitorAgtClasses 14 }

slaMonitorAgentConfiguredAgentAddr OBJECT-TYPE
    SYNTAX         InetAddress
    MAX-ACCESS     read-write
    STATUS         current
    DESCRIPTION
        "The IP address of the SLA Monitor agent. If the value 
        of this attribute is 0.0.0.0, the SLA Monitor agent will
        utilize an active device IP address by default."

    ::= { slaMonitorAgtClasses 15 }

slaMonitorAgentConfiguredAgentPort OBJECT-TYPE
    SYNTAX         InetPortNumber
    MAX-ACCESS     read-write
    STATUS         current
    DESCRIPTION
        "The UDP port utilized by the SLA Monitor agent for
        agent-server communication. If the value of this 
        attribute is zero, the SLA Monitor agent will utilize 
        a default port value for communication purposes."

    ::= { slaMonitorAgtClasses 16 }

slaMonitorAgentConfiguredServerAddrType OBJECT-TYPE
    SYNTAX         InetAddressType
    MAX-ACCESS     read-write
    STATUS         current
    DESCRIPTION
        "The type of IP address used by the server. This
        object is limited to IPv4 and IPv6 addresses."

    ::= { slaMonitorAgtClasses 17 }

slaMonitorAgentConfiguredServerAddr OBJECT-TYPE
    SYNTAX         InetAddress
    MAX-ACCESS     read-write
    STATUS         current
    DESCRIPTION
        "The IP address of the SLA Monitor server with which
        the agent is allowed to register. If the value of this
        attribute is not 0.0.0.0, the SLA Monitor agent may
        only respond to server requests originating at the
        specified IP address (or the IP address specified by 
        the slaMonitorAgentConfiguredAltServerAddr object if 
        it is non-zero)."

    ::= { slaMonitorAgtClasses 18 }

slaMonitorAgentConfiguredServerPort OBJECT-TYPE
    SYNTAX         InetPortNumber
    MAX-ACCESS     read-write
    STATUS         current
    DESCRIPTION
        "The TCP port utilized by the SLA Monitor server with 
        which the agent is allowed to register. If the value
        of this attribute is non-zero, the SLA Monitor agent
        may only respond to server requests originating from
        the specified port (or from the port specified by the 
        slaMonitorAgentConfiguredAltServerPort object if it 
        is non-zero)."

    ::= { slaMonitorAgtClasses 19 }

slaMonitorAgentConfiguredAltServerAddrType OBJECT-TYPE
    SYNTAX         InetAddressType
    MAX-ACCESS     read-write
    STATUS         current
    DESCRIPTION
        "The type of IP address used by the server. This
        object is limited to IPv4 and IPv6 addresses."

    ::= { slaMonitorAgtClasses 20 }

slaMonitorAgentConfiguredAltServerAddr OBJECT-TYPE
    SYNTAX         InetAddress
    MAX-ACCESS     read-write
    STATUS         current
    DESCRIPTION
        "The IP address of the alternate SLA Monitor server 
        with which the agent is allowed to register. If the 
        value of this attribute is not 0.0.0.0, the SLA Monitor 
        agent may only respond to server requests originating 
        at the specified IP address (or the IP address
        specified by the slaMonitorAgentConfiguredServerAddr
        object if it is non-zero)."

    ::= { slaMonitorAgtClasses 21 }

slaMonitorAgentConfiguredAltServerPort OBJECT-TYPE
    SYNTAX         InetPortNumber
    MAX-ACCESS     read-write
    STATUS         current
    DESCRIPTION
        "The TCP port utilized by the alternate SLA Monitor 
        server with which the agent is allowed to register. 
        If the value of this attribute is non-zero, the SLA 
        Monitor agent may only respond to server requests 
        originating from the specified port (or from the port
        specified by the slaMonitorAgentConfiguredServerPort
        object if it is non-zero)."

    ::= { slaMonitorAgtClasses 22 }

slaMonitorAgentToAgentPort OBJECT-TYPE
    SYNTAX         InetPortNumber
    MAX-ACCESS     read-only
    STATUS         current
    DESCRIPTION
        "The base UDP port currently used by the SLA Monitor 
        agent for agent-agent communication. The base UDP port
        is used to derive multiple agent communication ports.

        An even base port values causes slaMonitorAgentToAgentPort
        and slaMonitorAgentToAgentPort+1 ports to be used. An 
        odd base port values causes slaMonitorAgentToAgentPort
        and slaMonitorAgentToAgentPort-1 ports to be used." 

    ::= { slaMonitorAgtClasses 23 }

slaMonitorAgentConfiguredAgentToAgentPort OBJECT-TYPE
    SYNTAX         InetPortNumber
    MAX-ACCESS     read-write
    STATUS         current
    DESCRIPTION
        "The UDP port utilized by the SLA Monitor agent for
        agent-agent communication. If the value of this 
        attribute is zero, the SLA Monitor agent will utilize 
        a default port value for the base agent-agent UDP
        communication port."

    ::= { slaMonitorAgtClasses 24 }

slaMonitorAgentEncryptionSupport OBJECT-TYPE
    SYNTAX         INTEGER {
                        available(1),
                        notAvailable(2)
                   }
    MAX-ACCESS     read-only
    STATUS         current
    DESCRIPTION
        "Specifies if encrypted agent-server communication
        is supported by the agent."

    ::= { slaMonitorAgtClasses 25 }

slaMonitorAgentConfiguredAgentVrfName OBJECT-TYPE
    SYNTAX          DisplayString (SIZE (0..32))
    MAX-ACCESS    read-write
    STATUS        current
    DESCRIPTION   "The name of the virtual Router which SLA Monitor
                   Agent IP address (slaMonitorAgentConfiguredAgentAddr)
                   is associated with.  This is only supported on VSP9K
                   for now"
    ::= { slaMonitorAgtClasses 26 }

slaMonitorAgentSlaParameter OBJECT-TYPE
    SYNTAX          DisplayString (SIZE (0..80))
    MAX-ACCESS    read-write
    STATUS        current
    DESCRIPTION   " String directly passed to the SLA Agent as parameter"
    ::= { slaMonitorAgtClasses 27  }

slaMonitorAgentCertFileInstallAction OBJECT-TYPE
    SYNTAX        INTEGER {
                      noAction(1),
                      install(2),
                      deinstall(3)
                  }
    MAX-ACCESS    read-write
    STATUS        current
    DESCRIPTION     "Operation object to install and deinstall the
                     certificate file to a platform specific location.
                     'noactio' -is default setting and always is returned
                          when this object is queried.
                     'install', object slaMonitorAgentCertFile will be
                          used as source certificate file to install .
                     'deinstall', will ignore object slaMonitorAgentCertFile
                          and just deinstall or remove the certificate file
                          from the installed location"
    DEFVAL   {noAction}
    ::= { slaMonitorAgtClasses 28 }
 
slaMonitorAgentCertFile OBJECT-TYPE
    SYNTAX          DisplayString (SIZE(0..128))
    MAX-ACCESS      read-write
    STATUS          current
    DESCRIPTION     "the certification file name for installation.
                     It is only valid or used when object
                     slaMonitorAgentCertFileInstallAction
                     is set to install.  Otherwise, it will be ignored"
    ::= { slaMonitorAgtClasses 29 }

slaMonitorAgentServerBypass OBJECT-TYPE
    SYNTAX         INTEGER {
                        enable(1),
                        disable(2)
                   }
    MAX-ACCESS     read-write
    STATUS         current
    DESCRIPTION
        "The value of this attribute determines whether
        the SLA Monitor agent can perform certain operations
        without being registered with a server. When this 
        attribute is set to 'enable(1)', an agent will respond
        to agent-to-agent test requests regardless of the 
        server registration status. A 'disable(2)' setting
        will restrict agent responses when the agent is not 
        registered with an SLA Monitor server."

    ::= { slaMonitorAgtClasses 30 }

slaMonitorAgentRefuseServerTests OBJECT-TYPE
    SYNTAX         INTEGER {
                        allow(1),
                        refuse(2)
                   }
    MAX-ACCESS     read-write
    STATUS         current
    DESCRIPTION
        "The value of this attribute determines whether
        the SLA Monitor agent will refuse test requests
        from the server. When this attribute is set to 
        'allow(1)', an agent will accept test requests
        from the server. A 'refuse(2)' setting will cause 
        the agent to reject test requests from the server.

        From a usage perspective, it may be necessary to
        temporarily refuse server test requests if the
        agent is being actively managed by a server but
        the administrator wishes to use the CLI or SNMP
        interfaces to initiate tests manually."

    ::= { slaMonitorAgtClasses 31 }

--
-- Avaya Networks SLA Monitor Agent Test Classes
--

slaMonitorAgtTestClasses OBJECT IDENTIFIER ::= { slaMonitorMibClasses 2 }

--
-- SLAMon NTR Test Control Table
--

slaMonitorNtrCtrlTable OBJECT-TYPE
    SYNTAX         SEQUENCE OF SlaMonitorNtrCtrlEntry
    MAX-ACCESS     not-accessible
    STATUS         current
    DESCRIPTION
        "Defines the SLAMon agent NTR test control table supporting
        the ability to initiate NTR tests remotely. The results of 
        NTR test operations are stored in the slaMonitorNtrResultsTable 
        and the slaMonitorNtrHopsTable."

    ::= { slaMonitorAgtTestClasses 1 }

slaMonitorNtrCtrlEntry OBJECT-TYPE
    SYNTAX         SlaMonitorNtrCtrlEntry
    MAX-ACCESS     not-accessible
    STATUS         current
    DESCRIPTION
        "Defines an entry in the slaMonitorNtrCtrlTable.  The first
        index element, slaMonitorNtrCtrlOwnerId, is of type SnmpAdminString, 
        allowing for a management application to identify its entries.  
        The second index, slaMonitorNtrCtrlTestName (also an SnmpAdminString),
        enables the same management application to have multiple requests 
        configured."

    INDEX { slaMonitorNtrCtrlOwnerId, slaMonitorNtrCtrlTestName }
    ::= { slaMonitorNtrCtrlTable 1 }

SlaMonitorNtrCtrlEntry ::= SEQUENCE {
    slaMonitorNtrCtrlOwnerId           SnmpAdminString,
    slaMonitorNtrCtrlTestName          SnmpAdminString,
    slaMonitorNtrCtrlTargetAddressType InetAddressType,
    slaMonitorNtrCtrlTargetAddress     InetAddress,
    slaMonitorNtrCtrlDscp              Dscp,
    slaMonitorNtrCtrlAttempts          Integer32,
    slaMonitorNtrCtrlPeriod            Integer32,
    slaMonitorNtrCtrlAdminStatus       INTEGER,
    slaMonitorNtrCtrlLabel             SnmpAdminString,
    slaMonitorNtrCtrlStorageType       StorageType,
    slaMonitorNtrCtrlRowStatus         RowStatus
}

slaMonitorNtrCtrlOwnerId OBJECT-TYPE
    SYNTAX         SnmpAdminString (SIZE(1..32))
    MAX-ACCESS     not-accessible
    STATUS         current
    DESCRIPTION
        "The owner of an NTR test."

    ::= { slaMonitorNtrCtrlEntry 1 }

 slaMonitorNtrCtrlTestName OBJECT-TYPE
    SYNTAX         SnmpAdminString (SIZE(1..32))
    MAX-ACCESS     not-accessible
    STATUS         current
    DESCRIPTION
        "The name of an NTR test.  This value is locally unique,
        within the scope of an slaMonitorNtrCtrlOwnerId."

    ::= { slaMonitorNtrCtrlEntry 2 }

slaMonitorNtrCtrlTargetAddressType OBJECT-TYPE
    SYNTAX         InetAddressType
    MAX-ACCESS     read-create
    STATUS         current
    DESCRIPTION
        "Specifies the target address type."

    DEFVAL { ipv4 }
    ::= { slaMonitorNtrCtrlEntry 3 }

slaMonitorNtrCtrlTargetAddress OBJECT-TYPE
    SYNTAX         InetAddress
    MAX-ACCESS     read-create
    STATUS         current
    DESCRIPTION
        "Specifies the target address used for the 
        NTR test. The address type can be determined 
        by examining the value of the corresponding 
        slaMonitorNtrCtrlTargetAddressType.

        A value for this object MUST be provided 
        during entry creation."

    ::= { slaMonitorNtrCtrlEntry 4 }

slaMonitorNtrCtrlDscp OBJECT-TYPE
    SYNTAX         Dscp
    MAX-ACCESS     read-create
    STATUS         current
    DESCRIPTION
        "Specifies the DSCP value for use in packets that
        are generated by the NTR test."

    DEFVAL { 0 }
    ::= { slaMonitorNtrCtrlEntry 5 }

slaMonitorNtrCtrlAttempts OBJECT-TYPE
    SYNTAX         Integer32 (1..10)
    MAX-ACCESS     read-create
    STATUS         current
    DESCRIPTION
        "Specifies the number of attempts are 
        generated by the NTR test."

    DEFVAL { 2 }
    ::= { slaMonitorNtrCtrlEntry 6 }

slaMonitorNtrCtrlPeriod OBJECT-TYPE
    SYNTAX         Integer32 (10000..200000)
    MAX-ACCESS     read-create
    STATUS         current
    DESCRIPTION
        "Specifies the interval between packets, in
        microseconds, generated by the NTR test."

    DEFVAL { 20000 }
    ::= { slaMonitorNtrCtrlEntry 7 }

slaMonitorNtrCtrlAdminStatus OBJECT-TYPE
    SYNTAX         INTEGER {
                       enabled(1), -- operation should be started
                       disabled(2) -- operation should be stopped
                   }
    MAX-ACCESS     read-create
    STATUS         current
    DESCRIPTION
        "Used to initiate an NTR test:

        enabled(1)  - initiate the test as defined by this
                      slaMonitorNtrCtrlEntry.
        disabled(2) - deactivate the test defined by this
                      slaMonitorNtrCtrlEntry, if possible.

        Refer to the corresponding slaMonitorNtrResultsOperStatus 
        to determine the operational state of the test defined by
        this entry. When queried, 'disabled(2)' is always returned
        for this attribute."

    DEFVAL { disabled }
    ::= { slaMonitorNtrCtrlEntry 8 }

slaMonitorNtrCtrlLabel OBJECT-TYPE
    SYNTAX         SnmpAdminString (SIZE(0..32))
    MAX-ACCESS     read-create
    STATUS         current
    DESCRIPTION
        "A label used to reference the NTR control entry
        in a textual manner."

    DEFVAL { "" }
    ::= { slaMonitorNtrCtrlEntry 9 }

slaMonitorNtrCtrlStorageType OBJECT-TYPE
    SYNTAX         StorageType
    MAX-ACCESS     read-create
    STATUS         current
    DESCRIPTION
        "The storage type for this conceptual row.

        Conceptual rows having the value 'permanent' need not
        allow write-access to any columnar objects in the row."

    DEFVAL { volatile }
    ::= { slaMonitorNtrCtrlEntry 10 }

slaMonitorNtrCtrlRowStatus OBJECT-TYPE
    SYNTAX         RowStatus
    MAX-ACCESS     read-create
    STATUS         current
    DESCRIPTION
        "This object allows entries to be created and deleted
        in the slaMonitorNtrCtrlTable. 

        Deletion of an entry in this table results in the 
        deletion of all corresponding (i.e., entries with the 
        same slaMonitorNtrCtrlOwnerId and slaMonitorNtrCtrlTestName 
        index values) entries in the slaMonitorNtrResultsTable and 
        the slaMonitorNtrHopsTable.

        Initiation of an NTR test corresponding to this entry
        is controlled via slaMonitorNtrCtrlAdminStatus and not
        by entry creation.

        The operational state of an NTR test can be determined
        by examining the corresponding slaMonitorNtrResultsOperStatus 
        object."

    ::= { slaMonitorNtrCtrlEntry 11 }

--
-- SLAMon NTR Test Results Table
--

slaMonitorNtrResultsTable OBJECT-TYPE
    SYNTAX         SEQUENCE OF SlaMonitorNtrResultsEntry
    MAX-ACCESS     not-accessible
    STATUS         current
    DESCRIPTION
        "Defines the SLAMon agent NTR results table that is used 
        to track the status of NTR tests initiated through the
        the slaMonitorNtrCtrlTable.

        An entry is added to the slaMonitorNtrResultsTable when 
        an NTR test defined by an slaMonitorNtrCtrlEntry is started 
        by transition of its slaMonitorNtrCtrlAdminStatus object to 
        'enabled(1)'.

        If the object slaMonitorNtrCtrlAdminStatus has the value 
        'disabled(2)', then successfully writing 'enabled(1)' to 
        the object slaMonitorNtrCtrlAdminStatus re-initializes an 
        already existing entry in the slaMonitorNtrResultsTable. 
        The values of objects in the re-initialized entry are the 
        same as the values of objects in a new entry would be.

        An entry is removed from the slaMonitorNtrResultsTable when
        its corresponding slaMonitorNtrCtrlEntry is deleted."

    ::= { slaMonitorAgtTestClasses 2 }

slaMonitorNtrResultsEntry OBJECT-TYPE
    SYNTAX         SlaMonitorNtrResultsEntry
    MAX-ACCESS     not-accessible
    STATUS         current
    DESCRIPTION
        "Defines an entry in the slaMonitorNtrResultsTable.  The
        slaMonitorNtrResultsTable has the same indexing as the
        slaMonitorNtrCtrlTable so that a slaMonitorNtrResultsEntry
        corresponds to the slaMonitorNtrCtrlEntry that caused it to
        be created."

    INDEX { slaMonitorNtrCtrlOwnerId, slaMonitorNtrCtrlTestName }
    ::= { slaMonitorNtrResultsTable 1 }

SlaMonitorNtrResultsEntry ::= SEQUENCE {
    slaMonitorNtrResultsOperStatus        INTEGER,
    slaMonitorNtrResultsSrcAddressType    InetAddressType,
    slaMonitorNtrResultsSrcAddress        InetAddress,
    slaMonitorNtrResultsDstAddressType    InetAddressType,
    slaMonitorNtrResultsDstAddress        InetAddress,
    slaMonitorNtrResultsSrcPort           InetPortNumber,
    slaMonitorNtrResultsDstPort           InetPortNumber,
    slaMonitorNtrResultsDscp              Dscp,
    slaMonitorNtrResultsTTL               Unsigned32,
    slaMonitorNtrResultsCompletionData    BITS,
    slaMonitorNtrResultsCompletionSummary SnmpAdminString,
    slaMonitorNtrResultsAbortData         BITS,
    slaMonitorNtrResultsHopCount          Unsigned32
}

slaMonitorNtrResultsOperStatus OBJECT-TYPE
    SYNTAX         INTEGER {
                       inProgress(1),  -- test is in progress
                       aborted(2),     -- test has been aborted
                       completed(3)    -- test is completed
                   }
    MAX-ACCESS     read-only
    STATUS         current
    DESCRIPTION
        "Reflects the operational state of an slaMonitorNtrCtrlEntry:

        inProgress(1)   - test is active.
        aborted(2)      - test has been stopped. Refer to object
                          slaMonitorNtrResultsAbortData for details.
        completed(3)    - test is completed. Refer to objects
                          slaMonitorNtrResultsCompletionData and
                          slaMonitorNtrResultsCompletionSummary for
                          details."

    ::= { slaMonitorNtrResultsEntry 1 }

slaMonitorNtrResultsSrcAddressType OBJECT-TYPE
    SYNTAX         InetAddressType
    MAX-ACCESS     read-only
    STATUS         current
    DESCRIPTION
        "Specifies the address type of the source IP
        address used for this test."

    ::= { slaMonitorNtrResultsEntry 2 }

slaMonitorNtrResultsSrcAddress OBJECT-TYPE
    SYNTAX         InetAddress
    MAX-ACCESS     read-only
    STATUS         current
    DESCRIPTION
        "Specifies the source IP address used 
        for this test."

    ::= { slaMonitorNtrResultsEntry 3 }

slaMonitorNtrResultsDstAddressType OBJECT-TYPE
    SYNTAX         InetAddressType
    MAX-ACCESS     read-only
    STATUS         current
    DESCRIPTION
        "Specifies the address type of the destination IP
        address used for this test."

    ::= { slaMonitorNtrResultsEntry 4 }

slaMonitorNtrResultsDstAddress OBJECT-TYPE
    SYNTAX         InetAddress
    MAX-ACCESS     read-only
    STATUS         current
    DESCRIPTION
        "Specifies the destination IP address used 
        for this test."

    ::= { slaMonitorNtrResultsEntry 5 }

slaMonitorNtrResultsSrcPort OBJECT-TYPE
    SYNTAX         InetPortNumber
    MAX-ACCESS     read-only
    STATUS         current
    DESCRIPTION
        "Specifies the Layer 4 source port used for this test."

    ::= { slaMonitorNtrResultsEntry 6 }

slaMonitorNtrResultsDstPort OBJECT-TYPE
    SYNTAX         InetPortNumber
    MAX-ACCESS     read-only
    STATUS         current
    DESCRIPTION
        "Specifies the Layer 4 destination port used for this test."

    ::= { slaMonitorNtrResultsEntry 7 }

slaMonitorNtrResultsDscp OBJECT-TYPE
    SYNTAX         Dscp
    MAX-ACCESS     read-only
    STATUS         current
    DESCRIPTION
        "Specifies the DSCP value contained in NTR test packets
        generated by the agent for this test."

    ::= { slaMonitorNtrResultsEntry 8 }

slaMonitorNtrResultsTTL OBJECT-TYPE
    SYNTAX         Unsigned32
    MAX-ACCESS     read-only
    STATUS         current
    DESCRIPTION
        "The maximum time-to-live (TTL) value used during the 
        execution of this test."

    ::= { slaMonitorNtrResultsEntry 9 }

slaMonitorNtrResultsCompletionData OBJECT-TYPE
    SYNTAX         BITS {
                        other(0),
                        remoteUnreachable(1),
                        remotePortUnreachable(2),
                        remoteNetUnreachable(3),
                        remoteHostUnreachable(4),
                        remoteProtocolUnreachable(5),
                        remoteFirewalledUnreachable(6),
                        remoteResponded(7),
                        remoteResponseLikely(8),
                        remoteNoResponse(9)
                   }
    MAX-ACCESS     read-only
    STATUS         current
    DESCRIPTION
        "Provides details related to test completion.
        Multiple bits may be set to convey test status."

    ::= { slaMonitorNtrResultsEntry 10 }

slaMonitorNtrResultsCompletionSummary OBJECT-TYPE
    SYNTAX         SnmpAdminString (SIZE(0..32))
    MAX-ACCESS     read-only
    STATUS         current
    DESCRIPTION
        "A user-readable string that is used to convey test
        results for completed tests in an easy-to-understand 
        format."

    DEFVAL { "" }
    ::= { slaMonitorNtrResultsEntry 11 }

slaMonitorNtrResultsAbortData OBJECT-TYPE
    SYNTAX         BITS {
                        other(0),
                        agentDisabled(1),
                        agentBusy(2),
                        timeout(3),
                        cancelled(4)
                   }
    MAX-ACCESS     read-only
    STATUS         current
    DESCRIPTION
        "Provides details for tests that were aborted.
        Multiple bits may be set to convey test status."

    ::= { slaMonitorNtrResultsEntry 12 }

slaMonitorNtrResultsHopCount OBJECT-TYPE
    SYNTAX         Unsigned32
    MAX-ACCESS     read-only
    STATUS         current
    DESCRIPTION
        "The total number of hops for which information has been
        acquired during the execution of this test."

    ::= { slaMonitorNtrResultsEntry 13 }

--
-- SLAMon NTR Test Hop Results Table
--

slaMonitorNtrHopsTable OBJECT-TYPE
    SYNTAX         SEQUENCE OF SlaMonitorNtrHopsEntry
    MAX-ACCESS     not-accessible
    STATUS         current
    DESCRIPTION
        "Defines the SLAMon agent NTR test hop table for
        keeping track of the results of NTR tests on a
        per-hop basis."

    ::= { slaMonitorAgtTestClasses 3 }

slaMonitorNtrHopsEntry OBJECT-TYPE
    SYNTAX         SlaMonitorNtrHopsEntry
    MAX-ACCESS     not-accessible
    STATUS         current
    DESCRIPTION
        "Defines an entry in the slaMonitorNtrHopsTable.

        The first two index elements identify the
        slaMonitorNtrCtrlEntry with which this 
        slaMonitorNtrHopsEntry is associated. The
        third index element, slaMonitorNtrHopsHopIndex, 
        selects a hop in an NTR test path."

    INDEX { slaMonitorNtrCtrlOwnerId, slaMonitorNtrCtrlTestName, slaMonitorNtrHopsHopIndex }
    ::= { slaMonitorNtrHopsTable 1 }

SlaMonitorNtrHopsEntry ::= SEQUENCE {
    slaMonitorNtrHopsHopIndex       Unsigned32,
    slaMonitorNtrHopsTgtAddressType InetAddressType,
    slaMonitorNtrHopsTgtAddress     InetAddress,
    slaMonitorNtrHopsRtt            Unsigned32,
    slaMonitorNtrHopsIngressDscp    Dscp,
    slaMonitorNtrHopsEgressDscp     Dscp
 }

slaMonitorNtrHopsHopIndex OBJECT-TYPE
    SYNTAX         Unsigned32 (1..'ffffffff'h)
    MAX-ACCESS     not-accessible
    STATUS         current
    DESCRIPTION
        "Specifies the hop index for an NTR test hop. 

        Values for this object with respect to the same
        slaMonitorNtrCtrlOwnerId and slaMonitorNtrCtrlTestName
        MUST start at 1 and be given increasing values for
        subsequent hops. The value of slaMonitorNtrHopsHopIndex
        does not necessarily represent the number of the hop 
        on the traced path, though this is normally the case."

    ::= { slaMonitorNtrHopsEntry 1 }

slaMonitorNtrHopsTgtAddressType OBJECT-TYPE
    SYNTAX         InetAddressType
    MAX-ACCESS     read-only
    STATUS         current
    DESCRIPTION
        "This object indicates the type of address stored
        in the corresponding slaMonitorNtrHopsTgtAddress
        object."

    ::= { slaMonitorNtrHopsEntry 2 }

slaMonitorNtrHopsTgtAddress OBJECT-TYPE
    SYNTAX         InetAddress
    MAX-ACCESS     read-only
    STATUS         current
    DESCRIPTION
        "This object reports the IP address associated with
        the NTR test hop."

    ::= { slaMonitorNtrHopsEntry 3 }

slaMonitorNtrHopsRtt OBJECT-TYPE
    SYNTAX         Unsigned32
    MAX-ACCESS     read-only
    STATUS         current
    DESCRIPTION
        "The NTR test round-trip-time (RTT), in microseconds,
        computed for this hop."

    ::= { slaMonitorNtrHopsEntry 4 }

slaMonitorNtrHopsIngressDscp OBJECT-TYPE
    SYNTAX         Dscp
    MAX-ACCESS     read-only
    STATUS         current
    DESCRIPTION
        "The DSCP value in the NTR test packet received by
        the target host (slaMonitorNtrHopsTgtAddress) for
        this hop."

    ::= { slaMonitorNtrHopsEntry 5 }

slaMonitorNtrHopsEgressDscp OBJECT-TYPE
    SYNTAX         Dscp
    MAX-ACCESS     read-only
    STATUS         current
    DESCRIPTION
        "The DSCP value in the NTR test response packet 
        received by the SLAMon agent for this hop."

    ::= { slaMonitorNtrHopsEntry 6 }

--
-- SLAMon RTP Test Control Table
--

slaMonitorRtpCtrlTable OBJECT-TYPE
    SYNTAX         SEQUENCE OF SlaMonitorRtpCtrlEntry
    MAX-ACCESS     not-accessible
    STATUS         current
    DESCRIPTION
        "Defines the SLAMon agent RTP test control table supporting
        the ability to initiate RTP tests remotely. The results of 
        RTP test operations are stored in the slaMonitorRtpResultsTable."

    ::= { slaMonitorAgtTestClasses 4 }

slaMonitorRtpCtrlEntry OBJECT-TYPE
    SYNTAX         SlaMonitorRtpCtrlEntry
    MAX-ACCESS     not-accessible
    STATUS         current
    DESCRIPTION
        "Defines an entry in the slaMonitorRtpCtrlTable.  The first
        index element, slaMonitorRtpCtrlOwnerId, is of type SnmpAdminString, 
        allowing for a management application to identify its entries.  
        The second index, slaMonitorRtpCtrlTestName (also an SnmpAdminString),
        enables the same management application to have multiple requests 
        configured."

    INDEX { slaMonitorRtpCtrlOwnerId, slaMonitorRtpCtrlTestName }
    ::= { slaMonitorRtpCtrlTable 1 }

SlaMonitorRtpCtrlEntry ::= SEQUENCE {
    slaMonitorRtpCtrlOwnerId           SnmpAdminString,
    slaMonitorRtpCtrlTestName          SnmpAdminString,
    slaMonitorRtpCtrlTargetAddressType InetAddressType,
    slaMonitorRtpCtrlTargetAddress     InetAddress,
    slaMonitorRtpCtrlDscp              Dscp,
    slaMonitorRtpCtrlTestPackets       Integer32,
    slaMonitorRtpCtrlSyncPackets       Integer32,
    slaMonitorRtpCtrlPeriod            Integer32,
    slaMonitorRtpCtrlAdminStatus       INTEGER,
    slaMonitorRtpCtrlLabel             SnmpAdminString,
    slaMonitorRtpCtrlStorageType       StorageType,
    slaMonitorRtpCtrlRowStatus         RowStatus
}

slaMonitorRtpCtrlOwnerId OBJECT-TYPE
    SYNTAX         SnmpAdminString (SIZE(1..32))
    MAX-ACCESS     not-accessible
    STATUS         current
    DESCRIPTION
        "The owner of an RTP test."

    ::= { slaMonitorRtpCtrlEntry 1 }

 slaMonitorRtpCtrlTestName OBJECT-TYPE
    SYNTAX         SnmpAdminString (SIZE(1..32))
    MAX-ACCESS     not-accessible
    STATUS         current
    DESCRIPTION
        "The name of an RTP test.  This is locally unique,
        within the scope of an slaMonitorRtpCtrlOwnerId."

    ::= { slaMonitorRtpCtrlEntry 2 }

slaMonitorRtpCtrlTargetAddressType OBJECT-TYPE
    SYNTAX         InetAddressType
    MAX-ACCESS     read-create
    STATUS         current
    DESCRIPTION
        "Specifies the target address type."

    DEFVAL { ipv4 }
    ::= { slaMonitorRtpCtrlEntry 3 }

slaMonitorRtpCtrlTargetAddress OBJECT-TYPE
    SYNTAX         InetAddress
    MAX-ACCESS     read-create
    STATUS         current
    DESCRIPTION
        "Specifies the target address used for the 
        RTP test. The address type can be determined 
        by examining the value of the corresponding 
        slaMonitorRtpCtrlTargetAddressType.

        A value for this object MUST be provided 
        during entry creation."

    ::= { slaMonitorRtpCtrlEntry 4 }

slaMonitorRtpCtrlDscp OBJECT-TYPE
    SYNTAX         Dscp
    MAX-ACCESS     read-create
    STATUS         current
    DESCRIPTION
        "Specifies the DSCP value for use in packets that
        are generated by the RTP test."

    DEFVAL { 0 }
    ::= { slaMonitorRtpCtrlEntry 5 }

slaMonitorRtpCtrlTestPackets OBJECT-TYPE
    SYNTAX         Integer32 (10..100)
    MAX-ACCESS     read-create
    STATUS         current
    DESCRIPTION
        "Specifies the number of test packets that are 
        generated by the RTP test. Test packets are used
        for jitter determination."

    DEFVAL { 50 }
    ::= { slaMonitorRtpCtrlEntry 6 }

slaMonitorRtpCtrlSyncPackets OBJECT-TYPE
    SYNTAX         Integer32 (10..100)
    MAX-ACCESS     read-create
    STATUS         current
    DESCRIPTION
        "Specifies the number of synchronization packets
        that are generated by the RTP test. Sync packets
        are used for network delay determination."

    DEFVAL { 10 }
    ::= { slaMonitorRtpCtrlEntry 7 }

slaMonitorRtpCtrlPeriod OBJECT-TYPE
    SYNTAX         Integer32 (10000..200000)
    MAX-ACCESS     read-create
    STATUS         current
    DESCRIPTION
        "Specifies the interval between packets (in
        microseconds) generated by the RTP test."

    DEFVAL { 20000 }
    ::= { slaMonitorRtpCtrlEntry 8 }

slaMonitorRtpCtrlAdminStatus OBJECT-TYPE
    SYNTAX         INTEGER {
                       enabled(1), -- operation should be started
                       disabled(2) -- operation should be stopped
                   }
    MAX-ACCESS     read-create
    STATUS         current
    DESCRIPTION
        "Used to initiate an RTP test:

        enabled(1)  - initiate the test as defined by this
                      slaMonitorRtpCtrlEntry.
        disabled(2) - deactivate the test defined by this
                      slaMonitorRtpCtrlEntry, if possible.

        Refer to the corresponding slaMonitorRtpResultsOperStatus 
        to determine the operational state of the test defined by
        this entry. When queried, 'disabled(2)' is always returned
        for this attribute."

    DEFVAL { disabled }
    ::= { slaMonitorRtpCtrlEntry 9 }

slaMonitorRtpCtrlLabel OBJECT-TYPE
    SYNTAX         SnmpAdminString (SIZE(0..32))
    MAX-ACCESS     read-create
    STATUS         current
    DESCRIPTION
        "A label used to reference the RTP control entry
        in a textual manner."

    DEFVAL { "" }
    ::= { slaMonitorRtpCtrlEntry 10 }

slaMonitorRtpCtrlStorageType OBJECT-TYPE
    SYNTAX         StorageType
    MAX-ACCESS     read-create
    STATUS         current
    DESCRIPTION
        "The storage type for this conceptual row.

        Conceptual rows having the value 'permanent' need not
        allow write-access to any columnar objects in the row."

    DEFVAL { volatile }
    ::= { slaMonitorRtpCtrlEntry 11 }

slaMonitorRtpCtrlRowStatus OBJECT-TYPE
    SYNTAX         RowStatus
    MAX-ACCESS     read-create
    STATUS         current
    DESCRIPTION
        "This object allows entries to be created and deleted
        in the slaMonitorRtpCtrlTable. 

        Deletion of an entry in this table results in the 
        deletion of all corresponding (i.e., entries with the 
        same slaMonitorRtpCtrlOwnerId and slaMonitorRtpCtrlTestName 
        index values) entries in the slaMonitorRtpResultsTable.

        Initiation of an RTP test corresponding to this entry
        is controlled via slaMonitorRtpCtrlAdminStatus and not
        by entry creation.

        The operational state of an RTP test can be determined
        by examining the corresponding slaMonitorRtpResultsOperStatus 
        object."

    ::= { slaMonitorRtpCtrlEntry 12 }

--
-- SLAMon RTP Test Results Table
--

slaMonitorRtpResultsTable OBJECT-TYPE
    SYNTAX         SEQUENCE OF SlaMonitorRtpResultsEntry
    MAX-ACCESS     not-accessible
    STATUS         current
    DESCRIPTION
        "Defines the SLAMon agent RTP results table that is used 
        to track the status of RTP tests initiated through the
        the slaMonitorRtpCtrlTable.

        An entry is added to the slaMonitorRtpResultsTable when 
        an RTP test defined by an slaMonitorRtpCtrlEntry is started 
        by transition of its slaMonitorRtpCtrlAdminStatus object to 
        'enabled(1)'.

        If the object slaMonitorRtpCtrlAdminStatus has the value 
        'disabled(2)', then successfully writing 'enabled(1)' to 
        the object slaMonitorRtpCtrlAdminStatus re-initializes an 
        already existing entry in the slaMonitorRtpResultsTable. 
        The values of objects in the re-initialized entry are the 
        same as the values of objects in a new entry would be.

        An entry is removed from the slaMonitorRtpResultsTable when
        its corresponding slaMonitorRtpCtrlEntry is deleted."

    ::= { slaMonitorAgtTestClasses 5 }

slaMonitorRtpResultsEntry OBJECT-TYPE
    SYNTAX         SlaMonitorRtpResultsEntry
    MAX-ACCESS     not-accessible
    STATUS         current
    DESCRIPTION
        "Defines an entry in the slaMonitorRtpResultsTable.  The
        slaMonitorRtpResultsTable has the same indexing as the
        slaMonitorRtpCtrlTable so that a slaMonitorRtpResultsEntry
        corresponds to the slaMonitorRtpCtrlEntry that caused it to
        be created."

    INDEX { slaMonitorRtpCtrlOwnerId, slaMonitorRtpCtrlTestName }
    ::= { slaMonitorRtpResultsTable 1 }

SlaMonitorRtpResultsEntry ::= SEQUENCE {
    slaMonitorRtpResultsOperStatus         INTEGER,
    slaMonitorRtpResultsSrcAddressType     InetAddressType,
    slaMonitorRtpResultsSrcAddress         InetAddress,
    slaMonitorRtpResultsDstAddressType     InetAddressType,
    slaMonitorRtpResultsDstAddress         InetAddress,
    slaMonitorRtpResultsSrcPort            InetPortNumber,
    slaMonitorRtpResultsDstPort            InetPortNumber,
    slaMonitorRtpResultsDscp               Dscp,
    slaMonitorRtpResultsAverageDelay       Unsigned32,
    slaMonitorRtpResultsMedianDelay        Unsigned32,
    slaMonitorRtpResultsPacketLoss         Unsigned32,
    slaMonitorRtpResultsOutOfOrderArrivals Unsigned32,
    slaMonitorRtpResultsJitterQuartile0    Unsigned32,
    slaMonitorRtpResultsJitterQuartile1    Unsigned32,
    slaMonitorRtpResultsJitterQuartile2    Unsigned32,
    slaMonitorRtpResultsJitterQuartile3    Unsigned32,
    slaMonitorRtpResultsJitterQuartile4    Unsigned32,
    slaMonitorRtpResultsAbortData          BITS
}

slaMonitorRtpResultsOperStatus OBJECT-TYPE
    SYNTAX         INTEGER {
                       inProgress(1),  -- test is in progress
                       aborted(2),     -- test has been aborted
                       completed(3)    -- test is completed
                   }
    MAX-ACCESS     read-only
    STATUS         current
    DESCRIPTION
        "Reflects the operational state of an slaMonitorRtpCtrlEntry:

        inProgress(1)   - test is active.
        aborted(2)      - test has been stopped. Refer to object
                          slaMonitorRtpResultsAbortData for details.
        completed(3)    - test is completed. Refer to objects
                          that contain completed test results (all 
                          attributes except slaMonitorRtpResultsAbortData)
                          for details."

    ::= { slaMonitorRtpResultsEntry 1 }

slaMonitorRtpResultsSrcAddressType OBJECT-TYPE
    SYNTAX         InetAddressType
    MAX-ACCESS     read-only
    STATUS         current
    DESCRIPTION
        "Specifies the address type of the source IP
        address used for this test."

    ::= { slaMonitorRtpResultsEntry 2 }

slaMonitorRtpResultsSrcAddress OBJECT-TYPE
    SYNTAX         InetAddress
    MAX-ACCESS     read-only
    STATUS         current
    DESCRIPTION
        "Specifies the source IP address used 
        for this test."

    ::= { slaMonitorRtpResultsEntry 3 }

slaMonitorRtpResultsDstAddressType OBJECT-TYPE
    SYNTAX         InetAddressType
    MAX-ACCESS     read-only
    STATUS         current
    DESCRIPTION
        "Specifies the address type of the destination IP
        address used for this test."

    ::= { slaMonitorRtpResultsEntry 4 }

slaMonitorRtpResultsDstAddress OBJECT-TYPE
    SYNTAX         InetAddress
    MAX-ACCESS     read-only
    STATUS         current
    DESCRIPTION
        "Specifies the destination IP address used 
        for this test."

    ::= { slaMonitorRtpResultsEntry 5 }

slaMonitorRtpResultsSrcPort OBJECT-TYPE
    SYNTAX         InetPortNumber
    MAX-ACCESS     read-only
    STATUS         current
    DESCRIPTION
        "Specifies the Layer 4 source port used for this test."

    ::= { slaMonitorRtpResultsEntry 6 }

slaMonitorRtpResultsDstPort OBJECT-TYPE
    SYNTAX         InetPortNumber
    MAX-ACCESS     read-only
    STATUS         current
    DESCRIPTION
        "Specifies the Layer 4 destination port used for this test."

    ::= { slaMonitorRtpResultsEntry 7 }

slaMonitorRtpResultsDscp OBJECT-TYPE
    SYNTAX         Dscp
    MAX-ACCESS     read-only
    STATUS         current
    DESCRIPTION
        "Specifies the DSCP value contained in RTP test packets
        generated by the agent for this test."

    ::= { slaMonitorRtpResultsEntry 8 }

slaMonitorRtpResultsAverageDelay OBJECT-TYPE
    SYNTAX         Unsigned32
    MAX-ACCESS     read-only
    STATUS         current
    DESCRIPTION
        "The average network delay (RTT) experienced during this
        test sequence, in microseconds."

    ::= { slaMonitorRtpResultsEntry 9 }

slaMonitorRtpResultsMedianDelay OBJECT-TYPE
    SYNTAX         Unsigned32
    MAX-ACCESS     read-only
    STATUS         current
    DESCRIPTION
        "The median network delay (RTT) experienced during this
        test sequence, in microseconds."

    ::= { slaMonitorRtpResultsEntry 10 }

slaMonitorRtpResultsPacketLoss OBJECT-TYPE
    SYNTAX         Unsigned32
    MAX-ACCESS     read-only
    STATUS         current
    DESCRIPTION
        "A count of packets lost during this test sequence."

    ::= { slaMonitorRtpResultsEntry 11 }

slaMonitorRtpResultsOutOfOrderArrivals OBJECT-TYPE
    SYNTAX         Unsigned32
    MAX-ACCESS     read-only
    STATUS         current
    DESCRIPTION
        "The number of out-of-order arrivals detected during
        this test sequence."

    ::= { slaMonitorRtpResultsEntry 12 }

slaMonitorRtpResultsJitterQuartile0 OBJECT-TYPE
    SYNTAX         Unsigned32
    MAX-ACCESS     read-only
    STATUS         current
    DESCRIPTION
        "The quartile 0 network jitter value, in microseconds,
        experienced during this test sequence."

    ::= { slaMonitorRtpResultsEntry 13 }

slaMonitorRtpResultsJitterQuartile1 OBJECT-TYPE
    SYNTAX         Unsigned32
    MAX-ACCESS     read-only
    STATUS         current
    DESCRIPTION
        "The quartile 1 network jitter value, in microseconds,
        experienced during this test sequence."

    ::= { slaMonitorRtpResultsEntry 14 }

slaMonitorRtpResultsJitterQuartile2 OBJECT-TYPE
    SYNTAX         Unsigned32
    MAX-ACCESS     read-only
    STATUS         current
    DESCRIPTION
        "The quartile 2 network jitter value, in microseconds,
        experienced during this test sequence."

    ::= { slaMonitorRtpResultsEntry 15 }

slaMonitorRtpResultsJitterQuartile3 OBJECT-TYPE
    SYNTAX         Unsigned32
    MAX-ACCESS     read-only
    STATUS         current
    DESCRIPTION
        "The quartile 3 network jitter value, in microseconds,
        experienced during this test sequence."

    ::= { slaMonitorRtpResultsEntry 16 }

slaMonitorRtpResultsJitterQuartile4 OBJECT-TYPE
    SYNTAX         Unsigned32
    MAX-ACCESS     read-only
    STATUS         current
    DESCRIPTION
        "The quartile 4 network jitter value, in microseconds,
        experienced during this test sequence."

    ::= { slaMonitorRtpResultsEntry 17 }

slaMonitorRtpResultsAbortData OBJECT-TYPE
    SYNTAX         BITS {
                        other(0),
                        agentDisabled(1),
                        agentBusy(2),
                        timeout(3),
                        cancelled(4),
                        deniedByTarget(5),
                        networkIssue(6),
                        timeSync(7)
                   }
    MAX-ACCESS     read-only
    STATUS         current
    DESCRIPTION
        "Provides details for tests that were aborted.
        Multiple bits may be set to convey test status."

    ::= { slaMonitorRtpResultsEntry 18 }

--
-- Notifications Section
--

slaMonitorAgentExceptionDetected NOTIFICATION-TYPE
    STATUS         current
    DESCRIPTION
            "Indicates that an exception event that impacts
            the local SLA Monitor agent has been detected."

    ::= { slaMonitorMibNotifications 1 }

--
-- Conformance Section
--

slaMonitorMibCompliances
                OBJECT IDENTIFIER ::= { slaMonitorMibConformance 1 }
slaMonitorMibGroups
                OBJECT IDENTIFIER ::= { slaMonitorMibConformance 2 }

slaMonitorMibCompliance MODULE-COMPLIANCE
    STATUS  current
    DESCRIPTION
            "Describes the requirements for conformance to the
             Avaya Networks SLA Monitor Agent MIB."

    MODULE  -- this module
    MANDATORY-GROUPS { slaMonitorAgentConfigGroup }

        OBJECT        slaMonitorAgentStatus  
        MIN-ACCESS    read-only
        DESCRIPTION  "Write access is not required."

        OBJECT        slaMonitorAgentCliAvailable  
        MIN-ACCESS    read-only
        DESCRIPTION  "Write access is not required."

        OBJECT        slaMonitorAgentCliTimeout  
        MIN-ACCESS    read-only
        DESCRIPTION  "Write access is not required."

        OBJECT        slaMonitorAgentCliTimeoutMode
        MIN-ACCESS    read-only
        DESCRIPTION  "Write access is not required."

        OBJECT        slaMonitorAgentConfiguredAgentAddrType
        MIN-ACCESS    read-only
        DESCRIPTION  "Write access is not required."

        OBJECT        slaMonitorAgentConfiguredAgentAddr
        MIN-ACCESS    read-only
        DESCRIPTION  "Write access is not required."

        OBJECT        slaMonitorAgentConfiguredAgentPort
        MIN-ACCESS    read-only
        DESCRIPTION  "Write access is not required."

        OBJECT        slaMonitorAgentConfiguredServerAddrType
        MIN-ACCESS    read-only
        DESCRIPTION  "Write access is not required."

        OBJECT        slaMonitorAgentConfiguredServerAddr
        MIN-ACCESS    read-only
        DESCRIPTION  "Write access is not required."

        OBJECT        slaMonitorAgentConfiguredServerPort
        MIN-ACCESS    read-only
        DESCRIPTION  "Write access is not required."

        OBJECT        slaMonitorAgentConfiguredAltServerAddrType
        MIN-ACCESS    read-only
        DESCRIPTION  "Write access is not required."

        OBJECT        slaMonitorAgentConfiguredAltServerAddr
        MIN-ACCESS    read-only
        DESCRIPTION  "Write access is not required."

        OBJECT        slaMonitorAgentConfiguredAltServerPort
        MIN-ACCESS    read-only
        DESCRIPTION  "Write access is not required."

        OBJECT        slaMonitorAgentConfiguredAgentToAgentPort
        MIN-ACCESS    read-only
        DESCRIPTION  "Write access is not required."

        OBJECT        slaMonitorAgentConfiguredAgentVrfName
        MIN-ACCESS    read-only
        DESCRIPTION  "Write access is not required."

        OBJECT        slaMonitorAgentSlaParameter
        MIN-ACCESS    read-only
        DESCRIPTION  "Write access is not required."

        OBJECT        slaMonitorAgentCertFileInstallAction
        MIN-ACCESS    read-only
        DESCRIPTION  "Write access is not required."

        OBJECT        slaMonitorAgentCertFile
        MIN-ACCESS    read-only
        DESCRIPTION  "Write access is not required."

        OBJECT        slaMonitorAgentServerBypass
        MIN-ACCESS    read-only
        DESCRIPTION  "Write access is not required."

        OBJECT        slaMonitorAgentRefuseServerTests
        MIN-ACCESS    read-only
        DESCRIPTION  "Write access is not required."

        GROUP   slaMonitorAgentNtrTestGroup
        DESCRIPTION
            "The slaMonitorAgentNtrTestGroup is optional."

        GROUP   slaMonitorAgentRtpTestGroup
        DESCRIPTION
            "The slaMonitorAgentRtpTestGroup is optional."

    ::= { slaMonitorMibCompliances 1 }

slaMonitorAgentConfigGroup OBJECT-GROUP
    OBJECTS {
             slaMonitorAgentStatus,
             slaMonitorAgentAddressType,
             slaMonitorAgentAddress,
             slaMonitorAgentPort,
             slaMonitorAgentRegisteredWithServer,
             slaMonitorAgentRegisteredServerAddrType,
             slaMonitorAgentRegisteredServerAddr,
             slaMonitorAgentRegisteredServerPort,
             slaMonitorAgentRegistrationTime,
             slaMonitorAgentCliAvailable,
             slaMonitorAgentCliTimeout,
             slaMonitorAgentCliTimeoutMode,
             slaMonitorAgentSupportedApps,
             slaMonitorAgentConfiguredAgentAddrType,
             slaMonitorAgentConfiguredAgentAddr,
             slaMonitorAgentConfiguredAgentPort,
             slaMonitorAgentConfiguredServerAddrType,
             slaMonitorAgentConfiguredServerAddr,
             slaMonitorAgentConfiguredServerPort,
             slaMonitorAgentConfiguredAltServerAddrType,
             slaMonitorAgentConfiguredAltServerAddr,
             slaMonitorAgentConfiguredAltServerPort,
             slaMonitorAgentToAgentPort,
             slaMonitorAgentConfiguredAgentToAgentPort,
             slaMonitorAgentEncryptionSupport,
             slaMonitorAgentConfiguredAgentVrfName,
             slaMonitorAgentSlaParameter,
             slaMonitorAgentCertFileInstallAction,
             slaMonitorAgentCertFile,
             slaMonitorAgentServerBypass,
             slaMonitorAgentRefuseServerTests
    }
    STATUS  current
    DESCRIPTION
            "Objects used for SLA Monitor Agent 
             configuration and monitoring."

    ::= { slaMonitorMibGroups 1 }

slaMonitorAgentNtrTestGroup OBJECT-GROUP
    OBJECTS {
             slaMonitorNtrCtrlTargetAddressType,
             slaMonitorNtrCtrlTargetAddress,
             slaMonitorNtrCtrlDscp,
             slaMonitorNtrCtrlAttempts,
             slaMonitorNtrCtrlPeriod,
             slaMonitorNtrCtrlAdminStatus,
             slaMonitorNtrCtrlLabel,
             slaMonitorNtrCtrlStorageType,
             slaMonitorNtrCtrlRowStatus,
             slaMonitorNtrResultsOperStatus,
             slaMonitorNtrResultsSrcAddressType,
             slaMonitorNtrResultsSrcAddress,
             slaMonitorNtrResultsDstAddressType,
             slaMonitorNtrResultsDstAddress,
             slaMonitorNtrResultsSrcPort,
             slaMonitorNtrResultsDstPort,
             slaMonitorNtrResultsDscp,
             slaMonitorNtrResultsTTL,
             slaMonitorNtrResultsCompletionData,
             slaMonitorNtrResultsCompletionSummary,
             slaMonitorNtrResultsAbortData,
             slaMonitorNtrResultsHopCount,
             slaMonitorNtrHopsTgtAddressType,
             slaMonitorNtrHopsTgtAddress,
             slaMonitorNtrHopsRtt,
             slaMonitorNtrHopsIngressDscp,
             slaMonitorNtrHopsEgressDscp
    }
    STATUS  current
    DESCRIPTION
            "Objects used for SLA Monitor Agent NTR
             test execution and results reporting."

    ::= { slaMonitorMibGroups 2 }

slaMonitorAgentRtpTestGroup OBJECT-GROUP
    OBJECTS {
             slaMonitorRtpCtrlTargetAddressType,
             slaMonitorRtpCtrlTargetAddress,
             slaMonitorRtpCtrlDscp,
             slaMonitorRtpCtrlTestPackets,
             slaMonitorRtpCtrlSyncPackets,
             slaMonitorRtpCtrlPeriod,
             slaMonitorRtpCtrlAdminStatus,
             slaMonitorRtpCtrlLabel,
             slaMonitorRtpCtrlStorageType,
             slaMonitorRtpCtrlRowStatus,
             slaMonitorRtpResultsOperStatus,
             slaMonitorRtpResultsSrcAddressType,
             slaMonitorRtpResultsSrcAddress,
             slaMonitorRtpResultsDstAddressType,
             slaMonitorRtpResultsDstAddress,
             slaMonitorRtpResultsSrcPort,
             slaMonitorRtpResultsDstPort,
             slaMonitorRtpResultsDscp,
             slaMonitorRtpResultsAverageDelay,
             slaMonitorRtpResultsMedianDelay,
             slaMonitorRtpResultsPacketLoss,
             slaMonitorRtpResultsOutOfOrderArrivals,
             slaMonitorRtpResultsJitterQuartile0,
             slaMonitorRtpResultsJitterQuartile1,
             slaMonitorRtpResultsJitterQuartile2,
             slaMonitorRtpResultsJitterQuartile3,
             slaMonitorRtpResultsJitterQuartile4,
             slaMonitorRtpResultsAbortData
    }
    STATUS  current
    DESCRIPTION
            "Objects used for SLA Monitor Agent RTP
             test execution and results reporting."

    ::= { slaMonitorMibGroups 3 }

END
