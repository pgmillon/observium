AVAYA-FABRIC-ATTACH-MIB DEFINITIONS ::= BEGIN

IMPORTS
    MODULE-IDENTITY, OBJECT-TYPE, Unsigned32, Integer32
            FROM SNMPv2-SMI
    MODULE-COMPLIANCE, OBJECT-GROUP
            FROM SNMPv2-CONF
    SnmpAdminString
            FROM SNMP-FRAMEWORK-MIB
    bayStackMibs
            FROM SYNOPTICS-ROOT-MIB
    RowStatus
            FROM SNMPv2-TC;

avayaFabricAttachMib MODULE-IDENTITY
    LAST-UPDATED "201404240000Z"     -- April 24, 2014
    ORGANIZATION "Avaya Networks, Inc."
    CONTACT-INFO "avaya.com"
    DESCRIPTION
        "This MIB module contains objects related to the Fabric Attach support."

    REVISION    "201404240000Z" -- April 24, 2014
    DESCRIPTION "Ver 6:  Updated FA element names in enumerations and 
                         object descriptions."

    REVISION    "201403030000Z" -- March 3, 2014
    DESCRIPTION "Ver 5:  Added FA Discovered Elements table."

    REVISION    "201401300000Z" -- January 30, 2014
    DESCRIPTION "Ver 4:  Added the ability to control host proxy operation.
                         Expanded and clarified FA element types."

    REVISION    "201311220000Z" -- November 22, 2013
    DESCRIPTION "Ver 3:  Added support for message authentication."

    REVISION    "201310110000Z" -- October 11, 2013
    DESCRIPTION "Ver 2:  Added avFabricAttachPortTable and avFabricAttachAutoAttachService.
                         Added RowStatus to IMPORTS."

    REVISION    "201308120000Z" -- August 12, 2013
    DESCRIPTION "Ver 1:  Initial version."

    ::= { bayStackMibs 46 }

avFabricAttachNotifications OBJECT IDENTIFIER ::= { avayaFabricAttachMib 0 }
avFabricAttachObjects       OBJECT IDENTIFIER ::= { avayaFabricAttachMib 1 }

--
-- Fabric Attach scalar attributes
--

avFabricAttachService OBJECT-TYPE
    SYNTAX         INTEGER {
                       enabled(1),
                       disabled(2)
                   }
    MAX-ACCESS     read-write
    STATUS         current
    DESCRIPTION
        "Exports the status of the Fabric 
        Attach service."

    ::= { avFabricAttachObjects 1 }

avFabricAttachElementType OBJECT-TYPE
    SYNTAX         INTEGER {
                       notSupported(1),
                       faServer(2),
                       faProxy(3),
                       faClientUntagged(4),
                       faClientTagged(5)
                   }
    MAX-ACCESS     read-write
    STATUS         current
    DESCRIPTION
        "Exports the Fabric Attach element type 
        indicating the services supported by 
        the system. May be read-only on platforms
        that only support a single element type."

    ::= { avFabricAttachObjects 2 }

avFabricAttachPrimaryServerId OBJECT-TYPE
    SYNTAX         OCTET STRING (SIZE (0..32))
    MAX-ACCESS     read-only
    STATUS         current
    DESCRIPTION
        "Exports primary server ID data on a FA
        Proxy if a primary server has been selected.
        A zero length string indicates that a
        primary server does not currently exist."

    ::= { avFabricAttachObjects 3 }

avFabricAttachPrimaryServerDescr OBJECT-TYPE
    SYNTAX         SnmpAdminString (SIZE (0..128))
    MAX-ACCESS     read-only
    STATUS         current
    DESCRIPTION
        "Exports a primary server description on a 
        FA Proxy if a primary server has been selected."

    ::= { avFabricAttachObjects 4 }

--
-- Fabric Attach I-SID/VLAN Assignment Table support        
--

avFabricAttachIsidVlanAsgnsTable OBJECT-TYPE
    SYNTAX      SEQUENCE OF AvFabricAttachIsidVlanAsgnsEntry
    MAX-ACCESS  not-accessible
    STATUS      current
    DESCRIPTION
        "This table contains the I-SID <--> VLAN assignments
        for the Fabric Attach application."

    ::= { avFabricAttachObjects 5 }

avFabricAttachIsidVlanAsgnsEntry OBJECT-TYPE
    SYNTAX      AvFabricAttachIsidVlanAsgnsEntry
    MAX-ACCESS  not-accessible
    STATUS      current
    DESCRIPTION
        "Information about the I-SID <--> VLAN assignments
        for the Fabric Attach application."

    INDEX { avFabricAttachIsidVlanAsgnsIfIndex, 
            avFabricAttachIsidVlanAsgnsIsid, 
            avFabricAttachIsidVlanAsgnsVlan }

    ::= { avFabricAttachIsidVlanAsgnsTable 1 }

AvFabricAttachIsidVlanAsgnsEntry ::= SEQUENCE {
    avFabricAttachIsidVlanAsgnsIfIndex    Integer32,
    avFabricAttachIsidVlanAsgnsIsid       Integer32,
    avFabricAttachIsidVlanAsgnsVlan       Integer32,
    avFabricAttachIsidVlanAsgnsState      INTEGER,
    avFabricAttachIsidVlanAsgnsRowStatus  RowStatus
}

avFabricAttachIsidVlanAsgnsIfIndex OBJECT-TYPE
    SYNTAX         Integer32 (0..65535)
    MAX-ACCESS     not-accessible
    STATUS         current
    DESCRIPTION
        "Interface identifier component of the I-SID <-> 
        VLAN assignment."

    ::= { avFabricAttachIsidVlanAsgnsEntry 1 }

avFabricAttachIsidVlanAsgnsIsid OBJECT-TYPE
    SYNTAX         Integer32 (0..16777215)
    MAX-ACCESS     not-accessible
    STATUS         current
    DESCRIPTION
        "I-SID component of the I-SID <-> VLAN 
        assignment."

    ::= { avFabricAttachIsidVlanAsgnsEntry 2 }

avFabricAttachIsidVlanAsgnsVlan OBJECT-TYPE
    SYNTAX         Integer32 (1..4094)
    MAX-ACCESS     not-accessible
    STATUS         current
    DESCRIPTION
        "VLAN ID component of the I-SID <-> VLAN 
        assignment."

    ::= { avFabricAttachIsidVlanAsgnsEntry 3 }

avFabricAttachIsidVlanAsgnsState OBJECT-TYPE
    SYNTAX         INTEGER {
                       other(1),
                       pending(2),
                       active(3),
                       rejected(4)
                   }
    MAX-ACCESS     read-only
    STATUS         current
    DESCRIPTION
        "The current state of the Fabric Attach
        I-SID <-> VLAN assignment."

    ::= { avFabricAttachIsidVlanAsgnsEntry 4 }

avFabricAttachIsidVlanAsgnsRowStatus OBJECT-TYPE
    SYNTAX         RowStatus
    MAX-ACCESS     read-create
    STATUS         current
    DESCRIPTION
        "This object allows entries to be created and deleted
        in the avFabricAttachIsidVlanAsgnsTable."

    ::= { avFabricAttachIsidVlanAsgnsEntry 5 }

--
-- Fabric Attach Port Table support
--

avFabricAttachPortTable OBJECT-TYPE
    SYNTAX      SEQUENCE OF AvFabricAttachPortEntry
    MAX-ACCESS  not-accessible
    STATUS      current
    DESCRIPTION
        "This table contains port-specific data
        for the Fabric Attach application."

    ::= { avFabricAttachObjects 6 }

avFabricAttachPortEntry OBJECT-TYPE
    SYNTAX      AvFabricAttachPortEntry
    MAX-ACCESS  not-accessible
    STATUS      current
    DESCRIPTION
        "Port-specific data related to the
        Fabric Attach application."

    INDEX { avFabricAttachPortIfIndex }

    ::= { avFabricAttachPortTable 1 }

AvFabricAttachPortEntry ::= SEQUENCE {
    avFabricAttachPortIfIndex    Integer32,
    avFabricAttachPortState      INTEGER,
    avFabricAttachPortRowStatus  RowStatus
}

avFabricAttachPortIfIndex OBJECT-TYPE
    SYNTAX         Integer32 (0..65535)
    MAX-ACCESS     not-accessible
    STATUS         current
    DESCRIPTION
        "Port (ifIndex) identifier attribute."

    ::= { avFabricAttachPortEntry 1 }

avFabricAttachPortState OBJECT-TYPE
    SYNTAX         INTEGER {
                       enabled(1),
                       disabled(2)
                   }
    MAX-ACCESS     read-create
    STATUS         current
    DESCRIPTION
        "The current port state from a Fabric Attach
        perspective. Indicates whether FA TLVs will
        be included in LLDPDUs generated on the port
        (enabled) or not (disabled)."

    ::= { avFabricAttachPortEntry 2 }

avFabricAttachPortRowStatus OBJECT-TYPE
    SYNTAX         RowStatus
    MAX-ACCESS     read-create
    STATUS         current
    DESCRIPTION
        "This object allows entries to be created, deleted
        and modified in the avFabricAttachPortTable, if the
        operation is supported by the agent."

    ::= { avFabricAttachPortEntry 3 }

avFabricAttachAutoAttachService OBJECT-TYPE
    SYNTAX         INTEGER {
                       enabled(1),
                       disabled(2)
                   }
    MAX-ACCESS     read-write
    STATUS         current
    DESCRIPTION
        "Controls the status of the Fabric 
        Attach Auto Attach service."

    ::= { avFabricAttachObjects 7 }

avFabricAttachMsgAuthStatus OBJECT-TYPE
    SYNTAX         INTEGER {
                       enabled(1),
                       disabled(2)
                   }
    MAX-ACCESS     read-write
    STATUS         current
    DESCRIPTION
        "Controls the current Fabric Attach 
        message authentication status."

    ::= { avFabricAttachObjects 8 }

avFabricAttachMsgAuthKey OBJECT-TYPE
    SYNTAX         OCTET STRING (SIZE(0..32))
    MAX-ACCESS     read-write
    STATUS         current
    DESCRIPTION
        "Provides access to the Fabric Attach 
        message authentication key. Can be used
        to establish a new key of length 1..32
        octets. Always returns a zero-length 
        string when queried."

    ::= { avFabricAttachObjects 9 }

avFabricAttachHostProxyStatus OBJECT-TYPE
    SYNTAX         INTEGER {
                       enabled(1),
                       disabled(2)
                   }
    MAX-ACCESS     read-write
    STATUS         current
    DESCRIPTION
        "Controls the current Fabric Attach 
        client proxy status. A FA Proxy provides
        proxy services to FA Clients only when
        client proxy support is enabled."

    ::= { avFabricAttachObjects 10 }

--
-- Fabric Attach Discovered Elements Table support
--

avFabricAttachDiscElemsTable OBJECT-TYPE
    SYNTAX      SEQUENCE OF AvFabricAttachDiscElemsEntry
    MAX-ACCESS  not-accessible
    STATUS      current
    DESCRIPTION
        "This table contains details about locally
        connected Fabric Attach elements that have
        been discovered."

    ::= { avFabricAttachObjects 11 }

avFabricAttachDiscElemsEntry OBJECT-TYPE
    SYNTAX      AvFabricAttachDiscElemsEntry
    MAX-ACCESS  not-accessible
    STATUS      current
    DESCRIPTION
        "Contains details about a locally connected
        Fabric Attach element."

    INDEX { avFabricAttachDiscElemsIfIndex }

    ::= { avFabricAttachDiscElemsTable 1 }

AvFabricAttachDiscElemsEntry ::= SEQUENCE {
    avFabricAttachDiscElemsIfIndex      Integer32,
    avFabricAttachDiscElemsElementType  INTEGER,
    avFabricAttachDiscElemsElementVlan  Integer32,
    avFabricAttachDiscElemsElementId    OCTET STRING
}

avFabricAttachDiscElemsIfIndex OBJECT-TYPE
    SYNTAX         Integer32 (0..65535)
    MAX-ACCESS     not-accessible
    STATUS         current
    DESCRIPTION
        "Identifies the interface through which the
        Fabric Attach element represented by this entry
        was discovered."

    ::= { avFabricAttachDiscElemsEntry 1 }

avFabricAttachDiscElemsElementType OBJECT-TYPE
    SYNTAX         INTEGER {
                       notSupported(1),
                       faServer(2),
                       faProxy(3),
                       faClientUntagged(4),
                       faClientTagged(5)
                   }
    MAX-ACCESS     read-only
    STATUS         current
    DESCRIPTION
        "Identifies the Fabric Attach element type
        as advertised through LLDP." 

    ::= { avFabricAttachDiscElemsEntry 2 }

avFabricAttachDiscElemsElementVlan OBJECT-TYPE
    SYNTAX         Integer32 (0..4095)
    MAX-ACCESS     read-only
    STATUS         current
    DESCRIPTION
        "Identifies the Fabric Attach element VLAN
        as advertised through LLDP." 

    ::= { avFabricAttachDiscElemsEntry 3 }

avFabricAttachDiscElemsElementId OBJECT-TYPE
    SYNTAX         OCTET STRING (SIZE (0..32))
    MAX-ACCESS     read-only
    STATUS         current
    DESCRIPTION
        "Exports the Chassis ID associated with the
        discovered Fabric Attach element as advertised
        through LLDP."

    ::= { avFabricAttachDiscElemsEntry 4 }

END
