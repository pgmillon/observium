-- COPYRIGHT NOTICE
-- Copyright (c) Radware Ltd. 2009
-- All rights reserved



ADMIN-ALTEON-AC-vADC-MIB DEFINITIONS ::= BEGIN
IMPORTS
    MODULE-IDENTITY, OBJECT-TYPE, Integer32, Counter32, Gauge32, TimeTicks, IpAddress
        FROM SNMPv2-SMI
    DisplayString, PhysAddress
        FROM SNMPv2-TC
    virt-admin
        FROM ALTEON-ROOT-MIB;

adminvADC MODULE-IDENTITY
    LAST-UPDATED "201006170000Z" --  17 June, 2010
    ORGANIZATION "Radware Ltd."
    CONTACT-INFO "Lobby 1 (Visitors) and Lobby 2 (Deliveries)
                  575 Corporate Drive
                  Mahwah, NJ 07430
                  support@radware.com"
    DESCRIPTION
        "The MIB module for the Alteon OS AdminContext configuration, statistics and
         information ."
    REVISION "201006170000Z" --  17 June, 2010
    DESCRIPTION
        "Added revision clause for SMIv2 compliance."
    ::= { virt-admin 1 }

adminvADCConfigs     OBJECT IDENTIFIER ::= { adminvADC 1 }
adminvADCInfo        OBJECT IDENTIFIER ::= { adminvADC 2 }
adminvADCBoot        OBJECT IDENTIFIER ::= { adminvADC 3 }
adminvADCStats       OBJECT IDENTIFIER ::= { adminvADC 4 }

vADCConfig        OBJECT IDENTIFIER ::= { adminvADCConfigs 1 }
vADCInfo          OBJECT IDENTIFIER ::= { adminvADCInfo 1 }
vADCBoot          OBJECT IDENTIFIER ::= { adminvADCBoot 1 }
vADCStat          OBJECT IDENTIFIER ::= { adminvADCStats 1 }


-- 
-- #START# vADC Configurations.
-- 
vADCMaxVADCId OBJECT-TYPE
    SYNTAX  Integer32 
    MAX-ACCESS  read-only
    STATUS  current
    DESCRIPTION
        "The maximum allowed vADC ID."
    ::= { vADCConfig 1 }

vADCMaxCU OBJECT-TYPE
    SYNTAX  Integer32 
    MAX-ACCESS  read-only
    STATUS  current
    DESCRIPTION
        "The maximum allowed Capacity Units."
    ::= { vADCConfig 2 }

-- vADC current config table for each vADC
vADCCurCfgTable OBJECT-TYPE
    SYNTAX  SEQUENCE OF VADCCurCfgTableEntry
    MAX-ACCESS  not-accessible
    STATUS  current
    DESCRIPTION
        "The table of vADC configuration."
    ::= { vADCConfig 3 }

vADCCurCfgTableEntry OBJECT-TYPE
    SYNTAX  VADCCurCfgTableEntry
    MAX-ACCESS  not-accessible
    STATUS  current
    DESCRIPTION
        "A row in the vADC configuration table."
    INDEX  { vADCCurCfgVADCId }
    ::= { vADCCurCfgTable 1 }

VADCCurCfgTableEntry ::= SEQUENCE {
    vADCCurCfgVADCId 		INTEGER,
    vADCCurCfgVlanId		OCTET STRING,
    vADCCurCfgName 		DisplayString,
    vADCCurCfgCU  		INTEGER,
    vADCCurCfgLimit 		INTEGER,
    vADCCurCfgState 		INTEGER,
    vADCCurCfgFeatGlobal	INTEGER,
    vADCCurCfgFeatBWM   	INTEGER,
    vADCCurCfgFeatITM   	INTEGER,
    vADCCurCfgFeatADOS   	INTEGER,
    vADCCurCfgFeatLLB   	INTEGER,
    vADCCurCfgSslLimit          INTEGER,
    vADCCurCfgCompLimit         INTEGER,
    vADCCurResetImageVersion 	DisplayString,       
    vADCCurSyncPeerSwitch	INTEGER
    }

vADCCurCfgVADCId OBJECT-TYPE
    SYNTAX  INTEGER
    MAX-ACCESS  read-only
    STATUS  current
    DESCRIPTION
        "The vADC identifier."
    ::= { vADCCurCfgTableEntry 1 }

vADCCurCfgVlanId OBJECT-TYPE
    SYNTAX  OCTET STRING
    MAX-ACCESS  read-only
    STATUS  current
    DESCRIPTION
        "The vlans list for vADCs. The vlans are
         presented in bitmap format. This string displays vlan number
         from 1 to 4090.

         in receiving order:

             OCTET 1  OCTET 2  .....
             xxxxxxxx xxxxxxxx .....
             ||    || |_ vlan 8

             ||    ||
             ||    ||___ vlan 7
             ||    |____ vlan 6
             ||      .    .   .
             ||_________ vlan 1
             |__________ Reserved

         where x : 1 - The represented vlan applied to the vADC.
                   0 - The represented vlan not applied to the vADC."
    ::= { vADCCurCfgTableEntry 2 }

vADCCurCfgName OBJECT-TYPE
    SYNTAX  DisplayString (SIZE(0..31))
    MAX-ACCESS  read-only
    STATUS  current
    DESCRIPTION
        "The vADC name."
    ::= { vADCCurCfgTableEntry 3 }

vADCCurCfgCU OBJECT-TYPE
    SYNTAX  INTEGER
    MAX-ACCESS  read-only
    STATUS  current
    DESCRIPTION
        "Default vADC Capacity Units."
    ::= { vADCCurCfgTableEntry 4 }

vADCCurCfgLimit OBJECT-TYPE
    SYNTAX  INTEGER  (0..20000)  
    MAX-ACCESS  read-only
    STATUS  current
    DESCRIPTION
        "The vADC Throughput value in Mbps."
    ::= { vADCCurCfgTableEntry 5 }

vADCCurCfgState	OBJECT-TYPE
    SYNTAX  INTEGER  {
	enabled(2),
	disabled(3)
	}
    MAX-ACCESS  read-only
    STATUS  current
    DESCRIPTION
        "Enable or disable a vADC"
    ::= { vADCCurCfgTableEntry 6 }

vADCCurCfgFeatGlobal OBJECT-TYPE
    SYNTAX  INTEGER  {
	enabled(2),
	disabled(3)
	}
    MAX-ACCESS  read-only
    STATUS  current
    DESCRIPTION
        "Enable or disable of global feature license for vADC."
    ::= { vADCCurCfgTableEntry 7 }

vADCCurCfgFeatBWM OBJECT-TYPE
    SYNTAX  INTEGER  {
	enabled(2),
	disabled(3)
	}
    MAX-ACCESS  read-only
    STATUS  current
    DESCRIPTION
        "Enable or disable of BWM feature license for vADC."
    ::= { vADCCurCfgTableEntry 8 }

vADCCurCfgFeatITM OBJECT-TYPE
    SYNTAX  INTEGER  {
	enabled(2),
	disabled(3)
	}
    MAX-ACCESS  read-only
    STATUS  current
    DESCRIPTION
        "Enable or disable of ITM feature license for vADC."
    ::= { vADCCurCfgTableEntry 9 }

vADCCurCfgFeatADOS OBJECT-TYPE
    SYNTAX  INTEGER  {
	enabled(2),
	disabled(3)
	}
    MAX-ACCESS  read-only
    STATUS  current
    DESCRIPTION
        "Enable or disable of ADoS feature license for vADC."
    ::= { vADCCurCfgTableEntry 10 }

vADCCurCfgFeatLLB OBJECT-TYPE
    SYNTAX  INTEGER  {
	enabled(2),
	disabled(3)
	}
    MAX-ACCESS  read-only
    STATUS  current
    DESCRIPTION
        "Enable or disable of LLB feature license for vADC."
    ::= { vADCCurCfgTableEntry 11 }

vADCCurCfgSslLimit OBJECT-TYPE
    SYNTAX  INTEGER  (0..60000)
    MAX-ACCESS read-only
    STATUS current
    DESCRIPTION
        "The maximum SSL throughput Limit allowed for vADC in CPSs.
         The SSL Throughput value should be in multiples of 10 CPSs blocks."
    ::= { vADCCurCfgTableEntry 12 }

vADCCurCfgCompLimit OBJECT-TYPE
    SYNTAX  INTEGER  (0..7500)
    MAX-ACCESS read-only
    STATUS current
    DESCRIPTION
        "The maximum compression throughput Limit allowed for vADC in Mbps.
         The compression Throughput value should be in multiples of 10 Mbps blocks."
    ::= { vADCCurCfgTableEntry 13 }

vADCCurResetImageVersion OBJECT-TYPE
    SYNTAX DisplayString (SIZE(0..128)) 
    MAX-ACCESS read-only
    STATUS current
    DESCRIPTION
        "Image version to use on next reset"
    ::= { vADCCurCfgTableEntry 14 }

vADCCurSyncPeerSwitch OBJECT-TYPE
    SYNTAX  INTEGER  (0..5)
    MAX-ACCESS  read-only
    STATUS  current
    DESCRIPTION
        "The ID of the Peer Switch (agSysPeerCurCfgIndex), with which the vADC in question is associated (values 1..5). Value 0 means no association."
    ::= { vADCCurCfgTableEntry 15 }


-- vADC current config table for each vADC
vADCNewCfgTable OBJECT-TYPE
    SYNTAX  SEQUENCE OF VADCNewCfgTableEntry
    MAX-ACCESS  not-accessible
    STATUS  current
    DESCRIPTION
        "The table of vADC configuration."
    ::= { vADCConfig 4 }

vADCNewCfgTableEntry OBJECT-TYPE
    SYNTAX  VADCNewCfgTableEntry
    MAX-ACCESS  not-accessible
    STATUS  current
    DESCRIPTION
        "A row in the vADC configuration table."
    INDEX  { vADCNewCfgVADCId }
    ::= { vADCNewCfgTable 1 }

VADCNewCfgTableEntry ::= SEQUENCE {
    vADCNewCfgVADCId 		INTEGER,
    vADCNewCfgVlanId		OCTET STRING,
    vADCNewCfgAddVlan		INTEGER,
    vADCNewCfgRemoveVlan	INTEGER,
    vADCNewCfgName 		DisplayString,
    vADCNewCfgCU  		INTEGER,
    vADCNewCfgLimit 		INTEGER,
    vADCNewCfgState 		INTEGER,
    vADCNewCfgDelete 		INTEGER,
    vADCNewCfgFeatGlobal        INTEGER,
    vADCNewCfgFeatBWM           INTEGER,
    vADCNewCfgFeatITM           INTEGER,
    vADCNewCfgFeatADOS          INTEGER,
    vADCNewCfgFeatLLB           INTEGER,
    vADCNewCfgSslLimit          INTEGER,
    vADCNewCfgCompLimit         INTEGER,
    vADCNewResetImageVersion    DisplayString,
    vADCNewSyncPeerSwitch	INTEGER
    }

vADCNewCfgVADCId OBJECT-TYPE
    SYNTAX  INTEGER
    MAX-ACCESS  read-only
    STATUS  current
    DESCRIPTION
        "The vADC identifier."
    ::= { vADCNewCfgTableEntry 1 }

vADCNewCfgVlanId OBJECT-TYPE
    SYNTAX  OCTET STRING
    MAX-ACCESS  read-only
    STATUS  current
    DESCRIPTION
        "The vlan list in the vADC in bitmap format."
    ::= { vADCNewCfgTableEntry 2 }

vADCNewCfgAddVlan OBJECT-TYPE
    SYNTAX  INTEGER  (1..4090)
    MAX-ACCESS  read-create
    STATUS  current
    DESCRIPTION
        "The vlan to be added to the specified vADC.  A '0' value is 
         returned when read."
    ::= { vADCNewCfgTableEntry 3 }

vADCNewCfgRemoveVlan OBJECT-TYPE
    SYNTAX  INTEGER  (1..4090)
    MAX-ACCESS  read-create
    STATUS  current
    DESCRIPTION
        "The vlan to be removed from the specified vADC.  A '0'
         value is returned when read."
    ::= { vADCNewCfgTableEntry 4 }

vADCNewCfgName OBJECT-TYPE
    SYNTAX  DisplayString (SIZE(0..31))
    MAX-ACCESS  read-create
    STATUS  current
    DESCRIPTION
        "The VADC name."
    ::= { vADCNewCfgTableEntry 5 }

vADCNewCfgCU OBJECT-TYPE
    SYNTAX  INTEGER
    MAX-ACCESS read-create
    STATUS current
    DESCRIPTION
        "The vADC Capacity Units."
    ::= { vADCNewCfgTableEntry 6 }

vADCNewCfgLimit OBJECT-TYPE
    SYNTAX  INTEGER  (0..20000)
    MAX-ACCESS read-create
    STATUS current
    DESCRIPTION
        "The throughput Limit allowed for vADC in Mbps."
    ::= { vADCNewCfgTableEntry 7 }

vADCNewCfgState	OBJECT-TYPE
    SYNTAX  INTEGER  {
	enabled(2),
	disabled(3)
	}
    MAX-ACCESS  read-create
    STATUS  current
    DESCRIPTION
        "Enable or disable a VADC"
    ::= { vADCNewCfgTableEntry 8 }

vADCNewCfgDelete OBJECT-TYPE
    SYNTAX  INTEGER  {
        other(1),
        delete(2)
        }
    MAX-ACCESS  read-create
    STATUS  current
    DESCRIPTION
        "This is an action object to create or delete a vADC.
         other(1) is returned always when read.
         The following values are writable: delete(2)...to delete a VADC"
    ::= { vADCNewCfgTableEntry 9 }

vADCNewCfgFeatGlobal OBJECT-TYPE
    SYNTAX  INTEGER  {
	enabled(2),
	disabled(3)
	}
    MAX-ACCESS  read-create
    STATUS  current
    DESCRIPTION
        "Enable or disable of Global feature license for vADC."
    ::= { vADCNewCfgTableEntry 10 }

vADCNewCfgFeatBWM OBJECT-TYPE
    SYNTAX  INTEGER  {
	enabled(2),
	disabled(3)
	}
    MAX-ACCESS  read-create
    STATUS  current
    DESCRIPTION
        "Enable or disable of BWM feature license for vADC."
    ::= { vADCNewCfgTableEntry 11 }

vADCNewCfgFeatITM OBJECT-TYPE
    SYNTAX  INTEGER  {
	enabled(2),
	disabled(3)
	}
    MAX-ACCESS  read-create
    STATUS  current
    DESCRIPTION
        "Enable or disable of ITM feature license for vADC."
    ::= { vADCNewCfgTableEntry 12 }

vADCNewCfgFeatADOS OBJECT-TYPE
    SYNTAX  INTEGER  {
	enabled(2),
	disabled(3)
	}
    MAX-ACCESS  read-create
    STATUS  current
    DESCRIPTION
        "Enable or disable of ADoS feature license for vADC."
    ::= { vADCNewCfgTableEntry 13 }

vADCNewCfgFeatLLB OBJECT-TYPE
    SYNTAX  INTEGER  {
	enabled(2),
	disabled(3)
	}
    MAX-ACCESS  read-create
    STATUS  current
    DESCRIPTION
        "Enable or disable of LLB feature license for vADC."
    ::= { vADCNewCfgTableEntry 14 }

vADCNewCfgSslLimit OBJECT-TYPE
    SYNTAX  INTEGER  (0..60000)
    MAX-ACCESS read-create
    STATUS current
    DESCRIPTION
        "The maximum SSL throughput Limit allowed for vADC in CPSs.
         The SSL Throughput value should be in multiples of 10 CPSs blocks."
    ::= { vADCNewCfgTableEntry 15 }

vADCNewCfgCompLimit OBJECT-TYPE
    SYNTAX  INTEGER  (0..7500)
    MAX-ACCESS read-create
    STATUS current
    DESCRIPTION
        "The maximum compression throughput Limit allowed for vADC in Mbps.
         The compression Throughput value should be in multiples of 10 Mbps blocks."
    ::= { vADCNewCfgTableEntry 16 }

vADCNewResetImageVersion OBJECT-TYPE
    SYNTAX DisplayString (SIZE(0..128)) 
    MAX-ACCESS read-write
    STATUS current
    DESCRIPTION
        "Image version to use on next reset"
    ::= { vADCNewCfgTableEntry 17 }

vADCNewSyncPeerSwitch OBJECT-TYPE
    SYNTAX  INTEGER  (0..5)
    MAX-ACCESS  read-write
    STATUS  current
    DESCRIPTION
        "The ID of the Peer Switch (agSysPeerNewCfgIndex), with which the vADC in question is associated (values 1..5). Value 0 means no association."
    ::= { vADCNewCfgTableEntry 18 }


-- System services current configuration menu for each vADC.
vADCCurCfgSysTable OBJECT-TYPE
    SYNTAX  SEQUENCE OF VADCCurCfgSysTableEntry
    MAX-ACCESS  not-accessible
    STATUS  current
    DESCRIPTION
        "The table of vADC System services configuration."
    ::= { vADCConfig 5 }

vADCCurCfgSysTableEntry OBJECT-TYPE
    SYNTAX  VADCCurCfgSysTableEntry
    MAX-ACCESS  not-accessible
    STATUS  current
    DESCRIPTION
        "A row in the vADC System services configuration table."
    INDEX  { vADCCurCfgSysVADCId }
    ::= { vADCCurCfgSysTable 1 }

VADCCurCfgSysTableEntry ::= SEQUENCE {
    vADCCurCfgSysMmgmtAddr	        IpAddress,
    vADCCurCfgSysMmgmtMask	        IpAddress,
    vADCCurCfgSysMmgmtGw	        IpAddress,
    vADCCurCfgSysMmgmtState	        INTEGER,
    vADCCurCfgSysPeerAddr	        IpAddress,
    vADCCurCfgSysPeerMask	        IpAddress,
    vADCCurCfgSysPeerGw 	        IpAddress,
    vADCCurCfgSysHttpsState	        INTEGER,
    vADCCurCfgSysSshState	        INTEGER,
    vADCCurCfgSysHttpState	        INTEGER,
    vADCCurCfgSysSnmpState	        INTEGER,
    vADCCurCfgSysSyslogState	        INTEGER,
    vADCCurCfgSysRadiusState	        INTEGER,
    vADCCurCfgSysTacacsState	        INTEGER,
    vADCCurCfgSysIdleState	        INTEGER,
    vADCCurCfgSysSmtpState	        INTEGER,
    vADCCurCfgSyslogDelegation          INTEGER,
    vADCCurCfgRadiusDelegation          INTEGER,
    vADCCurCfgTacacsDelegation          INTEGER,
    vADCCurCfgSmtpDelegation            INTEGER,
    vADCCurCfgSysMmgmtIpv6Addr          DisplayString,
    vADCCurCfgSysMmgmtIpv6PrefixLen     INTEGER,
    vADCCurCfgSysMmgmtIpv6Gateway       DisplayString,
    vADCCurCfgSysPeerIpv6Addr           DisplayString,
    vADCCurCfgSysPeerIpv6PrefixLen      INTEGER,
    vADCCurCfgSysPeerIpv6Gateway        DisplayString,
    vADCCurCfgSysTnetState              INTEGER,
    vADCCurCfgSysHaId                   INTEGER,
    vADCCurCfgSysPeerId                 INTEGER,
    vADCCurCfgSysVADCId                 INTEGER,
    vADCCurCfgIdleDelegation            INTEGER,
    vADCCurCfgSysMmgmtDelegation        INTEGER,
    vADCCurCfgSysPeerName               DisplayString
    }

vADCCurCfgSysMmgmtAddr OBJECT-TYPE
    SYNTAX  IpAddress
    MAX-ACCESS  read-only
    STATUS  current
    DESCRIPTION
        "The vADC system services management IP address."
    ::= { vADCCurCfgSysTableEntry 1 }

vADCCurCfgSysMmgmtMask OBJECT-TYPE
    SYNTAX  IpAddress
    MAX-ACCESS  read-only
    STATUS  current
    DESCRIPTION
        "The vADC system services management IP subnet mask address."
    ::= { vADCCurCfgSysTableEntry 2 }

vADCCurCfgSysMmgmtGw OBJECT-TYPE
    SYNTAX  IpAddress
    MAX-ACCESS  read-only
    STATUS  current
    DESCRIPTION
        "The vADC system services management IP gateway address."
    ::= { vADCCurCfgSysTableEntry 3 }

vADCCurCfgSysMmgmtState	OBJECT-TYPE
    SYNTAX  INTEGER  {
	enabled(2),
	disabled(3)
	}
    MAX-ACCESS  read-only
    STATUS  current
    DESCRIPTION
        "Enable or disable a vADC management system service."
    ::= { vADCCurCfgSysTableEntry 4 }

vADCCurCfgSysPeerAddr OBJECT-TYPE
    SYNTAX  IpAddress
    MAX-ACCESS  read-only
    STATUS  current
    DESCRIPTION
        "The vADC system services peer IP address."
    ::= { vADCCurCfgSysTableEntry 5 }

vADCCurCfgSysPeerMask OBJECT-TYPE
    SYNTAX  IpAddress
    MAX-ACCESS  read-only
    STATUS  current
    DESCRIPTION
        "The vADC system services peer IP subnet mask address."
    ::= { vADCCurCfgSysTableEntry 6 }

vADCCurCfgSysPeerGw OBJECT-TYPE
    SYNTAX  IpAddress
    MAX-ACCESS  read-only
    STATUS  current
    DESCRIPTION
        "The vADC system services peer IP gateway address."
    ::= { vADCCurCfgSysTableEntry 7 }

vADCCurCfgSysHttpsState OBJECT-TYPE
    SYNTAX  INTEGER  {
	enabled(2),
	disabled(3)
	}
    MAX-ACCESS  read-only
    STATUS  current
    DESCRIPTION
        "Enable or disable a vADC https system service."
    ::= { vADCCurCfgSysTableEntry 8 }

vADCCurCfgSysSshState OBJECT-TYPE
    SYNTAX  INTEGER  {
	enabled(2),
	disabled(3)
	}
    MAX-ACCESS  read-only
    STATUS  current
    DESCRIPTION
        "Enable or disable a vADC ssh system service."
    ::= { vADCCurCfgSysTableEntry 9 }

vADCCurCfgSysHttpState OBJECT-TYPE
    SYNTAX  INTEGER  {
	enabled(2),
	disabled(3)
	}
    MAX-ACCESS  read-only
    STATUS  current
    DESCRIPTION
        "Enable or disable a vADC http system service."
    ::= { vADCCurCfgSysTableEntry 10 }

vADCCurCfgSysSnmpState OBJECT-TYPE
    SYNTAX  INTEGER  {
	enabled(2),
	disabled(3)
	}
    MAX-ACCESS  read-only
    STATUS  current
    DESCRIPTION
        "Enable or disable a vADC snmp system service."
    ::= { vADCCurCfgSysTableEntry 11 }

vADCCurCfgSysSyslogState OBJECT-TYPE
    SYNTAX  INTEGER  {
	enabled(2),
	disabled(3)
	}
    MAX-ACCESS  read-only
    STATUS  current
    DESCRIPTION
        "Enable or disable a vADC syslog system service."
    ::= { vADCCurCfgSysTableEntry 12 }

vADCCurCfgSysRadiusState OBJECT-TYPE
    SYNTAX  INTEGER  {
	enabled(2),
	disabled(3)
	}
    MAX-ACCESS  read-only
    STATUS  current
    DESCRIPTION
        "Enable or disable a vADC radius system service."
    ::= { vADCCurCfgSysTableEntry 13 }

vADCCurCfgSysTacacsState OBJECT-TYPE
    SYNTAX  INTEGER  {
	enabled(2),
	disabled(3)
	}
    MAX-ACCESS  read-only
    STATUS  current
    DESCRIPTION
        "Enable or disable a vADC tacacs system service."
    ::= { vADCCurCfgSysTableEntry 14 }

vADCCurCfgSysIdleState	OBJECT-TYPE
    SYNTAX  INTEGER  {
	enabled(2),
	disabled(3)
	}
    MAX-ACCESS  read-only
    STATUS  current
    DESCRIPTION
        "Enable or disable a vADC idle system service."
    ::= { vADCCurCfgSysTableEntry 15 }

vADCCurCfgSysSmtpState	OBJECT-TYPE
    SYNTAX  INTEGER  {
	enabled(2),
	disabled(3)
	}
    MAX-ACCESS  read-only
    STATUS  current
    DESCRIPTION
        "Enable or disable a vADC smtp system service."
    ::= { vADCCurCfgSysTableEntry 16 }

vADCCurCfgSyslogDelegation OBJECT-TYPE
    SYNTAX  INTEGER  {
	enabled(2),
        disabled(3)
        }
    MAX-ACCESS  read-only
    STATUS  current
    DESCRIPTION
        "Enable or disable delegation for vADC syslog system service."
    ::= { vADCCurCfgSysTableEntry 17 }

vADCCurCfgRadiusDelegation OBJECT-TYPE
    SYNTAX  INTEGER  {
	enabled(2),
        disabled(3)
        }
    MAX-ACCESS  read-only
    STATUS  current
    DESCRIPTION
        "Enable or disable delegation for vADC radius system service."
    ::= { vADCCurCfgSysTableEntry 18 }

vADCCurCfgTacacsDelegation OBJECT-TYPE
    SYNTAX  INTEGER  {
	enabled(2),
        disabled(3)
        }
    MAX-ACCESS  read-only
    STATUS  current
    DESCRIPTION
        "Enable or disable delegation for vADC tacacs system service."
    ::= { vADCCurCfgSysTableEntry 19 }

vADCCurCfgSmtpDelegation OBJECT-TYPE
    SYNTAX  INTEGER  {
	enabled(2),
        disabled(3)
        } 
    MAX-ACCESS  read-only
    STATUS  current
    DESCRIPTION
        "Enable or disable delegation for vADC smtp system service."
    ::= { vADCCurCfgSysTableEntry 20 }

vADCCurCfgSysMmgmtIpv6Addr OBJECT-TYPE
    SYNTAX DisplayString (SIZE(0..40))
    MAX-ACCESS  read-only
    STATUS  current
    DESCRIPTION
        "The IPV6 address of the vADC management port.
        Address should be 16-byte haxadecimal colon notation.
        Valid IPv6 address should be in any of the following forms xxxx:xxxx:xxxx:xxxx:xxxx:xxxx:xxxx:xxxx
        or xxxx::xxxx:xxxx:xxxx:xxxx or ::xxxx "
    ::= { vADCCurCfgSysTableEntry 21 }

vADCCurCfgSysMmgmtIpv6PrefixLen OBJECT-TYPE
    SYNTAX  INTEGER  (0..128)
    MAX-ACCESS  read-only
    STATUS  current
    DESCRIPTION
        "The IPV6 prefix length of the vADC management port. "
    ::= { vADCCurCfgSysTableEntry 22 }

vADCCurCfgSysMmgmtIpv6Gateway OBJECT-TYPE
    SYNTAX DisplayString (SIZE(0..40))
    MAX-ACCESS  read-only
    STATUS  current
    DESCRIPTION
        "The IPV6 Gateway of the vADC management port.
        Address should be 16-byte haxadecimal colon notation.
        Valid IPv6 address should be in any of the following forms xxxx:xxxx:xxxx:xxxx:xxxx:xxxx:xxxx:xxxx
        or xxxx::xxxx:xxxx:xxxx:xxxx or ::xxxx "
    ::= { vADCCurCfgSysTableEntry 23 }

vADCCurCfgSysPeerIpv6Addr OBJECT-TYPE
    SYNTAX DisplayString (SIZE(0..40))
    MAX-ACCESS  read-only
    STATUS  current
    DESCRIPTION
        "The peer IPV6 Address of the vADC system services.
        Address should be 16-byte haxadecimal colon notation.
        Valid IPv6 address should be in any of the following forms xxxx:xxxx:xxxx:xxxx:xxxx:xxxx:xxxx:xxxx
        or xxxx::xxxx:xxxx:xxxx:xxxx or ::xxxx "
    ::= { vADCCurCfgSysTableEntry 24 }

vADCCurCfgSysPeerIpv6PrefixLen OBJECT-TYPE
    SYNTAX  INTEGER  (0..128)
    MAX-ACCESS  read-only
    STATUS  current
    DESCRIPTION
        "The vADC system services peer IPv6 prefix length. "
    ::= { vADCCurCfgSysTableEntry 25 }

vADCCurCfgSysPeerIpv6Gateway OBJECT-TYPE
    SYNTAX DisplayString (SIZE(0..40))
    MAX-ACCESS  read-only
    STATUS  current
    DESCRIPTION
        "The Peer IPV6 gateway of the vADC system services.
        Address should be 16-byte haxadecimal colon notation.
        Valid IPv6 address should be in any of the following forms xxxx:xxxx:xxxx:xxxx:xxxx:xxxx:xxxx:xxxx
        or xxxx::xxxx:xxxx:xxxx:xxxx or ::xxxx "
    ::= { vADCCurCfgSysTableEntry 26 }

vADCCurCfgSysTnetState OBJECT-TYPE
    SYNTAX  INTEGER  {
        enabled(2),
        disabled(3)
        }
    MAX-ACCESS  read-only
    STATUS  current
    DESCRIPTION
        "Enable or disable vADC Telnet access."
    ::= { vADCCurCfgSysTableEntry 27}

vADCCurCfgSysHaId OBJECT-TYPE
    SYNTAX  INTEGER  (0..64)
    MAX-ACCESS  read-only
    STATUS  current
    DESCRIPTION
        "HA ID for vADC"
    ::= { vADCCurCfgSysTableEntry 28 }

vADCCurCfgSysPeerId OBJECT-TYPE
    SYNTAX  INTEGER  (0..28)
    MAX-ACCESS  read-only
    STATUS  current
    DESCRIPTION
        "Peer ID for vADC"
    ::= { vADCCurCfgSysTableEntry 29 }

vADCCurCfgSysVADCId OBJECT-TYPE
    SYNTAX  INTEGER
    MAX-ACCESS  read-only
    STATUS  current
    DESCRIPTION
        "The vADC identifier."
    ::= { vADCCurCfgSysTableEntry 30 }

vADCCurCfgIdleDelegation OBJECT-TYPE
    SYNTAX  INTEGER  {
        enabled(2),
        disabled(3)
        }
    MAX-ACCESS  read-only
    STATUS  current
    DESCRIPTION
        "Enable or disable delegation for vADC idle timeout system service."
    ::= { vADCCurCfgSysTableEntry 31 }

vADCCurCfgSysMmgmtDelegation OBJECT-TYPE
    SYNTAX  INTEGER  {
        enabled(2),
        disabled(3)
        }
    MAX-ACCESS  read-only
    STATUS  current
    DESCRIPTION
        "Enable or disable delegation for vADC management system service."
    ::= { vADCCurCfgSysTableEntry 32 }

vADCCurCfgSysPeerName OBJECT-TYPE
    SYNTAX DisplayString (SIZE(0..31))
    MAX-ACCESS  read-only
    STATUS  current
    DESCRIPTION
        "The vADC system services peer Name."
    ::= { vADCCurCfgSysTableEntry 33 }

-- System services new configuration menu for each vADC
vADCNewCfgSysTable OBJECT-TYPE
    SYNTAX  SEQUENCE OF VADCNewCfgSysTableEntry
    MAX-ACCESS  not-accessible
    STATUS  current
    DESCRIPTION
        "The table of vADC System services configuration."
    ::= { vADCConfig 6 }

vADCNewCfgSysTableEntry OBJECT-TYPE
    SYNTAX  VADCNewCfgSysTableEntry
    MAX-ACCESS  not-accessible
    STATUS  current
    DESCRIPTION
        "A row in the vADC system services configuration table."
    INDEX  { vADCNewCfgSysVADCId }
    ::= { vADCNewCfgSysTable 1 }

VADCNewCfgSysTableEntry ::= SEQUENCE {
    vADCNewCfgSysMmgmtAddr	        IpAddress,
    vADCNewCfgSysMmgmtMask	        IpAddress,
    vADCNewCfgSysMmgmtGw	        IpAddress,
    vADCNewCfgSysMmgmtState	        INTEGER,
    vADCNewCfgSysPeerAddr	        IpAddress,
    vADCNewCfgSysPeerMask	        IpAddress,
    vADCNewCfgSysPeerGw 	        IpAddress,
    vADCNewCfgSysHttpsState	        INTEGER,
    vADCNewCfgSysSshState	        INTEGER,
    vADCNewCfgSysHttpState	        INTEGER,
    vADCNewCfgSysSnmpState	        INTEGER,
    vADCNewCfgSysSyslogState	        INTEGER,
    vADCNewCfgSysRadiusState	        INTEGER,
    vADCNewCfgSysTacacsState	        INTEGER,
    vADCNewCfgSysIdleState	        INTEGER,
    vADCNewCfgSysSmtpState	        INTEGER,
    vADCNewCfgSyslogDelegation          INTEGER,
    vADCNewCfgRadiusDelegation          INTEGER,
    vADCNewCfgTacacsDelegation          INTEGER,
    vADCNewCfgSmtpDelegation            INTEGER,
    vADCNewCfgSysMmgmtIpv6Addr          DisplayString,
    vADCNewCfgSysMmgmtIpv6PrefixLen     INTEGER,
    vADCNewCfgSysMmgmtIpv6Gateway       DisplayString,
    vADCNewCfgSysPeerIpv6Addr           DisplayString,
    vADCNewCfgSysPeerIpv6PrefixLen      INTEGER,
    vADCNewCfgSysPeerIpv6Gateway        DisplayString,
    vADCNewCfgSysTnetState              INTEGER,
    vADCNewCfgSysHaId                   INTEGER,
    vADCNewCfgSysPeerId                 INTEGER,
    vADCNewCfgSysVADCId                 INTEGER,
    vADCNewCfgIdleDelegation            INTEGER,
    vADCNewCfgSysMmgmtDelegation        INTEGER,
    vADCNewCfgSysPeerName               DisplayString
    }

vADCNewCfgSysMmgmtAddr OBJECT-TYPE
    SYNTAX  IpAddress
    MAX-ACCESS  read-create
    STATUS  current
    DESCRIPTION
        "The vADC system services management IP address."
    ::= { vADCNewCfgSysTableEntry 1 }

vADCNewCfgSysMmgmtMask OBJECT-TYPE
    SYNTAX  IpAddress
    MAX-ACCESS  read-create
    STATUS  current
    DESCRIPTION
        "The vADC system services management IP subnet mask address."
    ::= { vADCNewCfgSysTableEntry 2 }

vADCNewCfgSysMmgmtGw OBJECT-TYPE
    SYNTAX  IpAddress
    MAX-ACCESS  read-create
    STATUS  current
    DESCRIPTION
        "The vADC system services management IP gateway address."
    ::= { vADCNewCfgSysTableEntry 3 }

vADCNewCfgSysMmgmtState	OBJECT-TYPE
    SYNTAX  INTEGER  {
	enabled(2),
	disabled(3)
	}
    MAX-ACCESS  read-create
    STATUS  current
    DESCRIPTION
        "Enable or disable a vADC management system service."
    ::= { vADCNewCfgSysTableEntry 4 }

vADCNewCfgSysPeerAddr OBJECT-TYPE
    SYNTAX  IpAddress
    MAX-ACCESS  read-create
    STATUS  current
    DESCRIPTION
        "The vADC system services peer IP address."
    ::= { vADCNewCfgSysTableEntry 5 }

vADCNewCfgSysPeerMask OBJECT-TYPE
    SYNTAX  IpAddress
    MAX-ACCESS  read-create
    STATUS  current
    DESCRIPTION
        "The vADC system services peer IP subnet mask address."
    ::= { vADCNewCfgSysTableEntry 6 }

vADCNewCfgSysPeerGw OBJECT-TYPE
    SYNTAX  IpAddress
    MAX-ACCESS  read-create
    STATUS  current
    DESCRIPTION
        "The vADC system services peer IP gateway address."
    ::= { vADCNewCfgSysTableEntry 7 }

vADCNewCfgSysHttpsState OBJECT-TYPE
    SYNTAX  INTEGER  {
	enabled(2),
	disabled(3)
	}
    MAX-ACCESS  read-create
    STATUS  current
    DESCRIPTION
        "Enable or disable a vADC https system service."
    ::= { vADCNewCfgSysTableEntry 8 }

vADCNewCfgSysSshState OBJECT-TYPE
    SYNTAX  INTEGER  {
	enabled(2),
	disabled(3)
	}
    MAX-ACCESS  read-create
    STATUS  current
    DESCRIPTION
        "Enable or disable a vADC ssh system service."
    ::= { vADCNewCfgSysTableEntry 9 }

vADCNewCfgSysHttpState OBJECT-TYPE
    SYNTAX  INTEGER  {
	enabled(2),
	disabled(3)
	}
    MAX-ACCESS  read-create
    STATUS  current
    DESCRIPTION
        "Enable or disable a vADC http system service."
    ::= { vADCNewCfgSysTableEntry 10 }

vADCNewCfgSysSnmpState OBJECT-TYPE
    SYNTAX  INTEGER  {
	enabled(2),
	disabled(3)
	}
    MAX-ACCESS  read-create
    STATUS  current
    DESCRIPTION
        "Enable or disable a vADC snmp system service."
    ::= { vADCNewCfgSysTableEntry 11 }

vADCNewCfgSysSyslogState OBJECT-TYPE
    SYNTAX  INTEGER  {
	enabled(2),
	disabled(3)
	}
    MAX-ACCESS  read-create
    STATUS  current
    DESCRIPTION
        "Enable or disable a vADC syslog system service."
    ::= { vADCNewCfgSysTableEntry 12 }

vADCNewCfgSysRadiusState OBJECT-TYPE
    SYNTAX  INTEGER  {
	enabled(2),
	disabled(3)
	}
    MAX-ACCESS  read-create
    STATUS  current
    DESCRIPTION
        "Enable or disable a vADC radius system service."
    ::= { vADCNewCfgSysTableEntry 13 }

vADCNewCfgSysTacacsState OBJECT-TYPE
    SYNTAX  INTEGER  {
	enabled(2),
	disabled(3)
	}
    MAX-ACCESS  read-create
    STATUS  current
    DESCRIPTION
        "Enable or disable a vADC tacacs system service."
    ::= { vADCNewCfgSysTableEntry 14 }

vADCNewCfgSysIdleState	OBJECT-TYPE
    SYNTAX  INTEGER  {
	enabled(2),
	disabled(3)
	}
    MAX-ACCESS  read-create
    STATUS  current
    DESCRIPTION
        "Enable or disable a vADC idle system service."
    ::= { vADCNewCfgSysTableEntry 15 }

vADCNewCfgSysSmtpState	OBJECT-TYPE
    SYNTAX  INTEGER  {
	enabled(2),
	disabled(3)
	}
    MAX-ACCESS  read-create
    STATUS  current
    DESCRIPTION
        "Enable or disable a vADC smtp system service."
    ::= { vADCNewCfgSysTableEntry 16 }

vADCNewCfgSyslogDelegation OBJECT-TYPE
    SYNTAX  INTEGER  {
	enabled(2),
        disabled(3)
        }
    MAX-ACCESS  read-create
    STATUS  current
    DESCRIPTION
        "Enable or disable delegation for vADC syslog system service."
    ::= { vADCNewCfgSysTableEntry 17 }

vADCNewCfgRadiusDelegation OBJECT-TYPE
    SYNTAX  INTEGER  {
	enabled(2),
        disabled(3)
    }
    MAX-ACCESS  read-create
    STATUS  current
    DESCRIPTION
        "Enable or disable delegation for vADC radius system service."
    ::= { vADCNewCfgSysTableEntry 18 }

vADCNewCfgTacacsDelegation OBJECT-TYPE
    SYNTAX  INTEGER  {
	enabled(2),
        disabled(3)
        }
    MAX-ACCESS  read-create
    STATUS  current
    DESCRIPTION
        "Enable or disable delegation for vADC tacacs system service."
    ::= { vADCNewCfgSysTableEntry 19 }

vADCNewCfgSmtpDelegation OBJECT-TYPE
    SYNTAX  INTEGER  {
	enabled(2),
        disabled(3)
        }
    MAX-ACCESS  read-create
    STATUS  current
    DESCRIPTION
        "Enable or disable delegation for vADC smtp system service."
    ::= { vADCNewCfgSysTableEntry 20 }

vADCNewCfgSysMmgmtIpv6Addr OBJECT-TYPE
    SYNTAX DisplayString (SIZE(0..40))
    MAX-ACCESS  read-create
    STATUS  current
    DESCRIPTION
        "The IPV6 address of the vADC management port.
        Address should be 16-byte haxadecimal colon notation.
        Valid IPv6 address should be in any of the following forms xxxx:xxxx:xxxx:xxxx:xxxx:xxxx:xxxx:xxxx
        or xxxx::xxxx:xxxx:xxxx:xxxx or ::xxxx "
    ::= { vADCNewCfgSysTableEntry 21 }

vADCNewCfgSysMmgmtIpv6PrefixLen OBJECT-TYPE
    SYNTAX  INTEGER  (0..128)
    MAX-ACCESS  read-create
    STATUS  current
    DESCRIPTION
        "The IPV6 prefix length of the vADC management port. "
    ::= { vADCNewCfgSysTableEntry 22 }

vADCNewCfgSysMmgmtIpv6Gateway OBJECT-TYPE
    SYNTAX DisplayString (SIZE(0..40))
    MAX-ACCESS  read-create
    STATUS  current
    DESCRIPTION
        "The IPV6 Gateway of the vADC management port.
        Address should be 16-byte haxadecimal colon notation.
        Valid IPv6 address should be in any of the following forms xxxx:xxxx:xxxx:xxxx:xxxx:xxxx:xxxx:xxxx
        or xxxx::xxxx:xxxx:xxxx:xxxx or ::xxxx "
    ::= { vADCNewCfgSysTableEntry 23 }

vADCNewCfgSysPeerIpv6Addr OBJECT-TYPE
    SYNTAX DisplayString (SIZE(0..40))
    MAX-ACCESS  read-create
    STATUS  current
    DESCRIPTION
        "The peer IPV6 Address of the vADC system services.
        Addrvess should be 16-byte haxadecimal colon notation.
        Valid IPv6 address should be in any of the following forms xxxx:xxxx:xxxx:xxxx:xxxx:xxxx:xxxx:xxxx
        or xxxx::xxxx:xxxx:xxxx:xxxx or ::xxxx "
    ::= { vADCNewCfgSysTableEntry 24 }

vADCNewCfgSysPeerIpv6PrefixLen OBJECT-TYPE
    SYNTAX  INTEGER  (0..128)
    MAX-ACCESS  read-create
    STATUS  current
    DESCRIPTION
        "The vADC system services peer IPv6 prefix length. "
    ::= { vADCNewCfgSysTableEntry 25 }

vADCNewCfgSysPeerIpv6Gateway OBJECT-TYPE
    SYNTAX DisplayString (SIZE(0..40))
    MAX-ACCESS  read-create
    STATUS  current
    DESCRIPTION
        "The Peer IPV6 gateway of the vADC system services.
        Address should be 16-byte haxadecimal colon notation.
        Valid IPv6 address should be in any of the following forms xxxx:xxxx:xxxx:xxxx:xxxx:xxxx:xxxx:xxxx
        or xxxx::xxxx:xxxx:xxxx:xxxx or ::xxxx "
    ::= { vADCNewCfgSysTableEntry 26 }

vADCNewCfgSysTnetState OBJECT-TYPE
    SYNTAX  INTEGER  {
        enabled(2),
        disabled(3)
        }
    MAX-ACCESS  read-create
    STATUS  current
    DESCRIPTION
        "Enable or disable vADC Telnet access."
    ::= { vADCNewCfgSysTableEntry 27 }

vADCNewCfgSysHaId OBJECT-TYPE
    SYNTAX  INTEGER  (0..64)
    MAX-ACCESS  read-create
    STATUS  current
    DESCRIPTION
        "HA ID for vADC"
    ::= { vADCNewCfgSysTableEntry 28 }

vADCNewCfgSysPeerId  OBJECT-TYPE
    SYNTAX  INTEGER  (0..28)
    MAX-ACCESS  read-create
    STATUS  current
    DESCRIPTION
        "Peer ID for vADC"
    ::= { vADCNewCfgSysTableEntry 29 }

vADCNewCfgSysVADCId OBJECT-TYPE
    SYNTAX  INTEGER
    MAX-ACCESS  read-only
    STATUS  current
    DESCRIPTION
        "The vADC identifier."
    ::= { vADCNewCfgSysTableEntry 30 }

vADCNewCfgIdleDelegation OBJECT-TYPE
    SYNTAX  INTEGER  {
        enabled(2),
        disabled(3)
        }
    MAX-ACCESS  read-create
    STATUS  current
    DESCRIPTION
        "Enable or disable delegation for vADC idle timeout system service."
    ::= { vADCNewCfgSysTableEntry 31 }

vADCNewCfgSysMmgmtDelegation OBJECT-TYPE
    SYNTAX  INTEGER  {
        enabled(2),
        disabled(3)
        }
    MAX-ACCESS  read-create
    STATUS  current
    DESCRIPTION
        "Enable or disable delegation for vADC management system service."
    ::= { vADCNewCfgSysTableEntry 32 }

vADCNewCfgSysPeerName OBJECT-TYPE
    SYNTAX DisplayString (SIZE(0..31))
    MAX-ACCESS  read-create
    STATUS  current
    DESCRIPTION
        "The vADC system services peer Name."
    ::= { vADCNewCfgSysTableEntry 33 }

-- alloweded network table for vADC current config
vADCCurCfgNetTable OBJECT-TYPE
    SYNTAX  SEQUENCE OF VADCCurCfgNetTableEntry
    MAX-ACCESS  not-accessible
    STATUS  current
    DESCRIPTION
        "The table of vADC configuration."
    ::= { vADCConfig 7 }

vADCCurCfgNetTableEntry OBJECT-TYPE
    SYNTAX  VADCCurCfgNetTableEntry
    MAX-ACCESS  not-accessible
    STATUS  current
    DESCRIPTION
        "A row in the VADC allowed network configuration table."
    INDEX  { vADCCurCfgNetVADCId, vADCCurCfgNetId }
    ::= { vADCCurCfgNetTable 1 }

-- vADCCurCfgNetIPBegin holds the vADCCurCfgNetIPSubnetAddress if the vlan is not shared.
VADCCurCfgNetTableEntry ::= SEQUENCE {
    vADCCurCfgNetId             INTEGER,
    vADCCurCfgNetVlanId         INTEGER,
    vADCCurCfgNetIPver          INTEGER,
    vADCCurCfgNetIPBegin        IpAddress, 
    vADCCurCfgNetMask           IpAddress,
    vADCCurCfgNetIPEnd          IpAddress,
    vADCCurCfgNetIPv6Begin      DisplayString,
    vADCCurCfgNetPrefix         INTEGER,
    vADCCurCfgNetIPv6End        DisplayString,
    vADCCurCfgNetVADCId         INTEGER
    }

vADCCurCfgNetId OBJECT-TYPE
    SYNTAX  INTEGER  (1..1024)
    MAX-ACCESS  read-only
    STATUS  current
    DESCRIPTION
        "The vADC allowed network identifier."
    ::= { vADCCurCfgNetTableEntry 1 }

vADCCurCfgNetVlanId OBJECT-TYPE
    SYNTAX  INTEGER  (1..4096)
    MAX-ACCESS  read-only
    STATUS  current
    DESCRIPTION
        "The vADC allowed network vlan identifier."
    ::= { vADCCurCfgNetTableEntry 2 }

vADCCurCfgNetIPver OBJECT-TYPE
    SYNTAX  INTEGER  {
        ipv4(4),
        ipv6(6)
        }
    MAX-ACCESS  read-only
    STATUS  current
    DESCRIPTION
        "The vADC allowed network ip version."
    ::= { vADCCurCfgNetTableEntry 3 }

vADCCurCfgNetIPBegin OBJECT-TYPE
    SYNTAX  IpAddress
    MAX-ACCESS  read-only
    STATUS  current
    DESCRIPTION
        "The vADC allowed network subnet begining IP address for shared vlan."
    ::= { vADCCurCfgNetTableEntry 4 }

vADCCurCfgNetMask OBJECT-TYPE
    SYNTAX  IpAddress
    MAX-ACCESS  read-only
    STATUS  current
    DESCRIPTION
        "The vADC allowed network subnet address."
    ::= { vADCCurCfgNetTableEntry 5 }

vADCCurCfgNetIPEnd OBJECT-TYPE
    SYNTAX  IpAddress
    MAX-ACCESS  read-only
    STATUS  current
    DESCRIPTION
        "The vADC allowed network subnet end IP address for shared vlan."
    ::= { vADCCurCfgNetTableEntry 6 }

vADCCurCfgNetIPv6Begin OBJECT-TYPE
    SYNTAX   DisplayString (SIZE(0..40))
    MAX-ACCESS  read-only
    STATUS  current
    DESCRIPTION
        "The IPv6 begining address of the interface. Address should be 4-byte 
         haxadecimal colon notation.
         Valid IPv6 address should be in any of the following forms
           xxxx:xxxx:xxxx:xxxx:xxxx:xxxx:xxxx:xxxx or
           xxxx::xxxx:xxxx:xxxx:xxxx or ::xxxx"
    ::= { vADCCurCfgNetTableEntry 7 }

vADCCurCfgNetPrefix OBJECT-TYPE
    SYNTAX  INTEGER(1..128) 
    MAX-ACCESS  read-only
    STATUS  current
    DESCRIPTION
        "The prefix length associated with this IP address ."
    ::= { vADCCurCfgNetTableEntry 8 }

vADCCurCfgNetIPv6End OBJECT-TYPE
    SYNTAX   DisplayString (SIZE(0..40))
    MAX-ACCESS  read-only
    STATUS  current
    DESCRIPTION
        "The IPv6 end address of the interface. Address should be 4-byte 
         haxadecimal colon notation.
         Valid IPv6 address should be in any of the following forms
           xxxx:xxxx:xxxx:xxxx:xxxx:xxxx:xxxx:xxxx or
           xxxx::xxxx:xxxx:xxxx:xxxx or ::xxxx"
    ::= { vADCCurCfgNetTableEntry 9 }

vADCCurCfgNetVADCId OBJECT-TYPE
    SYNTAX  INTEGER
    MAX-ACCESS  read-only
    STATUS  current
    DESCRIPTION
        "The vADC identifier."
    ::= { vADCCurCfgNetTableEntry 10 }

-- New config for vADC Allowed network.
vADCNewCfgNetTable OBJECT-TYPE
    SYNTAX  SEQUENCE OF VADCNewCfgNetTableEntry
    MAX-ACCESS  not-accessible
    STATUS  current
    DESCRIPTION
        "The table of vADC allowed network new configuration."
    ::= { vADCConfig 8 }

vADCNewCfgNetTableEntry OBJECT-TYPE
    SYNTAX  VADCNewCfgNetTableEntry
    MAX-ACCESS  not-accessible
    STATUS  current
    DESCRIPTION
        "A row in the VADC allowed network configuration table."
    INDEX  { vADCNewCfgNetVADCId, vADCNewCfgNetId }
    ::= { vADCNewCfgNetTable 1 }

VADCNewCfgNetTableEntry ::= SEQUENCE {
    vADCNewCfgNetId             INTEGER,
    vADCNewCfgNetVlanId         INTEGER,
    vADCNewCfgNetIPver          INTEGER,
    vADCNewCfgNetIPBegin        IpAddress,
    vADCNewCfgNetMask           IpAddress,
    vADCNewCfgNetIPEnd          IpAddress,
    vADCNewCfgNetRemId          INTEGER,
    vADCNewCfgNetIPv6Begin      DisplayString,
    vADCNewCfgNetPrefix         INTEGER,
    vADCNewCfgNetIPv6End        DisplayString,
    vADCNewCfgNetVADCId         INTEGER
    }

vADCNewCfgNetId OBJECT-TYPE
    SYNTAX  INTEGER  (1..1024)
    MAX-ACCESS  read-only
    STATUS  current
    DESCRIPTION
        "The vADC allowed network identifier."
    ::= { vADCNewCfgNetTableEntry 1 }

vADCNewCfgNetVlanId OBJECT-TYPE
    SYNTAX  INTEGER  (1..4096)
    MAX-ACCESS  read-create
    STATUS  current
    DESCRIPTION
        "The new vADC allowed network vlan identifier."
    ::= { vADCNewCfgNetTableEntry 2 }

vADCNewCfgNetIPver OBJECT-TYPE
    SYNTAX  INTEGER  {
        ipv4(4),
        ipv6(6)
        }
    MAX-ACCESS  read-create
    STATUS  current
    DESCRIPTION
        "The new vADC allowed network ip version."
    ::= { vADCNewCfgNetTableEntry 3 }

vADCNewCfgNetIPBegin OBJECT-TYPE
    SYNTAX  IpAddress
    MAX-ACCESS  read-create
    STATUS  current
    DESCRIPTION
        "The vADC allowed network subnet begining IP address for shared vlan or 
         subnet IP address for non shared vlan."
    ::= { vADCNewCfgNetTableEntry 4 }

vADCNewCfgNetMask OBJECT-TYPE
    SYNTAX  IpAddress
    MAX-ACCESS  read-create
    STATUS  current
    DESCRIPTION
        "The vADC allowed network subnet address."
    ::= { vADCNewCfgNetTableEntry 5 }

vADCNewCfgNetIPEnd OBJECT-TYPE
    SYNTAX  IpAddress
    MAX-ACCESS  read-create
    STATUS  current
    DESCRIPTION
        "The vADC allowed network subnet end IP address for shared vlan."
    ::= { vADCNewCfgNetTableEntry 6 }

vADCNewCfgNetRemId OBJECT-TYPE
    SYNTAX  INTEGER  {
        other(1),
        delete(2)
        }
    MAX-ACCESS  read-create
    STATUS  current
    DESCRIPTION
        "This is an action object to create or delete a vADC allowed network.
         other(1) is returned always when read.
         The following values are writable: delete(2)...to delete a vADC allowed network"
    ::= { vADCNewCfgNetTableEntry 7 }

vADCNewCfgNetIPv6Begin OBJECT-TYPE
    SYNTAX   DisplayString (SIZE(0..40))
    MAX-ACCESS  read-create
    STATUS  current
    DESCRIPTION
        "The IPv6 begining address of the interface. Address should be 4-byte 
         haxadecimal colon notation.
         Valid IPv6 address should be in any of the following forms
           xxxx:xxxx:xxxx:xxxx:xxxx:xxxx:xxxx:xxxx or
           xxxx::xxxx:xxxx:xxxx:xxxx or ::xxxx"
    ::= { vADCNewCfgNetTableEntry 8 }

vADCNewCfgNetPrefix OBJECT-TYPE
    SYNTAX  INTEGER(1..128) 
    MAX-ACCESS  read-create
    STATUS  current
    DESCRIPTION
        "The prefix length associated with this IP address ."
    ::= { vADCNewCfgNetTableEntry 9 }

vADCNewCfgNetIPv6End OBJECT-TYPE
    SYNTAX   DisplayString (SIZE(0..40))
    MAX-ACCESS  read-create
    STATUS  current
    DESCRIPTION
        "The IPv6 end address of the interface. Address should be 4-byte 
         haxadecimal colon notation.
         Valid IPv6 address should be in any of the following forms
           xxxx:xxxx:xxxx:xxxx:xxxx:xxxx:xxxx:xxxx or
           xxxx::xxxx:xxxx:xxxx:xxxx or ::xxxx"
    ::= { vADCNewCfgNetTableEntry 10 }

vADCNewCfgNetVADCId OBJECT-TYPE
    SYNTAX  INTEGER
    MAX-ACCESS  read-only
    STATUS  current
    DESCRIPTION
        "The vADC identifier."
    ::= { vADCNewCfgNetTableEntry 11 }

-- Configuration Table for vADC Users.

vADCAccessUser         OBJECT IDENTIFIER ::= { vADCConfig 9 }
vADCAccessUid          OBJECT IDENTIFIER ::= { vADCAccessUser 1 }

-- Current configuration Table for vADC Users.

vADCUserCurCfgTable OBJECT-TYPE
    SYNTAX  SEQUENCE OF VADCUserCurCfgTableEntry
    MAX-ACCESS  not-accessible
    STATUS  current
    DESCRIPTION
        "vADC Current User configuration Table."
    ::= { vADCAccessUid 1 }

vADCUserCurCfgTableEntry OBJECT-TYPE
    SYNTAX  VADCUserCurCfgTableEntry
    MAX-ACCESS  not-accessible
    STATUS  current
    DESCRIPTION
        "A row in the VADC User Table."
    INDEX  { vADCUserCurCfgVADCId,  vADCUserCurCfgUId }
    ::= { vADCUserCurCfgTable 1 }

VADCUserCurCfgTableEntry ::= SEQUENCE {
    vADCUserCurCfgVADCId       Integer32,
    vADCUserCurCfgUId          Integer32,
    vADCUserCurCos             INTEGER,
    vADCUserCurCfgName         DisplayString,
    vADCUserCurCfgAdminPswd    DisplayString,
    vADCUserCurCfgPswd         DisplayString,
    vADCUserCurCfgConfPswd     DisplayString,
    vADCUserCurCfgBackdoor     INTEGER,
    vADCUserCurCfgCrtMng       INTEGER,
    vADCUserCurCfgState        INTEGER
    }

vADCUserCurCfgVADCId OBJECT-TYPE
    SYNTAX Integer32
    MAX-ACCESS  read-only
    STATUS  current
    DESCRIPTION
        "The VADC identifier."
    ::= { vADCUserCurCfgTableEntry 1 }

vADCUserCurCfgUId OBJECT-TYPE
    SYNTAX Integer32
    MAX-ACCESS  read-only
    STATUS  current
    DESCRIPTION
        "The User identifier."
    ::= { vADCUserCurCfgTableEntry 2 }

vADCUserCurCos OBJECT-TYPE
    SYNTAX  INTEGER {
        user(0),
        l3Oper(1),
        slboper(2),
        slbview(3),
        crtadmin(4),
        l4oper(5),
        oper(6),
        l3admin(7),
        slbadmin(8),
        l4admin(9),
        admin(10)
        }
    MAX-ACCESS  read-only
    STATUS  current
    DESCRIPTION
        "The user class of service."
    ::= { vADCUserCurCfgTableEntry 3 }

vADCUserCurCfgName OBJECT-TYPE
    SYNTAX  DisplayString (SIZE(0..8))
    MAX-ACCESS  read-only
    STATUS  current
    DESCRIPTION
        "The user name."
    ::= { vADCUserCurCfgTableEntry 4 }

vADCUserCurCfgAdminPswd OBJECT-TYPE
    SYNTAX  DisplayString (SIZE(0..128))
    MAX-ACCESS  read-only
    STATUS  current
    DESCRIPTION
        "The character string representing the admin password."
    ::= { vADCUserCurCfgTableEntry 5 }

vADCUserCurCfgPswd OBJECT-TYPE
    SYNTAX  DisplayString (SIZE(0..128))
    MAX-ACCESS  read-only
    STATUS  current
    DESCRIPTION
        "The character string representing the user password."
    ::= { vADCUserCurCfgTableEntry 6 }

vADCUserCurCfgConfPswd OBJECT-TYPE
    SYNTAX  DisplayString (SIZE(0..128))
    MAX-ACCESS  read-only
    STATUS  current
    DESCRIPTION
        "The character string is used to confirm the user password."
    ::= { vADCUserCurCfgTableEntry 7 }

vADCUserCurCfgBackdoor OBJECT-TYPE
    SYNTAX  INTEGER  {
        enabled(2),
        disabled(3)
        }
    MAX-ACCESS  read-only
    STATUS  current
    DESCRIPTION
        "Enable or disable vadc user backdoor access."
    ::= { vADCUserCurCfgTableEntry 8 }

vADCUserCurCfgCrtMng OBJECT-TYPE
    SYNTAX  INTEGER  {
        enabled(2),
        disabled(3)
        }
    MAX-ACCESS  read-only
    STATUS  current
    DESCRIPTION
        "Enable or disable certificate management permissions."
    ::= { vADCUserCurCfgTableEntry 9 }

vADCUserCurCfgState OBJECT-TYPE
    SYNTAX  INTEGER  {
        enabled(2),
        disabled(3)
        }
    MAX-ACCESS  read-only
    STATUS  current
    DESCRIPTION
        "Enable or disable a user."
    ::= { vADCUserCurCfgTableEntry 10 }

-- New configuration Table for vADC Users.

vADCUserNewCfgTable OBJECT-TYPE
    SYNTAX  SEQUENCE OF VADCUserNewCfgTableEntry
    MAX-ACCESS  not-accessible
    STATUS  current
    DESCRIPTION
        "vADC New User configuration Table."
    ::= { vADCAccessUid 2 }

vADCUserNewCfgTableEntry OBJECT-TYPE
    SYNTAX  VADCUserNewCfgTableEntry
    MAX-ACCESS  not-accessible
    STATUS  current
    DESCRIPTION
        "A row in the VADC User Table."
    INDEX  { vADCUserNewCfgVADCId,  vADCUserNewCfgUId }
    ::= { vADCUserNewCfgTable 1 }

VADCUserNewCfgTableEntry ::= SEQUENCE {
    vADCUserNewCfgVADCId       Integer32,
    vADCUserNewCfgUId          Integer32,
    vADCUserNewCos             INTEGER,
    vADCUserNewCfgName         DisplayString,
    vADCUserNewCfgAdminPswd    DisplayString,
    vADCUserNewCfgPswd         DisplayString,
    vADCUserNewCfgConfPswd     DisplayString,
    vADCUserNewCfgBackdoor     INTEGER,
    vADCUserNewCfgCrtMng       INTEGER,
    vADCUserNewCfgState        INTEGER,
    vADCUserNewCfgDelete       INTEGER
    }

vADCUserNewCfgVADCId OBJECT-TYPE
    SYNTAX Integer32
    MAX-ACCESS  read-write
    STATUS  current
    DESCRIPTION
        "The VADC identifier."
    ::= { vADCUserNewCfgTableEntry 1 }

vADCUserNewCfgUId OBJECT-TYPE
    SYNTAX Integer32
    MAX-ACCESS  read-write
    STATUS  current
    DESCRIPTION
        "The User identifier."
    ::= { vADCUserNewCfgTableEntry 2 }

vADCUserNewCos OBJECT-TYPE
    SYNTAX  INTEGER {
        user(0),
        l3oper(1),
        slboper(2),
        slbview(3),
        crtadmin(4),
        l4oper(5),
        oper(6),
        l3admin(7),
        slbadmin(8),
        l4admin(9),
        admin(10)
        }
    MAX-ACCESS  read-write
    STATUS  current
    DESCRIPTION
        "The user class of service."
    ::= { vADCUserNewCfgTableEntry 3 }

vADCUserNewCfgName OBJECT-TYPE
    SYNTAX  DisplayString (SIZE(0..8))
    MAX-ACCESS  read-write
    STATUS  current
    DESCRIPTION
        "The user name."
    ::= { vADCUserNewCfgTableEntry 4 }

vADCUserNewCfgAdminPswd OBJECT-TYPE
    SYNTAX  DisplayString (SIZE(0..128))
    MAX-ACCESS  read-write
    STATUS  current
    DESCRIPTION
        "The character string representing the admin password."
    ::= { vADCUserNewCfgTableEntry 5 }

vADCUserNewCfgPswd OBJECT-TYPE
    SYNTAX  DisplayString (SIZE(0..128))
    MAX-ACCESS  read-write
    STATUS  current
    DESCRIPTION
        "The character string representing the user password."
    ::= { vADCUserNewCfgTableEntry 6 }

vADCUserNewCfgConfPswd OBJECT-TYPE
    SYNTAX  DisplayString (SIZE(0..128))
    MAX-ACCESS  read-write
    STATUS  current
    DESCRIPTION
        "The character string is used to confirm the user password."
    ::= { vADCUserNewCfgTableEntry 7 }

vADCUserNewCfgBackdoor OBJECT-TYPE
    SYNTAX  INTEGER  {
        enabled(2),
        disabled(3)
        }
    MAX-ACCESS  read-write
    STATUS  current
    DESCRIPTION
        "Enable or disable vadc user backdoor access."
    ::= { vADCUserNewCfgTableEntry 8 }

vADCUserNewCfgCrtMng OBJECT-TYPE
    SYNTAX  INTEGER  {
        enabled(2),
        disabled(3)
        }
    MAX-ACCESS  read-write
    STATUS  current
    DESCRIPTION
        "Enable or disable certificate management permissions."
    ::= { vADCUserNewCfgTableEntry 9 }

vADCUserNewCfgState OBJECT-TYPE
    SYNTAX  INTEGER  {
        enabled(2),
        disabled(3)
        }
    MAX-ACCESS  read-write
    STATUS  current
    DESCRIPTION
        "Enable or disable a user."
    ::= { vADCUserNewCfgTableEntry 10 }

vADCUserNewCfgDelete OBJECT-TYPE
    SYNTAX  INTEGER  {
        other(1),
        delete(2)
        }
    MAX-ACCESS  read-create
    STATUS  current
    DESCRIPTION
        "This is an action object to create or delete a User.
         other(1) is returned always when read.
         The following values are writable: delete(2)...to delete a User"
    ::= { vADCUserNewCfgTableEntry 11 }

-- New configuration Table Ends for vADC Users.

vADCUsersPswdTable OBJECT-TYPE
    SYNTAX  SEQUENCE OF VADCUsersPswdTableEntry
    MAX-ACCESS  not-accessible
    STATUS  current
    DESCRIPTION
        "vADC Users Table."
    ::= { vADCAccessUser 2 }

vADCUsersPswdTableEntry OBJECT-TYPE
    SYNTAX  VADCUsersPswdTableEntry
    MAX-ACCESS  not-accessible
    STATUS  current
    DESCRIPTION
        "A row in the VADC User Table."
    INDEX  { vADCUsersVADCId }
    ::= { vADCUsersPswdTable 1 }

VADCUsersPswdTableEntry ::= SEQUENCE {
    vADCUsersVADCId                 Integer32,
    vADCAccessUsrPasswd             DisplayString,
    vADCAccessSlbOperPasswd         DisplayString,
    vADCAccessL4OperPasswd          DisplayString, 
    vADCAccessOperPasswd            DisplayString,
    vADCAccessSlbAdminPasswd        DisplayString,
    vADCAccessL4AdminPasswd         DisplayString,
    vADCAccessAdminPasswd           DisplayString,
    vADCAccessAdminNewPasswd        DisplayString,
    vADCAccessAdminConfNewPasswd    DisplayString
    }

vADCUsersVADCId OBJECT-TYPE
    SYNTAX Integer32
    MAX-ACCESS  read-write
    STATUS  current
    DESCRIPTION
        "The VADC identifier."
    ::= { vADCUsersPswdTableEntry 1 }

vADCAccessUsrPasswd OBJECT-TYPE
    SYNTAX  DisplayString (SIZE(0..128))
    MAX-ACCESS  read-write
    STATUS  current
    DESCRIPTION
        "The character string representing the user password."
    ::= { vADCUsersPswdTableEntry 2 }

vADCAccessSlbOperPasswd OBJECT-TYPE
    SYNTAX  DisplayString (SIZE(0..128))
    MAX-ACCESS  read-write
    STATUS  current
    DESCRIPTION
        "The character string representing the SLB operator(slboper)
         password."
    ::= { vADCUsersPswdTableEntry 3 }

vADCAccessL4OperPasswd OBJECT-TYPE
    SYNTAX  DisplayString (SIZE(0..128))
    MAX-ACCESS  read-write
    STATUS  current
    DESCRIPTION
        "The character string representing the L4 operator(l4oper)
        password."
    ::= { vADCUsersPswdTableEntry 4 }

vADCAccessOperPasswd OBJECT-TYPE
    SYNTAX  DisplayString (SIZE(0..128))
    MAX-ACCESS  read-write
    STATUS  current
    DESCRIPTION
        "The character string representing the Operator(oper) password."
    ::= { vADCUsersPswdTableEntry 5 }

vADCAccessSlbAdminPasswd OBJECT-TYPE
    SYNTAX  DisplayString (SIZE(0..128))
    MAX-ACCESS  read-write
    STATUS  current
    DESCRIPTION
        "The character string representing the Slb Admin (slbadmin)
         password."
    ::= { vADCUsersPswdTableEntry 6 }

vADCAccessL4AdminPasswd OBJECT-TYPE
    SYNTAX  DisplayString (SIZE(0..128))
    MAX-ACCESS  read-write
    STATUS  current
    DESCRIPTION
        "The character string representing the L4 Admin(l4admin)
         password."
    ::= { vADCUsersPswdTableEntry 7 }

vADCAccessAdminPasswd OBJECT-TYPE
    SYNTAX  DisplayString (SIZE(0..128))
    MAX-ACCESS  read-write
    STATUS  current
    DESCRIPTION
        "The character string representing the current Administrator(admin)
         password."
    ::= { vADCUsersPswdTableEntry 8 }

vADCAccessAdminNewPasswd OBJECT-TYPE
    SYNTAX  DisplayString (SIZE(0..128))
    MAX-ACCESS  read-write
    STATUS  current
    DESCRIPTION
        "The character string representing the Administrator(admin)
         New password."
    ::= { vADCUsersPswdTableEntry 9 }

vADCAccessAdminConfNewPasswd OBJECT-TYPE
    SYNTAX  DisplayString (SIZE(0..128))
    MAX-ACCESS  read-write
    STATUS  current
    DESCRIPTION
        "The character string is used to confirm the Administrator(admin)
         New password."
    ::= { vADCUsersPswdTableEntry 10 }

-- Configuration Table Ends for vADC Users.

-- 
-- #END# vADC Configurations. 
-- 

-- vADC Info Menu

vADCInfoAvailableCU OBJECT-TYPE
    SYNTAX  INTEGER  (1..28)
    MAX-ACCESS read-only
    STATUS current
    DESCRIPTION
        "The available vADC Capacity Units."
    ::= { vADCInfo 1 }

vADCInfoAvailableThruput OBJECT-TYPE
    SYNTAX  INTEGER  (1..20000)
    MAX-ACCESS read-only
    STATUS current
    DESCRIPTION
        "The available throughput in Mbps."
    ::= { vADCInfo 2 }

vADCInfoTable OBJECT-TYPE
    SYNTAX SEQUENCE OF VADCInfoTableEntry
    MAX-ACCESS not-accessible
    STATUS current
    DESCRIPTION
        "The table of vADC information."
    ::= { vADCInfo 3 }

vADCInfoTableEntry OBJECT-TYPE
    SYNTAX VADCInfoTableEntry
    MAX-ACCESS not-accessible
    STATUS current
    DESCRIPTION
        "Information about a particular vADC."
    INDEX { vADCInfoId }
    ::= { vADCInfoTable 1 }

VADCInfoTableEntry ::= SEQUENCE {
    vADCInfoId                INTEGER,
    vADCInfoName 	      DisplayString,
    vADCInfoStatus            INTEGER,
    vADCInfoVRRPStatus        INTEGER,
    vADCInfoCU                INTEGER,
    vADCInfoThroughput        INTEGER,
    vADCInfoLimit             INTEGER,
    vADCInfoSPcpu             INTEGER,
    vADCInfoMPcpu             INTEGER,
    vADCInfoCUMbit            Integer32,
    vADCInfoUpTime            DisplayString
    }

vADCInfoId OBJECT-TYPE
    SYNTAX  INTEGER  (1..28)
    MAX-ACCESS read-only
    STATUS current
    DESCRIPTION
        "The VADC identifier."
    ::= { vADCInfoTableEntry 1 }

vADCInfoName OBJECT-TYPE
    SYNTAX  DisplayString (SIZE(0..18))
    MAX-ACCESS  read-only
    STATUS  current
    DESCRIPTION
        "The vADC name."
    ::= { vADCInfoTableEntry 2 }

vADCInfoStatus OBJECT-TYPE
    SYNTAX  INTEGER  {
	disabled(0),
	init(1),
	running(2),
	down(3),
	stopping(4),
	restarting(5),
	querying(6)
	}
    MAX-ACCESS  read-only
    STATUS  current
    DESCRIPTION
        "vADC state information."
    ::= { vADCInfoTableEntry 3 }

vADCInfoVRRPStatus OBJECT-TYPE
    SYNTAX  INTEGER  {
	init(1),
	master(2),
	backup(3),
	holdoff(4),
	off(5),
	active(6),
	standby(7)
	}
    MAX-ACCESS  read-only
    STATUS  current
    DESCRIPTION
        "The vADC VRRP state information"
    ::= { vADCInfoTableEntry 4 }

vADCInfoCU OBJECT-TYPE
    SYNTAX  INTEGER  (1..28)
    MAX-ACCESS read-only
    STATUS current
    DESCRIPTION
        "The vADC Capacity Units."
    ::= { vADCInfoTableEntry 5 }

vADCInfoThroughput OBJECT-TYPE
    SYNTAX  INTEGER  (1..20000)
    MAX-ACCESS read-only
    STATUS current
    DESCRIPTION
        "The Maximum throughput allowed for vADC in Mbps."
    ::= { vADCInfoTableEntry 6 }

vADCInfoLimit OBJECT-TYPE
    SYNTAX  INTEGER  (0..20000)
    MAX-ACCESS read-only
    STATUS current
    DESCRIPTION
        "The throughput Limit for vADC in Mbps."
    ::= { vADCInfoTableEntry 7 }

vADCInfoSPcpu OBJECT-TYPE
    SYNTAX  INTEGER  (0..100)
    MAX-ACCESS read-only
    STATUS current
    DESCRIPTION
        "The percentage of SP CPU usage for vADC."
    ::= { vADCInfoTableEntry 8 }

vADCInfoMPcpu OBJECT-TYPE
    SYNTAX  INTEGER  (0..100)
    MAX-ACCESS read-only
    STATUS current
    DESCRIPTION
        "The percentage of MP CPU usage for vADC."
    ::= { vADCInfoTableEntry 9 }

vADCInfoCUMbit OBJECT-TYPE
    SYNTAX  Integer32
    MAX-ACCESS read-only
    STATUS current
    DESCRIPTION
        "The value of CU in Mbit."
    ::= { vADCInfoTableEntry 10 }

vADCInfoUpTime OBJECT-TYPE
    SYNTAX  DisplayString
    MAX-ACCESS read-only
    STATUS current
    DESCRIPTION
        "The vADC uptime information."
    ::= { vADCInfoTableEntry 11 }

vADCInfoConfigChangeTime OBJECT-TYPE
    SYNTAX  TimeTicks
    MAX-ACCESS  read-only
    STATUS  current
    DESCRIPTION
        "The value of sysUpTime at the last vADC configuration change."
    ::= { vADCInfo 4 }

-- Boot vADC information.
vADCBootTable OBJECT-TYPE
    SYNTAX SEQUENCE OF VADCBootTableEntry
    MAX-ACCESS not-accessible
    STATUS current
    DESCRIPTION
        "The table of vADC Boot Table."
    ::= { vADCBoot 1 }

vADCBootTableEntry OBJECT-TYPE
    SYNTAX VADCBootTableEntry
    MAX-ACCESS not-accessible
    STATUS current
    DESCRIPTION
        "Information about a particular vADC."
    INDEX { vADCBootVADCId }
    ::= { vADCBootTable 1 }

VADCBootTableEntry ::= SEQUENCE {
    vADCBootVADCId            INTEGER,
    vADCBootAction            INTEGER
    }

vADCBootVADCId OBJECT-TYPE
    SYNTAX  INTEGER  (1..28)
    MAX-ACCESS read-only
    STATUS current
    DESCRIPTION
        "The vADC identifier."
    ::= { vADCBootTableEntry 1 }

vADCBootAction OBJECT-TYPE
    SYNTAX  INTEGER {
            none(1),
            reset(2)
            }
    MAX-ACCESS  read-create
    STATUS  current
    DESCRIPTION
            "This object may contain the following values:
                 none(1)
                      This action does not reboot vADC.
                      Setting this object to none(1) has no effect.

                 reset(2)
                      This action will reboot vADC without apply/save
                      the unapplied/unsaved configuration changes.
	     "
    ::= { vADCBootTableEntry 2 }

-- vADC stats Accelaration Resources table for each vADC
vADCStatsAccelResourceTable OBJECT-TYPE
    SYNTAX  SEQUENCE OF VADCStatsAccelResourceTableEntry
    MAX-ACCESS  not-accessible
    STATUS  current
    DESCRIPTION
        "The table of vADC vADCStatsAccelResourceTableEntries."
    ::= { vADCStat 1 }

vADCStatsAccelResourceTableEntry OBJECT-TYPE
    SYNTAX VADCStatsAccelResourceTableEntry
    MAX-ACCESS  not-accessible
    STATUS  current
    DESCRIPTION
        "A row in the vADC accelarration resources statistics table."
    INDEX  { vADCIndex }
    ::= { vADCStatsAccelResourceTable 1 }

VADCStatsAccelResourceTableEntry ::= SEQUENCE {
    vADCIndex                 INTEGER,
    vADCName               DisplayString,
    vADCStatsCompLimit     INTEGER,
    vADCStatsCompUtil      INTEGER,
    vADCStatsSSLLimit      INTEGER,
    vADCStatsSSLUtil       INTEGER
    }

    vADCIndex OBJECT-TYPE
    SYNTAX  INTEGER
    MAX-ACCESS  read-only
    STATUS  current
    DESCRIPTION
        "The vADC identifier."
    ::= { vADCStatsAccelResourceTableEntry 1 }

    vADCName OBJECT-TYPE
    SYNTAX DisplayString
    MAX-ACCESS read-only
    STATUS current
    DESCRIPTION
        "The vADC name."
    ::= { vADCStatsAccelResourceTableEntry 2 }

    vADCStatsCompLimit OBJECT-TYPE
    SYNTAX INTEGER
    MAX-ACCESS read-only
    STATUS current
    DESCRIPTION
        " the compression limit allocated to vADC "
    ::= { vADCStatsAccelResourceTableEntry 3 }

    vADCStatsCompUtil OBJECT-TYPE
    SYNTAX INTEGER
    MAX-ACCESS read-only
    STATUS current
    DESCRIPTION
        "the compression limit utilized by vADC"
    ::= { vADCStatsAccelResourceTableEntry 4 }

    vADCStatsSSLLimit OBJECT-TYPE
    SYNTAX INTEGER
    MAX-ACCESS read-only
    STATUS current
    DESCRIPTION
        "the SSL limit allocated to vADC"
    ::= { vADCStatsAccelResourceTableEntry 5 }

    vADCStatsSSLUtil OBJECT-TYPE
    SYNTAX INTEGER
    MAX-ACCESS read-only
    STATUS current
    DESCRIPTION
        " the SSL limit utilized by vADC"
    ::= { vADCStatsAccelResourceTableEntry 6 }

-- vADC Memory stats for each vADC
vADCMemStatsTable OBJECT-TYPE
    SYNTAX  SEQUENCE OF VADCMemStatsTableEntry
    MAX-ACCESS  not-accessible
    STATUS  current
    DESCRIPTION
        "The table of vADC vADCMemStatsTableEntries."
    ::= { vADCStat 2 }

vADCMemStatsTableEntry OBJECT-TYPE
    SYNTAX VADCMemStatsTableEntry
    MAX-ACCESS  not-accessible
    STATUS  current
    DESCRIPTION
        "A row in the vADC Memory table."
    INDEX  { vADCMemStatsIndex }
    ::= { vADCMemStatsTable 1 }

VADCMemStatsTableEntry ::= SEQUENCE {
    vADCMemStatsIndex      	INTEGER,
    vADCMemStatsName       	DisplayString,
    vADCMemStatsCurrentMemory   INTEGER,
    vADCMemStatsHiWaterMark     INTEGER
    }

    vADCMemStatsIndex OBJECT-TYPE
    SYNTAX  INTEGER
    MAX-ACCESS  read-only
    STATUS  current
    DESCRIPTION
        "The vADC index."
    ::= { vADCMemStatsTableEntry 1 }

    vADCMemStatsName OBJECT-TYPE
    SYNTAX DisplayString
    MAX-ACCESS read-only
    STATUS current
    DESCRIPTION
        "The vADC name."
    ::= { vADCMemStatsTableEntry 2 }

    vADCMemStatsCurrentMemory OBJECT-TYPE
    SYNTAX INTEGER
    MAX-ACCESS read-only
    STATUS current
    DESCRIPTION
        " The current memory of vADC in KiloBytes."
    ::= { vADCMemStatsTableEntry 3 }

    vADCMemStatsHiWaterMark OBJECT-TYPE
    SYNTAX INTEGER
    MAX-ACCESS read-only
    STATUS current
    DESCRIPTION
        "The high watermark of vADC in KiloBytes."
    ::= { vADCMemStatsTableEntry 4 }

END
