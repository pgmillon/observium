AVAYA-WLAN-TC-MIB DEFINITIONS ::= BEGIN

IMPORTS
    MODULE-IDENTITY, Integer32, Unsigned32
        FROM SNMPv2-SMI
    TEXTUAL-CONVENTION
        FROM SNMPv2-TC
    SnmpAdminString
        FROM SNMP-FRAMEWORK-MIB
    avayaWlanMibs
        FROM SYNOPTICS-ROOT-MIB;

avayaWlanTcMib MODULE-IDENTITY
    LAST-UPDATED "201107230000Z" -- 23 July 2011
    ORGANIZATION "Avaya, Inc"
    CONTACT-INFO "Avaya, Inc"
    DESCRIPTION
        "Avaya WLAN Textual Conventions MIB

        Copyright 2010 - 2011 Avaya, Inc.
        All rights reserved.
        This Avaya SNMP Management Information Base Specification
        (Specification) embodies Avaya's confidential and proprietary
        intellectual property.  Avaya retains all title and ownership
        in the Specification, including any revisions.

        This Specification is supplied 'AS IS,' and Avaya makes no warranty,
        either express or implied, as to the use, operation, condition, or
        performance of the Specification."

    REVISION "201112150000Z" -- 15 Decemeber 2011
    DESCRIPTION "v5:  Following new TCs are added for MobSw notifications:
        AvWlanMobVlanRole
        AvWlanMobVlanState
        AvWlanSwitchNotifAuxLimitsMap
    "

    REVISION "201111210000Z" -- 21 November 2011
    DESCRIPTION "v4:  Following updates are done:
        Added more values in AvWlanSwitchModel.
        Added AvWlanLoadBalanceMetric."

    REVISION "201110110000Z" -- 11 October 2011
    DESCRIPTION "v3: Added AvWlanPacketCaptureFilterMask TC for packet capture module.
        Added captureProfile component to AvWlanConfigSyncComponents"

    REVISION "201107230000Z" -- 23 July 2011
    DESCRIPTION "v2: Added ap8120-O to AvWlanAPModel TC.
        Changed ap8120E to ap8120-E
        Added AvWlanRadioAntenna, AvWlanRadioAntennaOrNone
        Added AvWlanRadioExtCableOrNone
        Added AvWlanCountryCode
        Added AvWlanCpProfileUpdateFileTypeOrNone
        Added AvWlanCpProfileUpdateActionStatus
        Added more channels to AvWlanRadioChannel and AvWlanRadioChannelOrZero
        Added more components to AvWlanConfigSyncComponents"
 
    REVISION "201101070000Z" -- 07 January 2011
    DESCRIPTION "v2: Added ap8120E to AvWlanAPModel TC."

    REVISION "201006250000Z" -- 25 June 2010
    DESCRIPTION  "v1:  Initial version."

    ::= { avayaWlanMibs 1 }

-- ===========================================================================
-- Textual Conventions
-- ===========================================================================

AvWlanDomainRole ::= TEXTUAL-CONVENTION
    STATUS       current
    DESCRIPTION
        "This TC indicates the status of an MDC(Mobility Domain Controller)."
    SYNTAX       INTEGER {
                     activeMdc(1),
                     backupMdc(2),
                     peerWc(3),
                     standalone(4)
                 }

AvWlanControllerModel ::= TEXTUAL-CONVENTION
    STATUS       current
    DESCRIPTION
        "This TC indicates a Wireless Controller type."
    SYNTAX       INTEGER {
                     wc8180(1)
                 }

AvWlanSwitchModel ::= TEXTUAL-CONVENTION
    STATUS       current
    DESCRIPTION
        "This TC indicates a Mobility Switch type."
    SYNTAX       INTEGER {
                     wc8180(1),
                     wsp8180(2),
                     ers8800(3)
                 }

AvWlanNumberAPsPerWC ::= TEXTUAL-CONVENTION
    DISPLAY-HINT "d"
    STATUS       current
    DESCRIPTION
        "This TC indicates the range of APs possible per WC(Wireless Controller)."
    SYNTAX       Unsigned32 (0..512)

AvWlanAPModel ::= TEXTUAL-CONVENTION
    STATUS       current
    DESCRIPTION
        "This TC indicates the AP models that WC supports.
         - ap8120 : indoor AP8120
         - ap8120-E: indoor AP8120 with external antenna(s)
         - ap8120-O: outdoor AP8120 "
    SYNTAX       INTEGER {
                     ap8120(2),
                     ap8120-E(3),
                     ap8120-O(4)
                 }

AvWlanAPModelOrNone ::= TEXTUAL-CONVENTION
    STATUS       current
    DESCRIPTION
        "This TC indicates the AP models that WC supports.  
         The meaning of the special value none(255) must be specified by 
         any object using this TC in its SYNTAX clause."
    SYNTAX       INTEGER {
                     ap8120(2),
                     ap8120-E(3),
                     ap8120-O(4),
                     none(255)
                 }

AvWlanAPStatus ::= TEXTUAL-CONVENTION
    STATUS       current
    DESCRIPTION
        "This TC indicates the status of an AP."
    SYNTAX       INTEGER {
                     managed(1),
                     unknown(2),
                     standalone(3),
                     rogue(4),
                     knownForeign(5)
                 }

AvWlanRadioChannel ::= TEXTUAL-CONVENTION
    DISPLAY-HINT "d"
    STATUS       current
    DESCRIPTION
        "This TC indicates a wireless radio channel."
    SYNTAX       Integer32 (1..14|34|36|38|40|42|44|46|48|52|56|60|64|
                            100|104|108|112|116|120|124|128|132|136|140|
                            149|153|157|161|165|
                            184|188|192|196|200|204|208|212|216)

AvWlanRadioChannelOrZero ::= TEXTUAL-CONVENTION
    DISPLAY-HINT "d"
    STATUS       current
    DESCRIPTION
        "This TC indicates a wireless radio channel.  The special value
         0 must have its meaning described by any objects of this type."
    SYNTAX       Integer32 (0..14|34|36|38|40|42|44|46|48|52|56|60|64|
                            100|104|108|112|116|120|124|128|132|136|140|
                            149|153|157|161|165|
                            184|188|192|196|200|204|208|212|216)

AvWlanRadioPower ::= TEXTUAL-CONVENTION
    DISPLAY-HINT "d"
    STATUS       current
    DESCRIPTION
        "This TC indicates a wireless radio power setting."
    SYNTAX       Integer32 (0..100)

AvWlanRadioAntenna ::= TEXTUAL-CONVENTION
    STATUS       current
    DESCRIPTION
        "This TC indicates a type of antenna attached on a radio in AP.
            - wl81AT070E6: Avaya AP external antenna (70 degree)
            - wl81AT180E6: Avaya AP external antenna (180 degree)"
    SYNTAX       INTEGER {
                    wl81AT070E6(2),
                    wl81AT180E6(4)
                 }

AvWlanRadioAntennaOrNone ::= TEXTUAL-CONVENTION
    STATUS       current
    DESCRIPTION
        "This TC indicates a type of antenna attached on a radio in AP. 
            - wl81AT070E6: Avaya AP external antenna (70 degree)
            - wl81AT180E6: Avaya AP external antenna (180 degree)
         The meaning of the special value none(255) must be specified by any 
         object using this TC in its SYNTAX clause."
    SYNTAX       INTEGER {
                    wl81AT070E6(2),
                    wl81AT180E6(4),
                    none(255)
                 }

AvWlanRadioExtCable ::= TEXTUAL-CONVENTION
    STATUS       current
    DESCRIPTION
        "This TC indicates a type of extension cable used to attach an antenna
         for a radio in AP."
    SYNTAX       INTEGER {
                    ft3(1),
                    ft10(2)
                 }

AvWlanRadioExtCableOrNone ::= TEXTUAL-CONVENTION
    STATUS       current
    DESCRIPTION
        "This TC indicates a type of extension cable used to attach an antenna 
         for a radio in AP. The meaning of the special value none(255) must be 
         specified by any object using this TC in its SYNTAX clause."
    SYNTAX       INTEGER {
                    ft3(1),
                    ft10(2),
                    none(255)
                 }

AvWlanRadioOperationMode ::= TEXTUAL-CONVENTION
    STATUS       current
    DESCRIPTION
        "The operation mode of a radio with respect to access and WIDS/WIPS
         functionality.

         accessWids(1): The radio provides both access and WIDS functionality

         widsWips(2): The radio provides only WIDS functionality (no access).
         If both avWlanWidpsApDeauthenticationAttack and
         avWlanWidpsClientThreatMitigation in AVAYA-WLAN-WIDPS-MIB are enabled,
         it also provides WIPS functionality."
    SYNTAX       INTEGER {
                     accessWids(1),
                     widsWips(2)
                 }

AvWlanRadioInterface ::= TEXTUAL-CONVENTION
    DISPLAY-HINT "d"
    STATUS       current
    DESCRIPTION
        "Identifies a radio interface."
    SYNTAX       Integer32 (1..3)

AvWlanRadioInterfaceOrZero ::= TEXTUAL-CONVENTION
    DISPLAY-HINT "d"
    STATUS       current
    DESCRIPTION
        "Identifies a radio interface.  The meaning of the special value 0
         must be defined be any object using this TC in its SYNTAX clause."
    SYNTAX       Integer32 (0..3)

AvWlanDataRateSet ::= TEXTUAL-CONVENTION
    DISPLAY-HINT "1x:"
    STATUS       current
    DESCRIPTION
        "An object of this type represents a set of data rates in the range
        of 1 Mbps through 63.5 Mbps, in increments of 0.5 Mbps (500 Kbps).
        The value of an object of this type contains a string of bits, where
        each bit corresponds to a particular data rate.  Bits start with the
        high order bit of the first octet, representing 0.5 Mbps, and are
        contiguous representing increasing data rates in increments of
        0.5 Mbps.  For example, the following bits correspond to the following
        data rates:
             Octet Bit         Mbps
             0     0x80        1
             0     0x40        1.5
             0     0x20        2
             0     0x10        2.5
             0     0x08        3
             0     0x04        3.5
             0     0x02        4
             0     0x01        4.5
             1     0x80        5
             1     0x40        5.5
                  . . . .
             15    0x20        63.5
        If the bit corresponding to a particular data rate is set, that rate
        is considered to be a member of the set of data rates.  The bit
        position BP for a particular data rate DR can be found using the
        following formula:
            BP = (DR * 2) - 2
        The bit value corresponding to a particular data rate can be found
        using the following formula, where BP is the bit position as above,
        and O is the array of octets returned as the value of an object of
        this type:
            bitValue = (O[BP/8] >> (7 - (BP % 8))) & 0x01
        Similarly, the bit for a particular data rate can be set as follows:
            O[BP/8] |= 0x80 >> (BP % 8)
        And cleared as follows:
            O[BP/8] &= ~(0x80 >> (BP % 8))
        Any trailing octets whose value is 0x00 may be truncated from the value
        of an object of this type."
    SYNTAX       OCTET STRING (SIZE(0..16))

AvWlanChannelSet ::= TEXTUAL-CONVENTION
    DISPLAY-HINT "1x:"
    STATUS       current
    DESCRIPTION
        "An object of this type represents a set of wireless channels in the
        range of 1 through 255.  The value of an object of this type contains
        a string of bits, where each bit corresponds to a particular channel.
        Bits start with the high order bit of the first octet, representing
        channel 1, and are contiguous representing increasing channel numbers.
        For example, the following bits correspond to the following channels:
             Octet Bit         Channel
             0     0x80        1
             0     0x40        2
             0     0x20        3
             0     0x10        4
             0     0x08        5
             0     0x04        6
             0     0x02        7
             0     0x01        8
             1     0x80        9
             1     0x40        10
                  . . . .
             31    0x02        255
        If the bit corresponding to a particular channel is set, that channel
        is considered to be a member of the set of channels.  The bit value
        corresponding to a particular channel CH can be found using the
        following formula, where O is the array of octets returned as the
        value of an object of this type:
            bitValue = (O[(CH-1)/8] >> (7 - ((CH-1) % 8))) & 0x01
        Similarly, the bit for a particular channel can be set as follows:
            O[(CH-1)/8] |= 0x80 >> ((CH-1) % 8)
        And cleared as follows:
            O[(CH-1)/8] &= ~(0x80 >> ((CH-1) % 8))
        Any trailing octets whose value is 0x00 may be truncated from the value
        of an object of this type."
    SYNTAX       OCTET STRING (SIZE(0..32))

AvWlanRPTimeOfDay ::= TEXTUAL-CONVENTION
    DISPLAY-HINT "255t"
    STATUS       current
    DESCRIPTION
        "This TC indicates one or more ranges of time during which access
         to the network is allowed or denied.  The format can be
         any of the following:

           1.  An empty string which indicates access is always allowed.

           2.  The string 'never', which indicates access is always denied.

           3.  The string 'any', which indicates access is always allowed.

           4.  The string 'al', which indicates access is always allowed.

           5.  A comma separated list of one or more strings in the format
               '<day><hhmm-hhmm>', each of which indicates that access is
               allowed on the specified day during the specified range of
               times.  The valid strings for '<day>' are:
                   'mo' - Monday
                   'tu' - Tuesday
                   'we' - Wednesday
                   'th' - Thursday
                   'fr' - Friday
                   'sa' - Saturday
                   'su' - Sunday
                   'wk' - Indicates all days of the week
         Note that no whitespace characters or other special characters
         other than those noted above are allowed."
    SYNTAX       OCTET STRING (SIZE(0..255))

AvWlanOui ::= TEXTUAL-CONVENTION
    DISPLAY-HINT "1x:"
    STATUS        current
    DESCRIPTION 
        "24-bit Organizationally Unique Identifier. Information on OUIs can 
        be found in IEEE 802-2001 [802-2001] Clause 9."
    SYNTAX       OCTET STRING(SIZE(3))

AvWlanTspecSuppAccessCategory ::= TEXTUAL-CONVENTION
    STATUS       current
    DESCRIPTION
        "Access category (AC) used for TSPEC.  Only those ACs that 
         support mandatory admission control are listed here."
    SYNTAX       INTEGER {
                    voice(1),
                    video(2)
                 }

AvWlanConfigSyncComponents ::= TEXTUAL-CONVENTION
    STATUS       current
    DESCRIPTION
        "Enumerates WLAN configuration components that participate in the
         mobility domain configuration sync operation."
    SYNTAX       BITS {
                     apDatabase(0),
                     apProfile(1),
                     radioProfile(2),
                     networkProfile(3),
                     autoRF(4),
                     domainConfig(5),
                     captivePortal(6),
                     qosAcl(7),
                     qosDiffserv(8),
                     radiusGlobal(9),
                     radiusAuth(10),
                     radiusAcct(11),
                     mobilityVlan(12),
                     e911Config(13),
                     widsWips(14),
                     widsKnownAp(15),
                     securityUserDb(16),
                     securityMacDb(17),
                     radiusProfile(18),
                     radiusProfileServer(19),
                     crypto(20),
                     captureProfile(21)
                 }

AvWlanAPLicenseCapacity ::= TEXTUAL-CONVENTION
    STATUS       current
    DESCRIPTION
        "This object identifies the maximum capacity of AP license of 
         the controller. The capacity is either None, 16 Locked or Unlimited.
         When 'unlimited' is specified, the actual capacity is the validated
         and supported AP license count for that release.
         Please refer to the release notes for this count."
    SYNTAX       INTEGER {
                    none(1),
                    sixteenLocked(2),
                    unlimited(3)
                 }

AvWlanLogMsgLevel ::= TEXTUAL-CONVENTION
    STATUS       current
    DESCRIPTION
        "This object identifies the severity level of log messages that will be
         saved in volatile memory or sent to a remote syslog server when they
         occur"
    SYNTAX       INTEGER {
                    critical(1),
                    serious(2),
                    informational(3),
                    none(4)
                 }

AvWlanCountryCode ::= TEXTUAL-CONVENTION
    STATUS       current
    DESCRIPTION
        "This TC indicates the country of operation for WLAN." 
    SYNTAX       SnmpAdminString (SIZE(0|2))

AvWlanImageFileOrNone ::= TEXTUAL-CONVENTION
    STATUS       current
    DESCRIPTION
        "This TC specifies the type of the file to be updated, usually 
        used in 'Captive Portal Profile Customization' action.
         - all:        all customizable files
         - account:    accounting image file
         - brand:      branding image file
         - background: background image file
         - logout:     logout background image file
         - pkgfile:    package file"
     SYNTAX      INTEGER {
                    all(1),
                    account(2),
                    brand(3),
                    background(4),
                    logout(5),
                    pkgfile(6),
                    none(255)
                 }

AvWlanFileUpdateStatus ::= TEXTUAL-CONVENTION
    STATUS       current
    DESCRIPTION
        "This TC specifies the status of the file update action, usually 
        used in the 'Captive Portal Profile Customization Update Action'"
     SYNTAX      INTEGER {
                    none(1), 
                    success(2), 
                    transferFailed(3), 
                    inProgress(4), 
                    fileProcFailed(5), 
                    fileNotFound(6), 
                    internalError(7),
                    noSuchProfile(8),
                    noSuchLocale(9),
                    noSuchController(10),
                    maxFileSizeExceed(11),
                    maxProfileSizeExceed(12)
                 }

AvWlanPacketCaptureFilterMask ::= TEXTUAL-CONVENTION
    STATUS       current
    DESCRIPTION
        "Bit mask to represent the various filter criteria which can
         be applied for a remote packet capture event. Only five filters
         are supported in this release.
         Note that value 0 will be the MSB in the first octet and will be
         contiguosly numbered till the last bit in the lower octets. So when
         the number of bits is not a multiple of eight, the remaining bits 
         will be in the final octet (filled by zero's).

         Usage examples:
         --------------
         If we want to set the value for beacons(0), data(2) and mgmt(3), 
         the value can be set in any of the following format:

         10110000b or '10110000'B or 0xB0 or 'B0'h. 
        "
    SYNTAX   BITS {
                     beacons(0),
                     probes(1),
                     data(2),
                     mgmt(3),
                     control(4)
                  }

AvWlanLoadBalanceMetric ::= TEXTUAL-CONVENTION
    STATUS       current
    DESCRIPTION
        "This TC indicates a type of load balancing metric. This is mainly used only 
        in status MIBs" 
    SYNTAX       INTEGER {
                    preferred(1),
                    alternate(2),
                    leastLoad(3),
                    cbfs(4)
                 }

AvWlanMobVlanRole ::= TEXTUAL-CONVENTION
    STATUS       current
    DESCRIPTION
        "This TC indicates the role of mobility vlan in a mobility domain.
        The following roles are supported for a mobility VLAN:
         - server:        Mobilty VLAN server
         - staticClient:  Static Mobility VLAN
         - dynamicClient: Learnt dynamic Mobility VLAN
         - none:          No role
        "
    SYNTAX       INTEGER {
                     server(1),
                     staticClient(2),
                     dynamicClient(3),
                     none(4)
                 }

AvWlanMobVlanState ::= TEXTUAL-CONVENTION
    STATUS       current
    DESCRIPTION
        "This TC indicates the state of mapped mobility vlan in the switch."
    SYNTAX       INTEGER {
                     active(1),
                     inactive(2)
                 }

AvWlanSwitchNotifAuxLimitsMap ::= TEXTUAL-CONVENTION
    STATUS       current
    DESCRIPTION
        "This objects is included in the avWlanSwitchLimitsReached notification to
        indicate which limits have been reached.  The meaning of each bit in
        this object, and the additional objects included in the notification
        when each bit is set, are described below.  Objects corresponding
        to each bit will appear in the notification in the order of the
        bit values, i.e., the objects for bit 0, if set, will appear first,
        followed by the objects for bit 1, if set, and so on.  The objects
        listed below, when included in avWlanSwitchLimitsReached, indicate the
        last values that were added to or attempted to be added to the
        table/list specified by each bit.  The meaning of each object depends
        on the bit with which the object is associated in a generated
        notification, as described below: 

        VlanMapTableFull(0)
              The current number of vlan mappings has reached the max limit.

        TunnelTableFull(1)
              The current number of tunnels has reached the max limit.

        MulticastTableFull(2)
              The current number of multicast groups has reached the max limit.
              "
    SYNTAX       BITS {
                     vlanMapTableFull(0),
                     tunnelTableFull(1),
                     multicastTableFull(2)
                 }

END
