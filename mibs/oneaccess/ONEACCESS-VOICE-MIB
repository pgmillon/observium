--          *****************************
--          *                           *
--          *         ONEOS MIB         *
--          *                           *
--          *****************************
--
--          ONEOS_MIB_STD_V05.1.R005_E001
--
--          Creation date : 15/03/2003
--			Modification date : 10/12/2008
--          VoiceStatMos added
-- 				VoIP part added		
--
--         Add object for VOIP (H323 MGCP SIP protocols) 
--
--          Compatibility with ONEOS_V32
--


ONEACCESS-VOICE-MIB DEFINITIONS ::= BEGIN
  IMPORTS
    oacExpIMVoice, oacMIBModules
      FROM ONEACCESS-GLOBAL-REG
    Integer32, Unsigned32, OBJECT-TYPE, TimeTicks, MODULE-IDENTITY
      FROM SNMPv2-SMI
    TEXTUAL-CONVENTION, DisplayString
      FROM SNMPv2-TC
    MODULE-COMPLIANCE, OBJECT-GROUP
      FROM SNMPv2-CONF;

-- ----------------------------------------------------------------------------
  oacVoiceMIBModule MODULE-IDENTITY
-- ----------------------------------------------------------------------------
    LAST-UPDATED "201305030000Z"
    ORGANIZATION " OneAccess "
    CONTACT-INFO
      "Pascal KESTELOOT
        Postal: ONE ACCESS
                381 Avenue du Général de Gaulle
                92140 Clamart, France
		      FRANCE

        Tel: (+33) 01 41 87 70 00
        Fax: (+33) 01 41 87 74 00

          E-mail: pascal.kesteloot@oneaccess-net.com"

    DESCRIPTION
      "This MIB module describes Voice Managed objects."

--  Revision history

    REVISION    "201305030000Z"
    DESCRIPTION
        "Add oacVoiceSipGwMaxToRegisterEndpoints  see PR 56028"

   	REVISION    "201110270000Z"
      DESCRIPTION
        "Contact updated"

-- change the index for oacMIBModules from 801 to its corresponding value
	::= { oacMIBModules 801 }

-- ----------------------------------------------------------------------------
-- >> textual conventions
-- ----------------------------------------------------------------------------

VoiceFxsPortStatus ::= TEXTUAL-CONVENTION
  STATUS current
  DESCRIPTION
    "Available values for Fxs voice port status."
  SYNTAX INTEGER
  {
    undefined(0),
    blocked(1),
    unblocked(2)
  }

VoiceFxsPathStatus ::= TEXTUAL-CONVENTION
  STATUS current
  DESCRIPTION
    "Available values for Fxs voice path status."
  SYNTAX INTEGER
  {
    idle(0),
    established(1)
  }

VoicePriPhPortType ::= TEXTUAL-CONVENTION
  STATUS current
  DESCRIPTION
    "Physical port type for a pri voice port."
  SYNTAX INTEGER
  {
    e1(3),
    t1(4)
  }

VoicePriProtocol ::= TEXTUAL-CONVENTION
  STATUS current
  DESCRIPTION
    "Protocol types for a pri voice port."
  SYNTAX INTEGER
  {
    e1Pri(3),
    e1Cas(4),
    t1Pri(5),
    t1Cas(6),
    none(255)
  }

VoiceBriProtocol ::= TEXTUAL-CONVENTION
  STATUS current
  DESCRIPTION
    "Protocol types for a bri voice port."
  SYNTAX INTEGER
  {
    briNt(1),
    briTe(2)
  }

VoiceFxsProtocol ::= TEXTUAL-CONVENTION
  STATUS current
  DESCRIPTION
    "Protocol types for a fxs voice port."
  SYNTAX INTEGER
  {
    onHook(3),
    offHook(4),
    ringing(5)
  }

VoiceAcDeacState ::= TEXTUAL-CONVENTION
  STATUS current
  DESCRIPTION
    "Activated-deactivated state."
  SYNTAX INTEGER
  {
    activated(1),
    deactivated(2)
  }

VoiceUpDnState ::= TEXTUAL-CONVENTION
  STATUS current
  DESCRIPTION
    "Up-down state."
  SYNTAX INTEGER
  {
    up(1),
    down(2)
  }

VoiceBriPortStatus ::= TEXTUAL-CONVENTION
  STATUS current
  DESCRIPTION
    "Available status values for a bri voice port."
  SYNTAX INTEGER
  {
    undefined(0),
    blocked(1),
    unblocked(2),
    activated(3),
    deactivated(4)
  }

VoiceIOCoder ::= TEXTUAL-CONVENTION
  STATUS current
  DESCRIPTION
    "Voice coder type for input-output."
  SYNTAX INTEGER
  {
    none(0),
    g711-64(1),
    g726-32(2),
    g726-40(3),
    sid(4),
    ces(5),
    fax(6)
  }

VoiceBearerCap ::= TEXTUAL-CONVENTION
  STATUS current
  DESCRIPTION
    "Available bearer capability types."
  SYNTAX INTEGER
  {
    voice(0),
    voice-band(1),
    unrestricted(2)
  }

VoiceChnType ::= TEXTUAL-CONVENTION
  STATUS current
  DESCRIPTION
    "Channel type for a voice port."
  SYNTAX INTEGER
  {
    signalling(0),
    voice(1)
  }

VoipPortType ::= TEXTUAL-CONVENTION
	STATUS current
	DESCRIPTION
		"Values for VoIP Port type"
	SYNTAX INTEGER
	{
	  fxo(1),
	  fxs(2),
	  bri(3),
	  pri(4)
	}

IsdnProtocolDescriptor ::= TEXTUAL-CONVENTION
	STATUS current
	DESCRIPTION
		"Values for Isdn Protocols"
	SYNTAX INTEGER
	{
	  briNt(1),
	  briTe(2),
	  e1Pri(3),
	  e1Cas(4),
	  t1Pri(5),
	  t1Cas(6),
	  none(255)
	}

PortVoipCurrentState ::= TEXTUAL-CONVENTION
	STATUS current
	DESCRIPTION
		"Values for VoIP current state"
	SYNTAX INTEGER
	{
	undefined(0),
	activated(1),
	deactivated(2),
	onhook(3),
	offhook(4),
	ringing(5)
	}	
     
ConfigState ::= TEXTUAL-CONVENTION
	STATUS current
	DESCRIPTION
		"Values for Port configuration State"
	SYNTAX INTEGER
	{
	up(1),
	down(2)
	}
	
IsdnLayerStatus ::= TEXTUAL-CONVENTION
	STATUS current
	DESCRIPTION
		"Values for ISDN layer status"
	SYNTAX INTEGER
	{
	undefined(0),
	activated(1),
	deactivated(2)
	} 

OacVoipGatewayState ::= TEXTUAL-CONVENTION
	STATUS current
	DESCRIPTION
		"values of gateway state"
	SYNTAX INTEGER
	{
	down(0),
	up(1)
	}
	
OacVoipPriPhysicalType ::= TEXTUAL-CONVENTION
	STATUS current
	DESCRIPTION
		"values for PRI physical type"
	SYNTAX INTEGER
	{
	ptE1(0),
	ptT1(1),
	none(2)
	}
	
OacVoipGatewayStateReason ::= TEXTUAL-CONVENTION
	STATUS current
	DESCRIPTION
		"Values for VoIP gateway state reasons"
	SYNTAX INTEGER
	{
	unknown(0),
	shutdown(1),
	autoconfigDown(2),
	interfaceDown(3),
	invalidIpAddress(4)
	}  

OacVoipGatewayRegistrationState ::= TEXTUAL-CONVENTION
	STATUS current
	DESCRIPTION
		"Gateway registration state"
	SYNTAX INTEGER
	{
	unregistered(0),
	registered(1)
	}
	
OacH323GwRasBwControl ::= TEXTUAL-CONVENTION
	STATUS current
	DESCRIPTION
		"H323 Gw RAS Bandwidth Control is enabled or disabled"
	SYNTAX INTEGER
	{
	disable(0),
	enable(1)
	}
	
OacH323GwPortabilityStatus ::= TEXTUAL-CONVENTION
	STATUS current
	DESCRIPTION
		"H323 Gateway Portability Status"
	SYNTAX INTEGER
	{
	undefined(0),
	enable(1),
	inProgress(2),
	done(3)
	}
	
OacVoipMgcpGatewayConnectionState ::= TEXTUAL-CONVENTION
	STATUS current
	DESCRIPTION
		"MGCP Gateway connection state"
	SYNTAX INTEGER
	{
	disconnected(0),
	connected(1)
	}

OacVoiceSipGwPhoneState ::= TEXTUAL-CONVENTION
	STATUS current
	DESCRIPTION
		"SIP Gateway phone registration state"
	SYNTAX INTEGER
	{
	registering(0),
	registered(1)
	}

-- ----------------------------------------------------------------------------
-- imported objects
-- ----------------------------------------------------------------------------

oacExpIMVoiceStatistics OBJECT IDENTIFIER ::= { oacExpIMVoice 2 }

oacVoiceStatObjects OBJECT IDENTIFIER ::= { oacExpIMVoiceStatistics 1 }
oacVoiceStatNotifications OBJECT IDENTIFIER ::= { oacExpIMVoiceStatistics 2 }
oacVoiceStatConformance OBJECT IDENTIFIER ::= { oacExpIMVoiceStatistics 3 }

-- 1. global objects
oacVoiceStatGlobal OBJECT IDENTIFIER ::= { oacVoiceStatObjects 1 }

-- 2. oacVoiceStatBles
oacVoiceStatBles OBJECT IDENTIFIER ::= { oacVoiceStatObjects 2 }
-- 2.1 oacVoicePortBles
oacVoicePortBles OBJECT IDENTIFIER ::= { oacVoiceStatBles 1 }
-- 2.2 oacVoiceDialPeerBles
oacVoiceDialPeerBles OBJECT IDENTIFIER ::= { oacVoiceStatBles 2 }
-- 2.3 oacVoiceConnectionBles
oacVoiceConnectionBles OBJECT IDENTIFIER ::= { oacVoiceStatBles 3 }

-- 3. VoIP Stats
oacVoiceStatVoip OBJECT IDENTIFIER ::= { oacVoiceStatObjects 3}

-- ----------------------------------------------------------------------------
-- 1. global objects
-- ----------------------------------------------------------------------------

oacVoiceFxsPorts OBJECT-TYPE
  SYNTAX Integer32
  MAX-ACCESS read-only
  STATUS current
  DESCRIPTION
    "Total number of fxs voice ports."
  ::= { oacVoiceStatGlobal 1 }

oacVoiceBriPorts OBJECT-TYPE
  SYNTAX Integer32
  MAX-ACCESS read-only
  STATUS current
  DESCRIPTION
    "Total number of bri voice ports."
  ::= { oacVoiceStatGlobal 2 }

oacVoicePriPorts OBJECT-TYPE
  SYNTAX Integer32
  MAX-ACCESS read-only
  STATUS current
  DESCRIPTION
    "Total number of pri voice ports."
  ::= { oacVoiceStatGlobal 3 }

oacVoiceVmoaConnections OBJECT-TYPE
  SYNTAX Integer32
  MAX-ACCESS read-only
  STATUS current
  DESCRIPTION
    "Total number of vmoa connections."
  ::= { oacVoiceStatGlobal 4 }

oacVoiceVtoaConnections OBJECT-TYPE
  SYNTAX Integer32
  MAX-ACCESS read-only
  STATUS current
  DESCRIPTION
    "Total number of vtoa connections."
  ::= { oacVoiceStatGlobal 5 }

oacVoiceFxsDialPeers OBJECT-TYPE
  SYNTAX Integer32
  MAX-ACCESS read-only
  STATUS current
  DESCRIPTION
    "Total number of fxs dial peers."
  ::= { oacVoiceStatGlobal 6 }

oacVoiceBriDialPeers OBJECT-TYPE
  SYNTAX Integer32
  MAX-ACCESS read-only
  STATUS current
  DESCRIPTION
    "Total number of bri dial peers."
  ::= { oacVoiceStatGlobal 7 }

oacVoicePriDialPeers OBJECT-TYPE
  SYNTAX Integer32
  MAX-ACCESS read-only
  STATUS current
  DESCRIPTION
    "Total number of pri dial peers."
  ::= { oacVoiceStatGlobal 8 }

-- ----------------------------------------------------------------------------
-- >> voice port fxs
-- ----------------------------------------------------------------------------

-- ----------------------------------------------------------------------------
-- 2. oacVoiceVoicePortFxsTable

oacVoiceVoicePortFxsTable OBJECT-TYPE
  SYNTAX SEQUENCE OF OacVoiceVoicePortFxsEntry
  MAX-ACCESS not-accessible
  STATUS current
  DESCRIPTION
    "Fxs voice port table."
  ::= { oacVoicePortBles 1 }

oacVoiceVoicePortFxsEntry OBJECT-TYPE
  SYNTAX OacVoiceVoicePortFxsEntry
  MAX-ACCESS not-accessible
  STATUS current
  DESCRIPTION
    "Fxs voice port table entry."
  INDEX { oacVoiceVoicePortFxsIfIndex  }
  ::= { oacVoiceVoicePortFxsTable 1 }

OacVoiceVoicePortFxsEntry ::= SEQUENCE {
  oacVoiceVoicePortFxsIfIndex
    Integer32,
  oacVoiceVoicePortVoicePortFxs
    DisplayString,
  oacVoiceVoicePortFxsProtocolState
    VoiceFxsProtocol,
  oacVoiceVoicePortFxsOperState
    VoiceAcDeacState,
  oacVoiceVoicePortFxsAdminState
    VoiceAcDeacState,
  oacVoiceVoicePortFxsConfigState
    VoiceUpDnState,
  oacVoiceVoicePortFxsAttachedDialPeer
    Integer32,
  oacVoiceVoicePortFxsVoiceCommNb
    Unsigned32
}

oacVoiceVoicePortFxsIfIndex  OBJECT-TYPE
  SYNTAX Integer32 (0..7)
  MAX-ACCESS read-only
  STATUS current
  DESCRIPTION
    "Interface index for this fxs voice port."
  ::= { oacVoiceVoicePortFxsEntry 1 }

oacVoiceVoicePortVoicePortFxs OBJECT-TYPE
  SYNTAX DisplayString (SIZE (0..5))
  MAX-ACCESS read-only
  STATUS current
  DESCRIPTION
    "Module/Line description."
  ::= { oacVoiceVoicePortFxsEntry 2 }

oacVoiceVoicePortFxsProtocolState  OBJECT-TYPE
  SYNTAX VoiceFxsProtocol
  MAX-ACCESS read-only
  STATUS current
  DESCRIPTION
    "Protocol port status."
  ::= { oacVoiceVoicePortFxsEntry 3 }

oacVoiceVoicePortFxsOperState  OBJECT-TYPE
  SYNTAX VoiceAcDeacState
  MAX-ACCESS read-only
  STATUS current
  DESCRIPTION
    "Operator port status."
  ::= { oacVoiceVoicePortFxsEntry 4 }

oacVoiceVoicePortFxsAdminState  OBJECT-TYPE
  SYNTAX VoiceAcDeacState
  MAX-ACCESS read-only
  STATUS current
  DESCRIPTION
    "Admin port status."
  ::= { oacVoiceVoicePortFxsEntry 5 }

oacVoiceVoicePortFxsConfigState  OBJECT-TYPE
  SYNTAX VoiceUpDnState
  MAX-ACCESS read-only
  STATUS current
  DESCRIPTION
    "Config status."
  ::= { oacVoiceVoicePortFxsEntry 6 }

oacVoiceVoicePortFxsAttachedDialPeer  OBJECT-TYPE
  SYNTAX Integer32
  MAX-ACCESS read-only
  STATUS current
  DESCRIPTION
    "Attached vmoa dial peer."
  ::= { oacVoiceVoicePortFxsEntry 7 }

oacVoiceVoicePortFxsVoiceCommNb  OBJECT-TYPE
  SYNTAX Unsigned32
  MAX-ACCESS read-only
  STATUS current
  DESCRIPTION
    "Voice communication number."
  ::= { oacVoiceVoicePortFxsEntry 8 }

-- ----------------------------------------------------------------------------
-- ----------------------------------------------------------------------------
-- >> voice port bri
-- ----------------------------------------------------------------------------

-- ----------------------------------------------------------------------------
-- 3. oacVoiceVoicePortBriTable

oacVoiceVoicePortBriTable OBJECT-TYPE
  SYNTAX SEQUENCE OF OacVoiceVoicePortBriEntry
  MAX-ACCESS not-accessible
  STATUS current
  DESCRIPTION
    "Bri voice port table."
  ::= { oacVoicePortBles 2 }

oacVoiceVoicePortBriEntry OBJECT-TYPE
  SYNTAX OacVoiceVoicePortBriEntry
  MAX-ACCESS not-accessible
  STATUS current
  DESCRIPTION
    "Bri voice port table entry."
  INDEX { oacVoiceVoicePortBriIfIndex  }
  ::= { oacVoiceVoicePortBriTable 1 }

OacVoiceVoicePortBriEntry ::= SEQUENCE {
  oacVoiceVoicePortBriIfIndex
    Integer32,
  oacVoiceVoicePortVoicePortBri
    DisplayString,
  oacVoiceVoicePortBriProtocolDescriptor
    VoiceBriProtocol,
  oacVoiceVoicePortBriProtocolState
    VoiceAcDeacState,
  oacVoiceVoicePortBriOperState
    VoiceAcDeacState,
  oacVoiceVoicePortBriAdminState
    VoiceAcDeacState,
  oacVoiceVoicePortBriConfigState
    VoiceUpDnState,
  oacVoiceVoicePortBriLayer1
    VoiceAcDeacState,
  oacVoiceVoicePortBriAttachedDialPeer
    Integer32,
  oacVoiceVoicePortBriVoiceCommNb
    Unsigned32
}

oacVoiceVoicePortBriIfIndex  OBJECT-TYPE
  SYNTAX Integer32 (0..7)
  MAX-ACCESS read-only
  STATUS current
  DESCRIPTION
    "Interface index for this bri voice port."
  ::= { oacVoiceVoicePortBriEntry 1 }

oacVoiceVoicePortVoicePortBri OBJECT-TYPE
  SYNTAX DisplayString (SIZE (0..5))
  MAX-ACCESS read-only
  STATUS current
  DESCRIPTION
    "Module/Line description."
  ::= { oacVoiceVoicePortBriEntry 2 }

oacVoiceVoicePortBriProtocolDescriptor  OBJECT-TYPE
  SYNTAX VoiceBriProtocol
  MAX-ACCESS read-only
  STATUS current
  DESCRIPTION
    "Protocol interface description."
  ::= { oacVoiceVoicePortBriEntry 3 }

oacVoiceVoicePortBriProtocolState  OBJECT-TYPE
  SYNTAX VoiceAcDeacState
  MAX-ACCESS read-only
  STATUS current
  DESCRIPTION
    "ELCP port status."
  ::= { oacVoiceVoicePortBriEntry 4 }

oacVoiceVoicePortBriOperState  OBJECT-TYPE
  SYNTAX VoiceAcDeacState
  MAX-ACCESS read-only
  STATUS current
  DESCRIPTION
    "Operator port status."
  ::= { oacVoiceVoicePortBriEntry 5 }

oacVoiceVoicePortBriAdminState  OBJECT-TYPE
  SYNTAX VoiceAcDeacState
  MAX-ACCESS read-only
  STATUS current
  DESCRIPTION
    "Admin port status."
  ::= { oacVoiceVoicePortBriEntry 6 }

oacVoiceVoicePortBriConfigState  OBJECT-TYPE
  SYNTAX VoiceUpDnState
  MAX-ACCESS read-only
  STATUS current
  DESCRIPTION
    "Config port status."
  ::= { oacVoiceVoicePortBriEntry 7 }

oacVoiceVoicePortBriLayer1  OBJECT-TYPE
  SYNTAX VoiceAcDeacState
  MAX-ACCESS read-only
  STATUS current
  DESCRIPTION
    "Layer 1 status."
  ::= { oacVoiceVoicePortBriEntry 8 }

oacVoiceVoicePortBriAttachedDialPeer  OBJECT-TYPE
  SYNTAX Integer32
  MAX-ACCESS read-only
  STATUS current
  DESCRIPTION
    "Attached vmoa dial peer."
  ::= { oacVoiceVoicePortBriEntry 9 }

oacVoiceVoicePortBriVoiceCommNb  OBJECT-TYPE
  SYNTAX Unsigned32
  MAX-ACCESS read-only
  STATUS current
  DESCRIPTION
    "Voice communication number."
  ::= { oacVoiceVoicePortBriEntry 10 }

-- ----------------------------------------------------------------------------
-- ----------------------------------------------------------------------------
-- >> voice port pri
-- ----------------------------------------------------------------------------

-- ----------------------------------------------------------------------------
-- 4. oacVoiceVoicePortPriTable

oacVoiceVoicePortPriTable OBJECT-TYPE
  SYNTAX SEQUENCE OF OacVoiceVoicePortPriEntry
  MAX-ACCESS not-accessible
  STATUS current
  DESCRIPTION
    "Pri voice port table."
  ::= { oacVoicePortBles 3 }

oacVoiceVoicePortPriEntry OBJECT-TYPE
  SYNTAX OacVoiceVoicePortPriEntry
  MAX-ACCESS not-accessible
  STATUS current
  DESCRIPTION
    "Pri voice port table entry."
  INDEX { oacVoiceVoicePortPriIfIndex  }
  ::= { oacVoiceVoicePortPriTable 1 }

OacVoiceVoicePortPriEntry ::= SEQUENCE {
  oacVoiceVoicePortPriIfIndex
    Integer32,
  oacVoiceVoicePortVoicePortPri
    DisplayString,
  oacVoiceVoicePortPriPhysicalType
    VoicePriPhPortType,
  oacVoiceVoicePortPriProtocolDescriptor
    VoicePriProtocol,
  oacVoiceVoicePortPriProtocolState
    VoiceAcDeacState,
  oacVoiceVoicePortPriOperState
    VoiceAcDeacState,
  oacVoiceVoicePortPriAdminState
    VoiceAcDeacState,
  oacVoiceVoicePortPriConfigState
    VoiceUpDnState,
  oacVoiceVoicePortPriLayer1
    VoiceAcDeacState,
  oacVoiceVoicePortPriAttachedDialPeer
    Integer32,
  oacVoiceVoicePortPriVoiceCommNb
    Unsigned32,
  oacVoiceVoicePortPriAisOccur
    Unsigned32,
  oacVoiceVoicePortPriRdiOccur
    Unsigned32
}

oacVoiceVoicePortPriIfIndex OBJECT-TYPE
  SYNTAX Integer32 (0..7)
  MAX-ACCESS read-only
  STATUS current
  DESCRIPTION
    "Interface index for this pri voice port."
  ::= { oacVoiceVoicePortPriEntry 1 }

oacVoiceVoicePortVoicePortPri OBJECT-TYPE
  SYNTAX DisplayString (SIZE (0..5))
  MAX-ACCESS read-only
  STATUS current
  DESCRIPTION
    "Module/Line description."
  ::= { oacVoiceVoicePortPriEntry 2 }

oacVoiceVoicePortPriPhysicalType OBJECT-TYPE
  SYNTAX VoicePriPhPortType
  MAX-ACCESS read-only
  STATUS current
  DESCRIPTION
    "Physical interface description."
  ::= { oacVoiceVoicePortPriEntry 3 }

oacVoiceVoicePortPriProtocolDescriptor OBJECT-TYPE
  SYNTAX VoicePriProtocol
  MAX-ACCESS read-only
  STATUS current
  DESCRIPTION
    "Protocol interface description."
  ::= { oacVoiceVoicePortPriEntry 4 }

oacVoiceVoicePortPriProtocolState OBJECT-TYPE
  SYNTAX VoiceAcDeacState
  MAX-ACCESS read-only
  STATUS current
  DESCRIPTION
    "Elcp port status."
  ::= { oacVoiceVoicePortPriEntry 5 }

oacVoiceVoicePortPriOperState OBJECT-TYPE
  SYNTAX VoiceAcDeacState
  MAX-ACCESS read-only
  STATUS current
  DESCRIPTION
    "Operator port status."
  ::= { oacVoiceVoicePortPriEntry 6 }

oacVoiceVoicePortPriAdminState OBJECT-TYPE
  SYNTAX VoiceAcDeacState
  MAX-ACCESS read-only
  STATUS current
  DESCRIPTION
    "Admin port status."
  ::= { oacVoiceVoicePortPriEntry 7 }

oacVoiceVoicePortPriConfigState OBJECT-TYPE
  SYNTAX VoiceUpDnState
  MAX-ACCESS read-only
  STATUS current
  DESCRIPTION
    "Config status."
  ::= { oacVoiceVoicePortPriEntry 8 }

oacVoiceVoicePortPriLayer1 OBJECT-TYPE
  SYNTAX VoiceAcDeacState
  MAX-ACCESS read-only
  STATUS current
  DESCRIPTION
    "Layer 1 status."
  ::= { oacVoiceVoicePortPriEntry 9 }

oacVoiceVoicePortPriAttachedDialPeer OBJECT-TYPE
  SYNTAX Integer32
  MAX-ACCESS read-only
  STATUS current
  DESCRIPTION
    "Attached vmoa dial peer."
  ::= { oacVoiceVoicePortPriEntry 10 }

oacVoiceVoicePortPriVoiceCommNb OBJECT-TYPE
  SYNTAX Unsigned32
  MAX-ACCESS read-only
  STATUS current
  DESCRIPTION
    "CommNb of VoicePortPriVoice"
  ::= { oacVoiceVoicePortPriEntry 11 }

oacVoiceVoicePortPriAisOccur OBJECT-TYPE
  SYNTAX Unsigned32
  MAX-ACCESS read-only
  STATUS current
  DESCRIPTION
    "Occurance of VoicePortPri"
  ::= { oacVoiceVoicePortPriEntry 12 }

oacVoiceVoicePortPriRdiOccur OBJECT-TYPE
  SYNTAX Unsigned32
  MAX-ACCESS read-only
  STATUS current
  DESCRIPTION
    "occurance of Voice ports pririoty"
  ::= { oacVoiceVoicePortPriEntry 13 }

-- ----------------------------------------------------------------------------
-- ----------------------------------------------------------------------------
-- >> vmoa connection
-- ----------------------------------------------------------------------------

-- ----------------------------------------------------------------------------
-- 5. oacVoiceVmoaConnTable
--

oacVoiceVmoaConnTable OBJECT-TYPE
  SYNTAX SEQUENCE OF OacVoiceVmoaConnEntry
  MAX-ACCESS not-accessible
  STATUS current
  DESCRIPTION
    "Vmoa connection table."
  ::= { oacVoiceConnectionBles 1 }

oacVoiceVmoaConnEntry OBJECT-TYPE
  SYNTAX OacVoiceVmoaConnEntry
  MAX-ACCESS not-accessible
  STATUS current
  DESCRIPTION
    "Vmoa connection table entry."
  INDEX { oacVoiceVmoaConnConnection }
  ::= { oacVoiceVmoaConnTable 1 }

OacVoiceVmoaConnEntry ::= SEQUENCE {
  oacVoiceVmoaConnConnection
    Integer32,
  oacVoiceVmoaConnVpVc
    DisplayString,
  oacVoiceVmoaConnCurrentState
    VoiceUpDnState,
  oacVoiceVmoaConnConfigState
    VoiceUpDnState,
  oacVoiceVmoaConnAtmVcFailureOccurence
    Unsigned32,
  oacVoiceVmoaConnAtmVcTotalFailureDuration
    TimeTicks
}

oacVoiceVmoaConnConnection OBJECT-TYPE
  SYNTAX Integer32 (0..3)
  MAX-ACCESS read-only
  STATUS current
  DESCRIPTION
    "Index of this vmoa connection."
  ::= { oacVoiceVmoaConnEntry 1 }

oacVoiceVmoaConnVpVc OBJECT-TYPE
  SYNTAX DisplayString (SIZE (0..20))
  MAX-ACCESS read-only
  STATUS current
  DESCRIPTION
    "ATM PVC description"
  ::= { oacVoiceVmoaConnEntry 2 }

oacVoiceVmoaConnCurrentState OBJECT-TYPE
  SYNTAX VoiceUpDnState
  MAX-ACCESS read-only
  STATUS current
  DESCRIPTION
    "Operator status."
  ::= { oacVoiceVmoaConnEntry 3 }

oacVoiceVmoaConnConfigState OBJECT-TYPE
  SYNTAX VoiceUpDnState
  MAX-ACCESS read-only
  STATUS current
  DESCRIPTION
    "Admin description."
  ::= { oacVoiceVmoaConnEntry 4 }

oacVoiceVmoaConnAtmVcFailureOccurence OBJECT-TYPE
  SYNTAX Unsigned32
  MAX-ACCESS read-only
  STATUS current
  DESCRIPTION
    "Number of PVC failure occurrences."
  ::= { oacVoiceVmoaConnEntry 5 }

oacVoiceVmoaConnAtmVcTotalFailureDuration OBJECT-TYPE
  SYNTAX TimeTicks
  MAX-ACCESS read-only
  STATUS current
  DESCRIPTION
    "Duration of PVC failure."
  ::= { oacVoiceVmoaConnEntry 6 }

-- ----------------------------------------------------------------------------
-- 6. oacVoiceVmoaConnLesTable
--

oacVoiceVmoaConnLesTable OBJECT-TYPE
  SYNTAX SEQUENCE OF OacVoiceVmoaConnLesEntry
  MAX-ACCESS not-accessible
  STATUS current
  DESCRIPTION
    "Vmoa connection les table."
  ::= { oacVoiceConnectionBles 2 }

oacVoiceVmoaConnLesEntry OBJECT-TYPE
  SYNTAX OacVoiceVmoaConnLesEntry
  MAX-ACCESS not-accessible
  STATUS current
  DESCRIPTION
    "Vmoa connection les table entry."
  INDEX { oacVoiceVmoaConnConnection }
  ::= { oacVoiceVmoaConnLesTable 1 }

OacVoiceVmoaConnLesEntry ::= SEQUENCE {
  oacVoiceVmoaConnLesVoicePathNum
    Unsigned32,
  oacVoiceVmoaConnLesTotalCpIwfOriginated
    Unsigned32,
  oacVoiceVmoaConnLesTotalCoIwfOriginated
    Unsigned32,
  oacVoiceVmoaConnLesCpIwfRestartNum
    Unsigned32,
  oacVoiceVmoaConnLesCoIwfRestartNum
    Unsigned32
}

oacVoiceVmoaConnLesVoicePathNum OBJECT-TYPE
  SYNTAX Unsigned32
  MAX-ACCESS read-only
  STATUS current
  DESCRIPTION
    "Number of path establishment."
  ::= { oacVoiceVmoaConnLesEntry 1 }

oacVoiceVmoaConnLesTotalCpIwfOriginated OBJECT-TYPE
  SYNTAX Unsigned32
  MAX-ACCESS read-only
  STATUS current
  DESCRIPTION
    "Number of paths established by CP."
  ::= { oacVoiceVmoaConnLesEntry 2 }

oacVoiceVmoaConnLesTotalCoIwfOriginated OBJECT-TYPE
  SYNTAX Unsigned32
  MAX-ACCESS read-only
  STATUS current
  DESCRIPTION
    "Number of paths established by CO."
  ::= { oacVoiceVmoaConnLesEntry 3 }

oacVoiceVmoaConnLesCpIwfRestartNum OBJECT-TYPE
  SYNTAX Unsigned32
  MAX-ACCESS read-only
  STATUS current
  DESCRIPTION
    "Number of restart originated by CP."
  ::= { oacVoiceVmoaConnLesEntry 4 }

oacVoiceVmoaConnLesCoIwfRestartNum OBJECT-TYPE
  SYNTAX Unsigned32
  MAX-ACCESS read-only
  STATUS current
  DESCRIPTION
    "Number of restart originated by CO."
  ::= { oacVoiceVmoaConnLesEntry 5 }

-- ----------------------------------------------------------------------------
-- 7. oacVoiceVmoaConnElcpTable
--

oacVoiceVmoaConnElcpTable OBJECT-TYPE
  SYNTAX SEQUENCE OF OacVoiceVmoaConnElcpEntry
  MAX-ACCESS not-accessible
  STATUS current
  DESCRIPTION
    "Vmoa connection elcp table."
  ::= { oacVoiceConnectionBles 3 }

oacVoiceVmoaConnElcpEntry OBJECT-TYPE
  SYNTAX OacVoiceVmoaConnElcpEntry
  MAX-ACCESS not-accessible
  STATUS current
  DESCRIPTION
    "Vmoa connection elcp table entry."
  INDEX { oacVoiceVmoaConnConnection }
  ::= { oacVoiceVmoaConnElcpTable 1 }

OacVoiceVmoaConnElcpEntry ::= SEQUENCE {
  oacVoiceVmoaConnElcpTotalSuccessfulAllocation
    Unsigned32,
  oacVoiceVmoaConnElcpTotalUnsuccessfulAllocation
    Unsigned32,
  oacVoiceVmoaConnElcpTotalAllocationDuration
    TimeTicks
}

oacVoiceVmoaConnElcpTotalSuccessfulAllocation OBJECT-TYPE
  SYNTAX Unsigned32
  MAX-ACCESS read-only
  STATUS current
  DESCRIPTION
    "Number of channel allocation."
  ::= { oacVoiceVmoaConnElcpEntry 1 }

oacVoiceVmoaConnElcpTotalUnsuccessfulAllocation OBJECT-TYPE
  SYNTAX Unsigned32
  MAX-ACCESS read-only
  STATUS current
  DESCRIPTION
    "Number of channel allocation failures."
  ::= { oacVoiceVmoaConnElcpEntry 2 }

oacVoiceVmoaConnElcpTotalAllocationDuration OBJECT-TYPE
  SYNTAX TimeTicks
  MAX-ACCESS read-only
  STATUS current
  DESCRIPTION
    "Duration in seconds of channel allocation."
  ::= { oacVoiceVmoaConnElcpEntry 3 }

-- ----------------------------------------------------------------------------
-- 8. oacVoiceVmoaConnLapv5Table

oacVoiceVmoaConnLapv5Table OBJECT-TYPE
  SYNTAX SEQUENCE OF OacVoiceVmoaConnLapv5Entry
  MAX-ACCESS not-accessible
  STATUS current
  DESCRIPTION
    "Vmoa connection lapv5 table."
  ::= { oacVoiceConnectionBles 4 }

oacVoiceVmoaConnLapv5Entry OBJECT-TYPE
  SYNTAX OacVoiceVmoaConnLapv5Entry
  MAX-ACCESS not-accessible
  STATUS current
  DESCRIPTION
    "Vmoa connection lapv5 table entry."
  INDEX { oacVoiceVmoaConnConnection }
  ::= { oacVoiceVmoaConnLapv5Table 1 }

OacVoiceVmoaConnLapv5Entry ::= SEQUENCE {
  oacVoiceVmoaConnLapv5NbrRxFrame
    Unsigned32,
  oacVoiceVmoaConnLapv5NbrTxFrame
    Unsigned32,
  oacVoiceVmoaConnLapv5NbrRxIFrame
    Unsigned32,
  oacVoiceVmoaConnLapv5NbrTxIFrame
    Unsigned32,
  oacVoiceVmoaConnLapv5NbrRxRejFrame
    Unsigned32,
  oacVoiceVmoaConnLapv5NbrTxRejFrame
    Unsigned32,
  oacVoiceVmoaConnLapv5NbrRxRnrFrame
    Unsigned32,
  oacVoiceVmoaConnLapv5NbrTxRnrFrame
    Unsigned32,
  oacVoiceVmoaConnLapv5NbrT200Expiration
    Unsigned32
}

oacVoiceVmoaConnLapv5NbrRxFrame OBJECT-TYPE
  SYNTAX Unsigned32
  MAX-ACCESS read-only
  STATUS current
  DESCRIPTION
    "Number of frames received in the signal channel."
  ::= { oacVoiceVmoaConnLapv5Entry 1 }

oacVoiceVmoaConnLapv5NbrTxFrame OBJECT-TYPE
  SYNTAX Unsigned32
  MAX-ACCESS read-only
  STATUS current
  DESCRIPTION
    "Number of frames sent on the signal channel."
  ::= { oacVoiceVmoaConnLapv5Entry 2 }

oacVoiceVmoaConnLapv5NbrRxIFrame OBJECT-TYPE
  SYNTAX Unsigned32
  MAX-ACCESS read-only
  STATUS current
  DESCRIPTION
    "Number of frames received in the signal channel."
  ::= { oacVoiceVmoaConnLapv5Entry 3 }

oacVoiceVmoaConnLapv5NbrTxIFrame OBJECT-TYPE
  SYNTAX Unsigned32
  MAX-ACCESS read-only
  STATUS current
  DESCRIPTION
    "Number of frames sent on the signal channel."
  ::= { oacVoiceVmoaConnLapv5Entry 4 }

oacVoiceVmoaConnLapv5NbrRxRejFrame OBJECT-TYPE
  SYNTAX Unsigned32
  MAX-ACCESS read-only
  STATUS current
  DESCRIPTION
    "Number of Reject frames received in the signal channel."
  ::= { oacVoiceVmoaConnLapv5Entry 5 }

oacVoiceVmoaConnLapv5NbrTxRejFrame OBJECT-TYPE
  SYNTAX Unsigned32
  MAX-ACCESS read-only
  STATUS current
  DESCRIPTION
    "Number of Reject frames sent on the signal channel."
  ::= { oacVoiceVmoaConnLapv5Entry 6 }

oacVoiceVmoaConnLapv5NbrRxRnrFrame OBJECT-TYPE
  SYNTAX Unsigned32
  MAX-ACCESS read-only
  STATUS current
  DESCRIPTION
    "Number of RNR frames received in the signal channel."
  ::= { oacVoiceVmoaConnLapv5Entry 7 }

oacVoiceVmoaConnLapv5NbrTxRnrFrame OBJECT-TYPE
  SYNTAX Unsigned32
  MAX-ACCESS read-only
  STATUS current
  DESCRIPTION
    "Number of RNR frames sent on the signal channel."
  ::= { oacVoiceVmoaConnLapv5Entry 8 }

oacVoiceVmoaConnLapv5NbrT200Expiration OBJECT-TYPE
  SYNTAX Unsigned32
  MAX-ACCESS read-only
  STATUS current
  DESCRIPTION
    "Number of timer T200 timeout on the signal channel."
  ::= { oacVoiceVmoaConnLapv5Entry 9 }

-- ----------------------------------------------------------------------------
-- 9. oacVoiceVmoaConnAal2Table

oacVoiceVmoaConnAal2Table OBJECT-TYPE
  SYNTAX SEQUENCE OF OacVoiceVmoaConnAal2Entry
  MAX-ACCESS not-accessible
  STATUS current
  DESCRIPTION
    "Vmoa connection aal2 table."
  ::= { oacVoiceConnectionBles 5 }

oacVoiceVmoaConnAal2Entry OBJECT-TYPE
  SYNTAX OacVoiceVmoaConnAal2Entry
  MAX-ACCESS not-accessible
  STATUS current
  DESCRIPTION
    "Vmoa connection aal2 table entry."
  INDEX { oacVoiceVmoaConnConnection }
  ::= { oacVoiceVmoaConnAal2Table 1 }

OacVoiceVmoaConnAal2Entry ::= SEQUENCE {
  oacVoiceVmoaConnAal2TotalFramesReceived
    Unsigned32,
  oacVoiceVmoaConnAal2TotalBytesReceived
    Unsigned32,
  oacVoiceVmoaConnAal2TotalFramesDiscardedReceived
    Unsigned32,
  oacVoiceVmoaConnAal2TotalFramesErrorsReceived
    Unsigned32,
  oacVoiceVmoaConnAal2TotalFramesSent
    Unsigned32,
  oacVoiceVmoaConnAal2TotalBytesSent
    Unsigned32,
  oacVoiceVmoaConnAal2TotalFramesDiscardedSent
    Unsigned32
}

oacVoiceVmoaConnAal2TotalFramesReceived OBJECT-TYPE
  SYNTAX Unsigned32
  MAX-ACCESS read-only
  STATUS current
  DESCRIPTION
    "Number of Aal2 frames received on the signal channel."
  ::= { oacVoiceVmoaConnAal2Entry 1 }

oacVoiceVmoaConnAal2TotalBytesReceived OBJECT-TYPE
  SYNTAX Unsigned32
  MAX-ACCESS read-only
  STATUS current
  DESCRIPTION
    "Number of Aal2 bytes received on the signal channel."
  ::= { oacVoiceVmoaConnAal2Entry 2 }

oacVoiceVmoaConnAal2TotalFramesDiscardedReceived OBJECT-TYPE
  SYNTAX Unsigned32
  MAX-ACCESS read-only
  STATUS current
  DESCRIPTION
    "Number of Aal2 frames received and discarded on the signal channel."
  ::= { oacVoiceVmoaConnAal2Entry 3 }

oacVoiceVmoaConnAal2TotalFramesErrorsReceived OBJECT-TYPE
  SYNTAX Unsigned32
  MAX-ACCESS read-only
  STATUS current
  DESCRIPTION
    "Number of Aal2 frames received with errors on the signal channel."
  ::= { oacVoiceVmoaConnAal2Entry 4 }

oacVoiceVmoaConnAal2TotalFramesSent OBJECT-TYPE
  SYNTAX Unsigned32
  MAX-ACCESS read-only
  STATUS current
  DESCRIPTION
    "Number of Aal2 frames sent on the signal channel."
  ::= { oacVoiceVmoaConnAal2Entry 5 }

oacVoiceVmoaConnAal2TotalBytesSent OBJECT-TYPE
  SYNTAX Unsigned32
  MAX-ACCESS read-only
  STATUS current
  DESCRIPTION
    "Number of Aal2 bytes sent on the signal channel."
  ::= { oacVoiceVmoaConnAal2Entry 6 }

oacVoiceVmoaConnAal2TotalFramesDiscardedSent OBJECT-TYPE
  SYNTAX Unsigned32
  MAX-ACCESS read-only
  STATUS current
  DESCRIPTION
    "Number of Aal2 frames discarded when sending on the signal channel."
  ::= { oacVoiceVmoaConnAal2Entry 7 }

-- ----------------------------------------------------------------------------
-- ----------------------------------------------------------------------------
-- >> vtoa connection
-- ----------------------------------------------------------------------------

-- ----------------------------------------------------------------------------
-- 10. oacVoiceVtoaConnTable
--

oacVoiceVtoaConnTable OBJECT-TYPE
  SYNTAX SEQUENCE OF OacVoiceVtoaConnEntry
  MAX-ACCESS not-accessible
  STATUS current
  DESCRIPTION
    "Vtoa connection table."
  ::= { oacVoiceConnectionBles 6 }

oacVoiceVtoaConnEntry OBJECT-TYPE
  SYNTAX OacVoiceVtoaConnEntry
  MAX-ACCESS not-accessible
  STATUS current
  DESCRIPTION
    "Vtoa connection table entry."
  INDEX { oacVoiceVtoaConnConnection }
  ::= { oacVoiceVtoaConnTable 1 }

OacVoiceVtoaConnEntry ::= SEQUENCE {
  oacVoiceVtoaConnConnection
    Integer32,
  oacVoiceVtoaConnVpVc
    DisplayString,
  oacVoiceVtoaConnCurrentState
    VoiceUpDnState,
  oacVoiceVtoaConnConfigState
    VoiceUpDnState,
  oacVoiceVtoaConnAtmVcFailureOccurence
    Unsigned32,
  oacVoiceVtoaConnAtmVcTotalFailureDuration
    TimeTicks
}

oacVoiceVtoaConnConnection OBJECT-TYPE
  SYNTAX Integer32 (0..3)
  MAX-ACCESS read-only
  STATUS current
  DESCRIPTION
    "Index of this vtoa connection."
  ::= { oacVoiceVtoaConnEntry 1 }

oacVoiceVtoaConnVpVc OBJECT-TYPE
  SYNTAX DisplayString (SIZE (0..20))
  MAX-ACCESS read-only
  STATUS current
  DESCRIPTION
    "ATM PVC description."
  ::= { oacVoiceVtoaConnEntry 2 }

oacVoiceVtoaConnCurrentState OBJECT-TYPE
  SYNTAX VoiceUpDnState
  MAX-ACCESS read-only
  STATUS current
  DESCRIPTION
    "Operator status."
  ::= { oacVoiceVtoaConnEntry 3 }

oacVoiceVtoaConnConfigState OBJECT-TYPE
  SYNTAX VoiceUpDnState
  MAX-ACCESS read-only
  STATUS current
  DESCRIPTION
    "Admin description."
  ::= { oacVoiceVtoaConnEntry 4 }

oacVoiceVtoaConnAtmVcFailureOccurence OBJECT-TYPE
  SYNTAX Unsigned32
  MAX-ACCESS read-only
  STATUS current
  DESCRIPTION
    "Number of occurrence of PVC failure."
  ::= { oacVoiceVtoaConnEntry 5 }

oacVoiceVtoaConnAtmVcTotalFailureDuration OBJECT-TYPE
  SYNTAX TimeTicks
  MAX-ACCESS read-only
  STATUS current
  DESCRIPTION
    "Duration of PVC failure in seconds."
  ::= { oacVoiceVtoaConnEntry 6 }

-- ----------------------------------------------------------------------------
-- 11. oacVoiceVtoaConnAal2Table

oacVoiceVtoaConnAal2Table OBJECT-TYPE
  SYNTAX SEQUENCE OF OacVoiceVtoaConnAal2Entry
  MAX-ACCESS not-accessible
  STATUS current
  DESCRIPTION
    "Vtoa connection aal2 table."
  ::= { oacVoiceConnectionBles 7 }

oacVoiceVtoaConnAal2Entry OBJECT-TYPE
  SYNTAX OacVoiceVtoaConnAal2Entry
  MAX-ACCESS not-accessible
  STATUS current
  DESCRIPTION
    "Vtoa connection aal2 table entry."
  INDEX { oacVoiceVtoaConnConnection }
  ::= { oacVoiceVtoaConnAal2Table 1 }

OacVoiceVtoaConnAal2Entry ::= SEQUENCE {
  oacVoiceVtoaConnAal2TotalFramesReceived
    Unsigned32,
  oacVoiceVtoaConnAal2TotalBytesReceived
    Unsigned32,
  oacVoiceVtoaConnAal2TotalFramesDiscardedReceived
    Unsigned32,
  oacVoiceVtoaConnAal2TotalFramesErrorsReceived
    Unsigned32,
  oacVoiceVtoaConnAal2TotalFramesSent
    Unsigned32,
  oacVoiceVtoaConnAal2TotalBytesSent
    Unsigned32,
  oacVoiceVtoaConnAal2TotalFramesDiscardedSent
    Unsigned32
}

oacVoiceVtoaConnAal2TotalFramesReceived OBJECT-TYPE
  SYNTAX Unsigned32
  MAX-ACCESS read-only
  STATUS current
  DESCRIPTION
    "Number of frames received."
  ::= { oacVoiceVtoaConnAal2Entry 1 }

oacVoiceVtoaConnAal2TotalBytesReceived OBJECT-TYPE
  SYNTAX Unsigned32
  MAX-ACCESS read-only
  STATUS current
  DESCRIPTION
    "Number of bytes received."
  ::= { oacVoiceVtoaConnAal2Entry 2 }

oacVoiceVtoaConnAal2TotalFramesDiscardedReceived OBJECT-TYPE
  SYNTAX Unsigned32
  MAX-ACCESS read-only
  STATUS current
  DESCRIPTION
    "Number of frames received and discarded."
  ::= { oacVoiceVtoaConnAal2Entry 3 }

oacVoiceVtoaConnAal2TotalFramesErrorsReceived OBJECT-TYPE
  SYNTAX Unsigned32
  MAX-ACCESS read-only
  STATUS current
  DESCRIPTION
    "Number of frames received with error."
  ::= { oacVoiceVtoaConnAal2Entry 4 }

oacVoiceVtoaConnAal2TotalFramesSent OBJECT-TYPE
  SYNTAX Unsigned32
  MAX-ACCESS read-only
  STATUS current
  DESCRIPTION
    "Number of frames sent."
  ::= { oacVoiceVtoaConnAal2Entry 5 }

oacVoiceVtoaConnAal2TotalBytesSent OBJECT-TYPE
  SYNTAX Unsigned32
  MAX-ACCESS read-only
  STATUS current
  DESCRIPTION
    "Number of bytes sent."
  ::= { oacVoiceVtoaConnAal2Entry 6 }

oacVoiceVtoaConnAal2TotalFramesDiscardedSent OBJECT-TYPE
  SYNTAX Unsigned32
  MAX-ACCESS read-only
  STATUS current
  DESCRIPTION
    "Number of frames discarded and not sent."
  ::= { oacVoiceVtoaConnAal2Entry 7 }

-- ----------------------------------------------------------------------------
-- ----------------------------------------------------------------------------
-- >> dial peer voice vmoa fxs
-- ----------------------------------------------------------------------------

-- ----------------------------------------------------------------------------
-- 12. oacVoiceDialPeerVoiceVmoafxsTable
--

oacVoiceDialPeerVoiceVmoafxsTable OBJECT-TYPE
  SYNTAX SEQUENCE OF OacVoiceDialPeerVoiceVmoafxsEntry
  MAX-ACCESS not-accessible
  STATUS current
  DESCRIPTION
    "Dial peer voice vmoa fxs table."
  ::= { oacVoiceDialPeerBles 1 }

oacVoiceDialPeerVoiceVmoafxsEntry OBJECT-TYPE
  SYNTAX OacVoiceDialPeerVoiceVmoafxsEntry
  MAX-ACCESS not-accessible
  STATUS current
  DESCRIPTION
    "Dial peer voice vmoa fxs table entry."
  INDEX { oacVoiceDialPeerVoiceVmoafxsDialPeer }
  ::= { oacVoiceDialPeerVoiceVmoafxsTable 1 }

OacVoiceDialPeerVoiceVmoafxsEntry ::= SEQUENCE {
  oacVoiceDialPeerVoiceVmoafxsDialPeer
    Integer32,
  oacVoiceDialPeerVoiceVmoafxsLinkedPort
    DisplayString,
  oacVoiceDialPeerVoiceVmoafxsCurrentState
    VoiceUpDnState,
  oacVoiceDialPeerVoiceVmoafxsPortStatus
    VoiceFxsPortStatus,
  oacVoiceDialPeerVoiceVmoafxsPathStatus
    VoiceFxsPathStatus,
  oacVoiceDialPeerVoiceVmoafxsCurrentTxCoder
    VoiceIOCoder,
  oacVoiceDialPeerVoiceVmoafxsCurrentRxCoder
    VoiceIOCoder,
  oacVoiceDialPeerVoiceVmofxsCurrentBc
    VoiceBearerCap,
  oacVoiceDialPeerVoiceVmoafxsCurrentCid
    Unsigned32,
  oacVoiceDialPeerVoiceVmoafxsBlockingOccurence
    Unsigned32,
  oacVoiceDialPeerVoiceVmoafxsTotalBlockingDuration
    TimeTicks,
  oacVoiceDialPeerVoiceVmoafxsVoicePacketSent
    Unsigned32,
  oacVoiceDialPeerVoiceVmoafxsVoicePacketReceived
    Unsigned32,
  oacVoiceDialPeerVoiceVmoafxsPathEstablished
    Unsigned32,
  oacVoiceDialPeerVoiceVmoafxsPathRqFailed
    Unsigned32,
  oacVoiceDialPeerVoiceVmoafxsPathDuration
    TimeTicks
}

oacVoiceDialPeerVoiceVmoafxsDialPeer OBJECT-TYPE
  SYNTAX Integer32 (0..7)
  MAX-ACCESS read-only
  STATUS current
  DESCRIPTION
    "Index of this dial peer entry."
  ::= { oacVoiceDialPeerVoiceVmoafxsEntry 1 }

oacVoiceDialPeerVoiceVmoafxsLinkedPort OBJECT-TYPE
  SYNTAX DisplayString (SIZE (1..20))
  MAX-ACCESS read-only
  STATUS current
  DESCRIPTION
    "Linked physical port."
  ::= { oacVoiceDialPeerVoiceVmoafxsEntry 2 }

oacVoiceDialPeerVoiceVmoafxsCurrentState OBJECT-TYPE
  SYNTAX VoiceUpDnState
  MAX-ACCESS read-only
  STATUS current
  DESCRIPTION
    "Operator status."
  ::= { oacVoiceDialPeerVoiceVmoafxsEntry 3 }

oacVoiceDialPeerVoiceVmoafxsPortStatus OBJECT-TYPE
  SYNTAX VoiceFxsPortStatus
  MAX-ACCESS read-only
  STATUS current
  DESCRIPTION
    "Dial peer status."
  ::= { oacVoiceDialPeerVoiceVmoafxsEntry 4 }

oacVoiceDialPeerVoiceVmoafxsPathStatus OBJECT-TYPE
  SYNTAX VoiceFxsPathStatus
  MAX-ACCESS read-only
  STATUS current
  DESCRIPTION
    "Voice path status."
  ::= { oacVoiceDialPeerVoiceVmoafxsEntry 5 }

oacVoiceDialPeerVoiceVmoafxsCurrentTxCoder OBJECT-TYPE
  SYNTAX VoiceIOCoder
  MAX-ACCESS read-only
  STATUS current
  DESCRIPTION
    "Current coder used to send digitised voice to uplink stream."
  ::= { oacVoiceDialPeerVoiceVmoafxsEntry 6 }

oacVoiceDialPeerVoiceVmoafxsCurrentRxCoder OBJECT-TYPE
  SYNTAX VoiceIOCoder
  MAX-ACCESS read-only
  STATUS current
  DESCRIPTION
    "Current coder used to receive digitised voice from uplink stream."
  ::= { oacVoiceDialPeerVoiceVmoafxsEntry 7 }

oacVoiceDialPeerVoiceVmofxsCurrentBc OBJECT-TYPE
  SYNTAX VoiceBearerCap
  MAX-ACCESS read-only
  STATUS current
  DESCRIPTION
    "Current bearer capability used for voice transport."
  ::= { oacVoiceDialPeerVoiceVmoafxsEntry 8 }

oacVoiceDialPeerVoiceVmoafxsCurrentCid OBJECT-TYPE
  SYNTAX Unsigned32
  MAX-ACCESS read-only
  STATUS current
  DESCRIPTION
    "Current CID connection used for voice transport."
  ::= { oacVoiceDialPeerVoiceVmoafxsEntry 9 }

oacVoiceDialPeerVoiceVmoafxsBlockingOccurence OBJECT-TYPE
  SYNTAX Unsigned32
  MAX-ACCESS read-only
  STATUS current
  DESCRIPTION
    "Number of occurrence for port blocking for this route line."
  ::= { oacVoiceDialPeerVoiceVmoafxsEntry 10 }

oacVoiceDialPeerVoiceVmoafxsTotalBlockingDuration OBJECT-TYPE
  SYNTAX TimeTicks
  MAX-ACCESS read-only
  STATUS current
  DESCRIPTION
    "Duration in seconds for port blocking for this route line."
  ::= { oacVoiceDialPeerVoiceVmoafxsEntry 11 }

oacVoiceDialPeerVoiceVmoafxsVoicePacketSent OBJECT-TYPE
  SYNTAX Unsigned32
  MAX-ACCESS read-only
  STATUS current
  DESCRIPTION
    "Number of voice packets sent."
  ::= { oacVoiceDialPeerVoiceVmoafxsEntry 12 }

oacVoiceDialPeerVoiceVmoafxsVoicePacketReceived OBJECT-TYPE
  SYNTAX Unsigned32
  MAX-ACCESS read-only
  STATUS current
  DESCRIPTION
    "Number of voice packets received."
  ::= { oacVoiceDialPeerVoiceVmoafxsEntry 13 }

oacVoiceDialPeerVoiceVmoafxsPathEstablished OBJECT-TYPE
  SYNTAX Unsigned32
  MAX-ACCESS read-only
  STATUS current
  DESCRIPTION
    "Number of path established."
  ::= { oacVoiceDialPeerVoiceVmoafxsEntry 14 }

oacVoiceDialPeerVoiceVmoafxsPathRqFailed OBJECT-TYPE
  SYNTAX Unsigned32
  MAX-ACCESS read-only
  STATUS current
  DESCRIPTION
    "Number of path request failures."
  ::= { oacVoiceDialPeerVoiceVmoafxsEntry 15 }

oacVoiceDialPeerVoiceVmoafxsPathDuration OBJECT-TYPE
  SYNTAX TimeTicks
  MAX-ACCESS read-only
  STATUS current
  DESCRIPTION
    "Path established duration."
  ::= { oacVoiceDialPeerVoiceVmoafxsEntry 16 }

-- ----------------------------------------------------------------------------
-- ----------------------------------------------------------------------------
-- >> dial peer voice port bri
-- ----------------------------------------------------------------------------

-- ----------------------------------------------------------------------------
-- 13. oacVoiceDialPeerVoiceVmoabriTable

oacVoiceDialPeerVoiceVmoabriTable OBJECT-TYPE
  SYNTAX SEQUENCE OF OacVoiceDialPeerVoiceVmoabriEntry
  MAX-ACCESS not-accessible
  STATUS current
  DESCRIPTION
    "Dial peer voice vmoabri table."
  ::= { oacVoiceDialPeerBles 2 }

oacVoiceDialPeerVoiceVmoabriEntry OBJECT-TYPE
  SYNTAX OacVoiceDialPeerVoiceVmoabriEntry
  MAX-ACCESS not-accessible
  STATUS current
  DESCRIPTION
    "Dial peer voice vmoabri table entry."
  INDEX { oacVoiceDialPeerVoiceVmoabriDialPeer }
  ::= { oacVoiceDialPeerVoiceVmoabriTable 1 }

OacVoiceDialPeerVoiceVmoabriEntry ::= SEQUENCE {
  oacVoiceDialPeerVoiceVmoabriDialPeer
    Integer32,
  oacVoiceDialPeerVoiceVmoabriPort
    DisplayString,
  oacVoiceDialPeerVoiceVmoabriCurrentState
    VoiceUpDnState,
  oacVoiceDialPeerVoiceVmoabriConfigState
    VoiceUpDnState,
  oacVoiceDialPeerVoiceVmoabriPortStatus
    VoiceBriPortStatus,
  oacVoiceDialPeerVoiceVmoabriBlockingOccurence
    Unsigned32,
  oacVoiceDialPeerVoiceVmoabriTotalBlockingDuration
    TimeTicks,
  oacVoiceDialPeerVoiceVmoabriBxAllocNum
    Unsigned32
}

oacVoiceDialPeerVoiceVmoabriDialPeer OBJECT-TYPE
  SYNTAX Integer32 (0..7)
  MAX-ACCESS read-only
  STATUS current
  DESCRIPTION
    "Index of this dial peer entry."
  ::= { oacVoiceDialPeerVoiceVmoabriEntry 1 }

oacVoiceDialPeerVoiceVmoabriPort OBJECT-TYPE
  SYNTAX DisplayString (SIZE (0..5))
  MAX-ACCESS read-only
  STATUS current
  DESCRIPTION
    "Linked physical Module/Line description."
  ::= { oacVoiceDialPeerVoiceVmoabriEntry 2 }

oacVoiceDialPeerVoiceVmoabriCurrentState OBJECT-TYPE
  SYNTAX VoiceUpDnState
  MAX-ACCESS read-only
  STATUS current
  DESCRIPTION
    "Operator status."
  ::= { oacVoiceDialPeerVoiceVmoabriEntry 3 }

oacVoiceDialPeerVoiceVmoabriConfigState OBJECT-TYPE
  SYNTAX VoiceUpDnState
  MAX-ACCESS read-only
  STATUS current
  DESCRIPTION
    "Dial peer status."
  ::= { oacVoiceDialPeerVoiceVmoabriEntry 4 }

oacVoiceDialPeerVoiceVmoabriPortStatus OBJECT-TYPE
  SYNTAX VoiceBriPortStatus
  MAX-ACCESS read-only
  STATUS current
  DESCRIPTION
    "Dial peer status."
  ::= { oacVoiceDialPeerVoiceVmoabriEntry 5 }

oacVoiceDialPeerVoiceVmoabriBlockingOccurence OBJECT-TYPE
  SYNTAX Unsigned32
  MAX-ACCESS read-only
  STATUS current
  DESCRIPTION
    "Number of occurrence for port blocking for this route line."
  ::= { oacVoiceDialPeerVoiceVmoabriEntry 6 }

oacVoiceDialPeerVoiceVmoabriTotalBlockingDuration OBJECT-TYPE
  SYNTAX TimeTicks
  MAX-ACCESS read-only
  STATUS current
  DESCRIPTION
    "Duration in seconds for port blocking for this route line."
  ::= { oacVoiceDialPeerVoiceVmoabriEntry 7 }

oacVoiceDialPeerVoiceVmoabriBxAllocNum OBJECT-TYPE
  SYNTAX Unsigned32
  MAX-ACCESS read-only
  STATUS current
  DESCRIPTION
    "Total number of comms."
  ::= { oacVoiceDialPeerVoiceVmoabriEntry 8 }

-- ----------------------------------------------------------------------------
-- 14. oacVoiceDialPeerVoiceVmoabriB1Table
--

oacVoiceDialPeerVoiceVmoabriB1Table OBJECT-TYPE
  SYNTAX SEQUENCE OF OacVoiceDialPeerVoiceVmoabriB1Entry
  MAX-ACCESS not-accessible
  STATUS current
  DESCRIPTION
    "Dial peer voice vmoabri b1 channel table."
  ::= { oacVoiceDialPeerBles 3 }

oacVoiceDialPeerVoiceVmoabriB1Entry OBJECT-TYPE
  SYNTAX OacVoiceDialPeerVoiceVmoabriB1Entry
  MAX-ACCESS not-accessible
  STATUS current
  DESCRIPTION
    "Dial peer voice vmoabri b1 channel table entry."
  INDEX { oacVoiceDialPeerVoiceVmoabriDialPeer }
  ::= { oacVoiceDialPeerVoiceVmoabriB1Table 1 }

OacVoiceDialPeerVoiceVmoabriB1Entry ::= SEQUENCE {
  oacVoiceDialPeerVoiceVmoabriB1CurrentTxCoder
    VoiceIOCoder,
  oacVoiceDialPeerVoiceVmoabriB1CurrentRxCoder
    VoiceIOCoder,
  oacVoiceDialPeerVoiceVmoabriB1CurrentBc
    VoiceBearerCap,
  oacVoiceDialPeerVoiceVmoabriB1CurrentCid
    Unsigned32,
  oacVoiceDialPeerVoiceVmoabriB1VoicePacketSent
    Unsigned32,
  oacVoiceDialPeerVoiceVmoabriB1VoicePacketReceived
    Unsigned32,
  oacVoiceDialPeerVoiceVmoabriB1BytesSent
    Unsigned32,
  oacVoiceDialPeerVoiceVmoabriB1BytesReceived
    Unsigned32,
  oacVoiceDialPeerVoiceVmoabriB1PathEstablished
    Unsigned32,
  oacVoiceDialPeerVoiceVmoabriB1PathDuration
    TimeTicks,
  oacVoiceDialPeerVoiceVmoabriB1Bundle
    INTEGER
}

oacVoiceDialPeerVoiceVmoabriB1CurrentTxCoder OBJECT-TYPE
  SYNTAX VoiceIOCoder
  MAX-ACCESS read-only
  STATUS current
  DESCRIPTION
    "Current coder used to send digitized voice to uplink stream."
  ::= { oacVoiceDialPeerVoiceVmoabriB1Entry 1 }

oacVoiceDialPeerVoiceVmoabriB1CurrentRxCoder OBJECT-TYPE
  SYNTAX VoiceIOCoder
  MAX-ACCESS read-only
  STATUS current
  DESCRIPTION
    "Current coder used to receive digitized voice from uplink stream."
  ::= { oacVoiceDialPeerVoiceVmoabriB1Entry 2 }

oacVoiceDialPeerVoiceVmoabriB1CurrentBc OBJECT-TYPE
  SYNTAX VoiceBearerCap
  MAX-ACCESS read-only
  STATUS current
  DESCRIPTION
    "Current bearer capability used for voice transport."
  ::= { oacVoiceDialPeerVoiceVmoabriB1Entry 3 }

oacVoiceDialPeerVoiceVmoabriB1CurrentCid OBJECT-TYPE
  SYNTAX Unsigned32
  MAX-ACCESS read-only
  STATUS current
  DESCRIPTION
    "Current CID connection used for voice transport."
  ::= { oacVoiceDialPeerVoiceVmoabriB1Entry 4 }

oacVoiceDialPeerVoiceVmoabriB1VoicePacketSent OBJECT-TYPE
  SYNTAX Unsigned32
  MAX-ACCESS read-only
  STATUS current
  DESCRIPTION
    "Number of frames sent to this route line."
  ::= { oacVoiceDialPeerVoiceVmoabriB1Entry 5 }

oacVoiceDialPeerVoiceVmoabriB1VoicePacketReceived OBJECT-TYPE
  SYNTAX Unsigned32
  MAX-ACCESS read-only
  STATUS current
  DESCRIPTION
    "Number of frames received from this route line."
  ::= { oacVoiceDialPeerVoiceVmoabriB1Entry 6 }

oacVoiceDialPeerVoiceVmoabriB1BytesSent OBJECT-TYPE
  SYNTAX Unsigned32
  MAX-ACCESS read-only
  STATUS current
  DESCRIPTION
    "Number of bytes sent to this route line."
  ::= { oacVoiceDialPeerVoiceVmoabriB1Entry 7 }

oacVoiceDialPeerVoiceVmoabriB1BytesReceived OBJECT-TYPE
  SYNTAX Unsigned32
  MAX-ACCESS read-only
  STATUS current
  DESCRIPTION
    "Number of bytes sent from this route line."
  ::= { oacVoiceDialPeerVoiceVmoabriB1Entry 8 }

oacVoiceDialPeerVoiceVmoabriB1PathEstablished OBJECT-TYPE
  SYNTAX Unsigned32
  MAX-ACCESS read-only
  STATUS current
  DESCRIPTION
    "Number of path established."
  ::= { oacVoiceDialPeerVoiceVmoabriB1Entry 9 }

oacVoiceDialPeerVoiceVmoabriB1PathDuration OBJECT-TYPE
  SYNTAX TimeTicks
  MAX-ACCESS read-only
  STATUS current
  DESCRIPTION
    "Path established duration."
  ::= { oacVoiceDialPeerVoiceVmoabriB1Entry 10 }

oacVoiceDialPeerVoiceVmoabriB1Bundle OBJECT-TYPE
  SYNTAX INTEGER {
      no(0),
      yes(1)
    }
  MAX-ACCESS read-only
  STATUS current
  DESCRIPTION
    "Channel bundle info."
  ::= { oacVoiceDialPeerVoiceVmoabriB1Entry 11 }

-- ----------------------------------------------------------------------------
-- 15. oacVoiceDialPeerVoiceVmoabriB2Table
--

oacVoiceDialPeerVoiceVmoabriB2Table OBJECT-TYPE
  SYNTAX SEQUENCE OF OacVoiceDialPeerVoiceVmoabriB2Entry
  MAX-ACCESS not-accessible
  STATUS current
  DESCRIPTION
    "Dial peer voice vmoabri b2 channel table."
  ::= { oacVoiceDialPeerBles 4 }

oacVoiceDialPeerVoiceVmoabriB2Entry OBJECT-TYPE
  SYNTAX OacVoiceDialPeerVoiceVmoabriB2Entry
  MAX-ACCESS not-accessible
  STATUS current
  DESCRIPTION
    "Dial peer voice vmoabri b2 channel table entry."
  INDEX { oacVoiceDialPeerVoiceVmoabriDialPeer }
  ::= { oacVoiceDialPeerVoiceVmoabriB2Table 1 }

OacVoiceDialPeerVoiceVmoabriB2Entry ::= SEQUENCE {
  oacVoiceDialPeerVoiceVmoabriB2CurrentTxCoder
    VoiceIOCoder,
  oacVoiceDialPeerVoiceVmoabriB2CurrentRxCoder
    VoiceIOCoder,
  oacVoiceDialPeerVoiceVmoabriB2CurrentBc
    VoiceBearerCap,
  oacVoiceDialPeerVoiceVmoabriB2CurrentCid
    Unsigned32,
  oacVoiceDialPeerVoiceVmoabriB2VoicePacketSent
    Unsigned32,
  oacVoiceDialPeerVoiceVmoabriB2VoicePacketReceived
    Unsigned32,
  oacVoiceDialPeerVoiceVmoabriB2BytesSent
    Unsigned32,
  oacVoiceDialPeerVoiceVmoabriB2BytesReceived
    Unsigned32,
  oacVoiceDialPeerVoiceVmoabriB2PathEstablished
    Unsigned32,
  oacVoiceDialPeerVoiceVmoabriB2PathDuration
    TimeTicks,
  oacVoiceDialPeerVoiceVmoabriB2Bundle
    INTEGER
}

oacVoiceDialPeerVoiceVmoabriB2CurrentTxCoder OBJECT-TYPE
  SYNTAX VoiceIOCoder
  MAX-ACCESS read-only
  STATUS current
  DESCRIPTION
    "Current coder used to send digitised voice to uplink stream."
  ::= { oacVoiceDialPeerVoiceVmoabriB2Entry 1 }

oacVoiceDialPeerVoiceVmoabriB2CurrentRxCoder OBJECT-TYPE
  SYNTAX VoiceIOCoder
  MAX-ACCESS read-only
  STATUS current
  DESCRIPTION
    "Current coder used to receive digitised voice from uplink stream."
  ::= { oacVoiceDialPeerVoiceVmoabriB2Entry 2 }

oacVoiceDialPeerVoiceVmoabriB2CurrentBc OBJECT-TYPE
  SYNTAX VoiceBearerCap
  MAX-ACCESS read-only
  STATUS current
  DESCRIPTION
    "Current bearer capability used for voice transport."
  ::= { oacVoiceDialPeerVoiceVmoabriB2Entry 3 }

oacVoiceDialPeerVoiceVmoabriB2CurrentCid OBJECT-TYPE
  SYNTAX Unsigned32
  MAX-ACCESS read-only
  STATUS current
  DESCRIPTION
    "Current CID connection used for voice transport."
  ::= { oacVoiceDialPeerVoiceVmoabriB2Entry 4 }

oacVoiceDialPeerVoiceVmoabriB2VoicePacketSent OBJECT-TYPE
  SYNTAX Unsigned32
  MAX-ACCESS read-only
  STATUS current
  DESCRIPTION
    "Number of frames sent to this route line."
  ::= { oacVoiceDialPeerVoiceVmoabriB2Entry 5 }

oacVoiceDialPeerVoiceVmoabriB2VoicePacketReceived OBJECT-TYPE
  SYNTAX Unsigned32
  MAX-ACCESS read-only
  STATUS current
  DESCRIPTION
    "Number of frames received from this route line."
  ::= { oacVoiceDialPeerVoiceVmoabriB2Entry 6 }

oacVoiceDialPeerVoiceVmoabriB2BytesSent OBJECT-TYPE
  SYNTAX Unsigned32
  MAX-ACCESS read-only
  STATUS current
  DESCRIPTION
    "Number of bytes sent to this route line."
  ::= { oacVoiceDialPeerVoiceVmoabriB2Entry 7 }

oacVoiceDialPeerVoiceVmoabriB2BytesReceived OBJECT-TYPE
  SYNTAX Unsigned32
  MAX-ACCESS read-only
  STATUS current
  DESCRIPTION
    "Number of bytes sent from this route line."
  ::= { oacVoiceDialPeerVoiceVmoabriB2Entry 8 }

oacVoiceDialPeerVoiceVmoabriB2PathEstablished OBJECT-TYPE
  SYNTAX Unsigned32
  MAX-ACCESS read-only
  STATUS current
  DESCRIPTION
    "Number of path established."
  ::= { oacVoiceDialPeerVoiceVmoabriB2Entry 9 }

oacVoiceDialPeerVoiceVmoabriB2PathDuration OBJECT-TYPE
  SYNTAX TimeTicks
  MAX-ACCESS read-only
  STATUS current
  DESCRIPTION
    "Path established duration."
  ::= { oacVoiceDialPeerVoiceVmoabriB2Entry 10 }

oacVoiceDialPeerVoiceVmoabriB2Bundle OBJECT-TYPE
  SYNTAX INTEGER {
      no(0),
      yes(1)
    }
  MAX-ACCESS read-only
  STATUS current
  DESCRIPTION
    "Channel bundle info."
  ::= { oacVoiceDialPeerVoiceVmoabriB2Entry 11 }

-- ----------------------------------------------------------------------------
-- 16. oacVoiceDialPeerVoiceVmoabriDTable
--

oacVoiceDialPeerVoiceVmoabriDTable OBJECT-TYPE
  SYNTAX SEQUENCE OF OacVoiceDialPeerVoiceVmoabriDEntry
  MAX-ACCESS not-accessible
  STATUS current
  DESCRIPTION
    "Dial peer voice vmoabri d channel table."
  ::= { oacVoiceDialPeerBles 5 }

oacVoiceDialPeerVoiceVmoabriDEntry OBJECT-TYPE
  SYNTAX OacVoiceDialPeerVoiceVmoabriDEntry
  MAX-ACCESS not-accessible
  STATUS current
  DESCRIPTION
    "Dial peer voice vmoabri d channel table entry."
  INDEX { oacVoiceDialPeerVoiceVmoabriDialPeer }
  ::= { oacVoiceDialPeerVoiceVmoabriDTable 1 }

OacVoiceDialPeerVoiceVmoabriDEntry ::= SEQUENCE {
  oacVoiceDialPeerVoiceVmoabriDCurrentCid
    Unsigned32,
  oacVoiceDialPeerVoiceVmoabriDFramesSent
    Unsigned32,
  oacVoiceDialPeerVoiceVmoabriDFramesReceived
    Unsigned32,
  oacVoiceDialPeerVoiceVmoabriDBytesSent
    Unsigned32,
  oacVoiceDialPeerVoiceVmoabriDBytesReceived
    Unsigned32
}

oacVoiceDialPeerVoiceVmoabriDCurrentCid OBJECT-TYPE
  SYNTAX Unsigned32
  MAX-ACCESS read-only
  STATUS current
  DESCRIPTION
    "Current CID connection used for voice transport."
  ::= { oacVoiceDialPeerVoiceVmoabriDEntry 1 }

oacVoiceDialPeerVoiceVmoabriDFramesSent OBJECT-TYPE
  SYNTAX Unsigned32
  MAX-ACCESS read-only
  STATUS current
  DESCRIPTION
    "Number of frames sent to this route line."
  ::= { oacVoiceDialPeerVoiceVmoabriDEntry 2 }

oacVoiceDialPeerVoiceVmoabriDFramesReceived OBJECT-TYPE
  SYNTAX Unsigned32
  MAX-ACCESS read-only
  STATUS current
  DESCRIPTION
    "Number of frames received from this route line."
  ::= { oacVoiceDialPeerVoiceVmoabriDEntry 3 }

oacVoiceDialPeerVoiceVmoabriDBytesSent OBJECT-TYPE
  SYNTAX Unsigned32
  MAX-ACCESS read-only
  STATUS current
  DESCRIPTION
    "Number of bytes sent to this route line."
  ::= { oacVoiceDialPeerVoiceVmoabriDEntry 4 }

oacVoiceDialPeerVoiceVmoabriDBytesReceived OBJECT-TYPE
  SYNTAX Unsigned32
  MAX-ACCESS read-only
  STATUS current
  DESCRIPTION
    "Number of bytes sent from this route line."
  ::= { oacVoiceDialPeerVoiceVmoabriDEntry 5 }

-- ----------------------------------------------------------------------------
-- ----------------------------------------------------------------------------
-- ----------------------------------------------------------------------------
-- >> dial peer vmoapri
-- ----------------------------------------------------------------------------

-- ----------------------------------------------------------------------------
-- 21. oacVoiceDialPeerVoiceVmoapriTable

oacVoiceDialPeerVoiceVmoapriTable OBJECT-TYPE
  SYNTAX SEQUENCE OF OacVoiceDialPeerVoiceVmoapriEntry
  MAX-ACCESS not-accessible
  STATUS current
  DESCRIPTION
    "Dial peer vmoapri table."
  ::= { oacVoiceDialPeerBles 6 }

oacVoiceDialPeerVoiceVmoapriEntry OBJECT-TYPE
  SYNTAX OacVoiceDialPeerVoiceVmoapriEntry
  MAX-ACCESS not-accessible
  STATUS current
  DESCRIPTION
    "Dial peer vmoapri table entry."
  INDEX { oacVoiceDialPeerVoiceVmoapriDialPeer }
  ::= { oacVoiceDialPeerVoiceVmoapriTable 1 }

OacVoiceDialPeerVoiceVmoapriEntry ::= SEQUENCE {
  oacVoiceDialPeerVoiceVmoapriDialPeer
    Integer32,
  oacVoiceDialPeerVoiceVmoapriLinkedPort
    DisplayString,
  oacVoiceDialPeerVoiceVmoapriPortStatus
    VoiceBriPortStatus,
  oacVoiceDialPeerVoiceVmoapriCurrentState
    VoiceUpDnState,
  oacVoiceDialPeerVoiceVmoapriConfigState
    VoiceUpDnState,
  oacVoiceDialPeerVoiceVmoapriBlockingOccurence
    Unsigned32,
  oacVoiceDialPeerVoiceVmoapriTotalBlockingDuration
    TimeTicks,
  oacVoiceDialPeerVoiceVmoapriBxAllocNum
    Unsigned32
}

oacVoiceDialPeerVoiceVmoapriDialPeer OBJECT-TYPE
  SYNTAX Integer32 (0..7)
  MAX-ACCESS read-only
  STATUS current
  DESCRIPTION
    "Index of this dial peer entry."
  ::= { oacVoiceDialPeerVoiceVmoapriEntry 1 }

oacVoiceDialPeerVoiceVmoapriLinkedPort OBJECT-TYPE
  SYNTAX DisplayString (SIZE (0..20))
  MAX-ACCESS read-only
  STATUS current
  DESCRIPTION
    "Linked physical Module/Line description."
  ::= { oacVoiceDialPeerVoiceVmoapriEntry 2 }

oacVoiceDialPeerVoiceVmoapriPortStatus OBJECT-TYPE
  SYNTAX VoiceBriPortStatus
  MAX-ACCESS read-only
  STATUS current
  DESCRIPTION
    "Dial peer status."
  ::= { oacVoiceDialPeerVoiceVmoapriEntry 3 }

oacVoiceDialPeerVoiceVmoapriCurrentState OBJECT-TYPE
  SYNTAX VoiceUpDnState
  MAX-ACCESS read-only
  STATUS current
  DESCRIPTION
    "Operator status."
  ::= { oacVoiceDialPeerVoiceVmoapriEntry 4 }

oacVoiceDialPeerVoiceVmoapriConfigState OBJECT-TYPE
  SYNTAX VoiceUpDnState
  MAX-ACCESS read-only
  STATUS current
  DESCRIPTION
    "Dial peer status."
  ::= { oacVoiceDialPeerVoiceVmoapriEntry 5 }

oacVoiceDialPeerVoiceVmoapriBlockingOccurence OBJECT-TYPE
  SYNTAX Unsigned32
  MAX-ACCESS read-only
  STATUS current
  DESCRIPTION
    "Number of occurrence for port blocking for this route line."
  ::= { oacVoiceDialPeerVoiceVmoapriEntry 6 }

oacVoiceDialPeerVoiceVmoapriTotalBlockingDuration OBJECT-TYPE
  SYNTAX TimeTicks
  MAX-ACCESS read-only
  STATUS current
  DESCRIPTION
    "Duration in seconds for port blocking for this route line."
  ::= { oacVoiceDialPeerVoiceVmoapriEntry 7 }

oacVoiceDialPeerVoiceVmoapriBxAllocNum OBJECT-TYPE
  SYNTAX Unsigned32
  MAX-ACCESS read-only
  STATUS current
  DESCRIPTION
    "Total number of comms."
  ::= { oacVoiceDialPeerVoiceVmoapriEntry 8 }

-- ----------------------------------------------------------------------------
-- 22. oacVoiceDialPeerVoiceVmoapriTsxTable

oacVoiceDialPeerVoiceVmoapriTsxTable OBJECT-TYPE
  SYNTAX SEQUENCE OF OacVoiceDialPeerVoiceVmoapriTsxEntry
  MAX-ACCESS not-accessible
  STATUS current
  DESCRIPTION
    "Dial peer voice vmoapri tsx table."
  ::= { oacVoiceDialPeerBles 7 }

oacVoiceDialPeerVoiceVmoapriTsxEntry OBJECT-TYPE
  SYNTAX OacVoiceDialPeerVoiceVmoapriTsxEntry
  MAX-ACCESS not-accessible
  STATUS current
  DESCRIPTION
    "Dial peer voice vmoapri tsx table entry."
  INDEX { oacVoiceDialPeerVoiceVmoapriDialPeer, oacVoiceDialPeerVoiceVmoapriTsxIndex }
  ::= { oacVoiceDialPeerVoiceVmoapriTsxTable 1 }

OacVoiceDialPeerVoiceVmoapriTsxEntry ::= SEQUENCE {
  oacVoiceDialPeerVoiceVmoapriTsxIndex
    Integer32,
  oacVoiceDialPeerVoiceVmoapriTsxChannelType
    VoiceChnType,
  oacVoiceDialPeerVoiceVmoapriTsxCurrentTxCoder
    VoiceIOCoder,
  oacVoiceDialPeerVoiceVmoapriTsxCurrentRxCoder
    VoiceIOCoder,
  oacVoiceDialPeerVoiceVmoapriTsxCurrentBC
    VoiceBearerCap,
  oacVoiceDialPeerVoiceVmoapriTsxCurrentCID
    Unsigned32,
  oacVoiceDialPeerVoiceVmoapriTsxVoicePacketSent
    Unsigned32,
  oacVoiceDialPeerVoiceVmoapriTsxVoicePacketReceived
    Unsigned32
}

oacVoiceDialPeerVoiceVmoapriTsxIndex OBJECT-TYPE
  SYNTAX Integer32 (1..31)
  MAX-ACCESS read-only
  STATUS current
  DESCRIPTION
    "Index number of the tsx connection."
  ::= { oacVoiceDialPeerVoiceVmoapriTsxEntry 1 }

oacVoiceDialPeerVoiceVmoapriTsxChannelType OBJECT-TYPE
  SYNTAX VoiceChnType
  MAX-ACCESS read-only
  STATUS current
  DESCRIPTION
    "Channel category."
  ::= { oacVoiceDialPeerVoiceVmoapriTsxEntry 2 }

oacVoiceDialPeerVoiceVmoapriTsxCurrentTxCoder OBJECT-TYPE
  SYNTAX VoiceIOCoder
  MAX-ACCESS read-only
  STATUS current
  DESCRIPTION
    "Current coder used to send digitised voice to uplink stream."
  ::= { oacVoiceDialPeerVoiceVmoapriTsxEntry 3 }

oacVoiceDialPeerVoiceVmoapriTsxCurrentRxCoder OBJECT-TYPE
  SYNTAX VoiceIOCoder
  MAX-ACCESS read-only
  STATUS current
  DESCRIPTION
    "Current coder used to receive digitised voice from uplink stream."
  ::= { oacVoiceDialPeerVoiceVmoapriTsxEntry 4 }

oacVoiceDialPeerVoiceVmoapriTsxCurrentBC OBJECT-TYPE
  SYNTAX VoiceBearerCap
  MAX-ACCESS read-only
  STATUS current
  DESCRIPTION
    "Current bearer capability used for voice transport."
  ::= { oacVoiceDialPeerVoiceVmoapriTsxEntry 5 }

oacVoiceDialPeerVoiceVmoapriTsxCurrentCID OBJECT-TYPE
  SYNTAX Unsigned32
  MAX-ACCESS read-only
  STATUS current
  DESCRIPTION
    "Current CID connection used for voice transport."
  ::= { oacVoiceDialPeerVoiceVmoapriTsxEntry 6 }

oacVoiceDialPeerVoiceVmoapriTsxVoicePacketSent OBJECT-TYPE
  SYNTAX Unsigned32
  MAX-ACCESS read-only
  STATUS current
  DESCRIPTION
    "Number of frames sent to this route line."
  ::= { oacVoiceDialPeerVoiceVmoapriTsxEntry 7 }

oacVoiceDialPeerVoiceVmoapriTsxVoicePacketReceived OBJECT-TYPE
  SYNTAX Unsigned32
  MAX-ACCESS read-only
  STATUS current
  DESCRIPTION
    "Number of frames received from this route line."
  ::= { oacVoiceDialPeerVoiceVmoapriTsxEntry 8 }

-- ----------------------------------------------------------------------------
-- ----------------------------------------------------------------------------
-- >> dial peer vtoaccs
-- ----------------------------------------------------------------------------

-- ----------------------------------------------------------------------------
-- 17. oacVoiceDialPeerVoiceVtoaccsTable

oacVoiceDialPeerVoiceVtoaccsTable OBJECT-TYPE
  SYNTAX SEQUENCE OF OacVoiceDialPeerVoiceVtoaccsEntry
  MAX-ACCESS not-accessible
  STATUS current
  DESCRIPTION
    "Dial peer voice vtoaccs table."
  ::= { oacVoiceDialPeerBles 8 }

oacVoiceDialPeerVoiceVtoaccsEntry OBJECT-TYPE
  SYNTAX OacVoiceDialPeerVoiceVtoaccsEntry
  MAX-ACCESS not-accessible
  STATUS current
  DESCRIPTION
    "Dial peer voice vtoaccs table entry."
  INDEX { oacVoiceDialPeerVoiceVtoaccsDialPeer }
  ::= { oacVoiceDialPeerVoiceVtoaccsTable 1 }

OacVoiceDialPeerVoiceVtoaccsEntry ::= SEQUENCE {
  oacVoiceDialPeerVoiceVtoaccsDialPeer
    Integer32,
  oacVoiceDialPeerVoiceVtoaccsLinkedPort
    DisplayString,
  oacVoiceDialPeerVoiceVtoaccsPortStatus
    VoiceBriPortStatus,
  oacVoiceDialPeerVoiceVtoaccsCurrentState
    VoiceUpDnState,
  oacVoiceDialPeerVoiceVtoaccsConfigState
    VoiceUpDnState,
  oacVoiceDialPeerVoiceVtoaccsBlockingOccurence
    Unsigned32,
  oacVoiceDialPeerVoiceVtoaccsTotalBlockingDuration
    TimeTicks,
  oacVoiceDialPeerVoiceVtoaccsBxAllocNum
    Unsigned32
}

oacVoiceDialPeerVoiceVtoaccsDialPeer OBJECT-TYPE
  SYNTAX Integer32 (0..7)
  MAX-ACCESS read-only
  STATUS current
  DESCRIPTION
    "Index of this dial peer entry."
  ::= { oacVoiceDialPeerVoiceVtoaccsEntry 1 }

oacVoiceDialPeerVoiceVtoaccsLinkedPort OBJECT-TYPE
  SYNTAX DisplayString (SIZE (0..20))
  MAX-ACCESS read-only
  STATUS current
  DESCRIPTION
    "Linked Physical Module/Line description."
  ::= { oacVoiceDialPeerVoiceVtoaccsEntry 2 }

oacVoiceDialPeerVoiceVtoaccsPortStatus OBJECT-TYPE
  SYNTAX VoiceBriPortStatus
  MAX-ACCESS read-only
  STATUS current
  DESCRIPTION
    "Dial peer status."
  ::= { oacVoiceDialPeerVoiceVtoaccsEntry 3 }

oacVoiceDialPeerVoiceVtoaccsCurrentState OBJECT-TYPE
  SYNTAX VoiceUpDnState
  MAX-ACCESS read-only
  STATUS current
  DESCRIPTION
    "Operator status."
  ::= { oacVoiceDialPeerVoiceVtoaccsEntry 4 }

oacVoiceDialPeerVoiceVtoaccsConfigState OBJECT-TYPE
  SYNTAX VoiceUpDnState
  MAX-ACCESS read-only
  STATUS current
  DESCRIPTION
    "Dial peer status."
  ::= { oacVoiceDialPeerVoiceVtoaccsEntry 5 }

oacVoiceDialPeerVoiceVtoaccsBlockingOccurence OBJECT-TYPE
  SYNTAX Unsigned32
  MAX-ACCESS read-only
  STATUS current
  DESCRIPTION
    "Number of occurrence for port blocking for this route line."
  ::= { oacVoiceDialPeerVoiceVtoaccsEntry 6 }

oacVoiceDialPeerVoiceVtoaccsTotalBlockingDuration OBJECT-TYPE
  SYNTAX TimeTicks
  MAX-ACCESS read-only
  STATUS current
  DESCRIPTION
    "Duration in seconds for port blocking for this route line."
  ::= { oacVoiceDialPeerVoiceVtoaccsEntry 7 }

oacVoiceDialPeerVoiceVtoaccsBxAllocNum OBJECT-TYPE
  SYNTAX Unsigned32
  MAX-ACCESS read-only
  STATUS current
  DESCRIPTION
    "Total number of comms."
  ::= { oacVoiceDialPeerVoiceVtoaccsEntry 8 }

-- ----------------------------------------------------------------------------
-- 18. oacVoiceDialPeerVoiceVtoaccsTsxTable

oacVoiceDialPeerVoiceVtoaccsTsxTable OBJECT-TYPE
  SYNTAX SEQUENCE OF OacVoiceDialPeerVoiceVtoaccsTsxEntry
  MAX-ACCESS not-accessible
  STATUS current
  DESCRIPTION
    "Dial peer voice vtoaccs tsx table."
  ::= { oacVoiceDialPeerBles 9 }

oacVoiceDialPeerVoiceVtoaccsTsxEntry OBJECT-TYPE
  SYNTAX OacVoiceDialPeerVoiceVtoaccsTsxEntry
  MAX-ACCESS not-accessible
  STATUS current
  DESCRIPTION
    "Dial peer voice vtoaccs tsx table entry."
  INDEX { oacVoiceDialPeerVoiceVtoaccsDialPeer, oacVoiceDialPeerVoiceVtoaccsTsxIndex }
  ::= { oacVoiceDialPeerVoiceVtoaccsTsxTable 1 }

OacVoiceDialPeerVoiceVtoaccsTsxEntry ::= SEQUENCE {
  oacVoiceDialPeerVoiceVtoaccsTsxIndex
    Integer32,
  oacVoiceDialPeerVoiceVtoaccsTsxChannelType
    VoiceChnType,
  oacVoiceDialPeerVoiceVtoaccsTsxCurrentTxCoder
    VoiceIOCoder,
  oacVoiceDialPeerVoiceVtoaccsTsxCurrentRxCoder
    VoiceIOCoder,
  oacVoiceDialPeerVoiceVtoaccsTsxCurrentBC
    VoiceBearerCap,
  oacVoiceDialPeerVoiceVtoaccsTsxCurrentCID
    Unsigned32,
  oacVoiceDialPeerVoiceVtoaccsTsxVoicePacketSent
    Unsigned32,
  oacVoiceDialPeerVoiceVtoaccsTsxVoicePacketReceived
    Unsigned32,
  oacVoiceDialPeerVoiceVtoaccsTsxBundle
    INTEGER
}

oacVoiceDialPeerVoiceVtoaccsTsxIndex OBJECT-TYPE
  SYNTAX Integer32 (1..31)
  MAX-ACCESS read-only
  STATUS current
  DESCRIPTION
    "Index number of channel."
  ::= { oacVoiceDialPeerVoiceVtoaccsTsxEntry 1 }

oacVoiceDialPeerVoiceVtoaccsTsxChannelType OBJECT-TYPE
  SYNTAX VoiceChnType
  MAX-ACCESS read-only
  STATUS current
  DESCRIPTION
    "Channel category."
  ::= { oacVoiceDialPeerVoiceVtoaccsTsxEntry 2 }

oacVoiceDialPeerVoiceVtoaccsTsxCurrentTxCoder OBJECT-TYPE
  SYNTAX VoiceIOCoder
  MAX-ACCESS read-only
  STATUS current
  DESCRIPTION
    "Current coder used to send digitised voice to uplink stream."
  ::= { oacVoiceDialPeerVoiceVtoaccsTsxEntry 3 }

oacVoiceDialPeerVoiceVtoaccsTsxCurrentRxCoder OBJECT-TYPE
  SYNTAX VoiceIOCoder
  MAX-ACCESS read-only
  STATUS current
  DESCRIPTION
    "Current coder used to receive digitised voice from uplink stream."
  ::= { oacVoiceDialPeerVoiceVtoaccsTsxEntry 4 }

oacVoiceDialPeerVoiceVtoaccsTsxCurrentBC OBJECT-TYPE
  SYNTAX VoiceBearerCap
  MAX-ACCESS read-only
  STATUS current
  DESCRIPTION
    "Current bearer capability used for voice transport."
  ::= { oacVoiceDialPeerVoiceVtoaccsTsxEntry 5 }

oacVoiceDialPeerVoiceVtoaccsTsxCurrentCID OBJECT-TYPE
  SYNTAX Unsigned32
  MAX-ACCESS read-only
  STATUS current
  DESCRIPTION
    "Current CID connection used for voice transport."
  ::= { oacVoiceDialPeerVoiceVtoaccsTsxEntry 6 }

oacVoiceDialPeerVoiceVtoaccsTsxVoicePacketSent OBJECT-TYPE
  SYNTAX Unsigned32
  MAX-ACCESS read-only
  STATUS current
  DESCRIPTION
    "Number of frames sent to this route line."
  ::= { oacVoiceDialPeerVoiceVtoaccsTsxEntry 7 }

oacVoiceDialPeerVoiceVtoaccsTsxVoicePacketReceived OBJECT-TYPE
  SYNTAX Unsigned32
  MAX-ACCESS read-only
  STATUS current
  DESCRIPTION
    "Number of frames received from this route line."
  ::= { oacVoiceDialPeerVoiceVtoaccsTsxEntry 8 }

oacVoiceDialPeerVoiceVtoaccsTsxBundle OBJECT-TYPE
  SYNTAX INTEGER {
      no(0),
      yes(1)
    }
  MAX-ACCESS read-only
  STATUS current
  DESCRIPTION
    "Channel bundle info."
  ::= { oacVoiceDialPeerVoiceVtoaccsTsxEntry 9 }

-- ----------------------------------------------------------------------------
-- ----------------------------------------------------------------------------
-- >> dial peer vtoacas
-- ----------------------------------------------------------------------------

-- ----------------------------------------------------------------------------
-- 19. oacVoiceDialPeerVoiceVtoacasTable

oacVoiceDialPeerVoiceVtoacasTable OBJECT-TYPE
  SYNTAX SEQUENCE OF OacVoiceDialPeerVoiceVtoacasEntry
  MAX-ACCESS not-accessible
  STATUS current
  DESCRIPTION
    "Dial peer voice vtoacas table."
  ::= { oacVoiceDialPeerBles 10 }

oacVoiceDialPeerVoiceVtoacasEntry OBJECT-TYPE
  SYNTAX OacVoiceDialPeerVoiceVtoacasEntry
  MAX-ACCESS not-accessible
  STATUS current
  DESCRIPTION
    "Dial peer voice vtoacas table entry."
  INDEX { oacVoiceDialPeerVoiceVtoacasDialPeer }
  ::= { oacVoiceDialPeerVoiceVtoacasTable 1 }

OacVoiceDialPeerVoiceVtoacasEntry ::= SEQUENCE {
  oacVoiceDialPeerVoiceVtoacasDialPeer
    Integer32,
  oacVoiceDialPeerVoiceVtoacasLinkedPort
    DisplayString,
  oacVoiceDialPeerVoiceVtoacasPortStatus
    VoiceBriPortStatus,
  oacVoiceDialPeerVoiceVtoacasCurrentState
    VoiceUpDnState,
  oacVoiceDialPeerVoiceVtoacasConfigState
    VoiceUpDnState,
  oacVoiceDialPeerVoiceVtoacasBlockingOccurence
    Unsigned32,
  oacVoiceDialPeerVoiceVtoacasTotalBlockingDuration
    TimeTicks,
  oacVoiceDialPeerVoiceVtoacasBxAllocNum
    Unsigned32
}

oacVoiceDialPeerVoiceVtoacasDialPeer OBJECT-TYPE
  SYNTAX Integer32 (0..7)
  MAX-ACCESS read-only
  STATUS current
  DESCRIPTION
    "Index of this dial peer entry."
  ::= { oacVoiceDialPeerVoiceVtoacasEntry 1 }

oacVoiceDialPeerVoiceVtoacasLinkedPort OBJECT-TYPE
  SYNTAX DisplayString (SIZE (0..20))
  MAX-ACCESS read-only
  STATUS current
  DESCRIPTION
    "Linked Physical Module/Line description."
  ::= { oacVoiceDialPeerVoiceVtoacasEntry 2 }

oacVoiceDialPeerVoiceVtoacasPortStatus OBJECT-TYPE
  SYNTAX VoiceBriPortStatus
  MAX-ACCESS read-only
  STATUS current
  DESCRIPTION
    "Operator status."
  ::= { oacVoiceDialPeerVoiceVtoacasEntry 3 }

oacVoiceDialPeerVoiceVtoacasCurrentState OBJECT-TYPE
  SYNTAX VoiceUpDnState
  MAX-ACCESS read-only
  STATUS current
  DESCRIPTION
    "Dial peer status."
  ::= { oacVoiceDialPeerVoiceVtoacasEntry 4 }

oacVoiceDialPeerVoiceVtoacasConfigState OBJECT-TYPE
  SYNTAX VoiceUpDnState
  MAX-ACCESS read-only
  STATUS current
  DESCRIPTION
    "Dial peer status."
  ::= { oacVoiceDialPeerVoiceVtoacasEntry 5 }

oacVoiceDialPeerVoiceVtoacasBlockingOccurence OBJECT-TYPE
  SYNTAX Unsigned32
  MAX-ACCESS read-only
  STATUS current
  DESCRIPTION
    "Number of occurrence for port blocking for this route line."
  ::= { oacVoiceDialPeerVoiceVtoacasEntry 6 }

oacVoiceDialPeerVoiceVtoacasTotalBlockingDuration OBJECT-TYPE
  SYNTAX TimeTicks
  MAX-ACCESS read-only
  STATUS current
  DESCRIPTION
    "Duration in seconds for port blocking for this route line."
  ::= { oacVoiceDialPeerVoiceVtoacasEntry 7 }

oacVoiceDialPeerVoiceVtoacasBxAllocNum OBJECT-TYPE
  SYNTAX Unsigned32
  MAX-ACCESS read-only
  STATUS current
  DESCRIPTION
    "Total number of comms."
  ::= { oacVoiceDialPeerVoiceVtoacasEntry 8 }

-- ----------------------------------------------------------------------------
-- 20. oacVoiceDialPeerVoiceVtoacasTsxTable

oacVoiceDialPeerVoiceVtoacasTsxTable OBJECT-TYPE
  SYNTAX SEQUENCE OF OacVoiceDialPeerVoiceVtoacasTsxEntry
  MAX-ACCESS not-accessible
  STATUS current
  DESCRIPTION
    "Dial peer vtoacas tsx table."
  ::= { oacVoiceDialPeerBles 11 }

oacVoiceDialPeerVoiceVtoacasTsxEntry OBJECT-TYPE
  SYNTAX OacVoiceDialPeerVoiceVtoacasTsxEntry
  MAX-ACCESS not-accessible
  STATUS current
  DESCRIPTION
    "Dial peer vtoacas tsx table entry."
  INDEX { oacVoiceDialPeerVoiceVtoacasDialPeer, oacVoiceDialPeerVoiceVtoacasTsxIndex }
  ::= { oacVoiceDialPeerVoiceVtoacasTsxTable 1 }

OacVoiceDialPeerVoiceVtoacasTsxEntry ::= SEQUENCE {
  oacVoiceDialPeerVoiceVtoacasTsxIndex
    Integer32,
  oacVoiceDialPeerVoiceVtoacasTsxChannelType
    VoiceChnType,
  oacVoiceDialPeerVoiceVtoacasTsxCurrentTxCoder
    VoiceIOCoder,
  oacVoiceDialPeerVoiceVtoacasTsxCurrentRxCoder
    VoiceIOCoder,
  oacVoiceDialPeerVoiceVtoacasTsxCurrentBC
    VoiceBearerCap,
  oacVoiceDialPeerVoiceVtoacasTsxCurrentCID
    Unsigned32,
  oacVoiceDialPeerVoiceVtoacasTsxVoicePacketSent
    Unsigned32,
  oacVoiceDialPeerVoiceVtoacasTsxVoicePacketReceived
    Unsigned32,
  oacVoiceDialPeerVoiceVtoacasTsxVoiceCasFramesSent
    Unsigned32,
  oacVoiceDialPeerVoiceVtoacasTsxVoiceCasFramesReceived
    Unsigned32,
  oacVoiceDialPeerVoiceVtoacasTsxBundle
    INTEGER
}

oacVoiceDialPeerVoiceVtoacasTsxIndex OBJECT-TYPE
  SYNTAX Integer32 (1..31)
  MAX-ACCESS read-only
  STATUS current
  DESCRIPTION
    "Index number of the tsx connexion."
  ::= { oacVoiceDialPeerVoiceVtoacasTsxEntry 1 }

oacVoiceDialPeerVoiceVtoacasTsxChannelType OBJECT-TYPE
  SYNTAX VoiceChnType
  MAX-ACCESS read-only
  STATUS current
  DESCRIPTION
    "Channel category."
  ::= { oacVoiceDialPeerVoiceVtoacasTsxEntry 2 }

oacVoiceDialPeerVoiceVtoacasTsxCurrentTxCoder OBJECT-TYPE
  SYNTAX VoiceIOCoder
  MAX-ACCESS read-only
  STATUS current
  DESCRIPTION
    "Current coder used to send digitised voice to uplink stream."
  ::= { oacVoiceDialPeerVoiceVtoacasTsxEntry 3 }

oacVoiceDialPeerVoiceVtoacasTsxCurrentRxCoder OBJECT-TYPE
  SYNTAX VoiceIOCoder
  MAX-ACCESS read-only
  STATUS current
  DESCRIPTION
    "Current coder used to receive digitised voice from uplink stream."
  ::= { oacVoiceDialPeerVoiceVtoacasTsxEntry 4 }

oacVoiceDialPeerVoiceVtoacasTsxCurrentBC OBJECT-TYPE
  SYNTAX VoiceBearerCap
  MAX-ACCESS read-only
  STATUS current
  DESCRIPTION
    "Current bearer capability used for voice transport."
  ::= { oacVoiceDialPeerVoiceVtoacasTsxEntry 5 }

oacVoiceDialPeerVoiceVtoacasTsxCurrentCID OBJECT-TYPE
  SYNTAX Unsigned32
  MAX-ACCESS read-only
  STATUS current
  DESCRIPTION
    "Current CID connection used for voice transport."
  ::= { oacVoiceDialPeerVoiceVtoacasTsxEntry 6 }

oacVoiceDialPeerVoiceVtoacasTsxVoicePacketSent OBJECT-TYPE
  SYNTAX Unsigned32
  MAX-ACCESS read-only
  STATUS current
  DESCRIPTION
    "Number of frames sent to this route line."
  ::= { oacVoiceDialPeerVoiceVtoacasTsxEntry 7 }

oacVoiceDialPeerVoiceVtoacasTsxVoicePacketReceived OBJECT-TYPE
  SYNTAX Unsigned32
  MAX-ACCESS read-only
  STATUS current
  DESCRIPTION
    "Number of frames received from this route line."
  ::= { oacVoiceDialPeerVoiceVtoacasTsxEntry 8 }

oacVoiceDialPeerVoiceVtoacasTsxVoiceCasFramesSent OBJECT-TYPE
  SYNTAX Unsigned32
  MAX-ACCESS read-only
  STATUS current
  DESCRIPTION
    "Number of CAS packets sent to this route line."
  ::= { oacVoiceDialPeerVoiceVtoacasTsxEntry 9 }

oacVoiceDialPeerVoiceVtoacasTsxVoiceCasFramesReceived OBJECT-TYPE
  SYNTAX Unsigned32
  MAX-ACCESS read-only
  STATUS current
  DESCRIPTION
    "Number of CAS packets received from this route line."
  ::= { oacVoiceDialPeerVoiceVtoacasTsxEntry 10 }

oacVoiceDialPeerVoiceVtoacasTsxBundle OBJECT-TYPE
  SYNTAX INTEGER {
      none(0),
      bundle1(1),
      bundle2(2)
    }
  MAX-ACCESS read-only
  STATUS current
  DESCRIPTION
    "Bundle option."
  ::= { oacVoiceDialPeerVoiceVtoacasTsxEntry 11 }

-- ----------------------------------------------------------------------------
-- ----------------------------------------------------------------------------
-- >> dial peer vtoaces
-- ----------------------------------------------------------------------------

-- ----------------------------------------------------------------------------
-- 11. oacVoiceDialPeerVoiceVtoacesTable

oacVoiceDialPeerVoiceVtoacesTable OBJECT-TYPE
  SYNTAX SEQUENCE OF OacVoiceDialPeerVoiceVtoacesEntry
  MAX-ACCESS not-accessible
  STATUS current
  DESCRIPTION
    "Dial peer voice vtoaces table."
  ::= { oacVoiceDialPeerBles 12 }

oacVoiceDialPeerVoiceVtoacesEntry OBJECT-TYPE
  SYNTAX OacVoiceDialPeerVoiceVtoacesEntry
  MAX-ACCESS not-accessible
  STATUS current
  DESCRIPTION
    "Dial peer voice vtoaces table entry."
  INDEX { oacVoiceDialPeerVoiceVtoacesDialPeer }
  ::= { oacVoiceDialPeerVoiceVtoacesTable 1 }

OacVoiceDialPeerVoiceVtoacesEntry ::= SEQUENCE {
  oacVoiceDialPeerVoiceVtoacesDialPeer
    Integer32,
  oacVoiceDialPeerVoiceVtoacesLinkedPort
    DisplayString,
  oacVoiceDialPeerVoiceVtoacesCurrentState
    VoiceUpDnState,
  oacVoiceDialPeerVoiceVtoacesConfigState
    VoiceUpDnState,
  oacVoiceDialPeerVoiceVtoacesCellLossIntegrationPeriod
    Unsigned32,
  oacVoiceDialPeerVoiceVtoacesOutOfSyncOccurences
    Unsigned32,
  oacVoiceDialPeerVoiceVtoacesTxCells
    Unsigned32,
  oacVoiceDialPeerVoiceVtoacesReassCells
    Unsigned32,
  oacVoiceDialPeerVoiceVtoacesBufOverflows
    Unsigned32,
  oacVoiceDialPeerVoiceVtoacesBufUnderflows
    Unsigned32,
  oacVoiceDialPeerVoiceVtoacesPointerReframes
    Unsigned32,
  oacVoiceDialPeerVoiceVtoacesHdrErrors
    Unsigned32,
  oacVoiceDialPeerVoiceVtoacesLossCells
    Unsigned32
}

oacVoiceDialPeerVoiceVtoacesDialPeer OBJECT-TYPE
  SYNTAX Integer32 (0..7)
  MAX-ACCESS read-only
  STATUS current
  DESCRIPTION
    "Index of this dial peer entry."
  ::= { oacVoiceDialPeerVoiceVtoacesEntry 1 }

oacVoiceDialPeerVoiceVtoacesLinkedPort OBJECT-TYPE
  SYNTAX DisplayString (SIZE (0..20))
  MAX-ACCESS read-only
  STATUS current
  DESCRIPTION
    "Linked Physical Module/Line description."
  ::= { oacVoiceDialPeerVoiceVtoacesEntry 2 }

oacVoiceDialPeerVoiceVtoacesCurrentState OBJECT-TYPE
  SYNTAX VoiceUpDnState
  MAX-ACCESS read-only
  STATUS current
  DESCRIPTION
    "Dial peer state."
  ::= { oacVoiceDialPeerVoiceVtoacesEntry 3 }

oacVoiceDialPeerVoiceVtoacesConfigState OBJECT-TYPE
  SYNTAX VoiceUpDnState
  MAX-ACCESS read-only
  STATUS current
  DESCRIPTION
    "Dial peer status."
  ::= { oacVoiceDialPeerVoiceVtoacesEntry 4 }

oacVoiceDialPeerVoiceVtoacesCellLossIntegrationPeriod OBJECT-TYPE
  SYNTAX Unsigned32
  MAX-ACCESS read-only
  STATUS current
  DESCRIPTION
    ""
  ::= { oacVoiceDialPeerVoiceVtoacesEntry 5 }

oacVoiceDialPeerVoiceVtoacesOutOfSyncOccurences OBJECT-TYPE
  SYNTAX Unsigned32
  MAX-ACCESS read-only
  STATUS current
  DESCRIPTION
    "Total number of out-of-sync occurences."
  ::= { oacVoiceDialPeerVoiceVtoacesEntry 6 }

oacVoiceDialPeerVoiceVtoacesTxCells OBJECT-TYPE
  SYNTAX Unsigned32
  MAX-ACCESS read-only
  STATUS current
  DESCRIPTION
    "Total number of tx cells."
  ::= { oacVoiceDialPeerVoiceVtoacesEntry 7 }

oacVoiceDialPeerVoiceVtoacesReassCells OBJECT-TYPE
  SYNTAX Unsigned32
  MAX-ACCESS read-only
  STATUS current
  DESCRIPTION
    "Total number of received valid cells."
  ::= { oacVoiceDialPeerVoiceVtoacesEntry 8 }

oacVoiceDialPeerVoiceVtoacesBufOverflows OBJECT-TYPE
  SYNTAX Unsigned32
  MAX-ACCESS read-only
  STATUS current
  DESCRIPTION
    "Total number of rx overflow occurences."
  ::= { oacVoiceDialPeerVoiceVtoacesEntry 9 }

oacVoiceDialPeerVoiceVtoacesBufUnderflows OBJECT-TYPE
  SYNTAX Unsigned32
  MAX-ACCESS read-only
  STATUS current
  DESCRIPTION
    "Total number of rx underrun occurences."
  ::= { oacVoiceDialPeerVoiceVtoacesEntry 10 }

oacVoiceDialPeerVoiceVtoacesPointerReframes OBJECT-TYPE
  SYNTAX Unsigned32
  MAX-ACCESS read-only
  STATUS current
  DESCRIPTION
    "Total number of rx invalid pointers."
  ::= { oacVoiceDialPeerVoiceVtoacesEntry 11 }

oacVoiceDialPeerVoiceVtoacesHdrErrors OBJECT-TYPE
  SYNTAX Unsigned32
  MAX-ACCESS read-only
  STATUS current
  DESCRIPTION
    "Total number of rx crc error occurences."
  ::= { oacVoiceDialPeerVoiceVtoacesEntry 12 }

oacVoiceDialPeerVoiceVtoacesLossCells OBJECT-TYPE
  SYNTAX Unsigned32
  MAX-ACCESS read-only
  STATUS current
  DESCRIPTION
    "Total number of rx cell loss."
  ::= { oacVoiceDialPeerVoiceVtoacesEntry 13 }

-- ----------------------------------------------------------------------------	
--  1 . oacVoicePortVoip
-- ----------------------------------------------------------------------------
oacVoicePortVoipTable OBJECT-TYPE
	SYNTAX SEQUENCE OF OacVoicePortVoipEntry
	MAX-ACCESS not-accessible
	STATUS current
	DESCRIPTION
		"VoIP Voice Ports Table"
	::= { oacVoiceStatVoip 1 }
                              
oacVoicePortVoipEntry OBJECT-TYPE
	SYNTAX OacVoicePortVoipEntry
	MAX-ACCESS not-accessible
	STATUS current
	DESCRIPTION
		"VoIP Voice Ports Table Entry"
	INDEX {oacVoicePortIfIndex }
	::= { oacVoicePortVoipTable 1 }
                                   
OacVoicePortVoipEntry ::= SEQUENCE {                
	oacVoicePortIfIndex
		Integer32,
	oacVoicePortVoipPortName
		DisplayString,
	oacVoicePortVoipPortType
		VoipPortType,
	oacVoicePortVoipPriPhysicalType
		OacVoipPriPhysicalType,
	oacVoicePortVoipIsdnProtocolDescriptor
		IsdnProtocolDescriptor,
	oacVoicePortVoipCurrentState
		PortVoipCurrentState,
	oacVoicePortVoipConfigState
		ConfigState,
	oacVoicePortVoipIsdnLayer1Status
		IsdnLayerStatus,
	oacVoicePortVoipIsdnLayer2Status
		DisplayString,
	oacVoicePortVoipAttachedDialPeer
		Integer32,
	oacVoicePortVoipCurrentCalls
		Integer32,
	oacVoicePortVoipIsdnTxFramesOnDChannel
		Integer32,
	oacVoicePortVoipIsdnRxFramesOnDChannel
		Integer32,
	oacVoicePortVoipPriNbAisOccurence
		Integer32,
	oacVoicePortVoipPriNbRdiOccurence
		Integer32, 
	oacVoicePortVoipOutCalls
		Integer32,
	oacVoicePortVoipOutCallsFailures
		Integer32,
	oacVoicePortVoipOutCallsUnsufficientPotsGroupResource
		Integer32,
	oacVoicePortVoipOutCallsIsdnPhysicalInterfaceDown
		Integer32,
	oacVoicePortVoipOutCallsIsdnCauseClass0
		Integer32,
	oacVoicePortVoipOutCallsIsdnCauseClass1
		Integer32,
	oacVoicePortVoipOutCallsIsdnCC1NormalCause
		Integer32,
	oacVoicePortVoipOutCallsCC1UserBusy
		Integer32,
	oacVoicePortVoipOutCallsCC1NoAnswer
		Integer32,
	oacVoicePortVoipOutCallsIsdnCauseClass2
		Integer32,
	oacVoicePortVoipOutCallsIsdnCauseClass3
		Integer32,
	oacVoicePortVoipOutCallsIsdnCauseClass4
		Integer32,
	oacVoicePortVoipOutCallsIsdnCauseClass5
		Integer32,
	oacVoicePortVoipOutCallsIsdnCauseClass6
		Integer32,
	oacVoicePortVoipOutCallsIsdnCauseClass7
		Integer32,
	oacVoicePortVoipIncCalls
		Integer32,
	oacVoicePortVoipIncCallsBackupInvoked
		Integer32,
	oacVoicePortVoipIncCallsFailures
		Integer32,
	oacVoicePortVoipIncCallsRemoteFailure
		Integer32,
	oacVoicePortVoipIncCallsUnknownNumber
		Integer32,
	oacVoicePortVoipIncCallsDspUnavailable
		Integer32,
	oacVoicePortVoipIncCallsNoVoipRessourceAvailable
		Integer32,
	oacVoicePortVoipIncCallsNotSpecified
		Integer32,
	oacVoicePortVoipMgcpOffHookEvents
		Integer32,
	oacVoicePortVoipMgcpOutCallsPathEstablished
		Integer32,
	oacVoicePortVoipMgcpRingingEvents
		Integer32,
	oacVoicePortVoipMgcpIncCallsPathEstablished
		Integer32
}

oacVoicePortIfIndex OBJECT-TYPE
	SYNTAX Integer32 (0..7)
	MAX-ACCESS read-only
	STATUS current
	DESCRIPTION
		"Voice Port Interface Index ex : 0, 1 ..."
	::= { oacVoicePortVoipEntry 1 }
	
oacVoicePortVoipPortName OBJECT-TYPE
	SYNTAX DisplayString (SIZE(0..10))
	MAX-ACCESS read-only
	STATUS current
	DESCRIPTION
		"Voice Port name ex : 5/0, 5/1"
	::= { oacVoicePortVoipEntry 2 }
	                           
oacVoicePortVoipPortType OBJECT-TYPE
	SYNTAX VoipPortType
	MAX-ACCESS read-only
	STATUS current
	DESCRIPTION
		"Voip Voice Port Type"
	::= { oacVoicePortVoipEntry 3 }

oacVoicePortVoipPriPhysicalType OBJECT-TYPE
	SYNTAX OacVoipPriPhysicalType
	MAX-ACCESS read-only
	STATUS current
	DESCRIPTION
		"PRI Physical Type"
	::= { oacVoicePortVoipEntry 4 }

oacVoicePortVoipIsdnProtocolDescriptor OBJECT-TYPE
	SYNTAX IsdnProtocolDescriptor
	MAX-ACCESS read-only
	STATUS current
	DESCRIPTION
		"Voip Isdn Protocol Descriptor"
	::= { oacVoicePortVoipEntry 5 }

oacVoicePortVoipCurrentState OBJECT-TYPE
	SYNTAX PortVoipCurrentState
	MAX-ACCESS read-only
	STATUS current
	DESCRIPTION
		"Voip Current State"
	::= { oacVoicePortVoipEntry 6 }

oacVoicePortVoipConfigState OBJECT-TYPE
	SYNTAX ConfigState
	MAX-ACCESS read-only
	STATUS current
	DESCRIPTION
		"Voip Port Configuration State"
	::= { oacVoicePortVoipEntry 7 }

oacVoicePortVoipIsdnLayer1Status OBJECT-TYPE
	SYNTAX IsdnLayerStatus
	MAX-ACCESS read-only
	STATUS current
	DESCRIPTION
		"Voip Isdn Layer 1 Status"
	::= { oacVoicePortVoipEntry 8 }

oacVoicePortVoipIsdnLayer2Status OBJECT-TYPE
	SYNTAX DisplayString
	MAX-ACCESS read-only
	STATUS current
	DESCRIPTION
		"Voip Isdn Layer 2 Status"
	::= { oacVoicePortVoipEntry 9 }

oacVoicePortVoipAttachedDialPeer OBJECT-TYPE
	SYNTAX Integer32
	MAX-ACCESS read-only 
	STATUS current
	DESCRIPTION
		"Voip Attached Dial Peer"
	::= { oacVoicePortVoipEntry 10 }

oacVoicePortVoipCurrentCalls OBJECT-TYPE
	SYNTAX Integer32
	MAX-ACCESS read-only 
	STATUS current
	DESCRIPTION
		"Number of Voip Current calls"
	::= { oacVoicePortVoipEntry 11 }
	
oacVoicePortVoipIsdnTxFramesOnDChannel OBJECT-TYPE
	SYNTAX Integer32
	MAX-ACCESS read-only 
	STATUS current
	DESCRIPTION
		"Number of Tx Frames on D channel"
	::= { oacVoicePortVoipEntry 12 }
		
oacVoicePortVoipIsdnRxFramesOnDChannel OBJECT-TYPE
	SYNTAX Integer32
	MAX-ACCESS read-only
	STATUS current
	DESCRIPTION
		"Number of Rx Frames on D channel"
	::= { oacVoicePortVoipEntry 13 }
	
oacVoicePortVoipPriNbAisOccurence OBJECT-TYPE
	SYNTAX Integer32
	MAX-ACCESS read-only 
	STATUS current
	DESCRIPTION
		"Number of PRI AIS occurences"
	::= { oacVoicePortVoipEntry 14 }
	
oacVoicePortVoipPriNbRdiOccurence OBJECT-TYPE
	SYNTAX Integer32
	MAX-ACCESS read-only
	STATUS current
	DESCRIPTION
		"Number of PRI RDI occurences"
	::= { oacVoicePortVoipEntry 15 }

oacVoicePortVoipOutCalls OBJECT-TYPE
	SYNTAX Integer32
	MAX-ACCESS read-only 
	STATUS current
	DESCRIPTION
		"Number of Voip outgoing calls"
	::= { oacVoicePortVoipEntry 16 }
	
oacVoicePortVoipOutCallsFailures OBJECT-TYPE
	SYNTAX Integer32
	MAX-ACCESS read-only 
	STATUS current
	DESCRIPTION
		"Number of failures of outgoing calls"
	::= { oacVoicePortVoipEntry 17 }
	
oacVoicePortVoipOutCallsUnsufficientPotsGroupResource OBJECT-TYPE
	SYNTAX Integer32
	MAX-ACCESS read-only
	STATUS current
	DESCRIPTION
		"Number of failures of outgoing calls
		 Error from Unsufficient Pots Group Resource"
	::= { oacVoicePortVoipEntry 18 }
	
oacVoicePortVoipOutCallsIsdnPhysicalInterfaceDown OBJECT-TYPE
	SYNTAX Integer32
	MAX-ACCESS read-only	
	STATUS current
	DESCRIPTION
		"Number of failures of outgoing calls
		 Error from Isdn Physical Interface down"
	::= { oacVoicePortVoipEntry 19 }
	
oacVoicePortVoipOutCallsIsdnCauseClass0 OBJECT-TYPE
	SYNTAX Integer32
	MAX-ACCESS read-only
	STATUS current
	DESCRIPTION
		"Number of failures of outgoing calls
		 Error Cause Class 0 : normal event"
	::= { oacVoicePortVoipEntry 20 }
	
oacVoicePortVoipOutCallsIsdnCauseClass1 OBJECT-TYPE
	SYNTAX Integer32
	MAX-ACCESS read-only
	STATUS current
	DESCRIPTION
		"Number of failures of outgoing calls
		 Error Cause Class 1 : normal event"
	::= { oacVoicePortVoipEntry 21 }
	
oacVoicePortVoipOutCallsIsdnCC1NormalCause OBJECT-TYPE
	SYNTAX Integer32
	MAX-ACCESS read-only
	STATUS current
	DESCRIPTION
		"Number of failures of outgoing calls
		 Error Cause Class 1 : normal Cause"
	::= { oacVoicePortVoipEntry 22 }
	
oacVoicePortVoipOutCallsCC1UserBusy OBJECT-TYPE
	SYNTAX Integer32
	MAX-ACCESS read-only
	STATUS current
	DESCRIPTION
		"Number of failures of outgoing calls
		 Error Cause Class 1 : User Busy"
	::= { oacVoicePortVoipEntry 23 }
	
oacVoicePortVoipOutCallsCC1NoAnswer OBJECT-TYPE
	SYNTAX Integer32
	MAX-ACCESS read-only
	STATUS current
	DESCRIPTION
		"Number of failures of outgoing calls
		 Error Cause Class 1 : No Answer"
	::= { oacVoicePortVoipEntry 24 }
	
oacVoicePortVoipOutCallsIsdnCauseClass2 OBJECT-TYPE
	SYNTAX Integer32
	MAX-ACCESS read-only
	STATUS current
	DESCRIPTION
		"Number of failures of outgoing calls
		 Error Cause Class 2 : unavailable resources"
	::= { oacVoicePortVoipEntry 25 }
	
oacVoicePortVoipOutCallsIsdnCauseClass3 OBJECT-TYPE
	SYNTAX Integer32
	MAX-ACCESS read-only
	STATUS current
	DESCRIPTION
		"Number of failures of outgoing calls
		 Error Cause Class 3 : unavailable service"
	::= { oacVoicePortVoipEntry 26 }
	
oacVoicePortVoipOutCallsIsdnCauseClass4 OBJECT-TYPE
	SYNTAX Integer32
	MAX-ACCESS read-only
	STATUS current
	DESCRIPTION
		"Number of failures of outgoing calls
		 Error Cause Class 4 : service not provided"
	::= { oacVoicePortVoipEntry 27 }
	
oacVoicePortVoipOutCallsIsdnCauseClass5 OBJECT-TYPE
	SYNTAX Integer32
	MAX-ACCESS read-only
	STATUS current
	DESCRIPTION
		"Number of failures of outgoing calls
		 Error Cause Class 5 : invalid message"
	::= { oacVoicePortVoipEntry 28 }
	
oacVoicePortVoipOutCallsIsdnCauseClass6 OBJECT-TYPE
	SYNTAX Integer32
	MAX-ACCESS read-only
	STATUS current
	DESCRIPTION
		"Number of failures of outgoing calls
		 Error Cause Class 6 : protocol error"
	::= { oacVoicePortVoipEntry 29 }
	
oacVoicePortVoipOutCallsIsdnCauseClass7 OBJECT-TYPE
	SYNTAX Integer32
	MAX-ACCESS read-only
	STATUS current
	DESCRIPTION
		"Number of failures of outgoing calls
		 Error Cause Class 7 : interworking"
	::= { oacVoicePortVoipEntry 30 }

oacVoicePortVoipIncCalls OBJECT-TYPE
	SYNTAX Integer32
	MAX-ACCESS read-only
	STATUS current
	DESCRIPTION
		"Number of incoming calls"
	::= { oacVoicePortVoipEntry 31 }
	
oacVoicePortVoipIncCallsBackupInvoked OBJECT-TYPE
	SYNTAX Integer32
	MAX-ACCESS read-only
	STATUS current
	DESCRIPTION
		"Number of incoming calls when backup invoked"
	::= { oacVoicePortVoipEntry 32 }
	
oacVoicePortVoipIncCallsFailures OBJECT-TYPE
	SYNTAX Integer32
	MAX-ACCESS read-only
	STATUS current
	DESCRIPTION
		"Number of failures of incoming calls"
	::= { oacVoicePortVoipEntry 33 }
	
oacVoicePortVoipIncCallsRemoteFailure OBJECT-TYPE
	SYNTAX Integer32
	MAX-ACCESS read-only
	STATUS current
	DESCRIPTION
		"Number of failures of incoming calls
		 Error is remote failure"
	::= { oacVoicePortVoipEntry 34 }

oacVoicePortVoipIncCallsUnknownNumber OBJECT-TYPE
	SYNTAX Integer32
	MAX-ACCESS read-only
	STATUS current
	DESCRIPTION
		"Number of failures of incoming calls
		 Error is unknown number"
	::= { oacVoicePortVoipEntry 35 }
	
oacVoicePortVoipIncCallsDspUnavailable OBJECT-TYPE
	SYNTAX Integer32
	MAX-ACCESS read-only
	STATUS current
	DESCRIPTION
		"Number of failures of incoming calls
		 Error is DSP unavailable"
	::= { oacVoicePortVoipEntry 36 }
	
oacVoicePortVoipIncCallsNoVoipRessourceAvailable OBJECT-TYPE
	SYNTAX Integer32
	MAX-ACCESS read-only
	STATUS current
	DESCRIPTION
		"Number of failures of incoming calls
		 Error is no VoIP resource available"
	::= { oacVoicePortVoipEntry 37 }
	
oacVoicePortVoipIncCallsNotSpecified OBJECT-TYPE
	SYNTAX Integer32
	MAX-ACCESS read-only
	STATUS current
	DESCRIPTION
		"Number of failures of incoming calls
		 Error is calls not specified"
	::= { oacVoicePortVoipEntry 38 }
 
oacVoicePortVoipMgcpOffHookEvents OBJECT-TYPE
	SYNTAX Integer32
	MAX-ACCESS read-only
	STATUS current
	DESCRIPTION
		"number of MGCP off hook events"
	::= { oacVoicePortVoipEntry 39 }
	
oacVoicePortVoipMgcpOutCallsPathEstablished OBJECT-TYPE
	SYNTAX Integer32
	MAX-ACCESS read-only
	STATUS current
	DESCRIPTION
		"number MGCP outgoing calls path established"
	::= { oacVoicePortVoipEntry 40 }
	
oacVoicePortVoipMgcpRingingEvents OBJECT-TYPE
	SYNTAX Integer32
	MAX-ACCESS read-only
	STATUS current
	DESCRIPTION
		"number of MGCP ringing events"
	::= { oacVoicePortVoipEntry 41 }
	
oacVoicePortVoipMgcpIncCallsPathEstablished OBJECT-TYPE
	SYNTAX Integer32
	MAX-ACCESS read-only
	STATUS current
	DESCRIPTION
		"number MGCP incoming calls path established"
	::= { oacVoicePortVoipEntry 42 }
	

-- ----------------------------------------------------------------------------	
--  2 . oacVoiceDialPeerVoipTable
-- ----------------------------------------------------------------------------
oacVoiceDialPeerVoipTable OBJECT-TYPE
	SYNTAX SEQUENCE OF OacVoiceDialPeerVoipEntry
	MAX-ACCESS not-accessible
	STATUS current
	DESCRIPTION
		"VoIP Voice Dial Peer Table"
	::= { oacVoiceStatVoip 2 }
                              
oacVoiceDialPeerVoipEntry OBJECT-TYPE
	SYNTAX OacVoiceDialPeerVoipEntry
	MAX-ACCESS not-accessible
	STATUS current
	DESCRIPTION
		"VoIP Voice Dial Peer Table Entry"
	INDEX {oacVoiceDialPeerIndex }
	::= { oacVoiceDialPeerVoipTable 1 }
                                   
OacVoiceDialPeerVoipEntry ::= SEQUENCE {
	oacVoiceDialPeerIndex
		Integer32,
	oacVoiceDialPeerCurrentCalls
		Integer32,
	oacVoiceDialPeerOutCalls
		Integer32,
	oacVoiceDialPeerOutCallsMgcpOffHookEvents
		Integer32,
	oacVoiceDialPeerOutCallsMgcpPathEstablished
		Integer32,
	oacVoiceDialPeerOutCallsFailures
		Integer32,
	oacVoiceDialPeerOutCallsRasFailures
		Integer32,
	oacVoiceDialPeerOutCallsRasFailGatekeeperUnavailable
		Integer32,
	oacVoiceDialPeerOutCallsRasFailAdmissionRejects
		Integer32,
	oacVoiceDialPeerOutCallsH225Q931Failures
		Integer32,
	oacVoiceDialPeerOutCallsHQFailCauseClass0
		Integer32,
	oacVoiceDialPeerOutCallsHQFailCauseClass1
		Integer32,
	oacVoiceDialPeerOutCallsHQFailCC1NormalCause
		Integer32,
	oacVoiceDialPeerOutCallsHQFailCC1UserBusy
		Integer32,
	oacVoiceDialPeerOutCallsHQFailCC1NoAnswer
		Integer32,
	oacVoiceDialPeerOutCallsHQFailCauseClass2
		Integer32,
	oacVoiceDialPeerOutCallsHQFailCauseClass3
		Integer32,
	oacVoiceDialPeerOutCallsHQFailCauseClass4
		Integer32,
	oacVoiceDialPeerOutCallsHQFailCauseClass5
		Integer32,
	oacVoiceDialPeerOutCallsHQFailCauseClass6
		Integer32,
	oacVoiceDialPeerOutCallsHQFailCauseClass7
		Integer32,
	oacVoiceDialPeerOutCallsH245Failures
		Integer32,
	oacVoiceDialPeerOutCallsH245FailIncompatibleCapabilities
		Integer32,
	oacVoiceDialPeerOutCallsH245FailProtocolErrors
		Integer32,
	oacVoiceDialPeerOutCallsInternalFailures
		Integer32,
	oacVoiceDialPeerOutCallsInternalFailDspUnavailable
		Integer32,
	oacVoiceDialPeerOutCallsInternalFailMaxBwExceeded
		Integer32,
	oacVoiceDialPeerOutCallsInternalFailMaxConnExceeded
		Integer32,
	oacVoiceDialPeerOutCallsInternalFailNotSpecified
		Integer32,
	oacVoiceDialPeerIncCalls
		Integer32,              
	oacVoiceDialPeerIncCallsMgcpRingingEvents
		Integer32,
	oacVoiceDialPeerIncCallsMgcpPathEstablished
		Integer32,		
	oacVoiceDialPeerIncCallsFailures
		Integer32,
	oacVoiceDialPeerIncCallsRasFailures
		Integer32,
	oacVoiceDialPeerIncCallsRasFailGatekeeperUnavailable
		Integer32,
	oacVoiceDialPeerIncCallsRasFailAdmissionRejects
		Integer32,
	oacVoiceDialPeerIncCallsLocalPortFailures
		Integer32,
	oacVoiceDialPeerIncCallsH245Failures
		Integer32,
	oacVoiceDialPeerIncCallsH245FailIncompatibleCapabilities
		Integer32,
	oacVoiceDialPeerIncCallsH245FailProtocolErrors
		Integer32,
	oacVoiceDialPeerIncCallsInternalFailures
		Integer32,
	oacVoiceDialPeerIncCallsInternalFailDspUnavailable
		Integer32,
	oacVoiceDialPeerIncCallsInternalFailUnknownNumber
		Integer32,
	oacVoiceDialPeerIncCallsInternalFailChannelPortUnavailable
		Integer32,
	oacVoiceDialPeerIncCallsInternalFailMaxBwExceeded
		Integer32,
	oacVoiceDialPeerIncCallsInternalFailMaxConnExceeded
		Integer32,
	oacVoiceDialPeerIncCallsInternalFailNotSpecified
		Integer32,
	oacVoiceDialPeerIncCallsAdviceofCharge
		Integer32,
	oacVoiceDialPeerRtpStatNbTxPackets
		Unsigned32,
	oacVoiceDialPeerRtpStatNbRxPackets
		Unsigned32,
	oacVoiceDialPeerRtpStatNbTxBytes
		Unsigned32,
	oacVoiceDialPeerRtpStatNbRxBytes
		Unsigned32,
	oacVoiceDialPeerRtpStatNbExcessiveJitterEvents
		Unsigned32,
	oacVoiceDialPeerRtpStatNbLostPackets
		Unsigned32,
	oacVoiceDialPeerRtpStatNbInvalidPackets
		Unsigned32,
	oacVoiceDialPeerModemNbSwitchingToModemMode
		Unsigned32,
	oacVoiceDialPeerFaxNbOutgoingFax
		Integer32,
	oacVoiceDialPeerFaxNbIncomingFax
		Integer32,
	oacVoiceDialPeerFaxNbFailures
		Integer32,
	oacVoiceDialPeerFaxFailureRequestMode
		Integer32,
	oacVoiceDialPeerFaxFailurePreMsgProcedure
		Integer32,
	oacVoiceDialPeerFaxFailurePage
		Integer32,
	oacVoiceDialPeerFaxNbTxPackets
		Unsigned32,
	oacVoiceDialPeerFaxNbRxPackets
		Unsigned32,
	oacVoiceDialPeerFaxNbTxBytes
		Unsigned32,
	oacVoiceDialPeerFaxNbRxBytes
		Unsigned32,
	oacVoiceDialPeerFaxNbLostPackets
		Unsigned32
}

oacVoiceDialPeerIndex OBJECT-TYPE
	SYNTAX Integer32
	MAX-ACCESS read-only
	STATUS current
	DESCRIPTION
		"Index number of voice Dial peer"
	::= { oacVoiceDialPeerVoipEntry 1 }
	
oacVoiceDialPeerCurrentCalls OBJECT-TYPE
	SYNTAX Integer32
	MAX-ACCESS read-only
	STATUS current
	DESCRIPTION
		"Number of dial peer current calls"
	::= { oacVoiceDialPeerVoipEntry 2 }

oacVoiceDialPeerOutCalls OBJECT-TYPE
	SYNTAX Integer32
	MAX-ACCESS read-only
	STATUS current
	DESCRIPTION
		"Number of Dial peer outgoing calls"
	::= { oacVoiceDialPeerVoipEntry 3 }

oacVoiceDialPeerOutCallsMgcpOffHookEvents OBJECT-TYPE
	SYNTAX Integer32
	MAX-ACCESS read-only
	STATUS current
	DESCRIPTION	
		" ? "
	::= { oacVoiceDialPeerVoipEntry 4 }	
	
oacVoiceDialPeerOutCallsMgcpPathEstablished OBJECT-TYPE
	SYNTAX Integer32
	MAX-ACCESS read-only  
	STATUS current
	DESCRIPTION
		"?"
	::= { oacVoiceDialPeerVoipEntry 5 }
		
oacVoiceDialPeerOutCallsFailures OBJECT-TYPE
	SYNTAX Integer32
	MAX-ACCESS read-only
	STATUS current
	DESCRIPTION
		"Number of dial peer outgoing calls failures"
	::= { oacVoiceDialPeerVoipEntry 6 }

oacVoiceDialPeerOutCallsRasFailures OBJECT-TYPE
	SYNTAX Integer32
	MAX-ACCESS read-only
	STATUS current
	DESCRIPTION
		"Number of dial peer outgoing calls failures
		 cause : RAS Failures"
	::= { oacVoiceDialPeerVoipEntry 7 }

oacVoiceDialPeerOutCallsRasFailGatekeeperUnavailable OBJECT-TYPE
	SYNTAX Integer32
	MAX-ACCESS read-only
	STATUS current
	DESCRIPTION
		"number of dial peer outgoing calls failures
		 cause : RAS failure : Gatekeeper Unavailable"
	::= { oacVoiceDialPeerVoipEntry 8 }

oacVoiceDialPeerOutCallsRasFailAdmissionRejects OBJECT-TYPE
	SYNTAX Integer32
	MAX-ACCESS read-only
	STATUS current
	DESCRIPTION
		"number of dial peer outgoing calls failures
		 cause : RAS failure : Admission Reject"
	::= { oacVoiceDialPeerVoipEntry 9 }

oacVoiceDialPeerOutCallsH225Q931Failures OBJECT-TYPE
	SYNTAX Integer32
	MAX-ACCESS read-only
	STATUS current
	DESCRIPTION
		"number of dial peer outgoing calls failures
		 cause : H225 / Q931 failures"
	::= { oacVoiceDialPeerVoipEntry 10 }

oacVoiceDialPeerOutCallsHQFailCauseClass0 OBJECT-TYPE
	SYNTAX Integer32
	MAX-ACCESS read-only
	STATUS current
	DESCRIPTION
		"number of dial peer outgoing calls failures
		 cause : H225 / Q931 failures : Cause class 0"
	::= { oacVoiceDialPeerVoipEntry 11 }

oacVoiceDialPeerOutCallsHQFailCauseClass1 OBJECT-TYPE
	SYNTAX Integer32
	MAX-ACCESS read-only
	STATUS current
	DESCRIPTION
		"number of dial peer outgoing calls failures
		 cause : H225 / Q931 failures : cause class 1"
	::= { oacVoiceDialPeerVoipEntry 12 }

oacVoiceDialPeerOutCallsHQFailCC1NormalCause OBJECT-TYPE
	SYNTAX Integer32
	MAX-ACCESS read-only
	STATUS current
	DESCRIPTION
		"number of dial peer outgoing calls failures
		 cause : H225 / Q931 failures : CC1 : normal cause"
	::= { oacVoiceDialPeerVoipEntry 13 }

oacVoiceDialPeerOutCallsHQFailCC1UserBusy OBJECT-TYPE
	SYNTAX Integer32
	MAX-ACCESS read-only
	STATUS current
	DESCRIPTION
		"number of dial peer outgoing calls failures
		 cause : H225 / Q931 failures CC1 : User Busy"
	::= { oacVoiceDialPeerVoipEntry 14 }

oacVoiceDialPeerOutCallsHQFailCC1NoAnswer OBJECT-TYPE
	SYNTAX Integer32
	MAX-ACCESS read-only
	STATUS current
	DESCRIPTION
		"number of dial peer outgoing calls failures
		 cause : H225 / Q931 failures CC1 : no answer"
	::= { oacVoiceDialPeerVoipEntry 15 }

oacVoiceDialPeerOutCallsHQFailCauseClass2 OBJECT-TYPE
	SYNTAX Integer32
	MAX-ACCESS read-only
	STATUS current
	DESCRIPTION
		"number of dial peer outgoing calls failures
		 cause : H225 / Q931 failures : Cause class 2"
	::= { oacVoiceDialPeerVoipEntry 16 }

oacVoiceDialPeerOutCallsHQFailCauseClass3 OBJECT-TYPE
	SYNTAX Integer32
	MAX-ACCESS read-only
	STATUS current
	DESCRIPTION
		"number of dial peer outgoing calls failures
		 cause : H225 / Q931 failures : cause class 3"
	::= { oacVoiceDialPeerVoipEntry 17 }

oacVoiceDialPeerOutCallsHQFailCauseClass4 OBJECT-TYPE
	SYNTAX Integer32
	MAX-ACCESS read-only
	STATUS current
	DESCRIPTION
		"number of dial peer outgoing calls failures
		 cause : H225 / Q931 failures : cause class 4"
	::= { oacVoiceDialPeerVoipEntry 18 }

oacVoiceDialPeerOutCallsHQFailCauseClass5 OBJECT-TYPE
	SYNTAX Integer32
	MAX-ACCESS read-only
	STATUS current
	DESCRIPTION
		"number of dial peer outgoing calls failures
		 cause : H225 / Q931 failures : cause class 5"
	::= { oacVoiceDialPeerVoipEntry 19 }

oacVoiceDialPeerOutCallsHQFailCauseClass6 OBJECT-TYPE
	SYNTAX Integer32
	MAX-ACCESS read-only
	STATUS current
	DESCRIPTION
		"number of dial peer outgoing calls failures
		 cause : H225 / Q931 failures : cause class 6"
	::= { oacVoiceDialPeerVoipEntry 20 }

oacVoiceDialPeerOutCallsHQFailCauseClass7 OBJECT-TYPE
	SYNTAX Integer32
	MAX-ACCESS read-only
	STATUS current
	DESCRIPTION
		"number of dial peer outgoing calls failures
		 cause : H225 / Q931 failures : cause class 7"
	::= { oacVoiceDialPeerVoipEntry 21 }

oacVoiceDialPeerOutCallsH245Failures OBJECT-TYPE
	SYNTAX Integer32
	MAX-ACCESS read-only
	STATUS current
	DESCRIPTION
		"number of dial peer outgoing calls failures
		 cause : H245 failures"
	::= { oacVoiceDialPeerVoipEntry 22 }

oacVoiceDialPeerOutCallsH245FailIncompatibleCapabilities OBJECT-TYPE
	SYNTAX Integer32
	MAX-ACCESS read-only
	STATUS current
	DESCRIPTION
		"number of dial peer outgoing calls failures
		 cause : H245 failures : incompatible capabilities"
	::= { oacVoiceDialPeerVoipEntry 23 }

oacVoiceDialPeerOutCallsH245FailProtocolErrors OBJECT-TYPE
	SYNTAX Integer32
	MAX-ACCESS read-only
	STATUS current
	DESCRIPTION
		"number of dial peer outgoing calls failures
		 cause : H245 failures : protocol errors"
	::= { oacVoiceDialPeerVoipEntry 24 }

oacVoiceDialPeerOutCallsInternalFailures OBJECT-TYPE
	SYNTAX Integer32
	MAX-ACCESS read-only
	STATUS current
	DESCRIPTION
		"number of dial peer outgoing calls failures
		 cause : internal failures"
	::= { oacVoiceDialPeerVoipEntry 25 }

oacVoiceDialPeerOutCallsInternalFailDspUnavailable OBJECT-TYPE
	SYNTAX Integer32
	MAX-ACCESS read-only
	STATUS current
	DESCRIPTION
		"number of dial peer outgoing calls failures
		 cause : internal failures : DSP unavailable"
	::= { oacVoiceDialPeerVoipEntry 26 }

oacVoiceDialPeerOutCallsInternalFailMaxBwExceeded OBJECT-TYPE
	SYNTAX Integer32
	MAX-ACCESS read-only
	STATUS current
	DESCRIPTION
		"number of dial peer outgoing calls failures
		 cause : internal failures : max bandwidth exceeded"
	::= { oacVoiceDialPeerVoipEntry 27 }

oacVoiceDialPeerOutCallsInternalFailMaxConnExceeded OBJECT-TYPE
	SYNTAX Integer32
	MAX-ACCESS read-only
	STATUS current
	DESCRIPTION
		"number of dial peer outgoing calls failures
		 cause : internal failures : max connections exceeded"
	::= { oacVoiceDialPeerVoipEntry 28 }

oacVoiceDialPeerOutCallsInternalFailNotSpecified OBJECT-TYPE
	SYNTAX Integer32
	MAX-ACCESS read-only
	STATUS current
	DESCRIPTION
		"number of dial peer outgoing calls failures
		 cause : internal failures : not specified"
	::= { oacVoiceDialPeerVoipEntry 29 }

oacVoiceDialPeerIncCalls OBJECT-TYPE
	SYNTAX Integer32
	MAX-ACCESS read-only
	STATUS current
	DESCRIPTION
		"Number of dial peer incoming calls"
	::= { oacVoiceDialPeerVoipEntry 30 }
	
oacVoiceDialPeerIncCallsMgcpRingingEvents OBJECT-TYPE
	SYNTAX Integer32
	MAX-ACCESS read-only
	STATUS current
	DESCRIPTION
		" ? "
	::= { oacVoiceDialPeerVoipEntry 31 }
	
oacVoiceDialPeerIncCallsMgcpPathEstablished OBJECT-TYPE
	SYNTAX Integer32
	MAX-ACCESS read-only
	STATUS current
	DESCRIPTION
		" ? "
	::= { oacVoiceDialPeerVoipEntry 32 }

oacVoiceDialPeerIncCallsFailures OBJECT-TYPE
	SYNTAX Integer32
	MAX-ACCESS read-only
	STATUS current
	DESCRIPTION
		"Number of dial peer incoming calls failures"
	::= { oacVoiceDialPeerVoipEntry 33 }

oacVoiceDialPeerIncCallsRasFailures OBJECT-TYPE
	SYNTAX Integer32
	MAX-ACCESS read-only
	STATUS current
	DESCRIPTION
		"Number of dial peer incoming calls failures
		 Cause : RAS failures"
	::= { oacVoiceDialPeerVoipEntry 34 }

oacVoiceDialPeerIncCallsRasFailGatekeeperUnavailable OBJECT-TYPE
	SYNTAX Integer32
	MAX-ACCESS read-only
	STATUS current
	DESCRIPTION
		"Number of dial peer incoming calls failures
		 Cause : RAS failures : gatekeeper unavailable"
	::= { oacVoiceDialPeerVoipEntry 35 }

oacVoiceDialPeerIncCallsRasFailAdmissionRejects OBJECT-TYPE
	SYNTAX Integer32
	MAX-ACCESS read-only
	STATUS current
	DESCRIPTION
		"Number of dial peer incoming calls failures
		 Cause : RAS failures : admission reject"
	::= { oacVoiceDialPeerVoipEntry 36 }

oacVoiceDialPeerIncCallsLocalPortFailures OBJECT-TYPE
	SYNTAX Integer32
	MAX-ACCESS read-only
	STATUS current
	DESCRIPTION
		"Number of dial peer incoming calls failures
		 Cause : local port failures"
	::= { oacVoiceDialPeerVoipEntry 37 }

oacVoiceDialPeerIncCallsH245Failures OBJECT-TYPE
	SYNTAX Integer32
	MAX-ACCESS read-only
	STATUS current
	DESCRIPTION
		"Number of dial peer incoming calls failures
		 Cause : H245 failures"
	::= { oacVoiceDialPeerVoipEntry 38 }

oacVoiceDialPeerIncCallsH245FailIncompatibleCapabilities OBJECT-TYPE
	SYNTAX Integer32
	MAX-ACCESS read-only
	STATUS current
	DESCRIPTION
		"Number of dial peer incoming calls failures
		 Cause : H245 failures : incompatible capabilities"
	::= { oacVoiceDialPeerVoipEntry 39 }

oacVoiceDialPeerIncCallsH245FailProtocolErrors OBJECT-TYPE
	SYNTAX Integer32
	MAX-ACCESS read-only
	STATUS current
	DESCRIPTION
		"Number of dial peer incoming calls failures
		 Cause : H245 failures : protocol errors"
	::= { oacVoiceDialPeerVoipEntry 40 }

oacVoiceDialPeerIncCallsInternalFailures OBJECT-TYPE
	SYNTAX Integer32
	MAX-ACCESS read-only
	STATUS current
	DESCRIPTION
		"Number of dial peer incoming calls failures
		 Cause : internal failures"
	::= { oacVoiceDialPeerVoipEntry 41 }

oacVoiceDialPeerIncCallsInternalFailDspUnavailable OBJECT-TYPE
	SYNTAX Integer32
	MAX-ACCESS read-only
	STATUS current
	DESCRIPTION
		"Number of dial peer incoming calls failures
		 Cause : internal failures : DSP unavailable"
	::= { oacVoiceDialPeerVoipEntry 42 }

oacVoiceDialPeerIncCallsInternalFailUnknownNumber OBJECT-TYPE
	SYNTAX Integer32
	MAX-ACCESS read-only
	STATUS current
	DESCRIPTION
		"Number of dial peer incoming calls failures
		 Cause : internal failures : unknown number"
	::= { oacVoiceDialPeerVoipEntry 43 }

oacVoiceDialPeerIncCallsInternalFailChannelPortUnavailable OBJECT-TYPE
	SYNTAX Integer32
	MAX-ACCESS read-only
	STATUS current
	DESCRIPTION
		"Number of dial peer incoming calls failures
		 Cause : internal failures : channel port unavailable"
	::= { oacVoiceDialPeerVoipEntry 44 }

oacVoiceDialPeerIncCallsInternalFailMaxBwExceeded OBJECT-TYPE
	SYNTAX Integer32
	MAX-ACCESS read-only
	STATUS current
	DESCRIPTION
		"Number of dial peer incoming calls failures
		 Cause : internal failures : max bandwidth exceeded"
	::= { oacVoiceDialPeerVoipEntry 45 }

oacVoiceDialPeerIncCallsInternalFailMaxConnExceeded OBJECT-TYPE
	SYNTAX Integer32
	MAX-ACCESS read-only
	STATUS current
	DESCRIPTION
		"Number of dial peer incoming calls failures
		 Cause : internal failures : max connections exceeded"
	::= { oacVoiceDialPeerVoipEntry 46 }
	
oacVoiceDialPeerIncCallsInternalFailNotSpecified OBJECT-TYPE
	SYNTAX Integer32
	MAX-ACCESS read-only
	STATUS current
	DESCRIPTION
		"Number of dial peer incoming calls failures
		 Cause : internal failures : not specified"
	::= { oacVoiceDialPeerVoipEntry 47 }
	
oacVoiceDialPeerIncCallsAdviceofCharge OBJECT-TYPE
	SYNTAX Integer32
	MAX-ACCESS read-only
	STATUS current
	DESCRIPTION
		" ? "
	::= { oacVoiceDialPeerVoipEntry 48 }
	
oacVoiceDialPeerRtpStatNbTxPackets OBJECT-TYPE
	SYNTAX Unsigned32
	MAX-ACCESS read-only
	STATUS current
	DESCRIPTION
		"Number of RTP Tx packets"
	::= { oacVoiceDialPeerVoipEntry 49 }

oacVoiceDialPeerRtpStatNbRxPackets OBJECT-TYPE
	SYNTAX Unsigned32
	MAX-ACCESS read-only
	STATUS current
	DESCRIPTION
		"Number of RTP Rx Packets"
	::= { oacVoiceDialPeerVoipEntry 50 }

oacVoiceDialPeerRtpStatNbTxBytes OBJECT-TYPE
	SYNTAX Unsigned32
	MAX-ACCESS read-only
	STATUS current
	DESCRIPTION
		"Number of RTP Tx Bytes"
	::= { oacVoiceDialPeerVoipEntry 51 }

oacVoiceDialPeerRtpStatNbRxBytes OBJECT-TYPE
	SYNTAX Unsigned32
	MAX-ACCESS read-only
	STATUS current
	DESCRIPTION
		"Number of RTP Rx Bytes"
	::= { oacVoiceDialPeerVoipEntry 52 }

oacVoiceDialPeerRtpStatNbExcessiveJitterEvents OBJECT-TYPE
	SYNTAX Unsigned32
	MAX-ACCESS read-only
	STATUS current
	DESCRIPTION
		"Number of RTP Excessive Jitter events"
	::= { oacVoiceDialPeerVoipEntry 53 }

oacVoiceDialPeerRtpStatNbLostPackets OBJECT-TYPE
	SYNTAX Unsigned32
	MAX-ACCESS read-only
	STATUS current
	DESCRIPTION
		"Number of RTP lost packets"
	::= { oacVoiceDialPeerVoipEntry 54 }

oacVoiceDialPeerRtpStatNbInvalidPackets OBJECT-TYPE
	SYNTAX Unsigned32
	MAX-ACCESS read-only
	STATUS current
	DESCRIPTION
		"Number of RTP invalid packets"
	::= { oacVoiceDialPeerVoipEntry 55 }

	
oacVoiceDialPeerModemNbSwitchingToModemMode OBJECT-TYPE
	SYNTAX Unsigned32
	MAX-ACCESS read-only
	STATUS current
	DESCRIPTION
		"number of switching to modem mode"
	::= { oacVoiceDialPeerVoipEntry 56 }

	
oacVoiceDialPeerFaxNbOutgoingFax OBJECT-TYPE
	SYNTAX Integer32
	MAX-ACCESS read-only
	STATUS current
	DESCRIPTION
		"Number of Outgoing fax"
	::= { oacVoiceDialPeerVoipEntry 57 }

oacVoiceDialPeerFaxNbIncomingFax OBJECT-TYPE
	SYNTAX Integer32
	MAX-ACCESS read-only
	STATUS current
	DESCRIPTION
		"Number of Incoming fax"
	::= { oacVoiceDialPeerVoipEntry 58 }

oacVoiceDialPeerFaxNbFailures OBJECT-TYPE
	SYNTAX Integer32
	MAX-ACCESS read-only
	STATUS current
	DESCRIPTION
		"Number of fax failures"
	::= { oacVoiceDialPeerVoipEntry 59 }

oacVoiceDialPeerFaxFailureRequestMode OBJECT-TYPE
	SYNTAX Integer32
	MAX-ACCESS read-only
	STATUS current
	DESCRIPTION
		"Number of Fax Failures
		 cause : request mode"
	::= { oacVoiceDialPeerVoipEntry 60 }

oacVoiceDialPeerFaxFailurePreMsgProcedure OBJECT-TYPE
	SYNTAX Integer32
	MAX-ACCESS read-only
	STATUS current
	DESCRIPTION
		"Number of fax failures
		 cause : pre-message procedure"
	::= { oacVoiceDialPeerVoipEntry 61 }

oacVoiceDialPeerFaxFailurePage OBJECT-TYPE
	SYNTAX Integer32
	MAX-ACCESS read-only
	STATUS current
	DESCRIPTION
		"Number of fax failures
		 cause : pages"
	::= { oacVoiceDialPeerVoipEntry 62 }

oacVoiceDialPeerFaxNbTxPackets OBJECT-TYPE
	SYNTAX Unsigned32
	MAX-ACCESS read-only
	STATUS current
	DESCRIPTION
		"Number of fax Tx packets"
	::= { oacVoiceDialPeerVoipEntry 63 }

oacVoiceDialPeerFaxNbRxPackets OBJECT-TYPE
	SYNTAX Unsigned32
	MAX-ACCESS read-only
	STATUS current
	DESCRIPTION
		"Number of fax Rx packets"
	::= { oacVoiceDialPeerVoipEntry 64 }

oacVoiceDialPeerFaxNbTxBytes OBJECT-TYPE
	SYNTAX Unsigned32
	MAX-ACCESS read-only
	STATUS current
	DESCRIPTION
		"Number of fax Tx Bytes"
	::= { oacVoiceDialPeerVoipEntry 65 }

oacVoiceDialPeerFaxNbRxBytes OBJECT-TYPE
	SYNTAX Unsigned32
	MAX-ACCESS read-only
	STATUS current
	DESCRIPTION
		"Number of fax Rx Bytes"
	::= { oacVoiceDialPeerVoipEntry 66 }

oacVoiceDialPeerFaxNbLostPackets OBJECT-TYPE
	SYNTAX Unsigned32
	MAX-ACCESS read-only
	STATUS current
	DESCRIPTION
		"Number of fax lost packets"
	::= { oacVoiceDialPeerVoipEntry 67 }


-- ----------------------------------------------------------------------------	
--  3 . oacVoiceH323Gw
-- ----------------------------------------------------------------------------
                              
oacVoiceH323Gw OBJECT IDENTIFIER ::= { oacVoiceStatVoip 3 }
                                   
oacVoiceH323GwState OBJECT-TYPE
	SYNTAX OacVoipGatewayState
	MAX-ACCESS read-only
	STATUS current
	DESCRIPTION
		"State of the H323 gateway"
	::= { oacVoiceH323Gw 1 }   
		
oacVoiceH323GwStateReason OBJECT-TYPE
	SYNTAX OacVoipGatewayStateReason
	MAX-ACCESS read-only
	STATUS current
	DESCRIPTION
		"H323 Gateway state reason"
	::= { oacVoiceH323Gw 2 }

oacVoiceH323GwRasBwControl OBJECT-TYPE
	SYNTAX OacH323GwRasBwControl
	MAX-ACCESS read-only
	STATUS current
	DESCRIPTION
		"control of oacVoiceH323GwRasBw"
	::= { oacVoiceH323Gw 3 }

oacVoiceH323GwPortabilityStatus OBJECT-TYPE
	SYNTAX OacH323GwPortabilityStatus
	MAX-ACCESS read-only
	STATUS current
	DESCRIPTION
		"?"
	::= { oacVoiceH323Gw 4 }

oacVoiceH323GwPortabilityStatusTimeout OBJECT-TYPE
	SYNTAX Integer32
	MAX-ACCESS read-only
	STATUS current
	DESCRIPTION
		"specify the timeout of oacVoiceH323GwPortabilityStatus"
	::= { oacVoiceH323Gw 5 }

oacVoiceH323GwDs0Configured OBJECT-TYPE
	SYNTAX Integer32
	MAX-ACCESS read-only
	STATUS current
	DESCRIPTION
		"specify the configured oacVoiceH323GwDs0"
	::= { oacVoiceH323Gw 6 }

oacVoiceH323GwDs0Low OBJECT-TYPE
	SYNTAX Integer32
	MAX-ACCESS read-only
	STATUS current
	DESCRIPTION
		"specify the low of oacVoiceH323GwDs0"
	::= { oacVoiceH323Gw 7 }

oacVoiceH323GwDs0High OBJECT-TYPE
	SYNTAX Integer32
	MAX-ACCESS read-only
	STATUS current
	DESCRIPTION
		"specify the high of oacVoiceH323GwDs0"
	::= { oacVoiceH323Gw 8 }

oacVoiceH323GwDs0Current  OBJECT-TYPE
	SYNTAX Integer32
	MAX-ACCESS read-only
	STATUS current
	DESCRIPTION
		"The current state of oacVoiceH323GwDs0"
	::= { oacVoiceH323Gw 9 }

oacVoiceH323GwBwConfigured OBJECT-TYPE
	SYNTAX Integer32
	MAX-ACCESS read-only
	STATUS current
	DESCRIPTION
		"the object specify the configured oacVoiceH323GwBw"
	::= { oacVoiceH323Gw 10 }

oacVoiceH323GwBwLow OBJECT-TYPE
	SYNTAX Integer32
	MAX-ACCESS read-only
	STATUS current
	DESCRIPTION
		"The Low of oacVoiceH323GwBw"
	::= { oacVoiceH323Gw 11 }

oacVoiceH323GwBwHigh OBJECT-TYPE
	SYNTAX Integer32
	MAX-ACCESS read-only
	STATUS current
	DESCRIPTION
		"The high of oacVoiceH323GwBw"
	::= { oacVoiceH323Gw 12 }

oacVoiceH323GwBwCurrent OBJECT-TYPE
	SYNTAX Integer32
	MAX-ACCESS read-only
	STATUS current
	DESCRIPTION
		"The current state of oacVoiceH323GwBwCurrent"
	::= { oacVoiceH323Gw 13 }

oacVoiceH323GwRegistrationState OBJECT-TYPE
	SYNTAX OacVoipGatewayRegistrationState
	MAX-ACCESS read-only
	STATUS current
	DESCRIPTION
		"H323 Gateway registration state"
	::= { oacVoiceH323Gw 14 }
			
oacVoiceH323GwGatekeeperIdentifier OBJECT-TYPE
	SYNTAX DisplayString (SIZE(0..40))
	MAX-ACCESS read-only
	STATUS current
	DESCRIPTION
		"H323 gakeeper Identifier where the H323Gw is eventually registered"
	::= { oacVoiceH323Gw 15 }

oacVoiceH323GwGatekeeperAddress OBJECT-TYPE
	SYNTAX DisplayString (SIZE(0..15))
	MAX-ACCESS read-only
	STATUS current
	DESCRIPTION
		"IP address of the gatekeeper"
	::= { oacVoiceH323Gw 16 }

oacVoiceH323GwRegistrationRequest OBJECT-TYPE
	SYNTAX Integer32
	MAX-ACCESS read-only
	STATUS current
	DESCRIPTION
		"Number of H323 Registration requests"
	::= { oacVoiceH323Gw 17 }

oacVoiceH323GwRegistrationFailures OBJECT-TYPE
	SYNTAX Integer32
	MAX-ACCESS read-only
	STATUS current
	DESCRIPTION
		"number of H323 registration failures"
	::= { oacVoiceH323Gw 18 }

oacVoiceH323GwRegFailNoResponse  OBJECT-TYPE
	SYNTAX Integer32
	MAX-ACCESS read-only
	STATUS current
	DESCRIPTION
		"Number of H323 registration failures
		 cause : no response"
	::= { oacVoiceH323Gw 19 }

oacVoiceH323GwRegFailInvalidIpAddress  OBJECT-TYPE
	SYNTAX Integer32
	MAX-ACCESS read-only
	STATUS current
	DESCRIPTION
		"Number of registration failures
		 cause : invalid IP address"
	::= { oacVoiceH323Gw 20 }

oacVoiceH323GwRegFailDuplicateAlias OBJECT-TYPE
	SYNTAX Integer32
	MAX-ACCESS read-only
	STATUS current
	DESCRIPTION
		"Number of H323 registration failures
		 cause : Duplicate alias"
	::= { oacVoiceH323Gw 21 }

oacVoiceH323GwRegFailInvalidTerminalType OBJECT-TYPE
	SYNTAX Integer32
	MAX-ACCESS read-only
	STATUS current
	DESCRIPTION
		"Number of H323 registration failures
		 cause : invalid terminal type"
	::= { oacVoiceH323Gw 22 }

oacVoiceH323GwRegFailResourceUnavailable OBJECT-TYPE
	SYNTAX Integer32
	MAX-ACCESS read-only
	STATUS current
	DESCRIPTION
		"Number of H323 registration failures
		 cause : resource unavailable"
	::= { oacVoiceH323Gw 23 }
	
oacVoiceH323GwRegFailInvalidAlias OBJECT-TYPE
	SYNTAX Integer32
	MAX-ACCESS read-only
	STATUS current
	DESCRIPTION
		"Number of H323 registration failures
		 cause : invalid alias"
	::= { oacVoiceH323Gw 24 }

oacVoiceH323GwRegFailSecurityDenial OBJECT-TYPE
	SYNTAX Integer32
	MAX-ACCESS read-only
	STATUS current
	DESCRIPTION
		"Number of H323 registration failures
		 cause : security denial"
	::= { oacVoiceH323Gw 25 }

oacVoiceH323GwRegFailUndefinedReason OBJECT-TYPE
	SYNTAX Integer32
	MAX-ACCESS read-only
	STATUS current
	DESCRIPTION
		"Number of H323 registration failures
		 cause : undefined reason"
	::= { oacVoiceH323Gw 26 }

oacVoiceH323GwAdmissionRequests OBJECT-TYPE
	SYNTAX Integer32
	MAX-ACCESS read-only
	STATUS current
	DESCRIPTION
		"Number of admission requests"
	::= { oacVoiceH323Gw 27 }

oacVoiceH323GwAdmissionRejects OBJECT-TYPE
	SYNTAX Integer32
	MAX-ACCESS read-only
	STATUS current
	DESCRIPTION
		"Number of H323 admission rejects"
	::= { oacVoiceH323Gw 28 }

oacVoiceH323GwAdmRejCalledPartyNotRegistered OBJECT-TYPE
	SYNTAX Integer32
	MAX-ACCESS read-only
	STATUS current
	DESCRIPTION
		"Number of H323 admission rejects
		 cause : called party not registered"
	::= { oacVoiceH323Gw 29 }

oacVoiceH323GwAdmRejInvalidPermission OBJECT-TYPE
	SYNTAX Integer32
	MAX-ACCESS read-only
	STATUS current
	DESCRIPTION
		"Number of H323 admission rejects
		 cause : invalid permission"
	::= { oacVoiceH323Gw 30 }

oacVoiceH323GwAdmRejRequestDenied   OBJECT-TYPE
	SYNTAX Integer32
	MAX-ACCESS read-only
	STATUS current
	DESCRIPTION
		"Number of H323 admission rejects
		 cause : request denied"
	::= { oacVoiceH323Gw 31 }

oacVoiceH323GwAdmRejCallerNotRegistered OBJECT-TYPE
	SYNTAX Integer32
	MAX-ACCESS read-only
	STATUS current
	DESCRIPTION
		"Number of H323 admission rejects
		 cause : caller not registered"
	::= { oacVoiceH323Gw 32 }

oacVoiceH323GwAdmRejResourceUnavailable OBJECT-TYPE
	SYNTAX Integer32
	MAX-ACCESS read-only
	STATUS current
	DESCRIPTION
		"Number of H323 admission rejects
		 cause : resource unavailable"
	::= { oacVoiceH323Gw 33 }

oacVoiceH323GwAdmRejSecurityDenial OBJECT-TYPE
	SYNTAX Integer32
	MAX-ACCESS read-only
	STATUS current
	DESCRIPTION
		"Number of H323 admission rejects
		 cause : security denial"
	::= { oacVoiceH323Gw 34 }

oacVoiceH323GwAdmRejInvalidEndpointIdent OBJECT-TYPE
	SYNTAX Integer32
	MAX-ACCESS read-only
	STATUS current
	DESCRIPTION
		"Number of H323 admission rejects
		 cause : invalid endpoint identity"
	::= { oacVoiceH323Gw 35 }

oacVoiceH323GwAdmRejIncompleteAddress OBJECT-TYPE
	SYNTAX Integer32
	MAX-ACCESS read-only
	STATUS current
	DESCRIPTION
		"Number of H323 admission rejects
		 cause : incomplete address"
	::= { oacVoiceH323Gw 36 }

oacVoiceH323GwAdmRejNotSpecified OBJECT-TYPE
	SYNTAX Integer32
	MAX-ACCESS read-only
	STATUS current
	DESCRIPTION
		"Number of H323 admission rejects
		 cause : not specified"
	::= { oacVoiceH323Gw 37 }

oacVoiceH323GwAdmRejUndefinedReason OBJECT-TYPE
	SYNTAX Integer32
	MAX-ACCESS read-only
	STATUS current
	DESCRIPTION
		"Number of H323 admission rejects
		 cause : undefined reason"
	::= { oacVoiceH323Gw 38 }


-- ----------------------------------------------------------------------------	
--  4 . oacVoiceSipGw
-- ----------------------------------------------------------------------------
                              
oacVoiceSipGw OBJECT IDENTIFIER ::= { oacVoiceStatVoip 4 }
                                   
oacVoiceSipGwState OBJECT-TYPE
	SYNTAX OacVoipGatewayState
	MAX-ACCESS read-only
	STATUS current
	DESCRIPTION
		"State of the SIP gateway"
	::= { oacVoiceSipGw 1 }

oacVoiceSipGwRegistrationState OBJECT-TYPE
	SYNTAX OacVoipGatewayRegistrationState
	MAX-ACCESS read-only
	STATUS current
	DESCRIPTION
		"Registration state of the SIP gateway"
	::= { oacVoiceSipGw 2 } 

oacVoiceSipGwRegistrarServer OBJECT-TYPE
	SYNTAX DisplayString (SIZE(0..39))
	MAX-ACCESS read-only
	STATUS current
	DESCRIPTION
		"IP address or DNS:port of registrar"
	::= { oacVoiceSipGw 3 } 

oacVoiceSipGwBandwidth OBJECT-TYPE
	SYNTAX DisplayString (SIZE(0..39))
	MAX-ACCESS read-only
	STATUS current
	DESCRIPTION
		"SIP Gateway Bandwidth"
	::= { oacVoiceSipGw 4 } 

oacVoiceSipGwRegistrationErrors OBJECT-TYPE
	SYNTAX Integer32
	MAX-ACCESS read-only
	STATUS current
	DESCRIPTION
		"Number of SIP Gateway registration errors"
	::= { oacVoiceSipGw 5 } 

oacVoiceSipGwRegisteredEndpoints OBJECT-TYPE
	SYNTAX Integer32
	MAX-ACCESS read-only
	STATUS current
	DESCRIPTION
		"Number of SIP Gateway registered Endpoints"
	::= { oacVoiceSipGw 6 } 

oacVoiceSipGwCurrentCalls OBJECT-TYPE
	SYNTAX Integer32
	MAX-ACCESS read-only
	STATUS current
	DESCRIPTION
		"Number of SIP Gateway current calls"
	::= { oacVoiceSipGw 7 } 

oacVoiceSipGwAuthenticationRejects OBJECT-TYPE
	SYNTAX Integer32
	MAX-ACCESS read-only
	STATUS current
	DESCRIPTION
		"Number of SIP Gateway authentication rejects"
	::= { oacVoiceSipGw 8 } 

oacVoiceSipGwEndpointTable OBJECT-TYPE
	SYNTAX SEQUENCE OF OacVoiceSipGwEndpointEntry
	MAX-ACCESS not-accessible
	STATUS current
	DESCRIPTION
		"VoIP SIP Gateway Endpoints table"
	::= { oacVoiceSipGw 9 } 

oacVoiceSipGwMaxToRegisterEndpoints OBJECT-TYPE
	SYNTAX Integer32
	MAX-ACCESS read-only
	STATUS current
	DESCRIPTION
		"Number of endpoint to be registered to an external registrar"
	::= { oacVoiceSipGw 10 } 
                              
oacVoiceSipGwEndpointEntry OBJECT-TYPE
	SYNTAX OacVoiceSipGwEndpointEntry
	MAX-ACCESS not-accessible
	STATUS current
	DESCRIPTION
		"VoIP SIP Gateway Endpoints Ports Table Entry"
	INDEX {oacVoiceSipGwPhoneIndex }
	::= { oacVoiceSipGwEndpointTable 1 }
                                   
OacVoiceSipGwEndpointEntry ::= SEQUENCE {
	oacVoiceSipGwPhoneIndex
		Integer32,
	oacVoiceSipGwPhoneState
		OacVoiceSipGwPhoneState,
	oacVoiceSipGwPhoneNumber
		DisplayString,
	oacVoiceSipGwPhoneSipId
		DisplayString,
	oacVoiceSipGwRegistrationTimeout
		DisplayString
	}
	
oacVoiceSipGwPhoneIndex OBJECT-TYPE
	SYNTAX Integer32
	MAX-ACCESS read-only
	STATUS current
	DESCRIPTION
		"VoIP SIP Phone Index"
	::= { oacVoiceSipGwEndpointEntry 1 } 

oacVoiceSipGwPhoneState OBJECT-TYPE
	SYNTAX OacVoiceSipGwPhoneState
	MAX-ACCESS read-only
	STATUS current
	DESCRIPTION
		"VoIP SIP Server State"
	::= { oacVoiceSipGwEndpointEntry 2 } 

oacVoiceSipGwPhoneNumber OBJECT-TYPE
	SYNTAX DisplayString (SIZE(0..35))
	MAX-ACCESS read-only
	STATUS current
	DESCRIPTION
		"VoIP SIP Phone Number"
	::= { oacVoiceSipGwEndpointEntry 3 } 

oacVoiceSipGwPhoneSipId  OBJECT-TYPE
	SYNTAX DisplayString (SIZE(0..40))
	MAX-ACCESS read-only
	STATUS current
	DESCRIPTION
		"VoIP SIP phone ID"
	::= { oacVoiceSipGwEndpointEntry 4 } 

oacVoiceSipGwRegistrationTimeout OBJECT-TYPE
	SYNTAX DisplayString (SIZE(0..39))
	MAX-ACCESS read-only
	STATUS current
	DESCRIPTION
		"VoIP SIP phone registration timeout"
	::= { oacVoiceSipGwEndpointEntry 5 }

-- ----------------------------------------------------------------------------	
--  5 . oacVoiceSipServer
-- ----------------------------------------------------------------------------
                              
oacVoiceSipServer OBJECT IDENTIFIER ::= { oacVoiceStatVoip 5 }
                                   
oacVoiceSipServerState OBJECT-TYPE
	SYNTAX OacVoipGatewayState
	MAX-ACCESS read-only
	STATUS current
	DESCRIPTION
		"State of the SIP Server"
	::= { oacVoiceSipServer 1 }

oacVoiceSipServerRegisteredEndpoints OBJECT-TYPE
	SYNTAX Integer32
	MAX-ACCESS read-only
	STATUS current
	DESCRIPTION
		"Number of SIP Server registered Endpoints"
	::= { oacVoiceSipServer 2 } 

oacVoiceSipServerRegistrarServer OBJECT-TYPE
	SYNTAX DisplayString (SIZE(0..40))
	MAX-ACCESS read-only
	STATUS current
	DESCRIPTION
		"IP address or DNS:port of registrar"
	::= { oacVoiceSipServer 3 } 

oacVoiceSipServerCurrentCalls OBJECT-TYPE
	SYNTAX Integer32
	MAX-ACCESS read-only
	STATUS current
	DESCRIPTION
		"Number of SIP Servery current calls"
	::= { oacVoiceSipServer 4 } 

oacVoiceSipServerEndpointTable OBJECT-TYPE
	SYNTAX SEQUENCE OF OacVoiceSipServerEndpointEntry
	MAX-ACCESS not-accessible
	STATUS current
	DESCRIPTION
		"VoIP SIP server Endpoints table"
	::= { oacVoiceSipServer 5 }
                              
oacVoiceSipServerEndpointEntry OBJECT-TYPE
	SYNTAX OacVoiceSipServerEndpointEntry
	MAX-ACCESS not-accessible
	STATUS current
	DESCRIPTION
		"VoIP SIP server Endpoints Ports Table Entry"
	INDEX {oacVoiceSipServerPhoneIndex }
	::= { oacVoiceSipServerEndpointTable 1 }
                                   
OacVoiceSipServerEndpointEntry ::= SEQUENCE {
	oacVoiceSipServerPhoneIndex
		Integer32,
	oacVoiceSipServerPhoneNumber
		DisplayString,
	oacVoiceSipServerPhoneIpAddress
		DisplayString,
	oacVoiceSipServerPhoneSipId
		DisplayString,
	oacVoiceSipServerRegistrationTime
		DisplayString,	
	oacVoiceSipServerRegistrationTimeout
		DisplayString
	}
	
oacVoiceSipServerPhoneIndex OBJECT-TYPE
	SYNTAX Integer32
	MAX-ACCESS read-only
	STATUS current
	DESCRIPTION
		"VoIP SIP Phone Index"
	::= { oacVoiceSipServerEndpointEntry 1 } 

oacVoiceSipServerPhoneNumber OBJECT-TYPE
	SYNTAX DisplayString (SIZE(0..35))
	MAX-ACCESS read-only
	STATUS current
	DESCRIPTION
		"VoIP SIP Phone Number"
	::= { oacVoiceSipServerEndpointEntry 2 } 

oacVoiceSipServerPhoneIpAddress OBJECT-TYPE
	SYNTAX DisplayString (SIZE(0..40))
	MAX-ACCESS read-only
	STATUS current
	DESCRIPTION
		"VoIP SIP Phone IP address"
	::= { oacVoiceSipServerEndpointEntry 3 } 
	
oacVoiceSipServerPhoneSipId  OBJECT-TYPE
	SYNTAX DisplayString (SIZE(0..40))
	MAX-ACCESS read-only
	STATUS current
	DESCRIPTION
		"VoIP SIP phone ID"
	::= { oacVoiceSipServerEndpointEntry 4 } 

oacVoiceSipServerRegistrationTime OBJECT-TYPE
	SYNTAX DisplayString (SIZE(0..39))
	MAX-ACCESS read-only
	STATUS current
	DESCRIPTION
		"VoIP SIP phone registration time"
	::= { oacVoiceSipServerEndpointEntry 5 }

oacVoiceSipServerRegistrationTimeout OBJECT-TYPE
	SYNTAX DisplayString (SIZE(0..39))
	MAX-ACCESS read-only
	STATUS current
	DESCRIPTION
		"VoIP SIP phone registration time out"
	::= { oacVoiceSipServerEndpointEntry 6 }

-- ----------------------------------------------------------------------------	
--  6 . oacVoiceMgcpGw
-- ----------------------------------------------------------------------------
                              
oacVoiceMgcpGw OBJECT IDENTIFIER ::= { oacVoiceStatVoip 6 }

oacVoiceMgcpGwState OBJECT-TYPE
	SYNTAX OacVoipGatewayState
	MAX-ACCESS read-only
	STATUS current
	DESCRIPTION
		"State of the MGCP gateway"
	::= { oacVoiceMgcpGw 1 }

oacVoiceMgcpGwCallAgentIpAddress OBJECT-TYPE
	SYNTAX DisplayString (SIZE(8..21))
	MAX-ACCESS read-only
	STATUS current
	DESCRIPTION
		"MGCP gateway call agent IP address"
	::= { oacVoiceMgcpGw 2 }

oacVoiceMgcpGwConnectionState OBJECT-TYPE
	SYNTAX OacVoipMgcpGatewayConnectionState
	MAX-ACCESS read-only
	STATUS current
	DESCRIPTION
		"State of the MGCP gateway"
	::= { oacVoiceMgcpGw 3 }

oacVoiceMgcpGwEstablishedPathCurrentNumber OBJECT-TYPE
	SYNTAX Integer32
	MAX-ACCESS read-only
	STATUS current
	DESCRIPTION
		"MGCP gateway established path current number"
	::= { oacVoiceMgcpGw 4 }

oacVoiceMgcpGwOutCallsOffHookEvents OBJECT-TYPE
	SYNTAX Integer32
	MAX-ACCESS read-only
	STATUS current
	DESCRIPTION
		"Number of MGCP gateway outgoing calls off hook events"
	::= { oacVoiceMgcpGw 5 }

oacVoiceMgcpGwOutCallsPathEstablished OBJECT-TYPE
	SYNTAX Integer32
	MAX-ACCESS read-only
	STATUS current
	DESCRIPTION
		"Number of MGCP gateway outgoing calls path established"
	::= { oacVoiceMgcpGw 6 }

oacVoiceMgcpGwIncCallsRingingEvents OBJECT-TYPE
	SYNTAX Integer32
	MAX-ACCESS read-only
	STATUS current
	DESCRIPTION
		"Number of MGCP gateway incoming calls ringing events"
	::= { oacVoiceMgcpGw 7 }

oacVoiceMgcpGwIncCallsPath OBJECT-TYPE
	SYNTAX Integer32
	MAX-ACCESS read-only
	STATUS current
	DESCRIPTION
		"Number of MGCP gateway incoming calls path"
	::= { oacVoiceMgcpGw 8 }
                                                                    

-- ----------------------------------------------------------------------------	
--  oacVoiceStatMos
-- ----------------------------------------------------------------------------
oacVoiceStatMos OBJECT IDENTIFIER ::= { oacVoiceStatObjects 4 }
-- oacVoiceStatMosEntry OBJECT IDENTIFIER ::= { oacVoiceStatMosTable 1 }

oacVoiceStatMosTable OBJECT-TYPE
  SYNTAX SEQUENCE OF OacVoiceStatMosEntry
  MAX-ACCESS not-accessible
  STATUS current
  DESCRIPTION
    "Voice MOS table."
  ::= { oacVoiceStatMos 1 }

oacVoiceStatMosEntry OBJECT-TYPE
  SYNTAX OacVoiceStatMosEntry
  MAX-ACCESS not-accessible
  STATUS current
  DESCRIPTION
    "Voice MOS table entry."
  INDEX { oacVoiceStatMosIndex  }
  ::= { oacVoiceStatMosTable 1 }

OacVoiceStatMosEntry ::= SEQUENCE {
  oacVoiceStatMosIndex
    Integer32,
  oacVoiceStatMosEntryNumberOfCalls
    Integer32,
  oacVoiceStatMosEntryMosAvg
    DisplayString (SIZE (0..5)),
  oacVoiceStatMosEntryMosMin
    DisplayString (SIZE (0..5)),
  oacVoiceStatMosEntryMosMax
    DisplayString (SIZE (0..5)),
  oacVoiceStatMosEntryErlAvg
    Integer32,
  oacVoiceStatMosEntryAcomAvg
    Integer32,
  oacVoiceStatMosEntryLossRateAvg
    Integer32,
  oacVoiceStatMosJitterAvg
  	Integer32,
  oacVoiceStatMosEntryMaxDelayAvg
    Integer32,
  oacVoiceStatMosEntryPddAvg
    Integer32
}

oacVoiceStatMosIndex OBJECT-TYPE
  SYNTAX Integer32 (0..1)
  MAX-ACCESS read-only
  STATUS current
  DESCRIPTION
    "MOS Index for H-1 or current: 0 for current and 1 for H-1."
  ::= { oacVoiceStatMosEntry 1 }

oacVoiceStatMosEntryNumberOfCalls OBJECT-TYPE
  SYNTAX Integer32
  MAX-ACCESS read-only
  STATUS current
  DESCRIPTION
    "Number of Calls."
  ::= { oacVoiceStatMosEntry 2 }

oacVoiceStatMosEntryMosAvg OBJECT-TYPE
  SYNTAX DisplayString (SIZE (0..5))
  MAX-ACCESS read-only
  STATUS current
  DESCRIPTION
    "Average of MOS."
  ::= { oacVoiceStatMosEntry 3 }

oacVoiceStatMosEntryMosMin OBJECT-TYPE
  SYNTAX DisplayString (SIZE (0..5))
  MAX-ACCESS read-only
  STATUS current
  DESCRIPTION
    "Minimum of MOS."
  ::= { oacVoiceStatMosEntry 4 }

oacVoiceStatMosEntryMosMax OBJECT-TYPE
  SYNTAX DisplayString (SIZE (0..5))
  MAX-ACCESS read-only
  STATUS current
  DESCRIPTION
    "Maximum of MOS."
  ::= { oacVoiceStatMosEntry 5 }

oacVoiceStatMosEntryErlAvg OBJECT-TYPE
  SYNTAX Integer32
  MAX-ACCESS read-only
  STATUS current
  DESCRIPTION
    "Average of ERL."
  ::= { oacVoiceStatMosEntry 6 }

oacVoiceStatMosEntryAcomAvg OBJECT-TYPE
  SYNTAX Integer32
  MAX-ACCESS read-only
  STATUS current
  DESCRIPTION
    "Average of ACOM."
  ::= { oacVoiceStatMosEntry 7 }

oacVoiceStatMosEntryLossRateAvg OBJECT-TYPE
  SYNTAX Integer32
  MAX-ACCESS read-only
  STATUS current
  DESCRIPTION
    "Average of loss-rate."
  ::= { oacVoiceStatMosEntry 8 }

oacVoiceStatMosJitterAvg OBJECT-TYPE
  SYNTAX Integer32
  MAX-ACCESS read-only
  STATUS current
  DESCRIPTION
    "Average of jitter."
  ::= { oacVoiceStatMosEntry 9 }

oacVoiceStatMosEntryMaxDelayAvg OBJECT-TYPE
  SYNTAX Integer32
  MAX-ACCESS read-only
  STATUS current
  DESCRIPTION
    "Average of Max delay."
  ::= { oacVoiceStatMosEntry 10 }

oacVoiceStatMosEntryPddAvg OBJECT-TYPE
  SYNTAX Integer32
  MAX-ACCESS read-only
  STATUS current
  DESCRIPTION
    "Average of Pdd (Post Dialed Delay)."
  ::= { oacVoiceStatMosEntry 11 }

-- ----------------------------------------------------------------------------
-- ----------------------------------------------------------------------------
-- ----------------------------------------------------------------------------

oacVoiceStatGroups OBJECT IDENTIFIER ::= { oacVoiceStatConformance 1}

oacVoiceStatCompliances OBJECT IDENTIFIER ::= { oacVoiceStatConformance 2}

oacVoiceStatCompliance MODULE-COMPLIANCE
      STATUS  current
      DESCRIPTION
          "The compliance statement for agents that support the
          ONEACCESS-VOICE-MIB."
      MODULE -- this module
          MANDATORY-GROUPS { oacVoiceStatGeneralGroup
                }

	::= { oacVoiceStatCompliances 1}

oacVoiceStatGeneralGroup OBJECT-GROUP
	OBJECTS {
    oacVoiceFxsPorts,
    oacVoiceBriPorts,
    oacVoicePriPorts,
    oacVoiceVmoaConnections,
    oacVoiceVtoaConnections,
    oacVoiceFxsDialPeers,
    oacVoiceBriDialPeers,
    oacVoicePriDialPeers,
    oacVoiceVoicePortFxsIfIndex,
    oacVoiceVoicePortVoicePortFxs,
    oacVoiceVoicePortFxsProtocolState,
    oacVoiceVoicePortFxsOperState,
    oacVoiceVoicePortFxsAdminState,
    oacVoiceVoicePortFxsConfigState,
    oacVoiceVoicePortFxsAttachedDialPeer,
    oacVoiceVoicePortFxsVoiceCommNb,
    oacVoiceVoicePortBriIfIndex,
    oacVoiceVoicePortVoicePortBri,
    oacVoiceVoicePortBriProtocolDescriptor,
    oacVoiceVoicePortBriProtocolState,
    oacVoiceVoicePortBriOperState,
    oacVoiceVoicePortBriAdminState,
    oacVoiceVoicePortBriConfigState,
    oacVoiceVoicePortBriLayer1,
    oacVoiceVoicePortBriAttachedDialPeer,
    oacVoiceVoicePortBriVoiceCommNb,
    oacVoiceVoicePortPriIfIndex,
    oacVoiceVoicePortVoicePortPri,
    oacVoiceVoicePortPriPhysicalType,
    oacVoiceVoicePortPriProtocolDescriptor,
    oacVoiceVoicePortPriProtocolState,
    oacVoiceVoicePortPriOperState,
    oacVoiceVoicePortPriAdminState,
    oacVoiceVoicePortPriConfigState,
    oacVoiceVoicePortPriLayer1,
    oacVoiceVoicePortPriAttachedDialPeer,
    oacVoiceVoicePortPriVoiceCommNb,
    oacVoiceVoicePortPriAisOccur,
    oacVoiceVoicePortPriRdiOccur,
    oacVoiceVmoaConnConnection,
    oacVoiceVmoaConnVpVc,
    oacVoiceVmoaConnCurrentState,
    oacVoiceVmoaConnConfigState,
    oacVoiceVmoaConnAtmVcFailureOccurence,
    oacVoiceVmoaConnAtmVcTotalFailureDuration,
    oacVoiceVmoaConnLesVoicePathNum,
    oacVoiceVmoaConnLesTotalCpIwfOriginated,
    oacVoiceVmoaConnLesTotalCoIwfOriginated,
    oacVoiceVmoaConnLesCpIwfRestartNum,
    oacVoiceVmoaConnLesCoIwfRestartNum,
    oacVoiceVmoaConnElcpTotalSuccessfulAllocation,
    oacVoiceVmoaConnElcpTotalUnsuccessfulAllocation,
    oacVoiceVmoaConnElcpTotalAllocationDuration,
    oacVoiceVmoaConnLapv5NbrRxFrame,
    oacVoiceVmoaConnLapv5NbrTxFrame,
    oacVoiceVmoaConnLapv5NbrRxIFrame,
    oacVoiceVmoaConnLapv5NbrTxIFrame,
    oacVoiceVmoaConnLapv5NbrRxRejFrame,
    oacVoiceVmoaConnLapv5NbrTxRejFrame,
    oacVoiceVmoaConnLapv5NbrRxRnrFrame,
    oacVoiceVmoaConnLapv5NbrTxRnrFrame,
    oacVoiceVmoaConnLapv5NbrT200Expiration,
    oacVoiceVmoaConnAal2TotalFramesReceived,
    oacVoiceVmoaConnAal2TotalBytesReceived,
    oacVoiceVmoaConnAal2TotalFramesDiscardedReceived,
    oacVoiceVmoaConnAal2TotalFramesErrorsReceived,
    oacVoiceVmoaConnAal2TotalFramesSent,
    oacVoiceVmoaConnAal2TotalBytesSent,
    oacVoiceVmoaConnAal2TotalFramesDiscardedSent,
    oacVoiceVtoaConnConnection,
    oacVoiceVtoaConnVpVc,
    oacVoiceVtoaConnCurrentState,
    oacVoiceVtoaConnConfigState,
    oacVoiceVtoaConnAtmVcFailureOccurence,
    oacVoiceVtoaConnAtmVcTotalFailureDuration,
    oacVoiceVtoaConnAal2TotalFramesReceived,
    oacVoiceVtoaConnAal2TotalBytesReceived,
    oacVoiceVtoaConnAal2TotalFramesDiscardedReceived,
    oacVoiceVtoaConnAal2TotalFramesErrorsReceived,
    oacVoiceVtoaConnAal2TotalFramesSent,
    oacVoiceVtoaConnAal2TotalBytesSent,
    oacVoiceVtoaConnAal2TotalFramesDiscardedSent,
    oacVoiceDialPeerVoiceVmoafxsDialPeer,
    oacVoiceDialPeerVoiceVmoafxsLinkedPort,
    oacVoiceDialPeerVoiceVmoafxsCurrentState,
    oacVoiceDialPeerVoiceVmoafxsPortStatus,
    oacVoiceDialPeerVoiceVmoafxsPathStatus,
    oacVoiceDialPeerVoiceVmoafxsCurrentTxCoder,
    oacVoiceDialPeerVoiceVmoafxsCurrentRxCoder,
    oacVoiceDialPeerVoiceVmofxsCurrentBc,
    oacVoiceDialPeerVoiceVmoafxsCurrentCid,
    oacVoiceDialPeerVoiceVmoafxsBlockingOccurence,
    oacVoiceDialPeerVoiceVmoafxsTotalBlockingDuration,
    oacVoiceDialPeerVoiceVmoafxsVoicePacketSent,
    oacVoiceDialPeerVoiceVmoafxsVoicePacketReceived,
    oacVoiceDialPeerVoiceVmoafxsPathEstablished,
    oacVoiceDialPeerVoiceVmoafxsPathRqFailed,
    oacVoiceDialPeerVoiceVmoafxsPathDuration,
    oacVoiceDialPeerVoiceVmoabriDialPeer,
    oacVoiceDialPeerVoiceVmoabriPort,
    oacVoiceDialPeerVoiceVmoabriCurrentState,
    oacVoiceDialPeerVoiceVmoabriConfigState,
    oacVoiceDialPeerVoiceVmoabriPortStatus,
    oacVoiceDialPeerVoiceVmoabriBlockingOccurence,
    oacVoiceDialPeerVoiceVmoabriTotalBlockingDuration,
    oacVoiceDialPeerVoiceVmoabriBxAllocNum,
    oacVoiceDialPeerVoiceVmoabriB1CurrentTxCoder,
    oacVoiceDialPeerVoiceVmoabriB1CurrentRxCoder,
    oacVoiceDialPeerVoiceVmoabriB1CurrentBc,
    oacVoiceDialPeerVoiceVmoabriB1CurrentCid,
    oacVoiceDialPeerVoiceVmoabriB1VoicePacketSent,
    oacVoiceDialPeerVoiceVmoabriB1VoicePacketReceived,
    oacVoiceDialPeerVoiceVmoabriB1BytesSent,
    oacVoiceDialPeerVoiceVmoabriB1BytesReceived,
    oacVoiceDialPeerVoiceVmoabriB1PathEstablished,
    oacVoiceDialPeerVoiceVmoabriB1PathDuration,
    oacVoiceDialPeerVoiceVmoabriB1Bundle,
    oacVoiceDialPeerVoiceVmoabriB2CurrentTxCoder,
    oacVoiceDialPeerVoiceVmoabriB2CurrentRxCoder,
    oacVoiceDialPeerVoiceVmoabriB2CurrentBc,
    oacVoiceDialPeerVoiceVmoabriB2CurrentCid,
    oacVoiceDialPeerVoiceVmoabriB2VoicePacketSent,
    oacVoiceDialPeerVoiceVmoabriB2VoicePacketReceived,
    oacVoiceDialPeerVoiceVmoabriB2BytesSent,
    oacVoiceDialPeerVoiceVmoabriB2BytesReceived,
    oacVoiceDialPeerVoiceVmoabriB2PathEstablished,
    oacVoiceDialPeerVoiceVmoabriB2PathDuration,
    oacVoiceDialPeerVoiceVmoabriB2Bundle,
    oacVoiceDialPeerVoiceVmoabriDCurrentCid,
    oacVoiceDialPeerVoiceVmoabriDFramesSent,
    oacVoiceDialPeerVoiceVmoabriDFramesReceived,
    oacVoiceDialPeerVoiceVmoabriDBytesSent,
    oacVoiceDialPeerVoiceVmoabriDBytesReceived,
    oacVoiceDialPeerVoiceVtoaccsDialPeer,
    oacVoiceDialPeerVoiceVtoaccsLinkedPort,
    oacVoiceDialPeerVoiceVtoaccsPortStatus,
    oacVoiceDialPeerVoiceVtoaccsCurrentState,
    oacVoiceDialPeerVoiceVtoaccsConfigState,
    oacVoiceDialPeerVoiceVtoaccsBlockingOccurence,
    oacVoiceDialPeerVoiceVtoaccsTotalBlockingDuration,
    oacVoiceDialPeerVoiceVtoaccsBxAllocNum,
    oacVoiceDialPeerVoiceVtoaccsTsxIndex,
    oacVoiceDialPeerVoiceVtoaccsTsxChannelType,
    oacVoiceDialPeerVoiceVtoaccsTsxCurrentTxCoder,
    oacVoiceDialPeerVoiceVtoaccsTsxCurrentRxCoder,
    oacVoiceDialPeerVoiceVtoaccsTsxCurrentBC,
    oacVoiceDialPeerVoiceVtoaccsTsxCurrentCID,
    oacVoiceDialPeerVoiceVtoaccsTsxVoicePacketSent,
    oacVoiceDialPeerVoiceVtoaccsTsxVoicePacketReceived,
    oacVoiceDialPeerVoiceVtoaccsTsxBundle,
    oacVoiceDialPeerVoiceVtoacasDialPeer,
    oacVoiceDialPeerVoiceVtoacasLinkedPort,
    oacVoiceDialPeerVoiceVtoacasPortStatus,
    oacVoiceDialPeerVoiceVtoacasCurrentState,
    oacVoiceDialPeerVoiceVtoacasConfigState,
    oacVoiceDialPeerVoiceVtoacasBlockingOccurence,
    oacVoiceDialPeerVoiceVtoacasTotalBlockingDuration,
    oacVoiceDialPeerVoiceVtoacasBxAllocNum,
    oacVoiceDialPeerVoiceVtoacasTsxIndex,
    oacVoiceDialPeerVoiceVtoacasTsxChannelType,
    oacVoiceDialPeerVoiceVtoacasTsxCurrentTxCoder,
    oacVoiceDialPeerVoiceVtoacasTsxCurrentRxCoder,
    oacVoiceDialPeerVoiceVtoacasTsxCurrentBC,
    oacVoiceDialPeerVoiceVtoacasTsxCurrentCID,
    oacVoiceDialPeerVoiceVtoacasTsxVoicePacketSent,
    oacVoiceDialPeerVoiceVtoacasTsxVoicePacketReceived,
    oacVoiceDialPeerVoiceVtoacasTsxVoiceCasFramesSent,
    oacVoiceDialPeerVoiceVtoacasTsxVoiceCasFramesReceived,
    oacVoiceDialPeerVoiceVtoacasTsxBundle,
    oacVoiceDialPeerVoiceVmoapriDialPeer,
    oacVoiceDialPeerVoiceVmoapriLinkedPort,
    oacVoiceDialPeerVoiceVmoapriPortStatus,
    oacVoiceDialPeerVoiceVmoapriCurrentState,
    oacVoiceDialPeerVoiceVmoapriConfigState,
    oacVoiceDialPeerVoiceVmoapriBlockingOccurence,
    oacVoiceDialPeerVoiceVmoapriTotalBlockingDuration,
    oacVoiceDialPeerVoiceVmoapriBxAllocNum,
    oacVoiceDialPeerVoiceVmoapriTsxIndex,
    oacVoiceDialPeerVoiceVmoapriTsxChannelType,
    oacVoiceDialPeerVoiceVmoapriTsxCurrentTxCoder,
    oacVoiceDialPeerVoiceVmoapriTsxCurrentRxCoder,
    oacVoiceDialPeerVoiceVmoapriTsxCurrentBC,
    oacVoiceDialPeerVoiceVmoapriTsxCurrentCID,
    oacVoiceDialPeerVoiceVmoapriTsxVoicePacketSent,
    oacVoiceDialPeerVoiceVmoapriTsxVoicePacketReceived,
    oacVoiceDialPeerVoiceVtoacesDialPeer,
    oacVoiceDialPeerVoiceVtoacesLinkedPort,
    oacVoiceDialPeerVoiceVtoacesCurrentState,
	oacVoiceDialPeerVoiceVtoacesConfigState,
	oacVoiceDialPeerVoiceVtoacesCellLossIntegrationPeriod,
	oacVoiceDialPeerVoiceVtoacesOutOfSyncOccurences,
	oacVoiceDialPeerVoiceVtoacesTxCells,
	oacVoiceDialPeerVoiceVtoacesReassCells,
	oacVoiceDialPeerVoiceVtoacesBufOverflows,
	oacVoiceDialPeerVoiceVtoacesBufUnderflows,
	oacVoiceDialPeerVoiceVtoacesPointerReframes,
	oacVoiceDialPeerVoiceVtoacesHdrErrors,
	oacVoiceDialPeerVoiceVtoacesLossCells,
	oacVoicePortIfIndex,
	oacVoicePortVoipPortName,
	oacVoicePortVoipPortType,
	oacVoicePortVoipPriPhysicalType,
	oacVoicePortVoipIsdnProtocolDescriptor,
	oacVoicePortVoipCurrentState,
	oacVoicePortVoipConfigState,
	oacVoicePortVoipIsdnLayer1Status,
	oacVoicePortVoipIsdnLayer2Status,
	oacVoicePortVoipAttachedDialPeer,
	oacVoicePortVoipCurrentCalls,
	oacVoicePortVoipIsdnTxFramesOnDChannel,
	oacVoicePortVoipIsdnRxFramesOnDChannel,
	oacVoicePortVoipPriNbAisOccurence,
	oacVoicePortVoipPriNbRdiOccurence,
	oacVoicePortVoipOutCalls,
	oacVoicePortVoipOutCallsFailures,
	oacVoicePortVoipOutCallsUnsufficientPotsGroupResource,
	oacVoicePortVoipOutCallsIsdnPhysicalInterfaceDown,
	oacVoicePortVoipOutCallsIsdnCauseClass0,
	oacVoicePortVoipOutCallsIsdnCauseClass1,
	oacVoicePortVoipOutCallsIsdnCC1NormalCause,
	oacVoicePortVoipOutCallsCC1UserBusy,
	oacVoicePortVoipOutCallsCC1NoAnswer,
	oacVoicePortVoipOutCallsIsdnCauseClass2,
	oacVoicePortVoipOutCallsIsdnCauseClass3,
	oacVoicePortVoipOutCallsIsdnCauseClass4,
	oacVoicePortVoipOutCallsIsdnCauseClass5,
	oacVoicePortVoipOutCallsIsdnCauseClass6,
	oacVoicePortVoipOutCallsIsdnCauseClass7,
	oacVoicePortVoipIncCalls,
	oacVoicePortVoipIncCallsBackupInvoked,
	oacVoicePortVoipIncCallsFailures,
	oacVoicePortVoipIncCallsRemoteFailure,
	oacVoicePortVoipIncCallsUnknownNumber,
	oacVoicePortVoipIncCallsDspUnavailable,
	oacVoicePortVoipIncCallsNoVoipRessourceAvailable,
	oacVoicePortVoipIncCallsNotSpecified,
	oacVoicePortVoipMgcpOffHookEvents,
	oacVoicePortVoipMgcpOutCallsPathEstablished,
	oacVoicePortVoipMgcpRingingEvents,
	oacVoicePortVoipMgcpIncCallsPathEstablished,
	oacVoiceDialPeerIndex,
	oacVoiceDialPeerCurrentCalls,
	oacVoiceDialPeerOutCalls,
	oacVoiceDialPeerOutCallsMgcpOffHookEvents,
	oacVoiceDialPeerOutCallsMgcpPathEstablished,
	oacVoiceDialPeerOutCallsFailures,
	oacVoiceDialPeerOutCallsRasFailures,
	oacVoiceDialPeerOutCallsRasFailGatekeeperUnavailable,
	oacVoiceDialPeerOutCallsRasFailAdmissionRejects,
	oacVoiceDialPeerOutCallsH225Q931Failures,
	oacVoiceDialPeerOutCallsHQFailCauseClass0,
	oacVoiceDialPeerOutCallsHQFailCauseClass1,
	oacVoiceDialPeerOutCallsHQFailCC1NormalCause,
	oacVoiceDialPeerOutCallsHQFailCC1UserBusy,
	oacVoiceDialPeerOutCallsHQFailCC1NoAnswer,
	oacVoiceDialPeerOutCallsHQFailCauseClass2,
	oacVoiceDialPeerOutCallsHQFailCauseClass3,
	oacVoiceDialPeerOutCallsHQFailCauseClass4,
	oacVoiceDialPeerOutCallsHQFailCauseClass5,
	oacVoiceDialPeerOutCallsHQFailCauseClass6,
	oacVoiceDialPeerOutCallsHQFailCauseClass7,
	oacVoiceDialPeerOutCallsH245Failures,
	oacVoiceDialPeerOutCallsH245FailIncompatibleCapabilities,
	oacVoiceDialPeerOutCallsH245FailProtocolErrors,
	oacVoiceDialPeerOutCallsInternalFailures,
	oacVoiceDialPeerOutCallsInternalFailDspUnavailable,
	oacVoiceDialPeerOutCallsInternalFailMaxBwExceeded,
	oacVoiceDialPeerOutCallsInternalFailMaxConnExceeded,
	oacVoiceDialPeerOutCallsInternalFailNotSpecified,
	oacVoiceDialPeerIncCalls,
	oacVoiceDialPeerIncCallsMgcpRingingEvents,
	oacVoiceDialPeerIncCallsMgcpPathEstablished,
	oacVoiceDialPeerIncCallsFailures,
	oacVoiceDialPeerIncCallsRasFailures,
	oacVoiceDialPeerIncCallsRasFailGatekeeperUnavailable,
	oacVoiceDialPeerIncCallsRasFailAdmissionRejects,
	oacVoiceDialPeerIncCallsLocalPortFailures,
	oacVoiceDialPeerIncCallsH245Failures,
	oacVoiceDialPeerIncCallsH245FailIncompatibleCapabilities,
	oacVoiceDialPeerIncCallsH245FailProtocolErrors,
	oacVoiceDialPeerIncCallsInternalFailures,
	oacVoiceDialPeerIncCallsInternalFailDspUnavailable,
	oacVoiceDialPeerIncCallsInternalFailUnknownNumber,
	oacVoiceDialPeerIncCallsInternalFailChannelPortUnavailable,
	oacVoiceDialPeerIncCallsInternalFailMaxBwExceeded,
	oacVoiceDialPeerIncCallsInternalFailMaxConnExceeded,
	oacVoiceDialPeerIncCallsInternalFailNotSpecified,
	oacVoiceDialPeerIncCallsAdviceofCharge,
	oacVoiceDialPeerRtpStatNbTxPackets,
	oacVoiceDialPeerRtpStatNbRxPackets,
	oacVoiceDialPeerRtpStatNbTxBytes,
	oacVoiceDialPeerRtpStatNbRxBytes,
	oacVoiceDialPeerRtpStatNbExcessiveJitterEvents,
	oacVoiceDialPeerRtpStatNbLostPackets,
	oacVoiceDialPeerRtpStatNbInvalidPackets,
	oacVoiceDialPeerModemNbSwitchingToModemMode,
	oacVoiceDialPeerFaxNbOutgoingFax,
	oacVoiceDialPeerFaxNbIncomingFax,
	oacVoiceDialPeerFaxNbFailures,
	oacVoiceDialPeerFaxFailureRequestMode,
	oacVoiceDialPeerFaxFailurePreMsgProcedure,
	oacVoiceDialPeerFaxFailurePage,
	oacVoiceDialPeerFaxNbTxPackets,
	oacVoiceDialPeerFaxNbRxPackets,
	oacVoiceDialPeerFaxNbTxBytes,
	oacVoiceDialPeerFaxNbRxBytes,
	oacVoiceDialPeerFaxNbLostPackets,
	oacVoiceH323GwState,
	oacVoiceH323GwStateReason,
	oacVoiceH323GwRasBwControl,
	oacVoiceH323GwPortabilityStatus,
	oacVoiceH323GwPortabilityStatusTimeout,
	oacVoiceH323GwDs0Configured,
	oacVoiceH323GwDs0Low,
	oacVoiceH323GwDs0High,
	oacVoiceH323GwDs0Current,
	oacVoiceH323GwBwConfigured,
	oacVoiceH323GwBwLow,
	oacVoiceH323GwBwHigh,
	oacVoiceH323GwBwCurrent,
	oacVoiceH323GwRegistrationState,
	oacVoiceH323GwGatekeeperIdentifier,
	oacVoiceH323GwGatekeeperAddress,
	oacVoiceH323GwRegistrationRequest,
	oacVoiceH323GwRegistrationFailures,
	oacVoiceH323GwRegFailNoResponse,
	oacVoiceH323GwRegFailInvalidIpAddress,
	oacVoiceH323GwRegFailDuplicateAlias,
	oacVoiceH323GwRegFailInvalidTerminalType,
	oacVoiceH323GwRegFailResourceUnavailable,
	oacVoiceH323GwRegFailInvalidAlias,
	oacVoiceH323GwRegFailSecurityDenial,
	oacVoiceH323GwRegFailUndefinedReason,
	oacVoiceH323GwAdmissionRequests,
	oacVoiceH323GwAdmissionRejects,
	oacVoiceH323GwAdmRejCalledPartyNotRegistered,
	oacVoiceH323GwAdmRejInvalidPermission,
	oacVoiceH323GwAdmRejRequestDenied,
	oacVoiceH323GwAdmRejCallerNotRegistered,
	oacVoiceH323GwAdmRejResourceUnavailable,
	oacVoiceH323GwAdmRejSecurityDenial,
	oacVoiceH323GwAdmRejInvalidEndpointIdent,
	oacVoiceH323GwAdmRejIncompleteAddress,
	oacVoiceH323GwAdmRejNotSpecified,
	oacVoiceH323GwAdmRejUndefinedReason,
	oacVoiceSipGwState,
	oacVoiceSipGwRegistrationState,
	oacVoiceSipGwRegistrarServer,
	oacVoiceSipGwBandwidth,
	oacVoiceSipGwRegistrationErrors,
	oacVoiceSipGwRegisteredEndpoints,
	oacVoiceSipGwCurrentCalls,
	oacVoiceSipGwAuthenticationRejects,
	oacVoiceSipGwMaxToRegisterEndpoints,
	oacVoiceSipGwPhoneIndex,
	oacVoiceSipGwPhoneState,
	oacVoiceSipGwPhoneNumber,
	oacVoiceSipGwPhoneSipId,
	oacVoiceSipGwRegistrationTimeout,
	oacVoiceSipServerState,
	oacVoiceSipServerRegisteredEndpoints,
	oacVoiceSipServerRegistrarServer,
	oacVoiceSipServerCurrentCalls,
	oacVoiceSipServerPhoneIndex,
	oacVoiceSipServerPhoneNumber,
	oacVoiceSipServerPhoneIpAddress,
	oacVoiceSipServerPhoneSipId,
	oacVoiceSipServerRegistrationTime,
	oacVoiceSipServerRegistrationTimeout,
	oacVoiceMgcpGwState,
	oacVoiceMgcpGwCallAgentIpAddress,
	oacVoiceMgcpGwConnectionState,
	oacVoiceMgcpGwEstablishedPathCurrentNumber,
	oacVoiceMgcpGwOutCallsOffHookEvents,
	oacVoiceMgcpGwOutCallsPathEstablished,
	oacVoiceMgcpGwIncCallsRingingEvents,
	oacVoiceMgcpGwIncCallsPath,
	oacVoiceStatMosIndex,
	oacVoiceStatMosEntryNumberOfCalls,
	oacVoiceStatMosEntryMosAvg,
	oacVoiceStatMosEntryMosMin,
	oacVoiceStatMosEntryMosMax,
	oacVoiceStatMosEntryErlAvg,
	oacVoiceStatMosEntryAcomAvg,
	oacVoiceStatMosEntryLossRateAvg,
	oacVoiceStatMosJitterAvg,
	oacVoiceStatMosEntryMaxDelayAvg,
	oacVoiceStatMosEntryPddAvg
}
  STATUS  current
  DESCRIPTION
    "This group is mandatory for all Voice entities."
  ::= { oacVoiceStatGroups 1 }

END
