CYAN-RS64-MIB DEFINITIONS ::= BEGIN
IMPORTS
    MODULE-IDENTITY,
    OBJECT-TYPE,
    Integer32,
    Unsigned32
                    FROM SNMPv2-SMI


    CyanAdminStateTc,
    CyanOpStateQualTc,
    CyanOpStateTc,
    CyanSecServiceStateTc
                    FROM CYAN-TC-MIB

    cyanEntityModules
		    FROM CYAN-MIB

    MODULE-COMPLIANCE, 
    OBJECT-GROUP
	            FROM SNMPv2-CONF;


cyanRS64Module MODULE-IDENTITY
    LAST-UPDATED "201412070545Z" -- Sun Dec  7 05:45:27 2014
    ORGANIZATION "Cyan, Inc."
    CONTACT-INFO
        "
        E-mail:  support@cyaninc.com

        Postal:  Cyan, Inc.
               1390 N. McDowell Blvd., # G-327
               Petaluma, CA  94954
               USA

        Tel:     +1-707-735-2300"

    DESCRIPTION    "MIB module for OC-192/STM-64 RS layer"

    REVISION     "201412070545Z" -- Sun Dec  7 05:45:27 2014
    DESCRIPTION  "Release 6.0 build 1416362081"

    ::= { cyanEntityModules 220 } 

cyanRS64MibObjects           OBJECT IDENTIFIER ::={ cyanRS64Module 1 }

cyanRS64Table    OBJECT-TYPE
    SYNTAX        SEQUENCE OF CyanRS64Entry
    MAX-ACCESS    not-accessible
    STATUS        current
    DESCRIPTION
        "A list of RS64 entries."
    ::= { cyanRS64MibObjects 1 }

cyanRS64Entry    OBJECT-TYPE
    SYNTAX        CyanRS64Entry
    MAX-ACCESS    not-accessible
    STATUS        current
    DESCRIPTION
        "An entry of RS64."
    INDEX {
        cyanRS64ShelfId ,
        cyanRS64ModuleId ,
        cyanRS64RS64Id 
    }
    ::= { cyanRS64Table 1 }

CyanRS64Entry  ::=
    SEQUENCE {
        cyanRS64ShelfId    Unsigned32,
        cyanRS64ModuleId    Unsigned32,
        cyanRS64RS64Id    Unsigned32,
        cyanRS64AdminState    CyanAdminStateTc,
        cyanRS64AutoinserviceSoakTimeSec    Integer32,
        cyanRS64OperState    CyanOpStateTc,
        cyanRS64OperStateQual    CyanOpStateQualTc,
        cyanRS64SecServState    CyanSecServiceStateTc
    }

cyanRS64ShelfId OBJECT-TYPE
    SYNTAX       Unsigned32 (0..255)
    MAX-ACCESS   not-accessible
    STATUS       current
    DESCRIPTION
        "Shelf Id"

    ::= { cyanRS64Entry 1 }
cyanRS64ModuleId OBJECT-TYPE
    SYNTAX       Unsigned32
    MAX-ACCESS   not-accessible
    STATUS       current
    DESCRIPTION
        "Module Id"

    ::= { cyanRS64Entry 2 }
cyanRS64RS64Id OBJECT-TYPE
    SYNTAX       Unsigned32
    MAX-ACCESS   not-accessible
    STATUS       current
    DESCRIPTION
        "RS64 Termination Id"

    ::= { cyanRS64Entry 3 }

cyanRS64AdminState OBJECT-TYPE
    SYNTAX       CyanAdminStateTc
    MAX-ACCESS   read-only
    STATUS       current
    DESCRIPTION
        "Administrative state"

    ::= { cyanRS64Entry 4 }

cyanRS64AutoinserviceSoakTimeSec OBJECT-TYPE
    SYNTAX       Integer32
    MAX-ACCESS   read-only
    STATUS       current
    DESCRIPTION
        "Auto-In-Service soak time"

    ::= { cyanRS64Entry 5 }

cyanRS64OperState OBJECT-TYPE
    SYNTAX       CyanOpStateTc
    MAX-ACCESS   read-only
    STATUS       current
    DESCRIPTION
        "Primary Operation State"

    ::= { cyanRS64Entry 6 }

cyanRS64OperStateQual OBJECT-TYPE
    SYNTAX       CyanOpStateQualTc
    MAX-ACCESS   read-only
    STATUS       current
    DESCRIPTION
        "Operation state qualifier"

    ::= { cyanRS64Entry 7 }

cyanRS64SecServState OBJECT-TYPE
    SYNTAX       CyanSecServiceStateTc
    MAX-ACCESS   read-only
    STATUS       current
    DESCRIPTION
        "Secondary service state"

    ::= { cyanRS64Entry 8 }

cyanRS64ObjectGroup OBJECT-GROUP
    OBJECTS {
        cyanRS64AdminState,
        cyanRS64AutoinserviceSoakTimeSec,
        cyanRS64OperState,
        cyanRS64OperStateQual,
        cyanRS64SecServState
    }

    STATUS current
    DESCRIPTION        "Group of objects that comes with RS64 module"
    ::= {cyanRS64Module 20}

cyanRS64Compliance MODULE-COMPLIANCE
    STATUS current
    DESCRIPTION
        "The basic info needed to be a cyan RS64"
    MODULE
    MANDATORY-GROUPS {
        cyanRS64ObjectGroup
    }
    ::= { cyanRS64Module 30 }


END
