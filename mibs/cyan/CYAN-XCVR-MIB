CYAN-XCVR-MIB DEFINITIONS ::= BEGIN
IMPORTS
    MODULE-IDENTITY,
    OBJECT-TYPE,
    Integer32,
    Counter64,
    Unsigned32
                    FROM SNMPv2-SMI

    DisplayString
                    FROM SNMPv2-TC

    CyanNoYesTc,
    CyanWdmTypeTc,
    CyanXcvrConnectorCodeTc,
    CyanOpStateTc,
    CyanXcvrIdentifierTc,
    CyanSecServiceStateTc,
    CyanOpStateQualTc,
    CyanAdminStateTc,
    CyanPowerClassTc
                    FROM CYAN-TC-MIB

    cyanEntityModules
		    FROM CYAN-MIB

    MODULE-COMPLIANCE, 
    OBJECT-GROUP
	            FROM SNMPv2-CONF;


cyanXcvrModule MODULE-IDENTITY
    LAST-UPDATED "201412070545Z" -- Sun Dec  7 05:45:28 2014
    ORGANIZATION "Cyan, Inc."
    CONTACT-INFO
        "
        E-mail:  support@cyaninc.com

        Postal:  Cyan, Inc.
               1390 N. McDowell Blvd., # G-327
               Petaluma, CA  94954
               USA

        Tel:     +1-707-735-2300"

    DESCRIPTION    "MIB module for Optical Transceiver"

    REVISION     "201412070545Z" -- Sun Dec  7 05:45:28 2014
    DESCRIPTION  "Release 6.0 build 1416362081"

    ::= { cyanEntityModules 140 } 

cyanXcvrMibObjects           OBJECT IDENTIFIER ::={ cyanXcvrModule 1 }

cyanXcvrTable    OBJECT-TYPE
    SYNTAX        SEQUENCE OF CyanXcvrEntry
    MAX-ACCESS    not-accessible
    STATUS        current
    DESCRIPTION
        "A list of Xcvr entries."
    ::= { cyanXcvrMibObjects 1 }

cyanXcvrEntry    OBJECT-TYPE
    SYNTAX        CyanXcvrEntry
    MAX-ACCESS    not-accessible
    STATUS        current
    DESCRIPTION
        "An entry of Xcvr."
    INDEX {
        cyanXcvrShelfId ,
        cyanXcvrModuleId ,
        cyanXcvrXcvrId 
    }
    ::= { cyanXcvrTable 1 }

CyanXcvrEntry  ::=
    SEQUENCE {
        cyanXcvrShelfId    Unsigned32,
        cyanXcvrModuleId    Unsigned32,
        cyanXcvrXcvrId    Unsigned32,
        cyanXcvrAdminState    CyanAdminStateTc,
        cyanXcvrAutoinserviceSoakTimeSec    Integer32,
        cyanXcvrComplianceCode    Counter64,
        cyanXcvrConnectorCode    CyanXcvrConnectorCodeTc,
        cyanXcvrCyanName    DisplayString,
        cyanXcvrCyanPartNumber    DisplayString,
        cyanXcvrDescription    DisplayString,
        cyanXcvrIdentifier    DisplayString,
        cyanXcvrIdentifierCode    CyanXcvrIdentifierTc,
        cyanXcvrLength9    Unsigned32,
        cyanXcvrMaxBitRate    Unsigned32,
        cyanXcvrMfgDateCode    DisplayString,
        cyanXcvrMinBitRate    Unsigned32,
        cyanXcvrMmf3Maxlen    Unsigned32,
        cyanXcvrMmf4Maxlen    Unsigned32,
        cyanXcvrName    DisplayString,
        cyanXcvrNominalBitRate    Unsigned32,
        cyanXcvrOidClass    DisplayString,
        cyanXcvrOperState    CyanOpStateTc,
        cyanXcvrOperStateQual    CyanOpStateQualTc,
        cyanXcvrOptSensitivityAdjustSupp    CyanNoYesTc,
        cyanXcvrOssLabel    DisplayString,
        cyanXcvrOuiCode    Integer32,
        cyanXcvrOwner    DisplayString,
        cyanXcvrPartNumber    DisplayString,
        cyanXcvrPowerClass    CyanPowerClassTc,
        cyanXcvrRealTimeDiagImplemented    CyanNoYesTc,
        cyanXcvrRxPwrHiAlrmThres    Integer32,
        cyanXcvrRxPwrHiWarnThres    Integer32,
        cyanXcvrRxPwrLoAlrmThres    Integer32,
        cyanXcvrRxPwrLoWarnThres    Integer32,
        cyanXcvrSecServState    CyanSecServiceStateTc,
        cyanXcvrSerialNumber    DisplayString,
        cyanXcvrSfpOptions    Unsigned32,
        cyanXcvrTempHiAlrmThres    Integer32,
        cyanXcvrTempHiWarnThres    Integer32,
        cyanXcvrTempLoAlrmThres    Integer32,
        cyanXcvrTempLoWarnThres    Integer32,
        cyanXcvrTemperature    Integer32,
        cyanXcvrTxBiasCurrent    Integer32,
        cyanXcvrTxBiasHiAlrmThres    Integer32,
        cyanXcvrTxBiasHiWarnThres    Integer32,
        cyanXcvrTxBiasLoAlrmThres    Integer32,
        cyanXcvrTxBiasLoWarnThres    Integer32,
        cyanXcvrTxPwrHiAlrmThres    Integer32,
        cyanXcvrTxPwrHiWarnThres    Integer32,
        cyanXcvrTxPwrLoAlrmThres    Integer32,
        cyanXcvrTxPwrLoWarnThres    Integer32,
        cyanXcvrVccVoltHiAlrmThres    Integer32,
        cyanXcvrVccVoltHiWarnThres    Integer32,
        cyanXcvrVccVoltLoAlrmThres    Integer32,
        cyanXcvrVccVoltLoWarnThres    Integer32,
        cyanXcvrVccVoltage    Integer32,
        cyanXcvrVendorName    DisplayString,
        cyanXcvrVendorRev    DisplayString,
        cyanXcvrWavelength    Integer32,
        cyanXcvrWdmType    CyanWdmTypeTc,
        cyanXcvrWlenError    Integer32,
        cyanXcvrWlenIsTunable    CyanNoYesTc,
        cyanXcvrWlenSetpoint    Integer32,
        cyanXcvrWlenTolerance    Integer32
    }

cyanXcvrShelfId OBJECT-TYPE
    SYNTAX       Unsigned32 (0..255)
    MAX-ACCESS   not-accessible
    STATUS       current
    DESCRIPTION
        "Shelf Id"

    ::= { cyanXcvrEntry 1 }
cyanXcvrModuleId OBJECT-TYPE
    SYNTAX       Unsigned32
    MAX-ACCESS   not-accessible
    STATUS       current
    DESCRIPTION
        "Module Id"

    ::= { cyanXcvrEntry 2 }
cyanXcvrXcvrId OBJECT-TYPE
    SYNTAX       Unsigned32
    MAX-ACCESS   not-accessible
    STATUS       current
    DESCRIPTION
        "Transceiver Id"

    ::= { cyanXcvrEntry 3 }

cyanXcvrAdminState OBJECT-TYPE
    SYNTAX       CyanAdminStateTc
    MAX-ACCESS   read-only
    STATUS       current
    DESCRIPTION
        "Administrative state"

    ::= { cyanXcvrEntry 4 }

cyanXcvrAutoinserviceSoakTimeSec OBJECT-TYPE
    SYNTAX       Integer32
    MAX-ACCESS   read-only
    STATUS       current
    DESCRIPTION
        "Auto-In-Service soak time"

    ::= { cyanXcvrEntry 5 }

cyanXcvrComplianceCode OBJECT-TYPE
    SYNTAX       Counter64
    MAX-ACCESS   read-only
    STATUS       current
    DESCRIPTION
        "Compliance code"

    ::= { cyanXcvrEntry 6 }

cyanXcvrConnectorCode OBJECT-TYPE
    SYNTAX       CyanXcvrConnectorCodeTc
    MAX-ACCESS   read-only
    STATUS       current
    DESCRIPTION
        "SFP/XFP/CFP Connector code"

    ::= { cyanXcvrEntry 7 }

cyanXcvrCyanName OBJECT-TYPE
    SYNTAX       DisplayString (SIZE(0..16))
    MAX-ACCESS   read-only
    STATUS       current
    DESCRIPTION
        "Cyan Optics"

    ::= { cyanXcvrEntry 8 }

cyanXcvrCyanPartNumber OBJECT-TYPE
    SYNTAX       DisplayString (SIZE(0..42))
    MAX-ACCESS   read-only
    STATUS       current
    DESCRIPTION
        "Cyan Part Number"

    ::= { cyanXcvrEntry 9 }

cyanXcvrDescription OBJECT-TYPE
    SYNTAX       DisplayString (SIZE(0..255))
    MAX-ACCESS   read-only
    STATUS       current
    DESCRIPTION
        "Description"

    ::= { cyanXcvrEntry 10 }

cyanXcvrIdentifier OBJECT-TYPE
    SYNTAX       DisplayString
    MAX-ACCESS   read-only
    STATUS       current
    DESCRIPTION
        "string OID"

    ::= { cyanXcvrEntry 11 }

cyanXcvrIdentifierCode OBJECT-TYPE
    SYNTAX       CyanXcvrIdentifierTc
    MAX-ACCESS   read-only
    STATUS       current
    DESCRIPTION
        "Identifier code"

    ::= { cyanXcvrEntry 12 }

cyanXcvrLength9 OBJECT-TYPE
    SYNTAX       Unsigned32
    MAX-ACCESS   read-only
    STATUS       current
    DESCRIPTION
        "Link length supported for single mode fibers (m)"

    ::= { cyanXcvrEntry 13 }

cyanXcvrMaxBitRate OBJECT-TYPE
    SYNTAX       Unsigned32
    MAX-ACCESS   read-only
    STATUS       current
    DESCRIPTION
        "Maximum bit rate (Mbps)"

    ::= { cyanXcvrEntry 14 }

cyanXcvrMfgDateCode OBJECT-TYPE
    SYNTAX       DisplayString
    MAX-ACCESS   read-only
    STATUS       current
    DESCRIPTION
        "Manufacturing Date"

    ::= { cyanXcvrEntry 15 }

cyanXcvrMinBitRate OBJECT-TYPE
    SYNTAX       Unsigned32
    MAX-ACCESS   read-only
    STATUS       current
    DESCRIPTION
        "Minimum bit rate (Mbps)"

    ::= { cyanXcvrEntry 16 }

cyanXcvrMmf3Maxlen OBJECT-TYPE
    SYNTAX       Unsigned32 (0..65535)
    MAX-ACCESS   read-only
    STATUS       current
    DESCRIPTION
        "Max MMF length OM3 in meters"

    ::= { cyanXcvrEntry 17 }

cyanXcvrMmf4Maxlen OBJECT-TYPE
    SYNTAX       Unsigned32 (0..65535)
    MAX-ACCESS   read-only
    STATUS       current
    DESCRIPTION
        "Max MMF length OM4 in meters"

    ::= { cyanXcvrEntry 18 }

cyanXcvrName OBJECT-TYPE
    SYNTAX       DisplayString
    MAX-ACCESS   read-only
    STATUS       current
    DESCRIPTION
        "Cyan name"

    ::= { cyanXcvrEntry 19 }

cyanXcvrNominalBitRate OBJECT-TYPE
    SYNTAX       Unsigned32
    MAX-ACCESS   read-only
    STATUS       current
    DESCRIPTION
        "Nominal bit rate (Mbps)"

    ::= { cyanXcvrEntry 20 }

cyanXcvrOidClass OBJECT-TYPE
    SYNTAX       DisplayString
    MAX-ACCESS   read-only
    STATUS       current
    DESCRIPTION
        "OID Class"

    ::= { cyanXcvrEntry 21 }

cyanXcvrOperState OBJECT-TYPE
    SYNTAX       CyanOpStateTc
    MAX-ACCESS   read-only
    STATUS       current
    DESCRIPTION
        "Primary Operation State"

    ::= { cyanXcvrEntry 22 }

cyanXcvrOperStateQual OBJECT-TYPE
    SYNTAX       CyanOpStateQualTc
    MAX-ACCESS   read-only
    STATUS       current
    DESCRIPTION
        "Operation state qualifier"

    ::= { cyanXcvrEntry 23 }

cyanXcvrOptSensitivityAdjustSupp OBJECT-TYPE
    SYNTAX       CyanNoYesTc
    MAX-ACCESS   read-only
    STATUS       current
    DESCRIPTION
        "Optical sensitivity adjustment supported"

    ::= { cyanXcvrEntry 24 }

cyanXcvrOssLabel OBJECT-TYPE
    SYNTAX       DisplayString (SIZE(0..80))
    MAX-ACCESS   read-only
    STATUS       current
    DESCRIPTION
        "CyMS label"

    ::= { cyanXcvrEntry 25 }

cyanXcvrOuiCode OBJECT-TYPE
    SYNTAX       Integer32
    MAX-ACCESS   read-only
    STATUS       current
    DESCRIPTION
        "IEEE Organization Unique Identifier"

    ::= { cyanXcvrEntry 26 }

cyanXcvrOwner OBJECT-TYPE
    SYNTAX       DisplayString (SIZE(0..80))
    MAX-ACCESS   read-only
    STATUS       current
    DESCRIPTION
        "Owner"

    ::= { cyanXcvrEntry 27 }

cyanXcvrPartNumber OBJECT-TYPE
    SYNTAX       DisplayString
    MAX-ACCESS   read-only
    STATUS       current
    DESCRIPTION
        "Part Number"

    ::= { cyanXcvrEntry 28 }

cyanXcvrPowerClass OBJECT-TYPE
    SYNTAX       CyanPowerClassTc
    MAX-ACCESS   read-only
    STATUS       current
    DESCRIPTION
        "Power classes: <=8W, <=16W, <=24W, >24W"

    ::= { cyanXcvrEntry 29 }

cyanXcvrRealTimeDiagImplemented OBJECT-TYPE
    SYNTAX       CyanNoYesTc
    MAX-ACCESS   read-only
    STATUS       current
    DESCRIPTION
        "Real-time diagnostics implemented"

    ::= { cyanXcvrEntry 30 }

cyanXcvrRxPwrHiAlrmThres OBJECT-TYPE
    SYNTAX       Integer32 (-128000..128000) -- Float value * 1000
    MAX-ACCESS   read-only
    STATUS       current
    DESCRIPTION
        "Receive power high alarm threshold (dBm)"

    ::= { cyanXcvrEntry 31 }

cyanXcvrRxPwrHiWarnThres OBJECT-TYPE
    SYNTAX       Integer32 (-128000..128000) -- Float value * 1000
    MAX-ACCESS   read-only
    STATUS       current
    DESCRIPTION
        "Receive power high warning threshold (dBm)"

    ::= { cyanXcvrEntry 32 }

cyanXcvrRxPwrLoAlrmThres OBJECT-TYPE
    SYNTAX       Integer32 (-128000..128000) -- Float value * 1000
    MAX-ACCESS   read-only
    STATUS       current
    DESCRIPTION
        "Receive power low alarm threshold (dBm)"

    ::= { cyanXcvrEntry 33 }

cyanXcvrRxPwrLoWarnThres OBJECT-TYPE
    SYNTAX       Integer32 (-128000..128000) -- Float value * 1000
    MAX-ACCESS   read-only
    STATUS       current
    DESCRIPTION
        "Receive power low warning threshold (dBm)"

    ::= { cyanXcvrEntry 34 }

cyanXcvrSecServState OBJECT-TYPE
    SYNTAX       CyanSecServiceStateTc
    MAX-ACCESS   read-only
    STATUS       current
    DESCRIPTION
        "Secondary service state"

    ::= { cyanXcvrEntry 35 }

cyanXcvrSerialNumber OBJECT-TYPE
    SYNTAX       DisplayString
    MAX-ACCESS   read-only
    STATUS       current
    DESCRIPTION
        "Serial Number"

    ::= { cyanXcvrEntry 36 }

cyanXcvrSfpOptions OBJECT-TYPE
    SYNTAX       Unsigned32
    MAX-ACCESS   read-only
    STATUS       current
    DESCRIPTION
        "Options"

    ::= { cyanXcvrEntry 37 }

cyanXcvrTempHiAlrmThres OBJECT-TYPE
    SYNTAX       Integer32 (-128000..128000) -- Float value * 1000
    MAX-ACCESS   read-only
    STATUS       current
    DESCRIPTION
        "Temperature high alarm threshold (C)"

    ::= { cyanXcvrEntry 38 }

cyanXcvrTempHiWarnThres OBJECT-TYPE
    SYNTAX       Integer32 (-128000..128000) -- Float value * 1000
    MAX-ACCESS   read-only
    STATUS       current
    DESCRIPTION
        "Temperature high warning threshold (C)"

    ::= { cyanXcvrEntry 39 }

cyanXcvrTempLoAlrmThres OBJECT-TYPE
    SYNTAX       Integer32 (-128000..128000) -- Float value * 1000
    MAX-ACCESS   read-only
    STATUS       current
    DESCRIPTION
        "Temperature low alarm threshold (C)"

    ::= { cyanXcvrEntry 40 }

cyanXcvrTempLoWarnThres OBJECT-TYPE
    SYNTAX       Integer32 (-128000..128000) -- Float value * 1000
    MAX-ACCESS   read-only
    STATUS       current
    DESCRIPTION
        "Temperature low warning threshold (C)"

    ::= { cyanXcvrEntry 41 }

cyanXcvrTemperature OBJECT-TYPE
    SYNTAX       Integer32 -- real32 * 1000
    MAX-ACCESS   read-only
    STATUS       current
    DESCRIPTION
        "Optical transceiver temperature (C)"

    ::= { cyanXcvrEntry 42 }

cyanXcvrTxBiasCurrent OBJECT-TYPE
    SYNTAX       Integer32 -- real32 * 1000
    MAX-ACCESS   read-only
    STATUS       current
    DESCRIPTION
        "Transmit bias current (A)"

    ::= { cyanXcvrEntry 43 }

cyanXcvrTxBiasHiAlrmThres OBJECT-TYPE
    SYNTAX       Integer32 -- Float Value * 1000
    MAX-ACCESS   read-only
    STATUS       current
    DESCRIPTION
        "Transmit bias current high alarm threshold (A)"

    ::= { cyanXcvrEntry 44 }

cyanXcvrTxBiasHiWarnThres OBJECT-TYPE
    SYNTAX       Integer32 -- Float Value * 1000
    MAX-ACCESS   read-only
    STATUS       current
    DESCRIPTION
        "Transmit bias current high warning threshold (A)"

    ::= { cyanXcvrEntry 45 }

cyanXcvrTxBiasLoAlrmThres OBJECT-TYPE
    SYNTAX       Integer32 -- Float Value * 1000
    MAX-ACCESS   read-only
    STATUS       current
    DESCRIPTION
        "Transmit bias current low alarm threshold (A)"

    ::= { cyanXcvrEntry 46 }

cyanXcvrTxBiasLoWarnThres OBJECT-TYPE
    SYNTAX       Integer32 -- Float Value * 1000
    MAX-ACCESS   read-only
    STATUS       current
    DESCRIPTION
        "Transmit bias current low warning threshold (A)"

    ::= { cyanXcvrEntry 47 }

cyanXcvrTxPwrHiAlrmThres OBJECT-TYPE
    SYNTAX       Integer32 (-128000..128000) -- Float value * 1000
    MAX-ACCESS   read-only
    STATUS       current
    DESCRIPTION
        "Transmit power high alarm threshold (dBm)"

    ::= { cyanXcvrEntry 48 }

cyanXcvrTxPwrHiWarnThres OBJECT-TYPE
    SYNTAX       Integer32 (-128000..128000) -- Float value * 1000
    MAX-ACCESS   read-only
    STATUS       current
    DESCRIPTION
        "Transmit power high warning threshold (dBm)"

    ::= { cyanXcvrEntry 49 }

cyanXcvrTxPwrLoAlrmThres OBJECT-TYPE
    SYNTAX       Integer32 (-128000..128000) -- Float value * 1000
    MAX-ACCESS   read-only
    STATUS       current
    DESCRIPTION
        "Transmit power low alarm threshold (dBm)"

    ::= { cyanXcvrEntry 50 }

cyanXcvrTxPwrLoWarnThres OBJECT-TYPE
    SYNTAX       Integer32 (-128000..128000) -- Float value * 1000
    MAX-ACCESS   read-only
    STATUS       current
    DESCRIPTION
        "Transmit power low warning threshold (dBm)"

    ::= { cyanXcvrEntry 51 }

cyanXcvrVccVoltHiAlrmThres OBJECT-TYPE
    SYNTAX       Integer32 -- Float Value * 1000
    MAX-ACCESS   read-only
    STATUS       current
    DESCRIPTION
        "VCC voltage high alarm threshold (V)"

    ::= { cyanXcvrEntry 52 }

cyanXcvrVccVoltHiWarnThres OBJECT-TYPE
    SYNTAX       Integer32 -- Float Value * 1000
    MAX-ACCESS   read-only
    STATUS       current
    DESCRIPTION
        "VCC voltage high warning threshold (V)"

    ::= { cyanXcvrEntry 53 }

cyanXcvrVccVoltLoAlrmThres OBJECT-TYPE
    SYNTAX       Integer32 -- Float Value * 1000
    MAX-ACCESS   read-only
    STATUS       current
    DESCRIPTION
        "VCC voltage low alarm threshold (V)"

    ::= { cyanXcvrEntry 54 }

cyanXcvrVccVoltLoWarnThres OBJECT-TYPE
    SYNTAX       Integer32 -- Float Value * 1000
    MAX-ACCESS   read-only
    STATUS       current
    DESCRIPTION
        "VCC voltage low warning threshold (V)"

    ::= { cyanXcvrEntry 55 }

cyanXcvrVccVoltage OBJECT-TYPE
    SYNTAX       Integer32 -- real32 * 1000
    MAX-ACCESS   read-only
    STATUS       current
    DESCRIPTION
        "VCC voltage (V)"

    ::= { cyanXcvrEntry 56 }

cyanXcvrVendorName OBJECT-TYPE
    SYNTAX       DisplayString (SIZE(0..16))
    MAX-ACCESS   read-only
    STATUS       current
    DESCRIPTION
        "Vendor's name"

    ::= { cyanXcvrEntry 57 }

cyanXcvrVendorRev OBJECT-TYPE
    SYNTAX       DisplayString (SIZE(0..4))
    MAX-ACCESS   read-only
    STATUS       current
    DESCRIPTION
        "Vendor revision"

    ::= { cyanXcvrEntry 58 }

cyanXcvrWavelength OBJECT-TYPE
    SYNTAX       Integer32 -- real32 * 1000
    MAX-ACCESS   read-only
    STATUS       current
    DESCRIPTION
        "Wavelength nominal (nm)"

    ::= { cyanXcvrEntry 59 }

cyanXcvrWdmType OBJECT-TYPE
    SYNTAX       CyanWdmTypeTc
    MAX-ACCESS   read-only
    STATUS       current
    DESCRIPTION
        "WDM type"

    ::= { cyanXcvrEntry 60 }

cyanXcvrWlenError OBJECT-TYPE
    SYNTAX       Integer32 -- real32 * 1000
    MAX-ACCESS   read-only
    STATUS       current
    DESCRIPTION
        "Tunable transceiver: Measured error between actual wavelength and entered setpoint"

    ::= { cyanXcvrEntry 61 }

cyanXcvrWlenIsTunable OBJECT-TYPE
    SYNTAX       CyanNoYesTc
    MAX-ACCESS   read-only
    STATUS       current
    DESCRIPTION
        "Tunable wavelength"

    ::= { cyanXcvrEntry 62 }

cyanXcvrWlenSetpoint OBJECT-TYPE
    SYNTAX       Integer32 -- real32 * 1000
    MAX-ACCESS   read-only
    STATUS       current
    DESCRIPTION
        "Tunable transceiver: Entered wavelength setpoint"

    ::= { cyanXcvrEntry 63 }

cyanXcvrWlenTolerance OBJECT-TYPE
    SYNTAX       Integer32 -- real32 * 1000
    MAX-ACCESS   read-only
    STATUS       current
    DESCRIPTION
        "Wavelength tolerance (+/-nm)"

    ::= { cyanXcvrEntry 64 }

cyanXcvrObjectGroup OBJECT-GROUP
    OBJECTS {
        cyanXcvrAdminState,
        cyanXcvrAutoinserviceSoakTimeSec,
        cyanXcvrComplianceCode,
        cyanXcvrConnectorCode,
        cyanXcvrCyanName,
        cyanXcvrCyanPartNumber,
        cyanXcvrDescription,
        cyanXcvrIdentifier,
        cyanXcvrIdentifierCode,
        cyanXcvrLength9,
        cyanXcvrMaxBitRate,
        cyanXcvrMfgDateCode,
        cyanXcvrMinBitRate,
        cyanXcvrMmf3Maxlen,
        cyanXcvrMmf4Maxlen,
        cyanXcvrName,
        cyanXcvrNominalBitRate,
        cyanXcvrOidClass,
        cyanXcvrOperState,
        cyanXcvrOperStateQual,
        cyanXcvrOptSensitivityAdjustSupp,
        cyanXcvrOssLabel,
        cyanXcvrOuiCode,
        cyanXcvrOwner,
        cyanXcvrPartNumber,
        cyanXcvrPowerClass,
        cyanXcvrRealTimeDiagImplemented,
        cyanXcvrRxPwrHiAlrmThres,
        cyanXcvrRxPwrHiWarnThres,
        cyanXcvrRxPwrLoAlrmThres,
        cyanXcvrRxPwrLoWarnThres,
        cyanXcvrSecServState,
        cyanXcvrSerialNumber,
        cyanXcvrSfpOptions,
        cyanXcvrTempHiAlrmThres,
        cyanXcvrTempHiWarnThres,
        cyanXcvrTempLoAlrmThres,
        cyanXcvrTempLoWarnThres,
        cyanXcvrTemperature,
        cyanXcvrTxBiasCurrent,
        cyanXcvrTxBiasHiAlrmThres,
        cyanXcvrTxBiasHiWarnThres,
        cyanXcvrTxBiasLoAlrmThres,
        cyanXcvrTxBiasLoWarnThres,
        cyanXcvrTxPwrHiAlrmThres,
        cyanXcvrTxPwrHiWarnThres,
        cyanXcvrTxPwrLoAlrmThres,
        cyanXcvrTxPwrLoWarnThres,
        cyanXcvrVccVoltHiAlrmThres,
        cyanXcvrVccVoltHiWarnThres,
        cyanXcvrVccVoltLoAlrmThres,
        cyanXcvrVccVoltLoWarnThres,
        cyanXcvrVccVoltage,
        cyanXcvrVendorName,
        cyanXcvrVendorRev,
        cyanXcvrWavelength,
        cyanXcvrWdmType,
        cyanXcvrWlenError,
        cyanXcvrWlenIsTunable,
        cyanXcvrWlenSetpoint,
        cyanXcvrWlenTolerance
    }

    STATUS current
    DESCRIPTION        "Group of objects that comes with Xcvr module"
    ::= {cyanXcvrModule 20}

cyanXcvrCompliance MODULE-COMPLIANCE
    STATUS current
    DESCRIPTION
        "The basic info needed to be a cyan Xcvr"
    MODULE
    MANDATORY-GROUPS {
        cyanXcvrObjectGroup
    }
    ::= { cyanXcvrModule 30 }


END
