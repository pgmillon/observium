CYAN-Z33FAN-MIB DEFINITIONS ::= BEGIN
IMPORTS
    MODULE-IDENTITY,
    OBJECT-TYPE,
    Integer32,
    Unsigned32
                    FROM SNMPv2-SMI

    DisplayString
                    FROM SNMPv2-TC

    CyanAdminStateTc,
    CyanOpStateQualTc,
    CyanSecServiceStateTc,
    CyanLEDTc,
    CyanOpStateTc
                    FROM CYAN-TC-MIB

    CyanTypeTc,
    cyanEntityModules
		    FROM CYAN-MIB

    MODULE-COMPLIANCE, 
    OBJECT-GROUP
	            FROM SNMPv2-CONF;


cyanZ33FanModule MODULE-IDENTITY
    LAST-UPDATED "201412070545Z" -- Sun Dec  7 05:45:28 2014
    ORGANIZATION "Cyan, Inc."
    CONTACT-INFO
        "
        E-mail:  support@cyaninc.com

        Postal:  Cyan, Inc.
               1390 N. McDowell Blvd., # G-327
               Petaluma, CA  94954
               USA

        Tel:     +1-707-735-2300"

    DESCRIPTION    "MIB module for Z33 Fan"

    REVISION     "201412070545Z" -- Sun Dec  7 05:45:28 2014
    DESCRIPTION  "Release 6.0 build 1416362081"

    ::= { cyanEntityModules 80 } 

cyanZ33FanMibObjects           OBJECT IDENTIFIER ::={ cyanZ33FanModule 1 }

cyanZ33FanTable    OBJECT-TYPE
    SYNTAX        SEQUENCE OF CyanZ33FanEntry
    MAX-ACCESS    not-accessible
    STATUS        current
    DESCRIPTION
        "A list of Z33Fan entries."
    ::= { cyanZ33FanMibObjects 1 }

cyanZ33FanEntry    OBJECT-TYPE
    SYNTAX        CyanZ33FanEntry
    MAX-ACCESS    not-accessible
    STATUS        current
    DESCRIPTION
        "An entry of Z33Fan."
    INDEX {
        cyanZ33FanShelfId ,
        cyanZ33FanZ33FanId 
    }
    ::= { cyanZ33FanTable 1 }

CyanZ33FanEntry  ::=
    SEQUENCE {
        cyanZ33FanShelfId    Unsigned32,
        cyanZ33FanZ33FanId    Unsigned32,
        cyanZ33FanAcoLed    CyanLEDTc,
        cyanZ33FanAdminState    CyanAdminStateTc,
        cyanZ33FanAssetTag    DisplayString,
        cyanZ33FanAutoinserviceSoakTimeSec    Integer32,
        cyanZ33FanBaseMacAddress    DisplayString,
        cyanZ33FanCriticalLed    CyanLEDTc,
        cyanZ33FanDescription    DisplayString,
        cyanZ33FanFanLed    CyanLEDTc,
        cyanZ33FanFilterLed    CyanLEDTc,
        cyanZ33FanIdentifier    DisplayString,
        cyanZ33FanMacBlockSize    Unsigned32,
        cyanZ33FanMajorLed    CyanLEDTc,
        cyanZ33FanMfgCleiCode    DisplayString,
        cyanZ33FanMfgEciCode    DisplayString,
        cyanZ33FanMfgModuleId    Unsigned32,
        cyanZ33FanMfgPartNumber    DisplayString,
        cyanZ33FanMfgRevision    DisplayString,
        cyanZ33FanMfgSerialNumber    DisplayString,
        cyanZ33FanMinorLed    CyanLEDTc,
        cyanZ33FanName    DisplayString,
        cyanZ33FanOidClass    DisplayString,
        cyanZ33FanOperState    CyanOpStateTc,
        cyanZ33FanOperStateQual    CyanOpStateQualTc,
        cyanZ33FanOssLabel    DisplayString,
        cyanZ33FanOwner    DisplayString,
        cyanZ33FanPartNumber    DisplayString,
        cyanZ33FanSecServState    CyanSecServiceStateTc,
        cyanZ33FanType    CyanTypeTc
    }

cyanZ33FanShelfId OBJECT-TYPE
    SYNTAX       Unsigned32 (0..255)
    MAX-ACCESS   not-accessible
    STATUS       current
    DESCRIPTION
        "Shelf Id"

    ::= { cyanZ33FanEntry 1 }
cyanZ33FanZ33FanId OBJECT-TYPE
    SYNTAX       Unsigned32
    MAX-ACCESS   not-accessible
    STATUS       current
    DESCRIPTION
        "Z33Fan Module Id"

    ::= { cyanZ33FanEntry 2 }

cyanZ33FanAcoLed OBJECT-TYPE
    SYNTAX       CyanLEDTc
    MAX-ACCESS   read-only
    STATUS       current
    DESCRIPTION
        "ACO LED"

    ::= { cyanZ33FanEntry 3 }

cyanZ33FanAdminState OBJECT-TYPE
    SYNTAX       CyanAdminStateTc
    MAX-ACCESS   read-only
    STATUS       current
    DESCRIPTION
        "Administrative state"

    ::= { cyanZ33FanEntry 4 }

cyanZ33FanAssetTag OBJECT-TYPE
    SYNTAX       DisplayString (SIZE(0..124))
    MAX-ACCESS   read-only
    STATUS       current
    DESCRIPTION
        "Asset Tag"

    ::= { cyanZ33FanEntry 5 }

cyanZ33FanAutoinserviceSoakTimeSec OBJECT-TYPE
    SYNTAX       Integer32
    MAX-ACCESS   read-only
    STATUS       current
    DESCRIPTION
        "Auto-In-Service soak time"

    ::= { cyanZ33FanEntry 6 }

cyanZ33FanBaseMacAddress OBJECT-TYPE
    SYNTAX       DisplayString
    MAX-ACCESS   read-only
    STATUS       current
    DESCRIPTION
        "Base MAC address of a range of addresses"

    ::= { cyanZ33FanEntry 7 }

cyanZ33FanCriticalLed OBJECT-TYPE
    SYNTAX       CyanLEDTc
    MAX-ACCESS   read-only
    STATUS       current
    DESCRIPTION
        "Critical alarm LED status"

    ::= { cyanZ33FanEntry 8 }

cyanZ33FanDescription OBJECT-TYPE
    SYNTAX       DisplayString (SIZE(0..255))
    MAX-ACCESS   read-only
    STATUS       current
    DESCRIPTION
        "Description"

    ::= { cyanZ33FanEntry 9 }

cyanZ33FanFanLed OBJECT-TYPE
    SYNTAX       CyanLEDTc
    MAX-ACCESS   read-only
    STATUS       current
    DESCRIPTION
        "Fan LED status"

    ::= { cyanZ33FanEntry 10 }

cyanZ33FanFilterLed OBJECT-TYPE
    SYNTAX       CyanLEDTc
    MAX-ACCESS   read-only
    STATUS       current
    DESCRIPTION
        "Filter LED status"

    ::= { cyanZ33FanEntry 11 }

cyanZ33FanIdentifier OBJECT-TYPE
    SYNTAX       DisplayString
    MAX-ACCESS   read-only
    STATUS       current
    DESCRIPTION
        "string OID"

    ::= { cyanZ33FanEntry 12 }

cyanZ33FanMacBlockSize OBJECT-TYPE
    SYNTAX       Unsigned32 (0..255)
    MAX-ACCESS   read-only
    STATUS       current
    DESCRIPTION
        "Number of MAC addresses allocated from the base MAC address"

    ::= { cyanZ33FanEntry 13 }

cyanZ33FanMajorLed OBJECT-TYPE
    SYNTAX       CyanLEDTc
    MAX-ACCESS   read-only
    STATUS       current
    DESCRIPTION
        "Major alarm LED status"

    ::= { cyanZ33FanEntry 14 }

cyanZ33FanMfgCleiCode OBJECT-TYPE
    SYNTAX       DisplayString (SIZE(0..10))
    MAX-ACCESS   read-only
    STATUS       current
    DESCRIPTION
        "Common Language Equipment Identifier"

    ::= { cyanZ33FanEntry 15 }

cyanZ33FanMfgEciCode OBJECT-TYPE
    SYNTAX       DisplayString (SIZE(0..6))
    MAX-ACCESS   read-only
    STATUS       current
    DESCRIPTION
        "Equipment Catalog Item"

    ::= { cyanZ33FanEntry 16 }

cyanZ33FanMfgModuleId OBJECT-TYPE
    SYNTAX       Unsigned32
    MAX-ACCESS   read-only
    STATUS       current
    DESCRIPTION
        "Module ID"

    ::= { cyanZ33FanEntry 17 }

cyanZ33FanMfgPartNumber OBJECT-TYPE
    SYNTAX       DisplayString (SIZE(0..16))
    MAX-ACCESS   read-only
    STATUS       current
    DESCRIPTION
        "Manufacturing part number"

    ::= { cyanZ33FanEntry 18 }

cyanZ33FanMfgRevision OBJECT-TYPE
    SYNTAX       DisplayString (SIZE(0..4))
    MAX-ACCESS   read-only
    STATUS       current
    DESCRIPTION
        "Mfg revision number"

    ::= { cyanZ33FanEntry 19 }

cyanZ33FanMfgSerialNumber OBJECT-TYPE
    SYNTAX       DisplayString (SIZE(0..16))
    MAX-ACCESS   read-only
    STATUS       current
    DESCRIPTION
        "Mfg serial number"

    ::= { cyanZ33FanEntry 20 }

cyanZ33FanMinorLed OBJECT-TYPE
    SYNTAX       CyanLEDTc
    MAX-ACCESS   read-only
    STATUS       current
    DESCRIPTION
        "Minor alarm LED status"

    ::= { cyanZ33FanEntry 21 }

cyanZ33FanName OBJECT-TYPE
    SYNTAX       DisplayString
    MAX-ACCESS   read-only
    STATUS       current
    DESCRIPTION
        "Cyan name"

    ::= { cyanZ33FanEntry 22 }

cyanZ33FanOidClass OBJECT-TYPE
    SYNTAX       DisplayString
    MAX-ACCESS   read-only
    STATUS       current
    DESCRIPTION
        "OID Class"

    ::= { cyanZ33FanEntry 23 }

cyanZ33FanOperState OBJECT-TYPE
    SYNTAX       CyanOpStateTc
    MAX-ACCESS   read-only
    STATUS       current
    DESCRIPTION
        "Primary Operation State"

    ::= { cyanZ33FanEntry 24 }

cyanZ33FanOperStateQual OBJECT-TYPE
    SYNTAX       CyanOpStateQualTc
    MAX-ACCESS   read-only
    STATUS       current
    DESCRIPTION
        "Operation state qualifier"

    ::= { cyanZ33FanEntry 25 }

cyanZ33FanOssLabel OBJECT-TYPE
    SYNTAX       DisplayString (SIZE(0..80))
    MAX-ACCESS   read-only
    STATUS       current
    DESCRIPTION
        "CyMS label"

    ::= { cyanZ33FanEntry 26 }

cyanZ33FanOwner OBJECT-TYPE
    SYNTAX       DisplayString (SIZE(0..80))
    MAX-ACCESS   read-only
    STATUS       current
    DESCRIPTION
        "Owner"

    ::= { cyanZ33FanEntry 27 }

cyanZ33FanPartNumber OBJECT-TYPE
    SYNTAX       DisplayString (SIZE(0..11))
    MAX-ACCESS   read-only
    STATUS       current
    DESCRIPTION
        "Cyan part number"

    ::= { cyanZ33FanEntry 28 }

cyanZ33FanSecServState OBJECT-TYPE
    SYNTAX       CyanSecServiceStateTc
    MAX-ACCESS   read-only
    STATUS       current
    DESCRIPTION
        "Secondary service state"

    ::= { cyanZ33FanEntry 29 }

cyanZ33FanType OBJECT-TYPE
    SYNTAX       CyanTypeTc
    MAX-ACCESS   read-only
    STATUS       current
    DESCRIPTION
        "Equipment type"

    ::= { cyanZ33FanEntry 30 }

cyanZ33FanObjectGroup OBJECT-GROUP
    OBJECTS {
        cyanZ33FanAcoLed,
        cyanZ33FanAdminState,
        cyanZ33FanAssetTag,
        cyanZ33FanAutoinserviceSoakTimeSec,
        cyanZ33FanBaseMacAddress,
        cyanZ33FanCriticalLed,
        cyanZ33FanDescription,
        cyanZ33FanFanLed,
        cyanZ33FanFilterLed,
        cyanZ33FanIdentifier,
        cyanZ33FanMacBlockSize,
        cyanZ33FanMajorLed,
        cyanZ33FanMfgCleiCode,
        cyanZ33FanMfgEciCode,
        cyanZ33FanMfgModuleId,
        cyanZ33FanMfgPartNumber,
        cyanZ33FanMfgRevision,
        cyanZ33FanMfgSerialNumber,
        cyanZ33FanMinorLed,
        cyanZ33FanName,
        cyanZ33FanOidClass,
        cyanZ33FanOperState,
        cyanZ33FanOperStateQual,
        cyanZ33FanOssLabel,
        cyanZ33FanOwner,
        cyanZ33FanPartNumber,
        cyanZ33FanSecServState,
        cyanZ33FanType
    }

    STATUS current
    DESCRIPTION        "Group of objects that comes with Z33Fan module"
    ::= {cyanZ33FanModule 20}

cyanZ33FanCompliance MODULE-COMPLIANCE
    STATUS current
    DESCRIPTION
        "The basic info needed to be a cyan Z33Fan"
    MODULE
    MANDATORY-GROUPS {
        cyanZ33FanObjectGroup
    }
    ::= { cyanZ33FanModule 30 }


END
