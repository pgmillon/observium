CYAN-ETH-MIB DEFINITIONS ::= BEGIN
IMPORTS
    MODULE-IDENTITY,
    OBJECT-TYPE,
    Integer32,
    Unsigned32
                    FROM SNMPv2-SMI


    CyanAdminStateTc,
    CyanFppSubTypeTc,
    CyanOpStateTc,
    CyanFppTypeTc,
    CyanOpStateQualTc,
    CyanSecServiceStateTc,
    CyanEnDisabledTc
                    FROM CYAN-TC-MIB

    cyanEntityModules
		    FROM CYAN-MIB

    MODULE-COMPLIANCE, 
    OBJECT-GROUP
	            FROM SNMPv2-CONF;


cyanEthModule MODULE-IDENTITY
    LAST-UPDATED "201412070545Z" -- Sun Dec  7 05:45:22 2014
    ORGANIZATION "Cyan, Inc."
    CONTACT-INFO
        "
        E-mail:  support@cyaninc.com

        Postal:  Cyan, Inc.
               1390 N. McDowell Blvd., # G-327
               Petaluma, CA  94954
               USA

        Tel:     +1-707-735-2300"

    DESCRIPTION    "MIB module for Ethrnet Termination"

    REVISION     "201412070545Z" -- Sun Dec  7 05:45:22 2014
    DESCRIPTION  "Release 6.0 build 1416362081"

    ::= { cyanEntityModules 180 } 

cyanEthMibObjects           OBJECT IDENTIFIER ::={ cyanEthModule 1 }

cyanEthTable    OBJECT-TYPE
    SYNTAX        SEQUENCE OF CyanEthEntry
    MAX-ACCESS    not-accessible
    STATUS        current
    DESCRIPTION
        "A list of Eth entries."
    ::= { cyanEthMibObjects 1 }

cyanEthEntry    OBJECT-TYPE
    SYNTAX        CyanEthEntry
    MAX-ACCESS    not-accessible
    STATUS        current
    DESCRIPTION
        "An entry of Eth."
    INDEX {
        cyanEthShelfId ,
        cyanEthModuleId ,
        cyanEthEthTermId 
    }
    ::= { cyanEthTable 1 }

CyanEthEntry  ::=
    SEQUENCE {
        cyanEthShelfId    Unsigned32,
        cyanEthModuleId    Unsigned32,
        cyanEthEthTermId    Unsigned32,
        cyanEthAdminState    CyanAdminStateTc,
        cyanEthAutoinserviceSoakTimeSec    Integer32,
        cyanEthFarEndPtpId    Unsigned32,
        cyanEthFarEndShelfId    Unsigned32,
        cyanEthFarEndSlotId    Unsigned32,
        cyanEthFarEndSystemId    Unsigned32,
        cyanEthFlowPointPoolSubtype    CyanFppSubTypeTc,
        cyanEthFppType    CyanFppTypeTc,
        cyanEthIpForwarding    CyanEnDisabledTc,
        cyanEthLinkOamEnableState    CyanEnDisabledTc,
        cyanEthOperState    CyanOpStateTc,
        cyanEthOperStateQual    CyanOpStateQualTc,
        cyanEthPortSpeedMbps    Unsigned32,
        cyanEthRouting    CyanEnDisabledTc,
        cyanEthSecServState    CyanSecServiceStateTc,
        cyanEthTopologyDiscovery    CyanEnDisabledTc
    }

cyanEthShelfId OBJECT-TYPE
    SYNTAX       Unsigned32 (0..255)
    MAX-ACCESS   not-accessible
    STATUS       current
    DESCRIPTION
        "Shelf Id"

    ::= { cyanEthEntry 1 }
cyanEthModuleId OBJECT-TYPE
    SYNTAX       Unsigned32
    MAX-ACCESS   not-accessible
    STATUS       current
    DESCRIPTION
        "Module Id"

    ::= { cyanEthEntry 2 }
cyanEthEthTermId OBJECT-TYPE
    SYNTAX       Unsigned32
    MAX-ACCESS   not-accessible
    STATUS       current
    DESCRIPTION
        "Ethernet Termination Id"

    ::= { cyanEthEntry 3 }

cyanEthAdminState OBJECT-TYPE
    SYNTAX       CyanAdminStateTc
    MAX-ACCESS   read-only
    STATUS       current
    DESCRIPTION
        "Administrative state"

    ::= { cyanEthEntry 4 }

cyanEthAutoinserviceSoakTimeSec OBJECT-TYPE
    SYNTAX       Integer32
    MAX-ACCESS   read-only
    STATUS       current
    DESCRIPTION
        "Auto-In-Service soak time"

    ::= { cyanEthEntry 5 }

cyanEthFarEndPtpId OBJECT-TYPE
    SYNTAX       Unsigned32 (0..65535)
    MAX-ACCESS   read-only
    STATUS       current
    DESCRIPTION
        "Port or Termination Point Id"

    ::= { cyanEthEntry 6 }

cyanEthFarEndShelfId OBJECT-TYPE
    SYNTAX       Unsigned32 (0..65535)
    MAX-ACCESS   read-only
    STATUS       current
    DESCRIPTION
        "Shelf Id"

    ::= { cyanEthEntry 7 }

cyanEthFarEndSlotId OBJECT-TYPE
    SYNTAX       Unsigned32 (0..65535)
    MAX-ACCESS   read-only
    STATUS       current
    DESCRIPTION
        "Slot Id"

    ::= { cyanEthEntry 8 }

cyanEthFarEndSystemId OBJECT-TYPE
    SYNTAX       Unsigned32
    MAX-ACCESS   read-only
    STATUS       current
    DESCRIPTION
        "System Id"

    ::= { cyanEthEntry 9 }

cyanEthFlowPointPoolSubtype OBJECT-TYPE
    SYNTAX       CyanFppSubTypeTc
    MAX-ACCESS   read-only
    STATUS       current
    DESCRIPTION
        ""

    ::= { cyanEthEntry 10 }

cyanEthFppType OBJECT-TYPE
    SYNTAX       CyanFppTypeTc
    MAX-ACCESS   read-only
    STATUS       current
    DESCRIPTION
        ""

    ::= { cyanEthEntry 11 }

cyanEthIpForwarding OBJECT-TYPE
    SYNTAX       CyanEnDisabledTc
    MAX-ACCESS   read-only
    STATUS       current
    DESCRIPTION
        "Enable/disable IP forwarding"

    ::= { cyanEthEntry 12 }

cyanEthLinkOamEnableState OBJECT-TYPE
    SYNTAX       CyanEnDisabledTc
    MAX-ACCESS   read-only
    STATUS       current
    DESCRIPTION
        "Ethernet 802.3ah Clause 57 link OAM"

    ::= { cyanEthEntry 13 }

cyanEthOperState OBJECT-TYPE
    SYNTAX       CyanOpStateTc
    MAX-ACCESS   read-only
    STATUS       current
    DESCRIPTION
        "Primary Operation State"

    ::= { cyanEthEntry 14 }

cyanEthOperStateQual OBJECT-TYPE
    SYNTAX       CyanOpStateQualTc
    MAX-ACCESS   read-only
    STATUS       current
    DESCRIPTION
        "Operation state qualifier"

    ::= { cyanEthEntry 15 }

cyanEthPortSpeedMbps OBJECT-TYPE
    SYNTAX       Unsigned32
    MAX-ACCESS   read-only
    STATUS       current
    DESCRIPTION
        "Operating speed"

    ::= { cyanEthEntry 16 }

cyanEthRouting OBJECT-TYPE
    SYNTAX       CyanEnDisabledTc
    MAX-ACCESS   read-only
    STATUS       current
    DESCRIPTION
        "Enable/disable Routing"

    ::= { cyanEthEntry 17 }

cyanEthSecServState OBJECT-TYPE
    SYNTAX       CyanSecServiceStateTc
    MAX-ACCESS   read-only
    STATUS       current
    DESCRIPTION
        "Secondary service state"

    ::= { cyanEthEntry 18 }

cyanEthTopologyDiscovery OBJECT-TYPE
    SYNTAX       CyanEnDisabledTc
    MAX-ACCESS   read-only
    STATUS       current
    DESCRIPTION
        "Enable/disable Physical Topology Discovery"

    ::= { cyanEthEntry 19 }

cyanEthObjectGroup OBJECT-GROUP
    OBJECTS {
        cyanEthAdminState,
        cyanEthAutoinserviceSoakTimeSec,
        cyanEthFarEndPtpId,
        cyanEthFarEndShelfId,
        cyanEthFarEndSlotId,
        cyanEthFarEndSystemId,
        cyanEthFlowPointPoolSubtype,
        cyanEthFppType,
        cyanEthIpForwarding,
        cyanEthLinkOamEnableState,
        cyanEthOperState,
        cyanEthOperStateQual,
        cyanEthPortSpeedMbps,
        cyanEthRouting,
        cyanEthSecServState,
        cyanEthTopologyDiscovery
    }

    STATUS current
    DESCRIPTION        "Group of objects that comes with Eth module"
    ::= {cyanEthModule 20}

cyanEthCompliance MODULE-COMPLIANCE
    STATUS current
    DESCRIPTION
        "The basic info needed to be a cyan Eth"
    MODULE
    MANDATORY-GROUPS {
        cyanEthObjectGroup
    }
    ::= { cyanEthModule 30 }


END
