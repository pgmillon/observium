CYAN-ODU2-MIB DEFINITIONS ::= BEGIN
IMPORTS
    MODULE-IDENTITY,
    OBJECT-TYPE,
    Integer32,
    Unsigned32
                    FROM SNMPv2-SMI


    CyanAdminStateTc,
    CyanLayerRateTc,
    CyanOpuPayloadTypeTc,
    CyanOpStateQualTc,
    CyanOpStateTc,
    CyanTPConnectionStateTc,
    CyanSecServiceStateTc
                    FROM CYAN-TC-MIB

    cyanEntityModules
		    FROM CYAN-MIB

    MODULE-COMPLIANCE, 
    OBJECT-GROUP
	            FROM SNMPv2-CONF;


cyanODU2Module MODULE-IDENTITY
    LAST-UPDATED "201412070545Z" -- Sun Dec  7 05:45:27 2014
    ORGANIZATION "Cyan, Inc."
    CONTACT-INFO
        "
        E-mail:  support@cyaninc.com

        Postal:  Cyan, Inc.
               1390 N. McDowell Blvd., # G-327
               Petaluma, CA  94954
               USA

        Tel:     +1-707-735-2300"

    DESCRIPTION    "MIB module for ODU-2 Path"

    REVISION     "201412070545Z" -- Sun Dec  7 05:45:27 2014
    DESCRIPTION  "Release 6.0 build 1416362081"

    ::= { cyanEntityModules 200 } 

cyanODU2MibObjects           OBJECT IDENTIFIER ::={ cyanODU2Module 1 }

cyanODU2Table    OBJECT-TYPE
    SYNTAX        SEQUENCE OF CyanODU2Entry
    MAX-ACCESS    not-accessible
    STATUS        current
    DESCRIPTION
        "A list of ODU2 entries."
    ::= { cyanODU2MibObjects 1 }

cyanODU2Entry    OBJECT-TYPE
    SYNTAX        CyanODU2Entry
    MAX-ACCESS    not-accessible
    STATUS        current
    DESCRIPTION
        "An entry of ODU2."
    INDEX {
        cyanODU2ShelfId ,
        cyanODU2ModuleId ,
        cyanODU2ODU2Id 
    }
    ::= { cyanODU2Table 1 }

CyanODU2Entry  ::=
    SEQUENCE {
        cyanODU2ShelfId    Unsigned32,
        cyanODU2ModuleId    Unsigned32,
        cyanODU2ODU2Id    Unsigned32,
        cyanODU2AcceptedPayloadType    CyanOpuPayloadTypeTc,
        cyanODU2AdaptationType    CyanOpuPayloadTypeTc,
        cyanODU2AdminState    CyanAdminStateTc,
        cyanODU2AutoinserviceSoakTimeSec    Integer32,
        cyanODU2ConnectionState    CyanTPConnectionStateTc,
        cyanODU2OperState    CyanOpStateTc,
        cyanODU2OperStateQual    CyanOpStateQualTc,
        cyanODU2SecServState    CyanSecServiceStateTc,
        cyanODU2SupportedRates    CyanLayerRateTc
    }

cyanODU2ShelfId OBJECT-TYPE
    SYNTAX       Unsigned32 (0..255)
    MAX-ACCESS   not-accessible
    STATUS       current
    DESCRIPTION
        "Shelf Id"

    ::= { cyanODU2Entry 1 }
cyanODU2ModuleId OBJECT-TYPE
    SYNTAX       Unsigned32
    MAX-ACCESS   not-accessible
    STATUS       current
    DESCRIPTION
        "Module Id"

    ::= { cyanODU2Entry 2 }
cyanODU2ODU2Id OBJECT-TYPE
    SYNTAX       Unsigned32
    MAX-ACCESS   not-accessible
    STATUS       current
    DESCRIPTION
        "ODU2 Termination Id"

    ::= { cyanODU2Entry 3 }

cyanODU2AcceptedPayloadType OBJECT-TYPE
    SYNTAX       CyanOpuPayloadTypeTc
    MAX-ACCESS   read-only
    STATUS       current
    DESCRIPTION
        "Received ODTUG Payload Type"

    ::= { cyanODU2Entry 4 }

cyanODU2AdaptationType OBJECT-TYPE
    SYNTAX       CyanOpuPayloadTypeTc
    MAX-ACCESS   read-only
    STATUS       current
    DESCRIPTION
        "Adaptation type"

    ::= { cyanODU2Entry 5 }

cyanODU2AdminState OBJECT-TYPE
    SYNTAX       CyanAdminStateTc
    MAX-ACCESS   read-only
    STATUS       current
    DESCRIPTION
        "Administrative state"

    ::= { cyanODU2Entry 6 }

cyanODU2AutoinserviceSoakTimeSec OBJECT-TYPE
    SYNTAX       Integer32
    MAX-ACCESS   read-only
    STATUS       current
    DESCRIPTION
        "Auto-In-Service soak time"

    ::= { cyanODU2Entry 7 }

cyanODU2ConnectionState OBJECT-TYPE
    SYNTAX       CyanTPConnectionStateTc
    MAX-ACCESS   read-only
    STATUS       current
    DESCRIPTION
        "Connection state"

    ::= { cyanODU2Entry 8 }

cyanODU2OperState OBJECT-TYPE
    SYNTAX       CyanOpStateTc
    MAX-ACCESS   read-only
    STATUS       current
    DESCRIPTION
        "Primary Operation State"

    ::= { cyanODU2Entry 9 }

cyanODU2OperStateQual OBJECT-TYPE
    SYNTAX       CyanOpStateQualTc
    MAX-ACCESS   read-only
    STATUS       current
    DESCRIPTION
        "Operation state qualifier"

    ::= { cyanODU2Entry 10 }

cyanODU2SecServState OBJECT-TYPE
    SYNTAX       CyanSecServiceStateTc
    MAX-ACCESS   read-only
    STATUS       current
    DESCRIPTION
        "Secondary service state"

    ::= { cyanODU2Entry 11 }

cyanODU2SupportedRates OBJECT-TYPE
    SYNTAX       CyanLayerRateTc
    MAX-ACCESS   read-only
    STATUS       current
    DESCRIPTION
        "Supported layer & rate"

    ::= { cyanODU2Entry 12 }

cyanODU2ObjectGroup OBJECT-GROUP
    OBJECTS {
        cyanODU2AcceptedPayloadType,
        cyanODU2AdaptationType,
        cyanODU2AdminState,
        cyanODU2AutoinserviceSoakTimeSec,
        cyanODU2ConnectionState,
        cyanODU2OperState,
        cyanODU2OperStateQual,
        cyanODU2SecServState,
        cyanODU2SupportedRates
    }

    STATUS current
    DESCRIPTION        "Group of objects that comes with ODU2 module"
    ::= {cyanODU2Module 20}

cyanODU2Compliance MODULE-COMPLIANCE
    STATUS current
    DESCRIPTION
        "The basic info needed to be a cyan ODU2"
    MODULE
    MANDATORY-GROUPS {
        cyanODU2ObjectGroup
    }
    ::= { cyanODU2Module 30 }


END
