CYAN-S64-MIB DEFINITIONS ::= BEGIN
IMPORTS
    MODULE-IDENTITY,
    OBJECT-TYPE,
    Integer32,
    Unsigned32
                    FROM SNMPv2-SMI

    DisplayString
                    FROM SNMPv2-TC

    CyanOpStateTc,
    CyanSecServiceStateTc,
    CyanSdhSnSignalLabelTc,
    CyanOpStateQualTc,
    CyanAdminStateTc,
    CyanNimTc
                    FROM CYAN-TC-MIB

    cyanEntityModules
		    FROM CYAN-MIB

    MODULE-COMPLIANCE, 
    OBJECT-GROUP
	            FROM SNMPv2-CONF;


cyanS64Module MODULE-IDENTITY
    LAST-UPDATED "201412070545Z" -- Sun Dec  7 05:45:23 2014
    ORGANIZATION "Cyan, Inc."
    CONTACT-INFO
        "
        E-mail:  support@cyaninc.com

        Postal:  Cyan, Inc.
               1390 N. McDowell Blvd., # G-327
               Petaluma, CA  94954
               USA

        Tel:     +1-707-735-2300"

    DESCRIPTION    "MIB module for STS-192c/VC-4-64c Path layer"

    REVISION     "201412070545Z" -- Sun Dec  7 05:45:23 2014
    DESCRIPTION  "Release 6.0 build 1416362081"

    ::= { cyanEntityModules 250 } 

cyanS64MibObjects           OBJECT IDENTIFIER ::={ cyanS64Module 1 }

cyanS64Table    OBJECT-TYPE
    SYNTAX        SEQUENCE OF CyanS64Entry
    MAX-ACCESS    not-accessible
    STATUS        current
    DESCRIPTION
        "A list of S64 entries."
    ::= { cyanS64MibObjects 1 }

cyanS64Entry    OBJECT-TYPE
    SYNTAX        CyanS64Entry
    MAX-ACCESS    not-accessible
    STATUS        current
    DESCRIPTION
        "An entry of S64."
    INDEX {
        cyanS64ShelfId ,
        cyanS64ModuleId ,
        cyanS64S64Id 
    }
    ::= { cyanS64Table 1 }

CyanS64Entry  ::=
    SEQUENCE {
        cyanS64ShelfId    Unsigned32,
        cyanS64ModuleId    Unsigned32,
        cyanS64S64Id    Unsigned32,
        cyanS64Accepted    CyanSdhSnSignalLabelTc,
        cyanS64AdminState    CyanAdminStateTc,
        cyanS64AutoinserviceSoakTimeSec    Integer32,
        cyanS64Description    DisplayString,
        cyanS64Expected    CyanSdhSnSignalLabelTc,
        cyanS64Inserted    CyanSdhSnSignalLabelTc,
        cyanS64Monitorterminate    CyanNimTc,
        cyanS64OperState    CyanOpStateTc,
        cyanS64OperStateQual    CyanOpStateQualTc,
        cyanS64SecServState    CyanSecServiceStateTc
    }

cyanS64ShelfId OBJECT-TYPE
    SYNTAX       Unsigned32 (0..255)
    MAX-ACCESS   not-accessible
    STATUS       current
    DESCRIPTION
        "Shelf Id"

    ::= { cyanS64Entry 1 }
cyanS64ModuleId OBJECT-TYPE
    SYNTAX       Unsigned32
    MAX-ACCESS   not-accessible
    STATUS       current
    DESCRIPTION
        "Module Id"

    ::= { cyanS64Entry 2 }
cyanS64S64Id OBJECT-TYPE
    SYNTAX       Unsigned32
    MAX-ACCESS   not-accessible
    STATUS       current
    DESCRIPTION
        "S64 Termination Id"

    ::= { cyanS64Entry 3 }

cyanS64Accepted OBJECT-TYPE
    SYNTAX       CyanSdhSnSignalLabelTc
    MAX-ACCESS   read-only
    STATUS       current
    DESCRIPTION
        "Received Signal Label value"

    ::= { cyanS64Entry 4 }

cyanS64AdminState OBJECT-TYPE
    SYNTAX       CyanAdminStateTc
    MAX-ACCESS   read-only
    STATUS       current
    DESCRIPTION
        "Administrative state"

    ::= { cyanS64Entry 5 }

cyanS64AutoinserviceSoakTimeSec OBJECT-TYPE
    SYNTAX       Integer32
    MAX-ACCESS   read-only
    STATUS       current
    DESCRIPTION
        "Auto-In-Service soak time"

    ::= { cyanS64Entry 6 }

cyanS64Description OBJECT-TYPE
    SYNTAX       DisplayString (SIZE(0..255))
    MAX-ACCESS   read-only
    STATUS       current
    DESCRIPTION
        "Description"

    ::= { cyanS64Entry 7 }

cyanS64Expected OBJECT-TYPE
    SYNTAX       CyanSdhSnSignalLabelTc
    MAX-ACCESS   read-only
    STATUS       current
    DESCRIPTION
        "Expected Signal Label value"

    ::= { cyanS64Entry 8 }

cyanS64Inserted OBJECT-TYPE
    SYNTAX       CyanSdhSnSignalLabelTc
    MAX-ACCESS   read-only
    STATUS       current
    DESCRIPTION
        "Transmited Signal Label value"

    ::= { cyanS64Entry 9 }

cyanS64Monitorterminate OBJECT-TYPE
    SYNTAX       CyanNimTc
    MAX-ACCESS   read-only
    STATUS       current
    DESCRIPTION
        "Enable Non-Intrusive Monitoring"

    ::= { cyanS64Entry 10 }

cyanS64OperState OBJECT-TYPE
    SYNTAX       CyanOpStateTc
    MAX-ACCESS   read-only
    STATUS       current
    DESCRIPTION
        "Primary Operation State"

    ::= { cyanS64Entry 11 }

cyanS64OperStateQual OBJECT-TYPE
    SYNTAX       CyanOpStateQualTc
    MAX-ACCESS   read-only
    STATUS       current
    DESCRIPTION
        "Operation state qualifier"

    ::= { cyanS64Entry 12 }

cyanS64SecServState OBJECT-TYPE
    SYNTAX       CyanSecServiceStateTc
    MAX-ACCESS   read-only
    STATUS       current
    DESCRIPTION
        "Secondary service state"

    ::= { cyanS64Entry 13 }

cyanS64ObjectGroup OBJECT-GROUP
    OBJECTS {
        cyanS64Accepted,
        cyanS64AdminState,
        cyanS64AutoinserviceSoakTimeSec,
        cyanS64Description,
        cyanS64Expected,
        cyanS64Inserted,
        cyanS64Monitorterminate,
        cyanS64OperState,
        cyanS64OperStateQual,
        cyanS64SecServState
    }

    STATUS current
    DESCRIPTION        "Group of objects that comes with S64 module"
    ::= {cyanS64Module 20}

cyanS64Compliance MODULE-COMPLIANCE
    STATUS current
    DESCRIPTION
        "The basic info needed to be a cyan S64"
    MODULE
    MANDATORY-GROUPS {
        cyanS64ObjectGroup
    }
    ::= { cyanS64Module 30 }


END
