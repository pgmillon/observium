CYAN-XAUI-MIB DEFINITIONS ::= BEGIN
IMPORTS
    MODULE-IDENTITY,
    OBJECT-TYPE,
    Integer32,
    Unsigned32
                    FROM SNMPv2-SMI


    CyanOpStateQualTc,
    CyanAdminStateTc,
    CyanSecServiceStateTc,
    CyanOpStateTc
                    FROM CYAN-TC-MIB

    cyanEntityModules
		    FROM CYAN-MIB

    MODULE-COMPLIANCE, 
    OBJECT-GROUP
	            FROM SNMPv2-CONF;


cyanXauiModule MODULE-IDENTITY
    LAST-UPDATED "201412070545Z" -- Sun Dec  7 05:45:28 2014
    ORGANIZATION "Cyan, Inc."
    CONTACT-INFO
        "
        E-mail:  support@cyaninc.com

        Postal:  Cyan, Inc.
               1390 N. McDowell Blvd., # G-327
               Petaluma, CA  94954
               USA

        Tel:     +1-707-735-2300"

    DESCRIPTION    "MIB module for Transport XAUI"

    REVISION     "201412070545Z" -- Sun Dec  7 05:45:28 2014
    DESCRIPTION  "Release 6.0 build 1416362081"

    ::= { cyanEntityModules 170 } 

cyanXauiMibObjects           OBJECT IDENTIFIER ::={ cyanXauiModule 1 }

cyanXauiTable    OBJECT-TYPE
    SYNTAX        SEQUENCE OF CyanXauiEntry
    MAX-ACCESS    not-accessible
    STATUS        current
    DESCRIPTION
        "A list of Xaui entries."
    ::= { cyanXauiMibObjects 1 }

cyanXauiEntry    OBJECT-TYPE
    SYNTAX        CyanXauiEntry
    MAX-ACCESS    not-accessible
    STATUS        current
    DESCRIPTION
        "An entry of Xaui."
    INDEX {
        cyanXauiShelfId ,
        cyanXauiModuleId ,
        cyanXauiXauiId 
    }
    ::= { cyanXauiTable 1 }

CyanXauiEntry  ::=
    SEQUENCE {
        cyanXauiShelfId    Unsigned32,
        cyanXauiModuleId    Unsigned32,
        cyanXauiXauiId    Unsigned32,
        cyanXauiAdminState    CyanAdminStateTc,
        cyanXauiAutoinserviceSoakTimeSec    Integer32,
        cyanXauiOperState    CyanOpStateTc,
        cyanXauiOperStateQual    CyanOpStateQualTc,
        cyanXauiPortSpeedMbps    Unsigned32,
        cyanXauiSecServState    CyanSecServiceStateTc
    }

cyanXauiShelfId OBJECT-TYPE
    SYNTAX       Unsigned32 (0..255)
    MAX-ACCESS   not-accessible
    STATUS       current
    DESCRIPTION
        "Shelf Id"

    ::= { cyanXauiEntry 1 }
cyanXauiModuleId OBJECT-TYPE
    SYNTAX       Unsigned32
    MAX-ACCESS   not-accessible
    STATUS       current
    DESCRIPTION
        "Module Id"

    ::= { cyanXauiEntry 2 }
cyanXauiXauiId OBJECT-TYPE
    SYNTAX       Unsigned32
    MAX-ACCESS   not-accessible
    STATUS       current
    DESCRIPTION
        "Xaui Id"

    ::= { cyanXauiEntry 3 }

cyanXauiAdminState OBJECT-TYPE
    SYNTAX       CyanAdminStateTc
    MAX-ACCESS   read-only
    STATUS       current
    DESCRIPTION
        "Administrative state"

    ::= { cyanXauiEntry 4 }

cyanXauiAutoinserviceSoakTimeSec OBJECT-TYPE
    SYNTAX       Integer32
    MAX-ACCESS   read-only
    STATUS       current
    DESCRIPTION
        "Auto-In-Service soak time"

    ::= { cyanXauiEntry 5 }

cyanXauiOperState OBJECT-TYPE
    SYNTAX       CyanOpStateTc
    MAX-ACCESS   read-only
    STATUS       current
    DESCRIPTION
        "Primary Operation State"

    ::= { cyanXauiEntry 6 }

cyanXauiOperStateQual OBJECT-TYPE
    SYNTAX       CyanOpStateQualTc
    MAX-ACCESS   read-only
    STATUS       current
    DESCRIPTION
        "Operation state qualifier"

    ::= { cyanXauiEntry 7 }

cyanXauiPortSpeedMbps OBJECT-TYPE
    SYNTAX       Unsigned32
    MAX-ACCESS   read-only
    STATUS       current
    DESCRIPTION
        "Operating speed"

    ::= { cyanXauiEntry 8 }

cyanXauiSecServState OBJECT-TYPE
    SYNTAX       CyanSecServiceStateTc
    MAX-ACCESS   read-only
    STATUS       current
    DESCRIPTION
        "Secondary service state"

    ::= { cyanXauiEntry 9 }

cyanXauiObjectGroup OBJECT-GROUP
    OBJECTS {
        cyanXauiAdminState,
        cyanXauiAutoinserviceSoakTimeSec,
        cyanXauiOperState,
        cyanXauiOperStateQual,
        cyanXauiPortSpeedMbps,
        cyanXauiSecServState
    }

    STATUS current
    DESCRIPTION        "Group of objects that comes with Xaui module"
    ::= {cyanXauiModule 20}

cyanXauiCompliance MODULE-COMPLIANCE
    STATUS current
    DESCRIPTION
        "The basic info needed to be a cyan Xaui"
    MODULE
    MANDATORY-GROUPS {
        cyanXauiObjectGroup
    }
    ::= { cyanXauiModule 30 }


END
